module Cisco-IOS-XR-openconfig-platform-pipeline-counters-p200-ext {
  yang-version 1;
  namespace "http://cisco.com/ns/yang/Cisco-IOS-XR-openconfig-platform-pipeline-counters-p200-ext";
  prefix p200;

  import openconfig-yang-types {
    prefix oc-yang;
  }
  import openconfig-extensions {
    prefix oc-ext;
  }
  import openconfig-platform {
    prefix oc-platform;
  }
  import openconfig-platform-pipeline-counters {
    prefix oc-ppc;
  }
  import Cisco-IOS-XR-openconfig-platform-pipeline-counters-ext {
    prefix cisco;
  }

  organization
    "Cisco Systems, Inc";
  contact
    "Cisco Systems
     Customer Service
     Postal: 170 West Tasman Drive
     San Jose, CA 95134
     
     Tel: +1 800 553-NETS
     
     E-mail: cs-yang@cisco.com";
  description
    "Adding augments to oc-ppc yang for providing vendor based counters for the p200 asic";

  revision 2026-01-27 {
    description
      "Initial csv file";
  }

  grouping cisco-p200-adverse-drop-counters {
    description
      "Adverse Drop leafs grouping for the p200 asic";
    leaf counter_hbm_db0_hbm_error_counters0_aerr_cntr {
      type oc-yang:counter64;
      description
        "Counter of addrrow or col parity errors indicated by AERR from HBM die. These errors are ignored by MMU";
    }
    leaf counter_hbm_db0_hbm_error_counters1_aerr_cntr {
      type oc-yang:counter64;
      description
        "Counter of addrrow or col parity errors indicated by AERR from HBM die. These errors are ignored by MMU";
    }
    leaf counter_hbm_db0_hbm_error_counters2_aerr_cntr {
      type oc-yang:counter64;
      description
        "Counter of addrrow or col parity errors indicated by AERR from HBM die. These errors are ignored by MMU";
    }
    leaf counter_hbm_db0_hbm_error_counters3_aerr_cntr {
      type oc-yang:counter64;
      description
        "Counter of addrrow or col parity errors indicated by AERR from HBM die. These errors are ignored by MMU";
    }
    leaf counter_hbm_db0_hbm_error_counters4_aerr_cntr {
      type oc-yang:counter64;
      description
        "Counter of addrrow or col parity errors indicated by AERR from HBM die. These errors are ignored by MMU";
    }
    leaf counter_hbm_db0_hbm_error_counters5_aerr_cntr {
      type oc-yang:counter64;
      description
        "Counter of addrrow or col parity errors indicated by AERR from HBM die. These errors are ignored by MMU";
    }
    leaf counter_hbm_db0_hbm_error_counters6_aerr_cntr {
      type oc-yang:counter64;
      description
        "Counter of addrrow or col parity errors indicated by AERR from HBM die. These errors are ignored by MMU";
    }
    leaf counter_hbm_db0_hbm_error_counters7_aerr_cntr {
      type oc-yang:counter64;
      description
        "Counter of addrrow or col parity errors indicated by AERR from HBM die. These errors are ignored by MMU";
    }
    leaf counter_hbm_db1_hbm_error_counters0_aerr_cntr {
      type oc-yang:counter64;
      description
        "Counter of addrrow or col parity errors indicated by AERR from HBM die. These errors are ignored by MMU";
    }
    leaf counter_hbm_db1_hbm_error_counters1_aerr_cntr {
      type oc-yang:counter64;
      description
        "Counter of addrrow or col parity errors indicated by AERR from HBM die. These errors are ignored by MMU";
    }
    leaf counter_hbm_db1_hbm_error_counters2_aerr_cntr {
      type oc-yang:counter64;
      description
        "Counter of addrrow or col parity errors indicated by AERR from HBM die. These errors are ignored by MMU";
    }
    leaf counter_hbm_db1_hbm_error_counters3_aerr_cntr {
      type oc-yang:counter64;
      description
        "Counter of addrrow or col parity errors indicated by AERR from HBM die. These errors are ignored by MMU";
    }
    leaf counter_hbm_db1_hbm_error_counters4_aerr_cntr {
      type oc-yang:counter64;
      description
        "Counter of addrrow or col parity errors indicated by AERR from HBM die. These errors are ignored by MMU";
    }
    leaf counter_hbm_db1_hbm_error_counters5_aerr_cntr {
      type oc-yang:counter64;
      description
        "Counter of addrrow or col parity errors indicated by AERR from HBM die. These errors are ignored by MMU";
    }
    leaf counter_hbm_db1_hbm_error_counters6_aerr_cntr {
      type oc-yang:counter64;
      description
        "Counter of addrrow or col parity errors indicated by AERR from HBM die. These errors are ignored by MMU";
    }
    leaf counter_hbm_db1_hbm_error_counters7_aerr_cntr {
      type oc-yang:counter64;
      description
        "Counter of addrrow or col parity errors indicated by AERR from HBM die. These errors are ignored by MMU";
    }
    leaf counter_hbm_db2_hbm_error_counters0_aerr_cntr {
      type oc-yang:counter64;
      description
        "Counter of addrrow or col parity errors indicated by AERR from HBM die. These errors are ignored by MMU";
    }
    leaf counter_hbm_db2_hbm_error_counters1_aerr_cntr {
      type oc-yang:counter64;
      description
        "Counter of addrrow or col parity errors indicated by AERR from HBM die. These errors are ignored by MMU";
    }
    leaf counter_hbm_db2_hbm_error_counters2_aerr_cntr {
      type oc-yang:counter64;
      description
        "Counter of addrrow or col parity errors indicated by AERR from HBM die. These errors are ignored by MMU";
    }
    leaf counter_hbm_db2_hbm_error_counters3_aerr_cntr {
      type oc-yang:counter64;
      description
        "Counter of addrrow or col parity errors indicated by AERR from HBM die. These errors are ignored by MMU";
    }
    leaf counter_hbm_db2_hbm_error_counters4_aerr_cntr {
      type oc-yang:counter64;
      description
        "Counter of addrrow or col parity errors indicated by AERR from HBM die. These errors are ignored by MMU";
    }
    leaf counter_hbm_db2_hbm_error_counters5_aerr_cntr {
      type oc-yang:counter64;
      description
        "Counter of addrrow or col parity errors indicated by AERR from HBM die. These errors are ignored by MMU";
    }
    leaf counter_hbm_db2_hbm_error_counters6_aerr_cntr {
      type oc-yang:counter64;
      description
        "Counter of addrrow or col parity errors indicated by AERR from HBM die. These errors are ignored by MMU";
    }
    leaf counter_hbm_db2_hbm_error_counters7_aerr_cntr {
      type oc-yang:counter64;
      description
        "Counter of addrrow or col parity errors indicated by AERR from HBM die. These errors are ignored by MMU";
    }
    leaf counter_hbm_db3_hbm_error_counters0_aerr_cntr {
      type oc-yang:counter64;
      description
        "Counter of addrrow or col parity errors indicated by AERR from HBM die. These errors are ignored by MMU";
    }
    leaf counter_hbm_db3_hbm_error_counters1_aerr_cntr {
      type oc-yang:counter64;
      description
        "Counter of addrrow or col parity errors indicated by AERR from HBM die. These errors are ignored by MMU";
    }
    leaf counter_hbm_db3_hbm_error_counters2_aerr_cntr {
      type oc-yang:counter64;
      description
        "Counter of addrrow or col parity errors indicated by AERR from HBM die. These errors are ignored by MMU";
    }
    leaf counter_hbm_db3_hbm_error_counters3_aerr_cntr {
      type oc-yang:counter64;
      description
        "Counter of addrrow or col parity errors indicated by AERR from HBM die. These errors are ignored by MMU";
    }
    leaf counter_hbm_db3_hbm_error_counters4_aerr_cntr {
      type oc-yang:counter64;
      description
        "Counter of addrrow or col parity errors indicated by AERR from HBM die. These errors are ignored by MMU";
    }
    leaf counter_hbm_db3_hbm_error_counters5_aerr_cntr {
      type oc-yang:counter64;
      description
        "Counter of addrrow or col parity errors indicated by AERR from HBM die. These errors are ignored by MMU";
    }
    leaf counter_hbm_db3_hbm_error_counters6_aerr_cntr {
      type oc-yang:counter64;
      description
        "Counter of addrrow or col parity errors indicated by AERR from HBM die. These errors are ignored by MMU";
    }
    leaf counter_hbm_db3_hbm_error_counters7_aerr_cntr {
      type oc-yang:counter64;
      description
        "Counter of addrrow or col parity errors indicated by AERR from HBM die. These errors are ignored by MMU";
    }
    leaf counter_hbm_db0_hbm_error_counters0_crc_error_cntr_pc0 {
      type oc-yang:counter64;
      description
        "Counter of CRC-12 errors on the whole 512b burst";
    }
    leaf counter_hbm_db0_hbm_error_counters1_crc_error_cntr_pc0 {
      type oc-yang:counter64;
      description
        "Counter of CRC-12 errors on the whole 512b burst";
    }
    leaf counter_hbm_db0_hbm_error_counters2_crc_error_cntr_pc0 {
      type oc-yang:counter64;
      description
        "Counter of CRC-12 errors on the whole 512b burst";
    }
    leaf counter_hbm_db0_hbm_error_counters3_crc_error_cntr_pc0 {
      type oc-yang:counter64;
      description
        "Counter of CRC-12 errors on the whole 512b burst";
    }
    leaf counter_hbm_db0_hbm_error_counters4_crc_error_cntr_pc0 {
      type oc-yang:counter64;
      description
        "Counter of CRC-12 errors on the whole 512b burst";
    }
    leaf counter_hbm_db0_hbm_error_counters5_crc_error_cntr_pc0 {
      type oc-yang:counter64;
      description
        "Counter of CRC-12 errors on the whole 512b burst";
    }
    leaf counter_hbm_db0_hbm_error_counters6_crc_error_cntr_pc0 {
      type oc-yang:counter64;
      description
        "Counter of CRC-12 errors on the whole 512b burst";
    }
    leaf counter_hbm_db0_hbm_error_counters7_crc_error_cntr_pc0 {
      type oc-yang:counter64;
      description
        "Counter of CRC-12 errors on the whole 512b burst";
    }
    leaf counter_hbm_db1_hbm_error_counters0_crc_error_cntr_pc0 {
      type oc-yang:counter64;
      description
        "Counter of CRC-12 errors on the whole 512b burst";
    }
    leaf counter_hbm_db1_hbm_error_counters1_crc_error_cntr_pc0 {
      type oc-yang:counter64;
      description
        "Counter of CRC-12 errors on the whole 512b burst";
    }
    leaf counter_hbm_db1_hbm_error_counters2_crc_error_cntr_pc0 {
      type oc-yang:counter64;
      description
        "Counter of CRC-12 errors on the whole 512b burst";
    }
    leaf counter_hbm_db1_hbm_error_counters3_crc_error_cntr_pc0 {
      type oc-yang:counter64;
      description
        "Counter of CRC-12 errors on the whole 512b burst";
    }
    leaf counter_hbm_db1_hbm_error_counters4_crc_error_cntr_pc0 {
      type oc-yang:counter64;
      description
        "Counter of CRC-12 errors on the whole 512b burst";
    }
    leaf counter_hbm_db1_hbm_error_counters5_crc_error_cntr_pc0 {
      type oc-yang:counter64;
      description
        "Counter of CRC-12 errors on the whole 512b burst";
    }
    leaf counter_hbm_db1_hbm_error_counters6_crc_error_cntr_pc0 {
      type oc-yang:counter64;
      description
        "Counter of CRC-12 errors on the whole 512b burst";
    }
    leaf counter_hbm_db1_hbm_error_counters7_crc_error_cntr_pc0 {
      type oc-yang:counter64;
      description
        "Counter of CRC-12 errors on the whole 512b burst";
    }
    leaf counter_hbm_db2_hbm_error_counters0_crc_error_cntr_pc0 {
      type oc-yang:counter64;
      description
        "Counter of CRC-12 errors on the whole 512b burst";
    }
    leaf counter_hbm_db2_hbm_error_counters1_crc_error_cntr_pc0 {
      type oc-yang:counter64;
      description
        "Counter of CRC-12 errors on the whole 512b burst";
    }
    leaf counter_hbm_db2_hbm_error_counters2_crc_error_cntr_pc0 {
      type oc-yang:counter64;
      description
        "Counter of CRC-12 errors on the whole 512b burst";
    }
    leaf counter_hbm_db2_hbm_error_counters3_crc_error_cntr_pc0 {
      type oc-yang:counter64;
      description
        "Counter of CRC-12 errors on the whole 512b burst";
    }
    leaf counter_hbm_db2_hbm_error_counters4_crc_error_cntr_pc0 {
      type oc-yang:counter64;
      description
        "Counter of CRC-12 errors on the whole 512b burst";
    }
    leaf counter_hbm_db2_hbm_error_counters5_crc_error_cntr_pc0 {
      type oc-yang:counter64;
      description
        "Counter of CRC-12 errors on the whole 512b burst";
    }
    leaf counter_hbm_db2_hbm_error_counters6_crc_error_cntr_pc0 {
      type oc-yang:counter64;
      description
        "Counter of CRC-12 errors on the whole 512b burst";
    }
    leaf counter_hbm_db2_hbm_error_counters7_crc_error_cntr_pc0 {
      type oc-yang:counter64;
      description
        "Counter of CRC-12 errors on the whole 512b burst";
    }
    leaf counter_hbm_db3_hbm_error_counters0_crc_error_cntr_pc0 {
      type oc-yang:counter64;
      description
        "Counter of CRC-12 errors on the whole 512b burst";
    }
    leaf counter_hbm_db3_hbm_error_counters1_crc_error_cntr_pc0 {
      type oc-yang:counter64;
      description
        "Counter of CRC-12 errors on the whole 512b burst";
    }
    leaf counter_hbm_db3_hbm_error_counters2_crc_error_cntr_pc0 {
      type oc-yang:counter64;
      description
        "Counter of CRC-12 errors on the whole 512b burst";
    }
    leaf counter_hbm_db3_hbm_error_counters3_crc_error_cntr_pc0 {
      type oc-yang:counter64;
      description
        "Counter of CRC-12 errors on the whole 512b burst";
    }
    leaf counter_hbm_db3_hbm_error_counters4_crc_error_cntr_pc0 {
      type oc-yang:counter64;
      description
        "Counter of CRC-12 errors on the whole 512b burst";
    }
    leaf counter_hbm_db3_hbm_error_counters5_crc_error_cntr_pc0 {
      type oc-yang:counter64;
      description
        "Counter of CRC-12 errors on the whole 512b burst";
    }
    leaf counter_hbm_db3_hbm_error_counters6_crc_error_cntr_pc0 {
      type oc-yang:counter64;
      description
        "Counter of CRC-12 errors on the whole 512b burst";
    }
    leaf counter_hbm_db3_hbm_error_counters7_crc_error_cntr_pc0 {
      type oc-yang:counter64;
      description
        "Counter of CRC-12 errors on the whole 512b burst";
    }
    leaf counter_hbm_db0_hbm_error_counters0_crc_error_cntr_pc1 {
      type oc-yang:counter64;
      description
        "Reserved";
    }
    leaf counter_hbm_db0_hbm_error_counters1_crc_error_cntr_pc1 {
      type oc-yang:counter64;
      description
        "Reserved";
    }
    leaf counter_hbm_db0_hbm_error_counters2_crc_error_cntr_pc1 {
      type oc-yang:counter64;
      description
        "Reserved";
    }
    leaf counter_hbm_db0_hbm_error_counters3_crc_error_cntr_pc1 {
      type oc-yang:counter64;
      description
        "Reserved";
    }
    leaf counter_hbm_db0_hbm_error_counters4_crc_error_cntr_pc1 {
      type oc-yang:counter64;
      description
        "Reserved";
    }
    leaf counter_hbm_db0_hbm_error_counters5_crc_error_cntr_pc1 {
      type oc-yang:counter64;
      description
        "Reserved";
    }
    leaf counter_hbm_db0_hbm_error_counters6_crc_error_cntr_pc1 {
      type oc-yang:counter64;
      description
        "Reserved";
    }
    leaf counter_hbm_db0_hbm_error_counters7_crc_error_cntr_pc1 {
      type oc-yang:counter64;
      description
        "Reserved";
    }
    leaf counter_hbm_db1_hbm_error_counters0_crc_error_cntr_pc1 {
      type oc-yang:counter64;
      description
        "Reserved";
    }
    leaf counter_hbm_db1_hbm_error_counters1_crc_error_cntr_pc1 {
      type oc-yang:counter64;
      description
        "Reserved";
    }
    leaf counter_hbm_db1_hbm_error_counters2_crc_error_cntr_pc1 {
      type oc-yang:counter64;
      description
        "Reserved";
    }
    leaf counter_hbm_db1_hbm_error_counters3_crc_error_cntr_pc1 {
      type oc-yang:counter64;
      description
        "Reserved";
    }
    leaf counter_hbm_db1_hbm_error_counters4_crc_error_cntr_pc1 {
      type oc-yang:counter64;
      description
        "Reserved";
    }
    leaf counter_hbm_db1_hbm_error_counters5_crc_error_cntr_pc1 {
      type oc-yang:counter64;
      description
        "Reserved";
    }
    leaf counter_hbm_db1_hbm_error_counters6_crc_error_cntr_pc1 {
      type oc-yang:counter64;
      description
        "Reserved";
    }
    leaf counter_hbm_db1_hbm_error_counters7_crc_error_cntr_pc1 {
      type oc-yang:counter64;
      description
        "Reserved";
    }
    leaf counter_hbm_db2_hbm_error_counters0_crc_error_cntr_pc1 {
      type oc-yang:counter64;
      description
        "Reserved";
    }
    leaf counter_hbm_db2_hbm_error_counters1_crc_error_cntr_pc1 {
      type oc-yang:counter64;
      description
        "Reserved";
    }
    leaf counter_hbm_db2_hbm_error_counters2_crc_error_cntr_pc1 {
      type oc-yang:counter64;
      description
        "Reserved";
    }
    leaf counter_hbm_db2_hbm_error_counters3_crc_error_cntr_pc1 {
      type oc-yang:counter64;
      description
        "Reserved";
    }
    leaf counter_hbm_db2_hbm_error_counters4_crc_error_cntr_pc1 {
      type oc-yang:counter64;
      description
        "Reserved";
    }
    leaf counter_hbm_db2_hbm_error_counters5_crc_error_cntr_pc1 {
      type oc-yang:counter64;
      description
        "Reserved";
    }
    leaf counter_hbm_db2_hbm_error_counters6_crc_error_cntr_pc1 {
      type oc-yang:counter64;
      description
        "Reserved";
    }
    leaf counter_hbm_db2_hbm_error_counters7_crc_error_cntr_pc1 {
      type oc-yang:counter64;
      description
        "Reserved";
    }
    leaf counter_hbm_db3_hbm_error_counters0_crc_error_cntr_pc1 {
      type oc-yang:counter64;
      description
        "Reserved";
    }
    leaf counter_hbm_db3_hbm_error_counters1_crc_error_cntr_pc1 {
      type oc-yang:counter64;
      description
        "Reserved";
    }
    leaf counter_hbm_db3_hbm_error_counters2_crc_error_cntr_pc1 {
      type oc-yang:counter64;
      description
        "Reserved";
    }
    leaf counter_hbm_db3_hbm_error_counters3_crc_error_cntr_pc1 {
      type oc-yang:counter64;
      description
        "Reserved";
    }
    leaf counter_hbm_db3_hbm_error_counters4_crc_error_cntr_pc1 {
      type oc-yang:counter64;
      description
        "Reserved";
    }
    leaf counter_hbm_db3_hbm_error_counters5_crc_error_cntr_pc1 {
      type oc-yang:counter64;
      description
        "Reserved";
    }
    leaf counter_hbm_db3_hbm_error_counters6_crc_error_cntr_pc1 {
      type oc-yang:counter64;
      description
        "Reserved";
    }
    leaf counter_hbm_db3_hbm_error_counters7_crc_error_cntr_pc1 {
      type oc-yang:counter64;
      description
        "Reserved";
    }
    leaf counter_hbm_db0_hbm_error_counters0_derr_cntr_dw0 {
      type oc-yang:counter64;
      description
        "Counter of write data parity errors indicated by DERR from HBM die. These errors are ignored by MMU. Counter for DW0, or DQ bits 31:0";
    }
    leaf counter_hbm_db0_hbm_error_counters1_derr_cntr_dw0 {
      type oc-yang:counter64;
      description
        "Counter of write data parity errors indicated by DERR from HBM die. These errors are ignored by MMU. Counter for DW0, or DQ bits 31:0";
    }
    leaf counter_hbm_db0_hbm_error_counters2_derr_cntr_dw0 {
      type oc-yang:counter64;
      description
        "Counter of write data parity errors indicated by DERR from HBM die. These errors are ignored by MMU. Counter for DW0, or DQ bits 31:0";
    }
    leaf counter_hbm_db0_hbm_error_counters3_derr_cntr_dw0 {
      type oc-yang:counter64;
      description
        "Counter of write data parity errors indicated by DERR from HBM die. These errors are ignored by MMU. Counter for DW0, or DQ bits 31:0";
    }
    leaf counter_hbm_db0_hbm_error_counters4_derr_cntr_dw0 {
      type oc-yang:counter64;
      description
        "Counter of write data parity errors indicated by DERR from HBM die. These errors are ignored by MMU. Counter for DW0, or DQ bits 31:0";
    }
    leaf counter_hbm_db0_hbm_error_counters5_derr_cntr_dw0 {
      type oc-yang:counter64;
      description
        "Counter of write data parity errors indicated by DERR from HBM die. These errors are ignored by MMU. Counter for DW0, or DQ bits 31:0";
    }
    leaf counter_hbm_db0_hbm_error_counters6_derr_cntr_dw0 {
      type oc-yang:counter64;
      description
        "Counter of write data parity errors indicated by DERR from HBM die. These errors are ignored by MMU. Counter for DW0, or DQ bits 31:0";
    }
    leaf counter_hbm_db0_hbm_error_counters7_derr_cntr_dw0 {
      type oc-yang:counter64;
      description
        "Counter of write data parity errors indicated by DERR from HBM die. These errors are ignored by MMU. Counter for DW0, or DQ bits 31:0";
    }
    leaf counter_hbm_db1_hbm_error_counters0_derr_cntr_dw0 {
      type oc-yang:counter64;
      description
        "Counter of write data parity errors indicated by DERR from HBM die. These errors are ignored by MMU. Counter for DW0, or DQ bits 31:0";
    }
    leaf counter_hbm_db1_hbm_error_counters1_derr_cntr_dw0 {
      type oc-yang:counter64;
      description
        "Counter of write data parity errors indicated by DERR from HBM die. These errors are ignored by MMU. Counter for DW0, or DQ bits 31:0";
    }
    leaf counter_hbm_db1_hbm_error_counters2_derr_cntr_dw0 {
      type oc-yang:counter64;
      description
        "Counter of write data parity errors indicated by DERR from HBM die. These errors are ignored by MMU. Counter for DW0, or DQ bits 31:0";
    }
    leaf counter_hbm_db1_hbm_error_counters3_derr_cntr_dw0 {
      type oc-yang:counter64;
      description
        "Counter of write data parity errors indicated by DERR from HBM die. These errors are ignored by MMU. Counter for DW0, or DQ bits 31:0";
    }
    leaf counter_hbm_db1_hbm_error_counters4_derr_cntr_dw0 {
      type oc-yang:counter64;
      description
        "Counter of write data parity errors indicated by DERR from HBM die. These errors are ignored by MMU. Counter for DW0, or DQ bits 31:0";
    }
    leaf counter_hbm_db1_hbm_error_counters5_derr_cntr_dw0 {
      type oc-yang:counter64;
      description
        "Counter of write data parity errors indicated by DERR from HBM die. These errors are ignored by MMU. Counter for DW0, or DQ bits 31:0";
    }
    leaf counter_hbm_db1_hbm_error_counters6_derr_cntr_dw0 {
      type oc-yang:counter64;
      description
        "Counter of write data parity errors indicated by DERR from HBM die. These errors are ignored by MMU. Counter for DW0, or DQ bits 31:0";
    }
    leaf counter_hbm_db1_hbm_error_counters7_derr_cntr_dw0 {
      type oc-yang:counter64;
      description
        "Counter of write data parity errors indicated by DERR from HBM die. These errors are ignored by MMU. Counter for DW0, or DQ bits 31:0";
    }
    leaf counter_hbm_db2_hbm_error_counters0_derr_cntr_dw0 {
      type oc-yang:counter64;
      description
        "Counter of write data parity errors indicated by DERR from HBM die. These errors are ignored by MMU. Counter for DW0, or DQ bits 31:0";
    }
    leaf counter_hbm_db2_hbm_error_counters1_derr_cntr_dw0 {
      type oc-yang:counter64;
      description
        "Counter of write data parity errors indicated by DERR from HBM die. These errors are ignored by MMU. Counter for DW0, or DQ bits 31:0";
    }
    leaf counter_hbm_db2_hbm_error_counters2_derr_cntr_dw0 {
      type oc-yang:counter64;
      description
        "Counter of write data parity errors indicated by DERR from HBM die. These errors are ignored by MMU. Counter for DW0, or DQ bits 31:0";
    }
    leaf counter_hbm_db2_hbm_error_counters3_derr_cntr_dw0 {
      type oc-yang:counter64;
      description
        "Counter of write data parity errors indicated by DERR from HBM die. These errors are ignored by MMU. Counter for DW0, or DQ bits 31:0";
    }
    leaf counter_hbm_db2_hbm_error_counters4_derr_cntr_dw0 {
      type oc-yang:counter64;
      description
        "Counter of write data parity errors indicated by DERR from HBM die. These errors are ignored by MMU. Counter for DW0, or DQ bits 31:0";
    }
    leaf counter_hbm_db2_hbm_error_counters5_derr_cntr_dw0 {
      type oc-yang:counter64;
      description
        "Counter of write data parity errors indicated by DERR from HBM die. These errors are ignored by MMU. Counter for DW0, or DQ bits 31:0";
    }
    leaf counter_hbm_db2_hbm_error_counters6_derr_cntr_dw0 {
      type oc-yang:counter64;
      description
        "Counter of write data parity errors indicated by DERR from HBM die. These errors are ignored by MMU. Counter for DW0, or DQ bits 31:0";
    }
    leaf counter_hbm_db2_hbm_error_counters7_derr_cntr_dw0 {
      type oc-yang:counter64;
      description
        "Counter of write data parity errors indicated by DERR from HBM die. These errors are ignored by MMU. Counter for DW0, or DQ bits 31:0";
    }
    leaf counter_hbm_db3_hbm_error_counters0_derr_cntr_dw0 {
      type oc-yang:counter64;
      description
        "Counter of write data parity errors indicated by DERR from HBM die. These errors are ignored by MMU. Counter for DW0, or DQ bits 31:0";
    }
    leaf counter_hbm_db3_hbm_error_counters1_derr_cntr_dw0 {
      type oc-yang:counter64;
      description
        "Counter of write data parity errors indicated by DERR from HBM die. These errors are ignored by MMU. Counter for DW0, or DQ bits 31:0";
    }
    leaf counter_hbm_db3_hbm_error_counters2_derr_cntr_dw0 {
      type oc-yang:counter64;
      description
        "Counter of write data parity errors indicated by DERR from HBM die. These errors are ignored by MMU. Counter for DW0, or DQ bits 31:0";
    }
    leaf counter_hbm_db3_hbm_error_counters3_derr_cntr_dw0 {
      type oc-yang:counter64;
      description
        "Counter of write data parity errors indicated by DERR from HBM die. These errors are ignored by MMU. Counter for DW0, or DQ bits 31:0";
    }
    leaf counter_hbm_db3_hbm_error_counters4_derr_cntr_dw0 {
      type oc-yang:counter64;
      description
        "Counter of write data parity errors indicated by DERR from HBM die. These errors are ignored by MMU. Counter for DW0, or DQ bits 31:0";
    }
    leaf counter_hbm_db3_hbm_error_counters5_derr_cntr_dw0 {
      type oc-yang:counter64;
      description
        "Counter of write data parity errors indicated by DERR from HBM die. These errors are ignored by MMU. Counter for DW0, or DQ bits 31:0";
    }
    leaf counter_hbm_db3_hbm_error_counters6_derr_cntr_dw0 {
      type oc-yang:counter64;
      description
        "Counter of write data parity errors indicated by DERR from HBM die. These errors are ignored by MMU. Counter for DW0, or DQ bits 31:0";
    }
    leaf counter_hbm_db3_hbm_error_counters7_derr_cntr_dw0 {
      type oc-yang:counter64;
      description
        "Counter of write data parity errors indicated by DERR from HBM die. These errors are ignored by MMU. Counter for DW0, or DQ bits 31:0";
    }
    leaf counter_hbm_db0_hbm_error_counters0_derr_cntr_dw1 {
      type oc-yang:counter64;
      description
        "Counter of write data parity errors indicated by DERR from HBM die. These errors are ignored by MMU. Counter for DW1, or DQ bits 63:32";
    }
    leaf counter_hbm_db0_hbm_error_counters1_derr_cntr_dw1 {
      type oc-yang:counter64;
      description
        "Counter of write data parity errors indicated by DERR from HBM die. These errors are ignored by MMU. Counter for DW1, or DQ bits 63:32";
    }
    leaf counter_hbm_db0_hbm_error_counters2_derr_cntr_dw1 {
      type oc-yang:counter64;
      description
        "Counter of write data parity errors indicated by DERR from HBM die. These errors are ignored by MMU. Counter for DW1, or DQ bits 63:32";
    }
    leaf counter_hbm_db0_hbm_error_counters3_derr_cntr_dw1 {
      type oc-yang:counter64;
      description
        "Counter of write data parity errors indicated by DERR from HBM die. These errors are ignored by MMU. Counter for DW1, or DQ bits 63:32";
    }
    leaf counter_hbm_db0_hbm_error_counters4_derr_cntr_dw1 {
      type oc-yang:counter64;
      description
        "Counter of write data parity errors indicated by DERR from HBM die. These errors are ignored by MMU. Counter for DW1, or DQ bits 63:32";
    }
    leaf counter_hbm_db0_hbm_error_counters5_derr_cntr_dw1 {
      type oc-yang:counter64;
      description
        "Counter of write data parity errors indicated by DERR from HBM die. These errors are ignored by MMU. Counter for DW1, or DQ bits 63:32";
    }
    leaf counter_hbm_db0_hbm_error_counters6_derr_cntr_dw1 {
      type oc-yang:counter64;
      description
        "Counter of write data parity errors indicated by DERR from HBM die. These errors are ignored by MMU. Counter for DW1, or DQ bits 63:32";
    }
    leaf counter_hbm_db0_hbm_error_counters7_derr_cntr_dw1 {
      type oc-yang:counter64;
      description
        "Counter of write data parity errors indicated by DERR from HBM die. These errors are ignored by MMU. Counter for DW1, or DQ bits 63:32";
    }
    leaf counter_hbm_db1_hbm_error_counters0_derr_cntr_dw1 {
      type oc-yang:counter64;
      description
        "Counter of write data parity errors indicated by DERR from HBM die. These errors are ignored by MMU. Counter for DW1, or DQ bits 63:32";
    }
    leaf counter_hbm_db1_hbm_error_counters1_derr_cntr_dw1 {
      type oc-yang:counter64;
      description
        "Counter of write data parity errors indicated by DERR from HBM die. These errors are ignored by MMU. Counter for DW1, or DQ bits 63:32";
    }
    leaf counter_hbm_db1_hbm_error_counters2_derr_cntr_dw1 {
      type oc-yang:counter64;
      description
        "Counter of write data parity errors indicated by DERR from HBM die. These errors are ignored by MMU. Counter for DW1, or DQ bits 63:32";
    }
    leaf counter_hbm_db1_hbm_error_counters3_derr_cntr_dw1 {
      type oc-yang:counter64;
      description
        "Counter of write data parity errors indicated by DERR from HBM die. These errors are ignored by MMU. Counter for DW1, or DQ bits 63:32";
    }
    leaf counter_hbm_db1_hbm_error_counters4_derr_cntr_dw1 {
      type oc-yang:counter64;
      description
        "Counter of write data parity errors indicated by DERR from HBM die. These errors are ignored by MMU. Counter for DW1, or DQ bits 63:32";
    }
    leaf counter_hbm_db1_hbm_error_counters5_derr_cntr_dw1 {
      type oc-yang:counter64;
      description
        "Counter of write data parity errors indicated by DERR from HBM die. These errors are ignored by MMU. Counter for DW1, or DQ bits 63:32";
    }
    leaf counter_hbm_db1_hbm_error_counters6_derr_cntr_dw1 {
      type oc-yang:counter64;
      description
        "Counter of write data parity errors indicated by DERR from HBM die. These errors are ignored by MMU. Counter for DW1, or DQ bits 63:32";
    }
    leaf counter_hbm_db1_hbm_error_counters7_derr_cntr_dw1 {
      type oc-yang:counter64;
      description
        "Counter of write data parity errors indicated by DERR from HBM die. These errors are ignored by MMU. Counter for DW1, or DQ bits 63:32";
    }
    leaf counter_hbm_db2_hbm_error_counters0_derr_cntr_dw1 {
      type oc-yang:counter64;
      description
        "Counter of write data parity errors indicated by DERR from HBM die. These errors are ignored by MMU. Counter for DW1, or DQ bits 63:32";
    }
    leaf counter_hbm_db2_hbm_error_counters1_derr_cntr_dw1 {
      type oc-yang:counter64;
      description
        "Counter of write data parity errors indicated by DERR from HBM die. These errors are ignored by MMU. Counter for DW1, or DQ bits 63:32";
    }
    leaf counter_hbm_db2_hbm_error_counters2_derr_cntr_dw1 {
      type oc-yang:counter64;
      description
        "Counter of write data parity errors indicated by DERR from HBM die. These errors are ignored by MMU. Counter for DW1, or DQ bits 63:32";
    }
    leaf counter_hbm_db2_hbm_error_counters3_derr_cntr_dw1 {
      type oc-yang:counter64;
      description
        "Counter of write data parity errors indicated by DERR from HBM die. These errors are ignored by MMU. Counter for DW1, or DQ bits 63:32";
    }
    leaf counter_hbm_db2_hbm_error_counters4_derr_cntr_dw1 {
      type oc-yang:counter64;
      description
        "Counter of write data parity errors indicated by DERR from HBM die. These errors are ignored by MMU. Counter for DW1, or DQ bits 63:32";
    }
    leaf counter_hbm_db2_hbm_error_counters5_derr_cntr_dw1 {
      type oc-yang:counter64;
      description
        "Counter of write data parity errors indicated by DERR from HBM die. These errors are ignored by MMU. Counter for DW1, or DQ bits 63:32";
    }
    leaf counter_hbm_db2_hbm_error_counters6_derr_cntr_dw1 {
      type oc-yang:counter64;
      description
        "Counter of write data parity errors indicated by DERR from HBM die. These errors are ignored by MMU. Counter for DW1, or DQ bits 63:32";
    }
    leaf counter_hbm_db2_hbm_error_counters7_derr_cntr_dw1 {
      type oc-yang:counter64;
      description
        "Counter of write data parity errors indicated by DERR from HBM die. These errors are ignored by MMU. Counter for DW1, or DQ bits 63:32";
    }
    leaf counter_hbm_db3_hbm_error_counters0_derr_cntr_dw1 {
      type oc-yang:counter64;
      description
        "Counter of write data parity errors indicated by DERR from HBM die. These errors are ignored by MMU. Counter for DW1, or DQ bits 63:32";
    }
    leaf counter_hbm_db3_hbm_error_counters1_derr_cntr_dw1 {
      type oc-yang:counter64;
      description
        "Counter of write data parity errors indicated by DERR from HBM die. These errors are ignored by MMU. Counter for DW1, or DQ bits 63:32";
    }
    leaf counter_hbm_db3_hbm_error_counters2_derr_cntr_dw1 {
      type oc-yang:counter64;
      description
        "Counter of write data parity errors indicated by DERR from HBM die. These errors are ignored by MMU. Counter for DW1, or DQ bits 63:32";
    }
    leaf counter_hbm_db3_hbm_error_counters3_derr_cntr_dw1 {
      type oc-yang:counter64;
      description
        "Counter of write data parity errors indicated by DERR from HBM die. These errors are ignored by MMU. Counter for DW1, or DQ bits 63:32";
    }
    leaf counter_hbm_db3_hbm_error_counters4_derr_cntr_dw1 {
      type oc-yang:counter64;
      description
        "Counter of write data parity errors indicated by DERR from HBM die. These errors are ignored by MMU. Counter for DW1, or DQ bits 63:32";
    }
    leaf counter_hbm_db3_hbm_error_counters5_derr_cntr_dw1 {
      type oc-yang:counter64;
      description
        "Counter of write data parity errors indicated by DERR from HBM die. These errors are ignored by MMU. Counter for DW1, or DQ bits 63:32";
    }
    leaf counter_hbm_db3_hbm_error_counters6_derr_cntr_dw1 {
      type oc-yang:counter64;
      description
        "Counter of write data parity errors indicated by DERR from HBM die. These errors are ignored by MMU. Counter for DW1, or DQ bits 63:32";
    }
    leaf counter_hbm_db3_hbm_error_counters7_derr_cntr_dw1 {
      type oc-yang:counter64;
      description
        "Counter of write data parity errors indicated by DERR from HBM die. These errors are ignored by MMU. Counter for DW1, or DQ bits 63:32";
    }
    leaf counter_hbm_db0_hbm_error_counters0_derr_cntr_dw2 {
      type oc-yang:counter64;
      description
        "Counter of write data parity errors indicated by DERR from HBM die. These errors are ignored by MMU. Counter for DW2, or DQ bits 95:64";
    }
    leaf counter_hbm_db0_hbm_error_counters1_derr_cntr_dw2 {
      type oc-yang:counter64;
      description
        "Counter of write data parity errors indicated by DERR from HBM die. These errors are ignored by MMU. Counter for DW2, or DQ bits 95:64";
    }
    leaf counter_hbm_db0_hbm_error_counters2_derr_cntr_dw2 {
      type oc-yang:counter64;
      description
        "Counter of write data parity errors indicated by DERR from HBM die. These errors are ignored by MMU. Counter for DW2, or DQ bits 95:64";
    }
    leaf counter_hbm_db0_hbm_error_counters3_derr_cntr_dw2 {
      type oc-yang:counter64;
      description
        "Counter of write data parity errors indicated by DERR from HBM die. These errors are ignored by MMU. Counter for DW2, or DQ bits 95:64";
    }
    leaf counter_hbm_db0_hbm_error_counters4_derr_cntr_dw2 {
      type oc-yang:counter64;
      description
        "Counter of write data parity errors indicated by DERR from HBM die. These errors are ignored by MMU. Counter for DW2, or DQ bits 95:64";
    }
    leaf counter_hbm_db0_hbm_error_counters5_derr_cntr_dw2 {
      type oc-yang:counter64;
      description
        "Counter of write data parity errors indicated by DERR from HBM die. These errors are ignored by MMU. Counter for DW2, or DQ bits 95:64";
    }
    leaf counter_hbm_db0_hbm_error_counters6_derr_cntr_dw2 {
      type oc-yang:counter64;
      description
        "Counter of write data parity errors indicated by DERR from HBM die. These errors are ignored by MMU. Counter for DW2, or DQ bits 95:64";
    }
    leaf counter_hbm_db0_hbm_error_counters7_derr_cntr_dw2 {
      type oc-yang:counter64;
      description
        "Counter of write data parity errors indicated by DERR from HBM die. These errors are ignored by MMU. Counter for DW2, or DQ bits 95:64";
    }
    leaf counter_hbm_db1_hbm_error_counters0_derr_cntr_dw2 {
      type oc-yang:counter64;
      description
        "Counter of write data parity errors indicated by DERR from HBM die. These errors are ignored by MMU. Counter for DW2, or DQ bits 95:64";
    }
    leaf counter_hbm_db1_hbm_error_counters1_derr_cntr_dw2 {
      type oc-yang:counter64;
      description
        "Counter of write data parity errors indicated by DERR from HBM die. These errors are ignored by MMU. Counter for DW2, or DQ bits 95:64";
    }
    leaf counter_hbm_db1_hbm_error_counters2_derr_cntr_dw2 {
      type oc-yang:counter64;
      description
        "Counter of write data parity errors indicated by DERR from HBM die. These errors are ignored by MMU. Counter for DW2, or DQ bits 95:64";
    }
    leaf counter_hbm_db1_hbm_error_counters3_derr_cntr_dw2 {
      type oc-yang:counter64;
      description
        "Counter of write data parity errors indicated by DERR from HBM die. These errors are ignored by MMU. Counter for DW2, or DQ bits 95:64";
    }
    leaf counter_hbm_db1_hbm_error_counters4_derr_cntr_dw2 {
      type oc-yang:counter64;
      description
        "Counter of write data parity errors indicated by DERR from HBM die. These errors are ignored by MMU. Counter for DW2, or DQ bits 95:64";
    }
    leaf counter_hbm_db1_hbm_error_counters5_derr_cntr_dw2 {
      type oc-yang:counter64;
      description
        "Counter of write data parity errors indicated by DERR from HBM die. These errors are ignored by MMU. Counter for DW2, or DQ bits 95:64";
    }
    leaf counter_hbm_db1_hbm_error_counters6_derr_cntr_dw2 {
      type oc-yang:counter64;
      description
        "Counter of write data parity errors indicated by DERR from HBM die. These errors are ignored by MMU. Counter for DW2, or DQ bits 95:64";
    }
    leaf counter_hbm_db1_hbm_error_counters7_derr_cntr_dw2 {
      type oc-yang:counter64;
      description
        "Counter of write data parity errors indicated by DERR from HBM die. These errors are ignored by MMU. Counter for DW2, or DQ bits 95:64";
    }
    leaf counter_hbm_db2_hbm_error_counters0_derr_cntr_dw2 {
      type oc-yang:counter64;
      description
        "Counter of write data parity errors indicated by DERR from HBM die. These errors are ignored by MMU. Counter for DW2, or DQ bits 95:64";
    }
    leaf counter_hbm_db2_hbm_error_counters1_derr_cntr_dw2 {
      type oc-yang:counter64;
      description
        "Counter of write data parity errors indicated by DERR from HBM die. These errors are ignored by MMU. Counter for DW2, or DQ bits 95:64";
    }
    leaf counter_hbm_db2_hbm_error_counters2_derr_cntr_dw2 {
      type oc-yang:counter64;
      description
        "Counter of write data parity errors indicated by DERR from HBM die. These errors are ignored by MMU. Counter for DW2, or DQ bits 95:64";
    }
    leaf counter_hbm_db2_hbm_error_counters3_derr_cntr_dw2 {
      type oc-yang:counter64;
      description
        "Counter of write data parity errors indicated by DERR from HBM die. These errors are ignored by MMU. Counter for DW2, or DQ bits 95:64";
    }
    leaf counter_hbm_db2_hbm_error_counters4_derr_cntr_dw2 {
      type oc-yang:counter64;
      description
        "Counter of write data parity errors indicated by DERR from HBM die. These errors are ignored by MMU. Counter for DW2, or DQ bits 95:64";
    }
    leaf counter_hbm_db2_hbm_error_counters5_derr_cntr_dw2 {
      type oc-yang:counter64;
      description
        "Counter of write data parity errors indicated by DERR from HBM die. These errors are ignored by MMU. Counter for DW2, or DQ bits 95:64";
    }
    leaf counter_hbm_db2_hbm_error_counters6_derr_cntr_dw2 {
      type oc-yang:counter64;
      description
        "Counter of write data parity errors indicated by DERR from HBM die. These errors are ignored by MMU. Counter for DW2, or DQ bits 95:64";
    }
    leaf counter_hbm_db2_hbm_error_counters7_derr_cntr_dw2 {
      type oc-yang:counter64;
      description
        "Counter of write data parity errors indicated by DERR from HBM die. These errors are ignored by MMU. Counter for DW2, or DQ bits 95:64";
    }
    leaf counter_hbm_db3_hbm_error_counters0_derr_cntr_dw2 {
      type oc-yang:counter64;
      description
        "Counter of write data parity errors indicated by DERR from HBM die. These errors are ignored by MMU. Counter for DW2, or DQ bits 95:64";
    }
    leaf counter_hbm_db3_hbm_error_counters1_derr_cntr_dw2 {
      type oc-yang:counter64;
      description
        "Counter of write data parity errors indicated by DERR from HBM die. These errors are ignored by MMU. Counter for DW2, or DQ bits 95:64";
    }
    leaf counter_hbm_db3_hbm_error_counters2_derr_cntr_dw2 {
      type oc-yang:counter64;
      description
        "Counter of write data parity errors indicated by DERR from HBM die. These errors are ignored by MMU. Counter for DW2, or DQ bits 95:64";
    }
    leaf counter_hbm_db3_hbm_error_counters3_derr_cntr_dw2 {
      type oc-yang:counter64;
      description
        "Counter of write data parity errors indicated by DERR from HBM die. These errors are ignored by MMU. Counter for DW2, or DQ bits 95:64";
    }
    leaf counter_hbm_db3_hbm_error_counters4_derr_cntr_dw2 {
      type oc-yang:counter64;
      description
        "Counter of write data parity errors indicated by DERR from HBM die. These errors are ignored by MMU. Counter for DW2, or DQ bits 95:64";
    }
    leaf counter_hbm_db3_hbm_error_counters5_derr_cntr_dw2 {
      type oc-yang:counter64;
      description
        "Counter of write data parity errors indicated by DERR from HBM die. These errors are ignored by MMU. Counter for DW2, or DQ bits 95:64";
    }
    leaf counter_hbm_db3_hbm_error_counters6_derr_cntr_dw2 {
      type oc-yang:counter64;
      description
        "Counter of write data parity errors indicated by DERR from HBM die. These errors are ignored by MMU. Counter for DW2, or DQ bits 95:64";
    }
    leaf counter_hbm_db3_hbm_error_counters7_derr_cntr_dw2 {
      type oc-yang:counter64;
      description
        "Counter of write data parity errors indicated by DERR from HBM die. These errors are ignored by MMU. Counter for DW2, or DQ bits 95:64";
    }
    leaf counter_hbm_db0_hbm_error_counters0_derr_cntr_dw3 {
      type oc-yang:counter64;
      description
        "Counter of write data parity errors indicated by DERR from HBM die. These errors are ignored by MMU. Counter for DW3, or DQ bits 127:96";
    }
    leaf counter_hbm_db0_hbm_error_counters1_derr_cntr_dw3 {
      type oc-yang:counter64;
      description
        "Counter of write data parity errors indicated by DERR from HBM die. These errors are ignored by MMU. Counter for DW3, or DQ bits 127:96";
    }
    leaf counter_hbm_db0_hbm_error_counters2_derr_cntr_dw3 {
      type oc-yang:counter64;
      description
        "Counter of write data parity errors indicated by DERR from HBM die. These errors are ignored by MMU. Counter for DW3, or DQ bits 127:96";
    }
    leaf counter_hbm_db0_hbm_error_counters3_derr_cntr_dw3 {
      type oc-yang:counter64;
      description
        "Counter of write data parity errors indicated by DERR from HBM die. These errors are ignored by MMU. Counter for DW3, or DQ bits 127:96";
    }
    leaf counter_hbm_db0_hbm_error_counters4_derr_cntr_dw3 {
      type oc-yang:counter64;
      description
        "Counter of write data parity errors indicated by DERR from HBM die. These errors are ignored by MMU. Counter for DW3, or DQ bits 127:96";
    }
    leaf counter_hbm_db0_hbm_error_counters5_derr_cntr_dw3 {
      type oc-yang:counter64;
      description
        "Counter of write data parity errors indicated by DERR from HBM die. These errors are ignored by MMU. Counter for DW3, or DQ bits 127:96";
    }
    leaf counter_hbm_db0_hbm_error_counters6_derr_cntr_dw3 {
      type oc-yang:counter64;
      description
        "Counter of write data parity errors indicated by DERR from HBM die. These errors are ignored by MMU. Counter for DW3, or DQ bits 127:96";
    }
    leaf counter_hbm_db0_hbm_error_counters7_derr_cntr_dw3 {
      type oc-yang:counter64;
      description
        "Counter of write data parity errors indicated by DERR from HBM die. These errors are ignored by MMU. Counter for DW3, or DQ bits 127:96";
    }
    leaf counter_hbm_db1_hbm_error_counters0_derr_cntr_dw3 {
      type oc-yang:counter64;
      description
        "Counter of write data parity errors indicated by DERR from HBM die. These errors are ignored by MMU. Counter for DW3, or DQ bits 127:96";
    }
    leaf counter_hbm_db1_hbm_error_counters1_derr_cntr_dw3 {
      type oc-yang:counter64;
      description
        "Counter of write data parity errors indicated by DERR from HBM die. These errors are ignored by MMU. Counter for DW3, or DQ bits 127:96";
    }
    leaf counter_hbm_db1_hbm_error_counters2_derr_cntr_dw3 {
      type oc-yang:counter64;
      description
        "Counter of write data parity errors indicated by DERR from HBM die. These errors are ignored by MMU. Counter for DW3, or DQ bits 127:96";
    }
    leaf counter_hbm_db1_hbm_error_counters3_derr_cntr_dw3 {
      type oc-yang:counter64;
      description
        "Counter of write data parity errors indicated by DERR from HBM die. These errors are ignored by MMU. Counter for DW3, or DQ bits 127:96";
    }
    leaf counter_hbm_db1_hbm_error_counters4_derr_cntr_dw3 {
      type oc-yang:counter64;
      description
        "Counter of write data parity errors indicated by DERR from HBM die. These errors are ignored by MMU. Counter for DW3, or DQ bits 127:96";
    }
    leaf counter_hbm_db1_hbm_error_counters5_derr_cntr_dw3 {
      type oc-yang:counter64;
      description
        "Counter of write data parity errors indicated by DERR from HBM die. These errors are ignored by MMU. Counter for DW3, or DQ bits 127:96";
    }
    leaf counter_hbm_db1_hbm_error_counters6_derr_cntr_dw3 {
      type oc-yang:counter64;
      description
        "Counter of write data parity errors indicated by DERR from HBM die. These errors are ignored by MMU. Counter for DW3, or DQ bits 127:96";
    }
    leaf counter_hbm_db1_hbm_error_counters7_derr_cntr_dw3 {
      type oc-yang:counter64;
      description
        "Counter of write data parity errors indicated by DERR from HBM die. These errors are ignored by MMU. Counter for DW3, or DQ bits 127:96";
    }
    leaf counter_hbm_db2_hbm_error_counters0_derr_cntr_dw3 {
      type oc-yang:counter64;
      description
        "Counter of write data parity errors indicated by DERR from HBM die. These errors are ignored by MMU. Counter for DW3, or DQ bits 127:96";
    }
    leaf counter_hbm_db2_hbm_error_counters1_derr_cntr_dw3 {
      type oc-yang:counter64;
      description
        "Counter of write data parity errors indicated by DERR from HBM die. These errors are ignored by MMU. Counter for DW3, or DQ bits 127:96";
    }
    leaf counter_hbm_db2_hbm_error_counters2_derr_cntr_dw3 {
      type oc-yang:counter64;
      description
        "Counter of write data parity errors indicated by DERR from HBM die. These errors are ignored by MMU. Counter for DW3, or DQ bits 127:96";
    }
    leaf counter_hbm_db2_hbm_error_counters3_derr_cntr_dw3 {
      type oc-yang:counter64;
      description
        "Counter of write data parity errors indicated by DERR from HBM die. These errors are ignored by MMU. Counter for DW3, or DQ bits 127:96";
    }
    leaf counter_hbm_db2_hbm_error_counters4_derr_cntr_dw3 {
      type oc-yang:counter64;
      description
        "Counter of write data parity errors indicated by DERR from HBM die. These errors are ignored by MMU. Counter for DW3, or DQ bits 127:96";
    }
    leaf counter_hbm_db2_hbm_error_counters5_derr_cntr_dw3 {
      type oc-yang:counter64;
      description
        "Counter of write data parity errors indicated by DERR from HBM die. These errors are ignored by MMU. Counter for DW3, or DQ bits 127:96";
    }
    leaf counter_hbm_db2_hbm_error_counters6_derr_cntr_dw3 {
      type oc-yang:counter64;
      description
        "Counter of write data parity errors indicated by DERR from HBM die. These errors are ignored by MMU. Counter for DW3, or DQ bits 127:96";
    }
    leaf counter_hbm_db2_hbm_error_counters7_derr_cntr_dw3 {
      type oc-yang:counter64;
      description
        "Counter of write data parity errors indicated by DERR from HBM die. These errors are ignored by MMU. Counter for DW3, or DQ bits 127:96";
    }
    leaf counter_hbm_db3_hbm_error_counters0_derr_cntr_dw3 {
      type oc-yang:counter64;
      description
        "Counter of write data parity errors indicated by DERR from HBM die. These errors are ignored by MMU. Counter for DW3, or DQ bits 127:96";
    }
    leaf counter_hbm_db3_hbm_error_counters1_derr_cntr_dw3 {
      type oc-yang:counter64;
      description
        "Counter of write data parity errors indicated by DERR from HBM die. These errors are ignored by MMU. Counter for DW3, or DQ bits 127:96";
    }
    leaf counter_hbm_db3_hbm_error_counters2_derr_cntr_dw3 {
      type oc-yang:counter64;
      description
        "Counter of write data parity errors indicated by DERR from HBM die. These errors are ignored by MMU. Counter for DW3, or DQ bits 127:96";
    }
    leaf counter_hbm_db3_hbm_error_counters3_derr_cntr_dw3 {
      type oc-yang:counter64;
      description
        "Counter of write data parity errors indicated by DERR from HBM die. These errors are ignored by MMU. Counter for DW3, or DQ bits 127:96";
    }
    leaf counter_hbm_db3_hbm_error_counters4_derr_cntr_dw3 {
      type oc-yang:counter64;
      description
        "Counter of write data parity errors indicated by DERR from HBM die. These errors are ignored by MMU. Counter for DW3, or DQ bits 127:96";
    }
    leaf counter_hbm_db3_hbm_error_counters5_derr_cntr_dw3 {
      type oc-yang:counter64;
      description
        "Counter of write data parity errors indicated by DERR from HBM die. These errors are ignored by MMU. Counter for DW3, or DQ bits 127:96";
    }
    leaf counter_hbm_db3_hbm_error_counters6_derr_cntr_dw3 {
      type oc-yang:counter64;
      description
        "Counter of write data parity errors indicated by DERR from HBM die. These errors are ignored by MMU. Counter for DW3, or DQ bits 127:96";
    }
    leaf counter_hbm_db3_hbm_error_counters7_derr_cntr_dw3 {
      type oc-yang:counter64;
      description
        "Counter of write data parity errors indicated by DERR from HBM die. These errors are ignored by MMU. Counter for DW3, or DQ bits 127:96";
    }
    leaf counter_hbm_db0_hbm_error_counters0_gen_error_rcvd_cntr {
      type oc-yang:counter64;
      description
        "Counter of Gen errors received from DRAM  invert crc";
    }
    leaf counter_hbm_db0_hbm_error_counters1_gen_error_rcvd_cntr {
      type oc-yang:counter64;
      description
        "Counter of Gen errors received from DRAM  invert crc";
    }
    leaf counter_hbm_db0_hbm_error_counters2_gen_error_rcvd_cntr {
      type oc-yang:counter64;
      description
        "Counter of Gen errors received from DRAM  invert crc";
    }
    leaf counter_hbm_db0_hbm_error_counters3_gen_error_rcvd_cntr {
      type oc-yang:counter64;
      description
        "Counter of Gen errors received from DRAM  invert crc";
    }
    leaf counter_hbm_db0_hbm_error_counters4_gen_error_rcvd_cntr {
      type oc-yang:counter64;
      description
        "Counter of Gen errors received from DRAM  invert crc";
    }
    leaf counter_hbm_db0_hbm_error_counters5_gen_error_rcvd_cntr {
      type oc-yang:counter64;
      description
        "Counter of Gen errors received from DRAM  invert crc";
    }
    leaf counter_hbm_db0_hbm_error_counters6_gen_error_rcvd_cntr {
      type oc-yang:counter64;
      description
        "Counter of Gen errors received from DRAM  invert crc";
    }
    leaf counter_hbm_db0_hbm_error_counters7_gen_error_rcvd_cntr {
      type oc-yang:counter64;
      description
        "Counter of Gen errors received from DRAM  invert crc";
    }
    leaf counter_hbm_db1_hbm_error_counters0_gen_error_rcvd_cntr {
      type oc-yang:counter64;
      description
        "Counter of Gen errors received from DRAM  invert crc";
    }
    leaf counter_hbm_db1_hbm_error_counters1_gen_error_rcvd_cntr {
      type oc-yang:counter64;
      description
        "Counter of Gen errors received from DRAM  invert crc";
    }
    leaf counter_hbm_db1_hbm_error_counters2_gen_error_rcvd_cntr {
      type oc-yang:counter64;
      description
        "Counter of Gen errors received from DRAM  invert crc";
    }
    leaf counter_hbm_db1_hbm_error_counters3_gen_error_rcvd_cntr {
      type oc-yang:counter64;
      description
        "Counter of Gen errors received from DRAM  invert crc";
    }
    leaf counter_hbm_db1_hbm_error_counters4_gen_error_rcvd_cntr {
      type oc-yang:counter64;
      description
        "Counter of Gen errors received from DRAM  invert crc";
    }
    leaf counter_hbm_db1_hbm_error_counters5_gen_error_rcvd_cntr {
      type oc-yang:counter64;
      description
        "Counter of Gen errors received from DRAM  invert crc";
    }
    leaf counter_hbm_db1_hbm_error_counters6_gen_error_rcvd_cntr {
      type oc-yang:counter64;
      description
        "Counter of Gen errors received from DRAM  invert crc";
    }
    leaf counter_hbm_db1_hbm_error_counters7_gen_error_rcvd_cntr {
      type oc-yang:counter64;
      description
        "Counter of Gen errors received from DRAM  invert crc";
    }
    leaf counter_hbm_db2_hbm_error_counters0_gen_error_rcvd_cntr {
      type oc-yang:counter64;
      description
        "Counter of Gen errors received from DRAM  invert crc";
    }
    leaf counter_hbm_db2_hbm_error_counters1_gen_error_rcvd_cntr {
      type oc-yang:counter64;
      description
        "Counter of Gen errors received from DRAM  invert crc";
    }
    leaf counter_hbm_db2_hbm_error_counters2_gen_error_rcvd_cntr {
      type oc-yang:counter64;
      description
        "Counter of Gen errors received from DRAM  invert crc";
    }
    leaf counter_hbm_db2_hbm_error_counters3_gen_error_rcvd_cntr {
      type oc-yang:counter64;
      description
        "Counter of Gen errors received from DRAM  invert crc";
    }
    leaf counter_hbm_db2_hbm_error_counters4_gen_error_rcvd_cntr {
      type oc-yang:counter64;
      description
        "Counter of Gen errors received from DRAM  invert crc";
    }
    leaf counter_hbm_db2_hbm_error_counters5_gen_error_rcvd_cntr {
      type oc-yang:counter64;
      description
        "Counter of Gen errors received from DRAM  invert crc";
    }
    leaf counter_hbm_db2_hbm_error_counters6_gen_error_rcvd_cntr {
      type oc-yang:counter64;
      description
        "Counter of Gen errors received from DRAM  invert crc";
    }
    leaf counter_hbm_db2_hbm_error_counters7_gen_error_rcvd_cntr {
      type oc-yang:counter64;
      description
        "Counter of Gen errors received from DRAM  invert crc";
    }
    leaf counter_hbm_db3_hbm_error_counters0_gen_error_rcvd_cntr {
      type oc-yang:counter64;
      description
        "Counter of Gen errors received from DRAM  invert crc";
    }
    leaf counter_hbm_db3_hbm_error_counters1_gen_error_rcvd_cntr {
      type oc-yang:counter64;
      description
        "Counter of Gen errors received from DRAM  invert crc";
    }
    leaf counter_hbm_db3_hbm_error_counters2_gen_error_rcvd_cntr {
      type oc-yang:counter64;
      description
        "Counter of Gen errors received from DRAM  invert crc";
    }
    leaf counter_hbm_db3_hbm_error_counters3_gen_error_rcvd_cntr {
      type oc-yang:counter64;
      description
        "Counter of Gen errors received from DRAM  invert crc";
    }
    leaf counter_hbm_db3_hbm_error_counters4_gen_error_rcvd_cntr {
      type oc-yang:counter64;
      description
        "Counter of Gen errors received from DRAM  invert crc";
    }
    leaf counter_hbm_db3_hbm_error_counters5_gen_error_rcvd_cntr {
      type oc-yang:counter64;
      description
        "Counter of Gen errors received from DRAM  invert crc";
    }
    leaf counter_hbm_db3_hbm_error_counters6_gen_error_rcvd_cntr {
      type oc-yang:counter64;
      description
        "Counter of Gen errors received from DRAM  invert crc";
    }
    leaf counter_hbm_db3_hbm_error_counters7_gen_error_rcvd_cntr {
      type oc-yang:counter64;
      description
        "Counter of Gen errors received from DRAM  invert crc";
    }
    leaf counter_hbm_db0_hbm_error_counters0_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters1_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters2_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters3_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters4_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters5_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters6_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters7_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters0_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters1_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters2_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters3_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters4_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters5_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters6_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db1_hbm_error_counters7_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters0_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters1_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters2_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters3_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters4_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters5_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters6_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db2_hbm_error_counters7_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters0_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters1_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters2_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters3_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters4_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters5_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters6_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db3_hbm_error_counters7_gen_error_sent_cntr {
      type oc-yang:counter64;
      description
        "[Defective: Alternatives are available at mmu_wr.DropPktCounterSms for the number of network pkts in error per sms interface and mmu_wr.GenErrDramPktsWrite for the number of DRAM pkts in error.] Counter of Gen errors sent to DRAM invert crc";
    }
    leaf counter_hbm_db0_hbm_error_counters0_multi_bit_ecc_error_cntr_pc0 {
      type oc-yang:counter64;
      description
        "Multi Bit Ecc Error on phase 0";
    }
    leaf counter_hbm_db0_hbm_error_counters1_multi_bit_ecc_error_cntr_pc0 {
      type oc-yang:counter64;
      description
        "Multi Bit Ecc Error on phase 0";
    }
    leaf counter_hbm_db0_hbm_error_counters2_multi_bit_ecc_error_cntr_pc0 {
      type oc-yang:counter64;
      description
        "Multi Bit Ecc Error on phase 0";
    }
    leaf counter_hbm_db0_hbm_error_counters3_multi_bit_ecc_error_cntr_pc0 {
      type oc-yang:counter64;
      description
        "Multi Bit Ecc Error on phase 0";
    }
    leaf counter_hbm_db0_hbm_error_counters4_multi_bit_ecc_error_cntr_pc0 {
      type oc-yang:counter64;
      description
        "Multi Bit Ecc Error on phase 0";
    }
    leaf counter_hbm_db0_hbm_error_counters5_multi_bit_ecc_error_cntr_pc0 {
      type oc-yang:counter64;
      description
        "Multi Bit Ecc Error on phase 0";
    }
    leaf counter_hbm_db0_hbm_error_counters6_multi_bit_ecc_error_cntr_pc0 {
      type oc-yang:counter64;
      description
        "Multi Bit Ecc Error on phase 0";
    }
    leaf counter_hbm_db0_hbm_error_counters7_multi_bit_ecc_error_cntr_pc0 {
      type oc-yang:counter64;
      description
        "Multi Bit Ecc Error on phase 0";
    }
    leaf counter_hbm_db1_hbm_error_counters0_multi_bit_ecc_error_cntr_pc0 {
      type oc-yang:counter64;
      description
        "Multi Bit Ecc Error on phase 0";
    }
    leaf counter_hbm_db1_hbm_error_counters1_multi_bit_ecc_error_cntr_pc0 {
      type oc-yang:counter64;
      description
        "Multi Bit Ecc Error on phase 0";
    }
    leaf counter_hbm_db1_hbm_error_counters2_multi_bit_ecc_error_cntr_pc0 {
      type oc-yang:counter64;
      description
        "Multi Bit Ecc Error on phase 0";
    }
    leaf counter_hbm_db1_hbm_error_counters3_multi_bit_ecc_error_cntr_pc0 {
      type oc-yang:counter64;
      description
        "Multi Bit Ecc Error on phase 0";
    }
    leaf counter_hbm_db1_hbm_error_counters4_multi_bit_ecc_error_cntr_pc0 {
      type oc-yang:counter64;
      description
        "Multi Bit Ecc Error on phase 0";
    }
    leaf counter_hbm_db1_hbm_error_counters5_multi_bit_ecc_error_cntr_pc0 {
      type oc-yang:counter64;
      description
        "Multi Bit Ecc Error on phase 0";
    }
    leaf counter_hbm_db1_hbm_error_counters6_multi_bit_ecc_error_cntr_pc0 {
      type oc-yang:counter64;
      description
        "Multi Bit Ecc Error on phase 0";
    }
    leaf counter_hbm_db1_hbm_error_counters7_multi_bit_ecc_error_cntr_pc0 {
      type oc-yang:counter64;
      description
        "Multi Bit Ecc Error on phase 0";
    }
    leaf counter_hbm_db2_hbm_error_counters0_multi_bit_ecc_error_cntr_pc0 {
      type oc-yang:counter64;
      description
        "Multi Bit Ecc Error on phase 0";
    }
    leaf counter_hbm_db2_hbm_error_counters1_multi_bit_ecc_error_cntr_pc0 {
      type oc-yang:counter64;
      description
        "Multi Bit Ecc Error on phase 0";
    }
    leaf counter_hbm_db2_hbm_error_counters2_multi_bit_ecc_error_cntr_pc0 {
      type oc-yang:counter64;
      description
        "Multi Bit Ecc Error on phase 0";
    }
    leaf counter_hbm_db2_hbm_error_counters3_multi_bit_ecc_error_cntr_pc0 {
      type oc-yang:counter64;
      description
        "Multi Bit Ecc Error on phase 0";
    }
    leaf counter_hbm_db2_hbm_error_counters4_multi_bit_ecc_error_cntr_pc0 {
      type oc-yang:counter64;
      description
        "Multi Bit Ecc Error on phase 0";
    }
    leaf counter_hbm_db2_hbm_error_counters5_multi_bit_ecc_error_cntr_pc0 {
      type oc-yang:counter64;
      description
        "Multi Bit Ecc Error on phase 0";
    }
    leaf counter_hbm_db2_hbm_error_counters6_multi_bit_ecc_error_cntr_pc0 {
      type oc-yang:counter64;
      description
        "Multi Bit Ecc Error on phase 0";
    }
    leaf counter_hbm_db2_hbm_error_counters7_multi_bit_ecc_error_cntr_pc0 {
      type oc-yang:counter64;
      description
        "Multi Bit Ecc Error on phase 0";
    }
    leaf counter_hbm_db3_hbm_error_counters0_multi_bit_ecc_error_cntr_pc0 {
      type oc-yang:counter64;
      description
        "Multi Bit Ecc Error on phase 0";
    }
    leaf counter_hbm_db3_hbm_error_counters1_multi_bit_ecc_error_cntr_pc0 {
      type oc-yang:counter64;
      description
        "Multi Bit Ecc Error on phase 0";
    }
    leaf counter_hbm_db3_hbm_error_counters2_multi_bit_ecc_error_cntr_pc0 {
      type oc-yang:counter64;
      description
        "Multi Bit Ecc Error on phase 0";
    }
    leaf counter_hbm_db3_hbm_error_counters3_multi_bit_ecc_error_cntr_pc0 {
      type oc-yang:counter64;
      description
        "Multi Bit Ecc Error on phase 0";
    }
    leaf counter_hbm_db3_hbm_error_counters4_multi_bit_ecc_error_cntr_pc0 {
      type oc-yang:counter64;
      description
        "Multi Bit Ecc Error on phase 0";
    }
    leaf counter_hbm_db3_hbm_error_counters5_multi_bit_ecc_error_cntr_pc0 {
      type oc-yang:counter64;
      description
        "Multi Bit Ecc Error on phase 0";
    }
    leaf counter_hbm_db3_hbm_error_counters6_multi_bit_ecc_error_cntr_pc0 {
      type oc-yang:counter64;
      description
        "Multi Bit Ecc Error on phase 0";
    }
    leaf counter_hbm_db3_hbm_error_counters7_multi_bit_ecc_error_cntr_pc0 {
      type oc-yang:counter64;
      description
        "Multi Bit Ecc Error on phase 0";
    }
    leaf counter_hbm_db0_hbm_error_counters0_multi_bit_ecc_error_cntr_pc1 {
      type oc-yang:counter64;
      description
        "Multi Bit Ecc Error on phase 1";
    }
    leaf counter_hbm_db0_hbm_error_counters1_multi_bit_ecc_error_cntr_pc1 {
      type oc-yang:counter64;
      description
        "Multi Bit Ecc Error on phase 1";
    }
    leaf counter_hbm_db0_hbm_error_counters2_multi_bit_ecc_error_cntr_pc1 {
      type oc-yang:counter64;
      description
        "Multi Bit Ecc Error on phase 1";
    }
    leaf counter_hbm_db0_hbm_error_counters3_multi_bit_ecc_error_cntr_pc1 {
      type oc-yang:counter64;
      description
        "Multi Bit Ecc Error on phase 1";
    }
    leaf counter_hbm_db0_hbm_error_counters4_multi_bit_ecc_error_cntr_pc1 {
      type oc-yang:counter64;
      description
        "Multi Bit Ecc Error on phase 1";
    }
    leaf counter_hbm_db0_hbm_error_counters5_multi_bit_ecc_error_cntr_pc1 {
      type oc-yang:counter64;
      description
        "Multi Bit Ecc Error on phase 1";
    }
    leaf counter_hbm_db0_hbm_error_counters6_multi_bit_ecc_error_cntr_pc1 {
      type oc-yang:counter64;
      description
        "Multi Bit Ecc Error on phase 1";
    }
    leaf counter_hbm_db0_hbm_error_counters7_multi_bit_ecc_error_cntr_pc1 {
      type oc-yang:counter64;
      description
        "Multi Bit Ecc Error on phase 1";
    }
    leaf counter_hbm_db1_hbm_error_counters0_multi_bit_ecc_error_cntr_pc1 {
      type oc-yang:counter64;
      description
        "Multi Bit Ecc Error on phase 1";
    }
    leaf counter_hbm_db1_hbm_error_counters1_multi_bit_ecc_error_cntr_pc1 {
      type oc-yang:counter64;
      description
        "Multi Bit Ecc Error on phase 1";
    }
    leaf counter_hbm_db1_hbm_error_counters2_multi_bit_ecc_error_cntr_pc1 {
      type oc-yang:counter64;
      description
        "Multi Bit Ecc Error on phase 1";
    }
    leaf counter_hbm_db1_hbm_error_counters3_multi_bit_ecc_error_cntr_pc1 {
      type oc-yang:counter64;
      description
        "Multi Bit Ecc Error on phase 1";
    }
    leaf counter_hbm_db1_hbm_error_counters4_multi_bit_ecc_error_cntr_pc1 {
      type oc-yang:counter64;
      description
        "Multi Bit Ecc Error on phase 1";
    }
    leaf counter_hbm_db1_hbm_error_counters5_multi_bit_ecc_error_cntr_pc1 {
      type oc-yang:counter64;
      description
        "Multi Bit Ecc Error on phase 1";
    }
    leaf counter_hbm_db1_hbm_error_counters6_multi_bit_ecc_error_cntr_pc1 {
      type oc-yang:counter64;
      description
        "Multi Bit Ecc Error on phase 1";
    }
    leaf counter_hbm_db1_hbm_error_counters7_multi_bit_ecc_error_cntr_pc1 {
      type oc-yang:counter64;
      description
        "Multi Bit Ecc Error on phase 1";
    }
    leaf counter_hbm_db2_hbm_error_counters0_multi_bit_ecc_error_cntr_pc1 {
      type oc-yang:counter64;
      description
        "Multi Bit Ecc Error on phase 1";
    }
    leaf counter_hbm_db2_hbm_error_counters1_multi_bit_ecc_error_cntr_pc1 {
      type oc-yang:counter64;
      description
        "Multi Bit Ecc Error on phase 1";
    }
    leaf counter_hbm_db2_hbm_error_counters2_multi_bit_ecc_error_cntr_pc1 {
      type oc-yang:counter64;
      description
        "Multi Bit Ecc Error on phase 1";
    }
    leaf counter_hbm_db2_hbm_error_counters3_multi_bit_ecc_error_cntr_pc1 {
      type oc-yang:counter64;
      description
        "Multi Bit Ecc Error on phase 1";
    }
    leaf counter_hbm_db2_hbm_error_counters4_multi_bit_ecc_error_cntr_pc1 {
      type oc-yang:counter64;
      description
        "Multi Bit Ecc Error on phase 1";
    }
    leaf counter_hbm_db2_hbm_error_counters5_multi_bit_ecc_error_cntr_pc1 {
      type oc-yang:counter64;
      description
        "Multi Bit Ecc Error on phase 1";
    }
    leaf counter_hbm_db2_hbm_error_counters6_multi_bit_ecc_error_cntr_pc1 {
      type oc-yang:counter64;
      description
        "Multi Bit Ecc Error on phase 1";
    }
    leaf counter_hbm_db2_hbm_error_counters7_multi_bit_ecc_error_cntr_pc1 {
      type oc-yang:counter64;
      description
        "Multi Bit Ecc Error on phase 1";
    }
    leaf counter_hbm_db3_hbm_error_counters0_multi_bit_ecc_error_cntr_pc1 {
      type oc-yang:counter64;
      description
        "Multi Bit Ecc Error on phase 1";
    }
    leaf counter_hbm_db3_hbm_error_counters1_multi_bit_ecc_error_cntr_pc1 {
      type oc-yang:counter64;
      description
        "Multi Bit Ecc Error on phase 1";
    }
    leaf counter_hbm_db3_hbm_error_counters2_multi_bit_ecc_error_cntr_pc1 {
      type oc-yang:counter64;
      description
        "Multi Bit Ecc Error on phase 1";
    }
    leaf counter_hbm_db3_hbm_error_counters3_multi_bit_ecc_error_cntr_pc1 {
      type oc-yang:counter64;
      description
        "Multi Bit Ecc Error on phase 1";
    }
    leaf counter_hbm_db3_hbm_error_counters4_multi_bit_ecc_error_cntr_pc1 {
      type oc-yang:counter64;
      description
        "Multi Bit Ecc Error on phase 1";
    }
    leaf counter_hbm_db3_hbm_error_counters5_multi_bit_ecc_error_cntr_pc1 {
      type oc-yang:counter64;
      description
        "Multi Bit Ecc Error on phase 1";
    }
    leaf counter_hbm_db3_hbm_error_counters6_multi_bit_ecc_error_cntr_pc1 {
      type oc-yang:counter64;
      description
        "Multi Bit Ecc Error on phase 1";
    }
    leaf counter_hbm_db3_hbm_error_counters7_multi_bit_ecc_error_cntr_pc1 {
      type oc-yang:counter64;
      description
        "Multi Bit Ecc Error on phase 1";
    }
    leaf counter_hbm_db0_hbm_error_counters0_rd_data_parity_error_cntr_pc0 {
      type oc-yang:counter64;
      description
        "Counter of read data parity errors on PC0";
    }
    leaf counter_hbm_db0_hbm_error_counters1_rd_data_parity_error_cntr_pc0 {
      type oc-yang:counter64;
      description
        "Counter of read data parity errors on PC0";
    }
    leaf counter_hbm_db0_hbm_error_counters2_rd_data_parity_error_cntr_pc0 {
      type oc-yang:counter64;
      description
        "Counter of read data parity errors on PC0";
    }
    leaf counter_hbm_db0_hbm_error_counters3_rd_data_parity_error_cntr_pc0 {
      type oc-yang:counter64;
      description
        "Counter of read data parity errors on PC0";
    }
    leaf counter_hbm_db0_hbm_error_counters4_rd_data_parity_error_cntr_pc0 {
      type oc-yang:counter64;
      description
        "Counter of read data parity errors on PC0";
    }
    leaf counter_hbm_db0_hbm_error_counters5_rd_data_parity_error_cntr_pc0 {
      type oc-yang:counter64;
      description
        "Counter of read data parity errors on PC0";
    }
    leaf counter_hbm_db0_hbm_error_counters6_rd_data_parity_error_cntr_pc0 {
      type oc-yang:counter64;
      description
        "Counter of read data parity errors on PC0";
    }
    leaf counter_hbm_db0_hbm_error_counters7_rd_data_parity_error_cntr_pc0 {
      type oc-yang:counter64;
      description
        "Counter of read data parity errors on PC0";
    }
    leaf counter_hbm_db1_hbm_error_counters0_rd_data_parity_error_cntr_pc0 {
      type oc-yang:counter64;
      description
        "Counter of read data parity errors on PC0";
    }
    leaf counter_hbm_db1_hbm_error_counters1_rd_data_parity_error_cntr_pc0 {
      type oc-yang:counter64;
      description
        "Counter of read data parity errors on PC0";
    }
    leaf counter_hbm_db1_hbm_error_counters2_rd_data_parity_error_cntr_pc0 {
      type oc-yang:counter64;
      description
        "Counter of read data parity errors on PC0";
    }
    leaf counter_hbm_db1_hbm_error_counters3_rd_data_parity_error_cntr_pc0 {
      type oc-yang:counter64;
      description
        "Counter of read data parity errors on PC0";
    }
    leaf counter_hbm_db1_hbm_error_counters4_rd_data_parity_error_cntr_pc0 {
      type oc-yang:counter64;
      description
        "Counter of read data parity errors on PC0";
    }
    leaf counter_hbm_db1_hbm_error_counters5_rd_data_parity_error_cntr_pc0 {
      type oc-yang:counter64;
      description
        "Counter of read data parity errors on PC0";
    }
    leaf counter_hbm_db1_hbm_error_counters6_rd_data_parity_error_cntr_pc0 {
      type oc-yang:counter64;
      description
        "Counter of read data parity errors on PC0";
    }
    leaf counter_hbm_db1_hbm_error_counters7_rd_data_parity_error_cntr_pc0 {
      type oc-yang:counter64;
      description
        "Counter of read data parity errors on PC0";
    }
    leaf counter_hbm_db2_hbm_error_counters0_rd_data_parity_error_cntr_pc0 {
      type oc-yang:counter64;
      description
        "Counter of read data parity errors on PC0";
    }
    leaf counter_hbm_db2_hbm_error_counters1_rd_data_parity_error_cntr_pc0 {
      type oc-yang:counter64;
      description
        "Counter of read data parity errors on PC0";
    }
    leaf counter_hbm_db2_hbm_error_counters2_rd_data_parity_error_cntr_pc0 {
      type oc-yang:counter64;
      description
        "Counter of read data parity errors on PC0";
    }
    leaf counter_hbm_db2_hbm_error_counters3_rd_data_parity_error_cntr_pc0 {
      type oc-yang:counter64;
      description
        "Counter of read data parity errors on PC0";
    }
    leaf counter_hbm_db2_hbm_error_counters4_rd_data_parity_error_cntr_pc0 {
      type oc-yang:counter64;
      description
        "Counter of read data parity errors on PC0";
    }
    leaf counter_hbm_db2_hbm_error_counters5_rd_data_parity_error_cntr_pc0 {
      type oc-yang:counter64;
      description
        "Counter of read data parity errors on PC0";
    }
    leaf counter_hbm_db2_hbm_error_counters6_rd_data_parity_error_cntr_pc0 {
      type oc-yang:counter64;
      description
        "Counter of read data parity errors on PC0";
    }
    leaf counter_hbm_db2_hbm_error_counters7_rd_data_parity_error_cntr_pc0 {
      type oc-yang:counter64;
      description
        "Counter of read data parity errors on PC0";
    }
    leaf counter_hbm_db3_hbm_error_counters0_rd_data_parity_error_cntr_pc0 {
      type oc-yang:counter64;
      description
        "Counter of read data parity errors on PC0";
    }
    leaf counter_hbm_db3_hbm_error_counters1_rd_data_parity_error_cntr_pc0 {
      type oc-yang:counter64;
      description
        "Counter of read data parity errors on PC0";
    }
    leaf counter_hbm_db3_hbm_error_counters2_rd_data_parity_error_cntr_pc0 {
      type oc-yang:counter64;
      description
        "Counter of read data parity errors on PC0";
    }
    leaf counter_hbm_db3_hbm_error_counters3_rd_data_parity_error_cntr_pc0 {
      type oc-yang:counter64;
      description
        "Counter of read data parity errors on PC0";
    }
    leaf counter_hbm_db3_hbm_error_counters4_rd_data_parity_error_cntr_pc0 {
      type oc-yang:counter64;
      description
        "Counter of read data parity errors on PC0";
    }
    leaf counter_hbm_db3_hbm_error_counters5_rd_data_parity_error_cntr_pc0 {
      type oc-yang:counter64;
      description
        "Counter of read data parity errors on PC0";
    }
    leaf counter_hbm_db3_hbm_error_counters6_rd_data_parity_error_cntr_pc0 {
      type oc-yang:counter64;
      description
        "Counter of read data parity errors on PC0";
    }
    leaf counter_hbm_db3_hbm_error_counters7_rd_data_parity_error_cntr_pc0 {
      type oc-yang:counter64;
      description
        "Counter of read data parity errors on PC0";
    }
    leaf counter_hbm_db0_hbm_error_counters0_rd_data_parity_error_cntr_pc1 {
      type oc-yang:counter64;
      description
        "Counter of read data parity errors on PC1";
    }
    leaf counter_hbm_db0_hbm_error_counters1_rd_data_parity_error_cntr_pc1 {
      type oc-yang:counter64;
      description
        "Counter of read data parity errors on PC1";
    }
    leaf counter_hbm_db0_hbm_error_counters2_rd_data_parity_error_cntr_pc1 {
      type oc-yang:counter64;
      description
        "Counter of read data parity errors on PC1";
    }
    leaf counter_hbm_db0_hbm_error_counters3_rd_data_parity_error_cntr_pc1 {
      type oc-yang:counter64;
      description
        "Counter of read data parity errors on PC1";
    }
    leaf counter_hbm_db0_hbm_error_counters4_rd_data_parity_error_cntr_pc1 {
      type oc-yang:counter64;
      description
        "Counter of read data parity errors on PC1";
    }
    leaf counter_hbm_db0_hbm_error_counters5_rd_data_parity_error_cntr_pc1 {
      type oc-yang:counter64;
      description
        "Counter of read data parity errors on PC1";
    }
    leaf counter_hbm_db0_hbm_error_counters6_rd_data_parity_error_cntr_pc1 {
      type oc-yang:counter64;
      description
        "Counter of read data parity errors on PC1";
    }
    leaf counter_hbm_db0_hbm_error_counters7_rd_data_parity_error_cntr_pc1 {
      type oc-yang:counter64;
      description
        "Counter of read data parity errors on PC1";
    }
    leaf counter_hbm_db1_hbm_error_counters0_rd_data_parity_error_cntr_pc1 {
      type oc-yang:counter64;
      description
        "Counter of read data parity errors on PC1";
    }
    leaf counter_hbm_db1_hbm_error_counters1_rd_data_parity_error_cntr_pc1 {
      type oc-yang:counter64;
      description
        "Counter of read data parity errors on PC1";
    }
    leaf counter_hbm_db1_hbm_error_counters2_rd_data_parity_error_cntr_pc1 {
      type oc-yang:counter64;
      description
        "Counter of read data parity errors on PC1";
    }
    leaf counter_hbm_db1_hbm_error_counters3_rd_data_parity_error_cntr_pc1 {
      type oc-yang:counter64;
      description
        "Counter of read data parity errors on PC1";
    }
    leaf counter_hbm_db1_hbm_error_counters4_rd_data_parity_error_cntr_pc1 {
      type oc-yang:counter64;
      description
        "Counter of read data parity errors on PC1";
    }
    leaf counter_hbm_db1_hbm_error_counters5_rd_data_parity_error_cntr_pc1 {
      type oc-yang:counter64;
      description
        "Counter of read data parity errors on PC1";
    }
    leaf counter_hbm_db1_hbm_error_counters6_rd_data_parity_error_cntr_pc1 {
      type oc-yang:counter64;
      description
        "Counter of read data parity errors on PC1";
    }
    leaf counter_hbm_db1_hbm_error_counters7_rd_data_parity_error_cntr_pc1 {
      type oc-yang:counter64;
      description
        "Counter of read data parity errors on PC1";
    }
    leaf counter_hbm_db2_hbm_error_counters0_rd_data_parity_error_cntr_pc1 {
      type oc-yang:counter64;
      description
        "Counter of read data parity errors on PC1";
    }
    leaf counter_hbm_db2_hbm_error_counters1_rd_data_parity_error_cntr_pc1 {
      type oc-yang:counter64;
      description
        "Counter of read data parity errors on PC1";
    }
    leaf counter_hbm_db2_hbm_error_counters2_rd_data_parity_error_cntr_pc1 {
      type oc-yang:counter64;
      description
        "Counter of read data parity errors on PC1";
    }
    leaf counter_hbm_db2_hbm_error_counters3_rd_data_parity_error_cntr_pc1 {
      type oc-yang:counter64;
      description
        "Counter of read data parity errors on PC1";
    }
    leaf counter_hbm_db2_hbm_error_counters4_rd_data_parity_error_cntr_pc1 {
      type oc-yang:counter64;
      description
        "Counter of read data parity errors on PC1";
    }
    leaf counter_hbm_db2_hbm_error_counters5_rd_data_parity_error_cntr_pc1 {
      type oc-yang:counter64;
      description
        "Counter of read data parity errors on PC1";
    }
    leaf counter_hbm_db2_hbm_error_counters6_rd_data_parity_error_cntr_pc1 {
      type oc-yang:counter64;
      description
        "Counter of read data parity errors on PC1";
    }
    leaf counter_hbm_db2_hbm_error_counters7_rd_data_parity_error_cntr_pc1 {
      type oc-yang:counter64;
      description
        "Counter of read data parity errors on PC1";
    }
    leaf counter_hbm_db3_hbm_error_counters0_rd_data_parity_error_cntr_pc1 {
      type oc-yang:counter64;
      description
        "Counter of read data parity errors on PC1";
    }
    leaf counter_hbm_db3_hbm_error_counters1_rd_data_parity_error_cntr_pc1 {
      type oc-yang:counter64;
      description
        "Counter of read data parity errors on PC1";
    }
    leaf counter_hbm_db3_hbm_error_counters2_rd_data_parity_error_cntr_pc1 {
      type oc-yang:counter64;
      description
        "Counter of read data parity errors on PC1";
    }
    leaf counter_hbm_db3_hbm_error_counters3_rd_data_parity_error_cntr_pc1 {
      type oc-yang:counter64;
      description
        "Counter of read data parity errors on PC1";
    }
    leaf counter_hbm_db3_hbm_error_counters4_rd_data_parity_error_cntr_pc1 {
      type oc-yang:counter64;
      description
        "Counter of read data parity errors on PC1";
    }
    leaf counter_hbm_db3_hbm_error_counters5_rd_data_parity_error_cntr_pc1 {
      type oc-yang:counter64;
      description
        "Counter of read data parity errors on PC1";
    }
    leaf counter_hbm_db3_hbm_error_counters6_rd_data_parity_error_cntr_pc1 {
      type oc-yang:counter64;
      description
        "Counter of read data parity errors on PC1";
    }
    leaf counter_hbm_db3_hbm_error_counters7_rd_data_parity_error_cntr_pc1 {
      type oc-yang:counter64;
      description
        "Counter of read data parity errors on PC1";
    }
    leaf counter_hbm_chnl0_hbm_read_error_counters0_missed_read_counter {
      type oc-yang:counter64;
      description
        "Counter of times that did not get read data from HBM when expecting it";
    }
    leaf counter_hbm_chnl0_hbm_read_error_counters1_missed_read_counter {
      type oc-yang:counter64;
      description
        "Counter of times that did not get read data from HBM when expecting it";
    }
    leaf counter_hbm_chnl1_hbm_read_error_counters0_missed_read_counter {
      type oc-yang:counter64;
      description
        "Counter of times that did not get read data from HBM when expecting it";
    }
    leaf counter_hbm_chnl1_hbm_read_error_counters1_missed_read_counter {
      type oc-yang:counter64;
      description
        "Counter of times that did not get read data from HBM when expecting it";
    }
    leaf counter_hbm_chnl2_hbm_read_error_counters0_missed_read_counter {
      type oc-yang:counter64;
      description
        "Counter of times that did not get read data from HBM when expecting it";
    }
    leaf counter_hbm_chnl2_hbm_read_error_counters1_missed_read_counter {
      type oc-yang:counter64;
      description
        "Counter of times that did not get read data from HBM when expecting it";
    }
    leaf counter_hbm_chnl3_hbm_read_error_counters0_missed_read_counter {
      type oc-yang:counter64;
      description
        "Counter of times that did not get read data from HBM when expecting it";
    }
    leaf counter_hbm_chnl3_hbm_read_error_counters1_missed_read_counter {
      type oc-yang:counter64;
      description
        "Counter of times that did not get read data from HBM when expecting it";
    }
    leaf counter_hbm_chnl4_hbm_read_error_counters0_missed_read_counter {
      type oc-yang:counter64;
      description
        "Counter of times that did not get read data from HBM when expecting it";
    }
    leaf counter_hbm_chnl4_hbm_read_error_counters1_missed_read_counter {
      type oc-yang:counter64;
      description
        "Counter of times that did not get read data from HBM when expecting it";
    }
    leaf counter_hbm_chnl5_hbm_read_error_counters0_missed_read_counter {
      type oc-yang:counter64;
      description
        "Counter of times that did not get read data from HBM when expecting it";
    }
    leaf counter_hbm_chnl5_hbm_read_error_counters1_missed_read_counter {
      type oc-yang:counter64;
      description
        "Counter of times that did not get read data from HBM when expecting it";
    }
    leaf counter_hbm_chnl6_hbm_read_error_counters0_missed_read_counter {
      type oc-yang:counter64;
      description
        "Counter of times that did not get read data from HBM when expecting it";
    }
    leaf counter_hbm_chnl6_hbm_read_error_counters1_missed_read_counter {
      type oc-yang:counter64;
      description
        "Counter of times that did not get read data from HBM when expecting it";
    }
    leaf counter_hbm_chnl7_hbm_read_error_counters0_missed_read_counter {
      type oc-yang:counter64;
      description
        "Counter of times that did not get read data from HBM when expecting it";
    }
    leaf counter_hbm_chnl7_hbm_read_error_counters1_missed_read_counter {
      type oc-yang:counter64;
      description
        "Counter of times that did not get read data from HBM when expecting it";
    }
    leaf counter_hbm_chnl8_hbm_read_error_counters0_missed_read_counter {
      type oc-yang:counter64;
      description
        "Counter of times that did not get read data from HBM when expecting it";
    }
    leaf counter_hbm_chnl8_hbm_read_error_counters1_missed_read_counter {
      type oc-yang:counter64;
      description
        "Counter of times that did not get read data from HBM when expecting it";
    }
    leaf counter_hbm_chnl9_hbm_read_error_counters0_missed_read_counter {
      type oc-yang:counter64;
      description
        "Counter of times that did not get read data from HBM when expecting it";
    }
    leaf counter_hbm_chnl9_hbm_read_error_counters1_missed_read_counter {
      type oc-yang:counter64;
      description
        "Counter of times that did not get read data from HBM when expecting it";
    }
    leaf counter_hbm_chnl10_hbm_read_error_counters0_missed_read_counter {
      type oc-yang:counter64;
      description
        "Counter of times that did not get read data from HBM when expecting it";
    }
    leaf counter_hbm_chnl10_hbm_read_error_counters1_missed_read_counter {
      type oc-yang:counter64;
      description
        "Counter of times that did not get read data from HBM when expecting it";
    }
    leaf counter_hbm_chnl11_hbm_read_error_counters0_missed_read_counter {
      type oc-yang:counter64;
      description
        "Counter of times that did not get read data from HBM when expecting it";
    }
    leaf counter_hbm_chnl11_hbm_read_error_counters1_missed_read_counter {
      type oc-yang:counter64;
      description
        "Counter of times that did not get read data from HBM when expecting it";
    }
    leaf counter_hbm_chnl12_hbm_read_error_counters0_missed_read_counter {
      type oc-yang:counter64;
      description
        "Counter of times that did not get read data from HBM when expecting it";
    }
    leaf counter_hbm_chnl12_hbm_read_error_counters1_missed_read_counter {
      type oc-yang:counter64;
      description
        "Counter of times that did not get read data from HBM when expecting it";
    }
    leaf counter_hbm_chnl13_hbm_read_error_counters0_missed_read_counter {
      type oc-yang:counter64;
      description
        "Counter of times that did not get read data from HBM when expecting it";
    }
    leaf counter_hbm_chnl13_hbm_read_error_counters1_missed_read_counter {
      type oc-yang:counter64;
      description
        "Counter of times that did not get read data from HBM when expecting it";
    }
    leaf counter_hbm_chnl14_hbm_read_error_counters0_missed_read_counter {
      type oc-yang:counter64;
      description
        "Counter of times that did not get read data from HBM when expecting it";
    }
    leaf counter_hbm_chnl14_hbm_read_error_counters1_missed_read_counter {
      type oc-yang:counter64;
      description
        "Counter of times that did not get read data from HBM when expecting it";
    }
    leaf counter_hbm_chnl15_hbm_read_error_counters0_missed_read_counter {
      type oc-yang:counter64;
      description
        "Counter of times that did not get read data from HBM when expecting it";
    }
    leaf counter_hbm_chnl15_hbm_read_error_counters1_missed_read_counter {
      type oc-yang:counter64;
      description
        "Counter of times that did not get read data from HBM when expecting it";
    }
    leaf counter_hbm_chnl0_hbm_read_error_counters0_unexpected_read_counter {
      type oc-yang:counter64;
      description
        "Counter of times that got read data when not expecting it";
    }
    leaf counter_hbm_chnl0_hbm_read_error_counters1_unexpected_read_counter {
      type oc-yang:counter64;
      description
        "Counter of times that got read data when not expecting it";
    }
    leaf counter_hbm_chnl1_hbm_read_error_counters0_unexpected_read_counter {
      type oc-yang:counter64;
      description
        "Counter of times that got read data when not expecting it";
    }
    leaf counter_hbm_chnl1_hbm_read_error_counters1_unexpected_read_counter {
      type oc-yang:counter64;
      description
        "Counter of times that got read data when not expecting it";
    }
    leaf counter_hbm_chnl2_hbm_read_error_counters0_unexpected_read_counter {
      type oc-yang:counter64;
      description
        "Counter of times that got read data when not expecting it";
    }
    leaf counter_hbm_chnl2_hbm_read_error_counters1_unexpected_read_counter {
      type oc-yang:counter64;
      description
        "Counter of times that got read data when not expecting it";
    }
    leaf counter_hbm_chnl3_hbm_read_error_counters0_unexpected_read_counter {
      type oc-yang:counter64;
      description
        "Counter of times that got read data when not expecting it";
    }
    leaf counter_hbm_chnl3_hbm_read_error_counters1_unexpected_read_counter {
      type oc-yang:counter64;
      description
        "Counter of times that got read data when not expecting it";
    }
    leaf counter_hbm_chnl4_hbm_read_error_counters0_unexpected_read_counter {
      type oc-yang:counter64;
      description
        "Counter of times that got read data when not expecting it";
    }
    leaf counter_hbm_chnl4_hbm_read_error_counters1_unexpected_read_counter {
      type oc-yang:counter64;
      description
        "Counter of times that got read data when not expecting it";
    }
    leaf counter_hbm_chnl5_hbm_read_error_counters0_unexpected_read_counter {
      type oc-yang:counter64;
      description
        "Counter of times that got read data when not expecting it";
    }
    leaf counter_hbm_chnl5_hbm_read_error_counters1_unexpected_read_counter {
      type oc-yang:counter64;
      description
        "Counter of times that got read data when not expecting it";
    }
    leaf counter_hbm_chnl6_hbm_read_error_counters0_unexpected_read_counter {
      type oc-yang:counter64;
      description
        "Counter of times that got read data when not expecting it";
    }
    leaf counter_hbm_chnl6_hbm_read_error_counters1_unexpected_read_counter {
      type oc-yang:counter64;
      description
        "Counter of times that got read data when not expecting it";
    }
    leaf counter_hbm_chnl7_hbm_read_error_counters0_unexpected_read_counter {
      type oc-yang:counter64;
      description
        "Counter of times that got read data when not expecting it";
    }
    leaf counter_hbm_chnl7_hbm_read_error_counters1_unexpected_read_counter {
      type oc-yang:counter64;
      description
        "Counter of times that got read data when not expecting it";
    }
    leaf counter_hbm_chnl8_hbm_read_error_counters0_unexpected_read_counter {
      type oc-yang:counter64;
      description
        "Counter of times that got read data when not expecting it";
    }
    leaf counter_hbm_chnl8_hbm_read_error_counters1_unexpected_read_counter {
      type oc-yang:counter64;
      description
        "Counter of times that got read data when not expecting it";
    }
    leaf counter_hbm_chnl9_hbm_read_error_counters0_unexpected_read_counter {
      type oc-yang:counter64;
      description
        "Counter of times that got read data when not expecting it";
    }
    leaf counter_hbm_chnl9_hbm_read_error_counters1_unexpected_read_counter {
      type oc-yang:counter64;
      description
        "Counter of times that got read data when not expecting it";
    }
    leaf counter_hbm_chnl10_hbm_read_error_counters0_unexpected_read_counter {
      type oc-yang:counter64;
      description
        "Counter of times that got read data when not expecting it";
    }
    leaf counter_hbm_chnl10_hbm_read_error_counters1_unexpected_read_counter {
      type oc-yang:counter64;
      description
        "Counter of times that got read data when not expecting it";
    }
    leaf counter_hbm_chnl11_hbm_read_error_counters0_unexpected_read_counter {
      type oc-yang:counter64;
      description
        "Counter of times that got read data when not expecting it";
    }
    leaf counter_hbm_chnl11_hbm_read_error_counters1_unexpected_read_counter {
      type oc-yang:counter64;
      description
        "Counter of times that got read data when not expecting it";
    }
    leaf counter_hbm_chnl12_hbm_read_error_counters0_unexpected_read_counter {
      type oc-yang:counter64;
      description
        "Counter of times that got read data when not expecting it";
    }
    leaf counter_hbm_chnl12_hbm_read_error_counters1_unexpected_read_counter {
      type oc-yang:counter64;
      description
        "Counter of times that got read data when not expecting it";
    }
    leaf counter_hbm_chnl13_hbm_read_error_counters0_unexpected_read_counter {
      type oc-yang:counter64;
      description
        "Counter of times that got read data when not expecting it";
    }
    leaf counter_hbm_chnl13_hbm_read_error_counters1_unexpected_read_counter {
      type oc-yang:counter64;
      description
        "Counter of times that got read data when not expecting it";
    }
    leaf counter_hbm_chnl14_hbm_read_error_counters0_unexpected_read_counter {
      type oc-yang:counter64;
      description
        "Counter of times that got read data when not expecting it";
    }
    leaf counter_hbm_chnl14_hbm_read_error_counters1_unexpected_read_counter {
      type oc-yang:counter64;
      description
        "Counter of times that got read data when not expecting it";
    }
    leaf counter_hbm_chnl15_hbm_read_error_counters0_unexpected_read_counter {
      type oc-yang:counter64;
      description
        "Counter of times that got read data when not expecting it";
    }
    leaf counter_hbm_chnl15_hbm_read_error_counters1_unexpected_read_counter {
      type oc-yang:counter64;
      description
        "Counter of times that got read data when not expecting it";
    }
    leaf counter_slice0_ifg_ifgbi_inbe_err_pkt_cnt_inbe_nph_err_pkt_cnt {
      type oc-yang:counter64;
      description
        "Bad Packet Count for inbe NPU Host";
    }
    leaf counter_slice1_ifg_ifgbi_inbe_err_pkt_cnt_inbe_nph_err_pkt_cnt {
      type oc-yang:counter64;
      description
        "Bad Packet Count for inbe NPU Host";
    }
    leaf counter_slice2_ifg_ifgbi_inbe_err_pkt_cnt_inbe_nph_err_pkt_cnt {
      type oc-yang:counter64;
      description
        "Bad Packet Count for inbe NPU Host";
    }
    leaf counter_slice3_ifg_ifgbi_inbe_err_pkt_cnt_inbe_nph_err_pkt_cnt {
      type oc-yang:counter64;
      description
        "Bad Packet Count for inbe NPU Host";
    }
    leaf counter_slice4_ifg_ifgbi_inbe_err_pkt_cnt_inbe_nph_err_pkt_cnt {
      type oc-yang:counter64;
      description
        "Bad Packet Count for inbe NPU Host";
    }
    leaf counter_slice5_ifg_ifgbi_inbe_err_pkt_cnt_inbe_nph_err_pkt_cnt {
      type oc-yang:counter64;
      description
        "Bad Packet Count for inbe NPU Host";
    }
    leaf counter_slice6_ifg_ifgbi_inbe_err_pkt_cnt_inbe_nph_err_pkt_cnt {
      type oc-yang:counter64;
      description
        "Bad Packet Count for inbe NPU Host";
    }
    leaf counter_slice7_ifg_ifgbi_inbe_err_pkt_cnt_inbe_nph_err_pkt_cnt {
      type oc-yang:counter64;
      description
        "Bad Packet Count for inbe NPU Host";
    }
    leaf counter_slice8_ifg_ifgbi_inbe_err_pkt_cnt_inbe_nph_err_pkt_cnt {
      type oc-yang:counter64;
      description
        "Bad Packet Count for inbe NPU Host";
    }
    leaf counter_slice9_ifg_ifgbi_inbe_err_pkt_cnt_inbe_nph_err_pkt_cnt {
      type oc-yang:counter64;
      description
        "Bad Packet Count for inbe NPU Host";
    }
    leaf counter_slice10_ifg_ifgbi_inbe_err_pkt_cnt_inbe_nph_err_pkt_cnt {
      type oc-yang:counter64;
      description
        "Bad Packet Count for inbe NPU Host";
    }
    leaf counter_slice11_ifg_ifgbi_inbe_err_pkt_cnt_inbe_nph_err_pkt_cnt {
      type oc-yang:counter64;
      description
        "Bad Packet Count for inbe NPU Host";
    }
    leaf counter_slice12_ifg_ifgbi_inbe_err_pkt_cnt_inbe_nph_err_pkt_cnt {
      type oc-yang:counter64;
      description
        "Bad Packet Count for inbe NPU Host";
    }
    leaf counter_slice13_ifg_ifgbi_inbe_err_pkt_cnt_inbe_nph_err_pkt_cnt {
      type oc-yang:counter64;
      description
        "Bad Packet Count for inbe NPU Host";
    }
    leaf counter_slice14_ifg_ifgbi_inbe_err_pkt_cnt_inbe_nph_err_pkt_cnt {
      type oc-yang:counter64;
      description
        "Bad Packet Count for inbe NPU Host";
    }
    leaf counter_slice15_ifg_ifgbi_inbe_err_pkt_cnt_inbe_nph_err_pkt_cnt {
      type oc-yang:counter64;
      description
        "Bad Packet Count for inbe NPU Host";
    }
    leaf counter_slice0_ifg_ifgbi_inbe_err_pkt_cnt_inbe_pdm_err_pkt_cnt {
      type oc-yang:counter64;
      description
        "Bad Packet Count for inbe packet DMA";
    }
    leaf counter_slice1_ifg_ifgbi_inbe_err_pkt_cnt_inbe_pdm_err_pkt_cnt {
      type oc-yang:counter64;
      description
        "Bad Packet Count for inbe packet DMA";
    }
    leaf counter_slice2_ifg_ifgbi_inbe_err_pkt_cnt_inbe_pdm_err_pkt_cnt {
      type oc-yang:counter64;
      description
        "Bad Packet Count for inbe packet DMA";
    }
    leaf counter_slice3_ifg_ifgbi_inbe_err_pkt_cnt_inbe_pdm_err_pkt_cnt {
      type oc-yang:counter64;
      description
        "Bad Packet Count for inbe packet DMA";
    }
    leaf counter_slice4_ifg_ifgbi_inbe_err_pkt_cnt_inbe_pdm_err_pkt_cnt {
      type oc-yang:counter64;
      description
        "Bad Packet Count for inbe packet DMA";
    }
    leaf counter_slice5_ifg_ifgbi_inbe_err_pkt_cnt_inbe_pdm_err_pkt_cnt {
      type oc-yang:counter64;
      description
        "Bad Packet Count for inbe packet DMA";
    }
    leaf counter_slice6_ifg_ifgbi_inbe_err_pkt_cnt_inbe_pdm_err_pkt_cnt {
      type oc-yang:counter64;
      description
        "Bad Packet Count for inbe packet DMA";
    }
    leaf counter_slice7_ifg_ifgbi_inbe_err_pkt_cnt_inbe_pdm_err_pkt_cnt {
      type oc-yang:counter64;
      description
        "Bad Packet Count for inbe packet DMA";
    }
    leaf counter_slice8_ifg_ifgbi_inbe_err_pkt_cnt_inbe_pdm_err_pkt_cnt {
      type oc-yang:counter64;
      description
        "Bad Packet Count for inbe packet DMA";
    }
    leaf counter_slice9_ifg_ifgbi_inbe_err_pkt_cnt_inbe_pdm_err_pkt_cnt {
      type oc-yang:counter64;
      description
        "Bad Packet Count for inbe packet DMA";
    }
    leaf counter_slice10_ifg_ifgbi_inbe_err_pkt_cnt_inbe_pdm_err_pkt_cnt {
      type oc-yang:counter64;
      description
        "Bad Packet Count for inbe packet DMA";
    }
    leaf counter_slice11_ifg_ifgbi_inbe_err_pkt_cnt_inbe_pdm_err_pkt_cnt {
      type oc-yang:counter64;
      description
        "Bad Packet Count for inbe packet DMA";
    }
    leaf counter_slice12_ifg_ifgbi_inbe_err_pkt_cnt_inbe_pdm_err_pkt_cnt {
      type oc-yang:counter64;
      description
        "Bad Packet Count for inbe packet DMA";
    }
    leaf counter_slice13_ifg_ifgbi_inbe_err_pkt_cnt_inbe_pdm_err_pkt_cnt {
      type oc-yang:counter64;
      description
        "Bad Packet Count for inbe packet DMA";
    }
    leaf counter_slice14_ifg_ifgbi_inbe_err_pkt_cnt_inbe_pdm_err_pkt_cnt {
      type oc-yang:counter64;
      description
        "Bad Packet Count for inbe packet DMA";
    }
    leaf counter_slice15_ifg_ifgbi_inbe_err_pkt_cnt_inbe_pdm_err_pkt_cnt {
      type oc-yang:counter64;
      description
        "Bad Packet Count for inbe packet DMA";
    }
    leaf counter_slice0_ifg_ifgbi_inbi_err_pkt_cnt_inbi_nph_err_pkt_cnt {
      type oc-yang:counter64;
      description
        "Bad NPU Host packet injected by CSS";
    }
    leaf counter_slice1_ifg_ifgbi_inbi_err_pkt_cnt_inbi_nph_err_pkt_cnt {
      type oc-yang:counter64;
      description
        "Bad NPU Host packet injected by CSS";
    }
    leaf counter_slice2_ifg_ifgbi_inbi_err_pkt_cnt_inbi_nph_err_pkt_cnt {
      type oc-yang:counter64;
      description
        "Bad NPU Host packet injected by CSS";
    }
    leaf counter_slice3_ifg_ifgbi_inbi_err_pkt_cnt_inbi_nph_err_pkt_cnt {
      type oc-yang:counter64;
      description
        "Bad NPU Host packet injected by CSS";
    }
    leaf counter_slice4_ifg_ifgbi_inbi_err_pkt_cnt_inbi_nph_err_pkt_cnt {
      type oc-yang:counter64;
      description
        "Bad NPU Host packet injected by CSS";
    }
    leaf counter_slice5_ifg_ifgbi_inbi_err_pkt_cnt_inbi_nph_err_pkt_cnt {
      type oc-yang:counter64;
      description
        "Bad NPU Host packet injected by CSS";
    }
    leaf counter_slice6_ifg_ifgbi_inbi_err_pkt_cnt_inbi_nph_err_pkt_cnt {
      type oc-yang:counter64;
      description
        "Bad NPU Host packet injected by CSS";
    }
    leaf counter_slice7_ifg_ifgbi_inbi_err_pkt_cnt_inbi_nph_err_pkt_cnt {
      type oc-yang:counter64;
      description
        "Bad NPU Host packet injected by CSS";
    }
    leaf counter_slice8_ifg_ifgbi_inbi_err_pkt_cnt_inbi_nph_err_pkt_cnt {
      type oc-yang:counter64;
      description
        "Bad NPU Host packet injected by CSS";
    }
    leaf counter_slice9_ifg_ifgbi_inbi_err_pkt_cnt_inbi_nph_err_pkt_cnt {
      type oc-yang:counter64;
      description
        "Bad NPU Host packet injected by CSS";
    }
    leaf counter_slice10_ifg_ifgbi_inbi_err_pkt_cnt_inbi_nph_err_pkt_cnt {
      type oc-yang:counter64;
      description
        "Bad NPU Host packet injected by CSS";
    }
    leaf counter_slice11_ifg_ifgbi_inbi_err_pkt_cnt_inbi_nph_err_pkt_cnt {
      type oc-yang:counter64;
      description
        "Bad NPU Host packet injected by CSS";
    }
    leaf counter_slice12_ifg_ifgbi_inbi_err_pkt_cnt_inbi_nph_err_pkt_cnt {
      type oc-yang:counter64;
      description
        "Bad NPU Host packet injected by CSS";
    }
    leaf counter_slice13_ifg_ifgbi_inbi_err_pkt_cnt_inbi_nph_err_pkt_cnt {
      type oc-yang:counter64;
      description
        "Bad NPU Host packet injected by CSS";
    }
    leaf counter_slice14_ifg_ifgbi_inbi_err_pkt_cnt_inbi_nph_err_pkt_cnt {
      type oc-yang:counter64;
      description
        "Bad NPU Host packet injected by CSS";
    }
    leaf counter_slice15_ifg_ifgbi_inbi_err_pkt_cnt_inbi_nph_err_pkt_cnt {
      type oc-yang:counter64;
      description
        "Bad NPU Host packet injected by CSS";
    }
    leaf counter_slice0_ifg_ifgbi_inbi_err_pkt_cnt_inbi_pdm_err_pkt_cnt {
      type oc-yang:counter64;
      description
        "Bad Packet DMA packet  injected by CSS";
    }
    leaf counter_slice1_ifg_ifgbi_inbi_err_pkt_cnt_inbi_pdm_err_pkt_cnt {
      type oc-yang:counter64;
      description
        "Bad Packet DMA packet  injected by CSS";
    }
    leaf counter_slice2_ifg_ifgbi_inbi_err_pkt_cnt_inbi_pdm_err_pkt_cnt {
      type oc-yang:counter64;
      description
        "Bad Packet DMA packet  injected by CSS";
    }
    leaf counter_slice3_ifg_ifgbi_inbi_err_pkt_cnt_inbi_pdm_err_pkt_cnt {
      type oc-yang:counter64;
      description
        "Bad Packet DMA packet  injected by CSS";
    }
    leaf counter_slice4_ifg_ifgbi_inbi_err_pkt_cnt_inbi_pdm_err_pkt_cnt {
      type oc-yang:counter64;
      description
        "Bad Packet DMA packet  injected by CSS";
    }
    leaf counter_slice5_ifg_ifgbi_inbi_err_pkt_cnt_inbi_pdm_err_pkt_cnt {
      type oc-yang:counter64;
      description
        "Bad Packet DMA packet  injected by CSS";
    }
    leaf counter_slice6_ifg_ifgbi_inbi_err_pkt_cnt_inbi_pdm_err_pkt_cnt {
      type oc-yang:counter64;
      description
        "Bad Packet DMA packet  injected by CSS";
    }
    leaf counter_slice7_ifg_ifgbi_inbi_err_pkt_cnt_inbi_pdm_err_pkt_cnt {
      type oc-yang:counter64;
      description
        "Bad Packet DMA packet  injected by CSS";
    }
    leaf counter_slice8_ifg_ifgbi_inbi_err_pkt_cnt_inbi_pdm_err_pkt_cnt {
      type oc-yang:counter64;
      description
        "Bad Packet DMA packet  injected by CSS";
    }
    leaf counter_slice9_ifg_ifgbi_inbi_err_pkt_cnt_inbi_pdm_err_pkt_cnt {
      type oc-yang:counter64;
      description
        "Bad Packet DMA packet  injected by CSS";
    }
    leaf counter_slice10_ifg_ifgbi_inbi_err_pkt_cnt_inbi_pdm_err_pkt_cnt {
      type oc-yang:counter64;
      description
        "Bad Packet DMA packet  injected by CSS";
    }
    leaf counter_slice11_ifg_ifgbi_inbi_err_pkt_cnt_inbi_pdm_err_pkt_cnt {
      type oc-yang:counter64;
      description
        "Bad Packet DMA packet  injected by CSS";
    }
    leaf counter_slice12_ifg_ifgbi_inbi_err_pkt_cnt_inbi_pdm_err_pkt_cnt {
      type oc-yang:counter64;
      description
        "Bad Packet DMA packet  injected by CSS";
    }
    leaf counter_slice13_ifg_ifgbi_inbi_err_pkt_cnt_inbi_pdm_err_pkt_cnt {
      type oc-yang:counter64;
      description
        "Bad Packet DMA packet  injected by CSS";
    }
    leaf counter_slice14_ifg_ifgbi_inbi_err_pkt_cnt_inbi_pdm_err_pkt_cnt {
      type oc-yang:counter64;
      description
        "Bad Packet DMA packet  injected by CSS";
    }
    leaf counter_slice15_ifg_ifgbi_inbi_err_pkt_cnt_inbi_pdm_err_pkt_cnt {
      type oc-yang:counter64;
      description
        "Bad Packet DMA packet  injected by CSS";
    }
    leaf counter_slice0_ifg_ifgbi_rcontext_alloc_err_cnt_rx_rcontext_alloc_err_cnt {
      type oc-yang:counter64;
      description
        "The amount of dropped packets due to reassembly context allocation error";
    }
    leaf counter_slice1_ifg_ifgbi_rcontext_alloc_err_cnt_rx_rcontext_alloc_err_cnt {
      type oc-yang:counter64;
      description
        "The amount of dropped packets due to reassembly context allocation error";
    }
    leaf counter_slice2_ifg_ifgbi_rcontext_alloc_err_cnt_rx_rcontext_alloc_err_cnt {
      type oc-yang:counter64;
      description
        "The amount of dropped packets due to reassembly context allocation error";
    }
    leaf counter_slice3_ifg_ifgbi_rcontext_alloc_err_cnt_rx_rcontext_alloc_err_cnt {
      type oc-yang:counter64;
      description
        "The amount of dropped packets due to reassembly context allocation error";
    }
    leaf counter_slice4_ifg_ifgbi_rcontext_alloc_err_cnt_rx_rcontext_alloc_err_cnt {
      type oc-yang:counter64;
      description
        "The amount of dropped packets due to reassembly context allocation error";
    }
    leaf counter_slice5_ifg_ifgbi_rcontext_alloc_err_cnt_rx_rcontext_alloc_err_cnt {
      type oc-yang:counter64;
      description
        "The amount of dropped packets due to reassembly context allocation error";
    }
    leaf counter_slice6_ifg_ifgbi_rcontext_alloc_err_cnt_rx_rcontext_alloc_err_cnt {
      type oc-yang:counter64;
      description
        "The amount of dropped packets due to reassembly context allocation error";
    }
    leaf counter_slice7_ifg_ifgbi_rcontext_alloc_err_cnt_rx_rcontext_alloc_err_cnt {
      type oc-yang:counter64;
      description
        "The amount of dropped packets due to reassembly context allocation error";
    }
    leaf counter_slice8_ifg_ifgbi_rcontext_alloc_err_cnt_rx_rcontext_alloc_err_cnt {
      type oc-yang:counter64;
      description
        "The amount of dropped packets due to reassembly context allocation error";
    }
    leaf counter_slice9_ifg_ifgbi_rcontext_alloc_err_cnt_rx_rcontext_alloc_err_cnt {
      type oc-yang:counter64;
      description
        "The amount of dropped packets due to reassembly context allocation error";
    }
    leaf counter_slice10_ifg_ifgbi_rcontext_alloc_err_cnt_rx_rcontext_alloc_err_cnt {
      type oc-yang:counter64;
      description
        "The amount of dropped packets due to reassembly context allocation error";
    }
    leaf counter_slice11_ifg_ifgbi_rcontext_alloc_err_cnt_rx_rcontext_alloc_err_cnt {
      type oc-yang:counter64;
      description
        "The amount of dropped packets due to reassembly context allocation error";
    }
    leaf counter_slice12_ifg_ifgbi_rcontext_alloc_err_cnt_rx_rcontext_alloc_err_cnt {
      type oc-yang:counter64;
      description
        "The amount of dropped packets due to reassembly context allocation error";
    }
    leaf counter_slice13_ifg_ifgbi_rcontext_alloc_err_cnt_rx_rcontext_alloc_err_cnt {
      type oc-yang:counter64;
      description
        "The amount of dropped packets due to reassembly context allocation error";
    }
    leaf counter_slice14_ifg_ifgbi_rcontext_alloc_err_cnt_rx_rcontext_alloc_err_cnt {
      type oc-yang:counter64;
      description
        "The amount of dropped packets due to reassembly context allocation error";
    }
    leaf counter_slice15_ifg_ifgbi_rcontext_alloc_err_cnt_rx_rcontext_alloc_err_cnt {
      type oc-yang:counter64;
      description
        "The amount of dropped packets due to reassembly context allocation error";
    }
    leaf counter_slice0_ifg_ifgbi_rcy_cntr_dash0_dash_hp_drop_full_pkt_cnt {
      type oc-yang:counter64;
      description
        "SOP Drop packet Count - Full High Priority packet drops based on WrSopThd";
    }
    leaf counter_slice0_ifg_ifgbi_rcy_cntr_dash1_dash_hp_drop_full_pkt_cnt {
      type oc-yang:counter64;
      description
        "SOP Drop packet Count - Full High Priority packet drops based on WrSopThd";
    }
    leaf counter_slice1_ifg_ifgbi_rcy_cntr_dash0_dash_hp_drop_full_pkt_cnt {
      type oc-yang:counter64;
      description
        "SOP Drop packet Count - Full High Priority packet drops based on WrSopThd";
    }
    leaf counter_slice1_ifg_ifgbi_rcy_cntr_dash1_dash_hp_drop_full_pkt_cnt {
      type oc-yang:counter64;
      description
        "SOP Drop packet Count - Full High Priority packet drops based on WrSopThd";
    }
    leaf counter_slice2_ifg_ifgbi_rcy_cntr_dash0_dash_hp_drop_full_pkt_cnt {
      type oc-yang:counter64;
      description
        "SOP Drop packet Count - Full High Priority packet drops based on WrSopThd";
    }
    leaf counter_slice2_ifg_ifgbi_rcy_cntr_dash1_dash_hp_drop_full_pkt_cnt {
      type oc-yang:counter64;
      description
        "SOP Drop packet Count - Full High Priority packet drops based on WrSopThd";
    }
    leaf counter_slice3_ifg_ifgbi_rcy_cntr_dash0_dash_hp_drop_full_pkt_cnt {
      type oc-yang:counter64;
      description
        "SOP Drop packet Count - Full High Priority packet drops based on WrSopThd";
    }
    leaf counter_slice3_ifg_ifgbi_rcy_cntr_dash1_dash_hp_drop_full_pkt_cnt {
      type oc-yang:counter64;
      description
        "SOP Drop packet Count - Full High Priority packet drops based on WrSopThd";
    }
    leaf counter_slice4_ifg_ifgbi_rcy_cntr_dash0_dash_hp_drop_full_pkt_cnt {
      type oc-yang:counter64;
      description
        "SOP Drop packet Count - Full High Priority packet drops based on WrSopThd";
    }
    leaf counter_slice4_ifg_ifgbi_rcy_cntr_dash1_dash_hp_drop_full_pkt_cnt {
      type oc-yang:counter64;
      description
        "SOP Drop packet Count - Full High Priority packet drops based on WrSopThd";
    }
    leaf counter_slice5_ifg_ifgbi_rcy_cntr_dash0_dash_hp_drop_full_pkt_cnt {
      type oc-yang:counter64;
      description
        "SOP Drop packet Count - Full High Priority packet drops based on WrSopThd";
    }
    leaf counter_slice5_ifg_ifgbi_rcy_cntr_dash1_dash_hp_drop_full_pkt_cnt {
      type oc-yang:counter64;
      description
        "SOP Drop packet Count - Full High Priority packet drops based on WrSopThd";
    }
    leaf counter_slice6_ifg_ifgbi_rcy_cntr_dash0_dash_hp_drop_full_pkt_cnt {
      type oc-yang:counter64;
      description
        "SOP Drop packet Count - Full High Priority packet drops based on WrSopThd";
    }
    leaf counter_slice6_ifg_ifgbi_rcy_cntr_dash1_dash_hp_drop_full_pkt_cnt {
      type oc-yang:counter64;
      description
        "SOP Drop packet Count - Full High Priority packet drops based on WrSopThd";
    }
    leaf counter_slice7_ifg_ifgbi_rcy_cntr_dash0_dash_hp_drop_full_pkt_cnt {
      type oc-yang:counter64;
      description
        "SOP Drop packet Count - Full High Priority packet drops based on WrSopThd";
    }
    leaf counter_slice7_ifg_ifgbi_rcy_cntr_dash1_dash_hp_drop_full_pkt_cnt {
      type oc-yang:counter64;
      description
        "SOP Drop packet Count - Full High Priority packet drops based on WrSopThd";
    }
    leaf counter_slice8_ifg_ifgbi_rcy_cntr_dash0_dash_hp_drop_full_pkt_cnt {
      type oc-yang:counter64;
      description
        "SOP Drop packet Count - Full High Priority packet drops based on WrSopThd";
    }
    leaf counter_slice8_ifg_ifgbi_rcy_cntr_dash1_dash_hp_drop_full_pkt_cnt {
      type oc-yang:counter64;
      description
        "SOP Drop packet Count - Full High Priority packet drops based on WrSopThd";
    }
    leaf counter_slice9_ifg_ifgbi_rcy_cntr_dash0_dash_hp_drop_full_pkt_cnt {
      type oc-yang:counter64;
      description
        "SOP Drop packet Count - Full High Priority packet drops based on WrSopThd";
    }
    leaf counter_slice9_ifg_ifgbi_rcy_cntr_dash1_dash_hp_drop_full_pkt_cnt {
      type oc-yang:counter64;
      description
        "SOP Drop packet Count - Full High Priority packet drops based on WrSopThd";
    }
    leaf counter_slice10_ifg_ifgbi_rcy_cntr_dash0_dash_hp_drop_full_pkt_cnt {
      type oc-yang:counter64;
      description
        "SOP Drop packet Count - Full High Priority packet drops based on WrSopThd";
    }
    leaf counter_slice10_ifg_ifgbi_rcy_cntr_dash1_dash_hp_drop_full_pkt_cnt {
      type oc-yang:counter64;
      description
        "SOP Drop packet Count - Full High Priority packet drops based on WrSopThd";
    }
    leaf counter_slice11_ifg_ifgbi_rcy_cntr_dash0_dash_hp_drop_full_pkt_cnt {
      type oc-yang:counter64;
      description
        "SOP Drop packet Count - Full High Priority packet drops based on WrSopThd";
    }
    leaf counter_slice11_ifg_ifgbi_rcy_cntr_dash1_dash_hp_drop_full_pkt_cnt {
      type oc-yang:counter64;
      description
        "SOP Drop packet Count - Full High Priority packet drops based on WrSopThd";
    }
    leaf counter_slice12_ifg_ifgbi_rcy_cntr_dash0_dash_hp_drop_full_pkt_cnt {
      type oc-yang:counter64;
      description
        "SOP Drop packet Count - Full High Priority packet drops based on WrSopThd";
    }
    leaf counter_slice12_ifg_ifgbi_rcy_cntr_dash1_dash_hp_drop_full_pkt_cnt {
      type oc-yang:counter64;
      description
        "SOP Drop packet Count - Full High Priority packet drops based on WrSopThd";
    }
    leaf counter_slice13_ifg_ifgbi_rcy_cntr_dash0_dash_hp_drop_full_pkt_cnt {
      type oc-yang:counter64;
      description
        "SOP Drop packet Count - Full High Priority packet drops based on WrSopThd";
    }
    leaf counter_slice13_ifg_ifgbi_rcy_cntr_dash1_dash_hp_drop_full_pkt_cnt {
      type oc-yang:counter64;
      description
        "SOP Drop packet Count - Full High Priority packet drops based on WrSopThd";
    }
    leaf counter_slice14_ifg_ifgbi_rcy_cntr_dash0_dash_hp_drop_full_pkt_cnt {
      type oc-yang:counter64;
      description
        "SOP Drop packet Count - Full High Priority packet drops based on WrSopThd";
    }
    leaf counter_slice14_ifg_ifgbi_rcy_cntr_dash1_dash_hp_drop_full_pkt_cnt {
      type oc-yang:counter64;
      description
        "SOP Drop packet Count - Full High Priority packet drops based on WrSopThd";
    }
    leaf counter_slice15_ifg_ifgbi_rcy_cntr_dash0_dash_hp_drop_full_pkt_cnt {
      type oc-yang:counter64;
      description
        "SOP Drop packet Count - Full High Priority packet drops based on WrSopThd";
    }
    leaf counter_slice15_ifg_ifgbi_rcy_cntr_dash1_dash_hp_drop_full_pkt_cnt {
      type oc-yang:counter64;
      description
        "SOP Drop packet Count - Full High Priority packet drops based on WrSopThd";
    }
    leaf counter_slice0_ifg_ifgbi_rcy_cntr_dash0_dash_hp_drop_pkt_cnt {
      type oc-yang:counter64;
      description
        "FIFO Full packet Count - Partial High Priority packet drops due to no space in FIFO";
    }
    leaf counter_slice0_ifg_ifgbi_rcy_cntr_dash1_dash_hp_drop_pkt_cnt {
      type oc-yang:counter64;
      description
        "FIFO Full packet Count - Partial High Priority packet drops due to no space in FIFO";
    }
    leaf counter_slice1_ifg_ifgbi_rcy_cntr_dash0_dash_hp_drop_pkt_cnt {
      type oc-yang:counter64;
      description
        "FIFO Full packet Count - Partial High Priority packet drops due to no space in FIFO";
    }
    leaf counter_slice1_ifg_ifgbi_rcy_cntr_dash1_dash_hp_drop_pkt_cnt {
      type oc-yang:counter64;
      description
        "FIFO Full packet Count - Partial High Priority packet drops due to no space in FIFO";
    }
    leaf counter_slice2_ifg_ifgbi_rcy_cntr_dash0_dash_hp_drop_pkt_cnt {
      type oc-yang:counter64;
      description
        "FIFO Full packet Count - Partial High Priority packet drops due to no space in FIFO";
    }
    leaf counter_slice2_ifg_ifgbi_rcy_cntr_dash1_dash_hp_drop_pkt_cnt {
      type oc-yang:counter64;
      description
        "FIFO Full packet Count - Partial High Priority packet drops due to no space in FIFO";
    }
    leaf counter_slice3_ifg_ifgbi_rcy_cntr_dash0_dash_hp_drop_pkt_cnt {
      type oc-yang:counter64;
      description
        "FIFO Full packet Count - Partial High Priority packet drops due to no space in FIFO";
    }
    leaf counter_slice3_ifg_ifgbi_rcy_cntr_dash1_dash_hp_drop_pkt_cnt {
      type oc-yang:counter64;
      description
        "FIFO Full packet Count - Partial High Priority packet drops due to no space in FIFO";
    }
    leaf counter_slice4_ifg_ifgbi_rcy_cntr_dash0_dash_hp_drop_pkt_cnt {
      type oc-yang:counter64;
      description
        "FIFO Full packet Count - Partial High Priority packet drops due to no space in FIFO";
    }
    leaf counter_slice4_ifg_ifgbi_rcy_cntr_dash1_dash_hp_drop_pkt_cnt {
      type oc-yang:counter64;
      description
        "FIFO Full packet Count - Partial High Priority packet drops due to no space in FIFO";
    }
    leaf counter_slice5_ifg_ifgbi_rcy_cntr_dash0_dash_hp_drop_pkt_cnt {
      type oc-yang:counter64;
      description
        "FIFO Full packet Count - Partial High Priority packet drops due to no space in FIFO";
    }
    leaf counter_slice5_ifg_ifgbi_rcy_cntr_dash1_dash_hp_drop_pkt_cnt {
      type oc-yang:counter64;
      description
        "FIFO Full packet Count - Partial High Priority packet drops due to no space in FIFO";
    }
    leaf counter_slice6_ifg_ifgbi_rcy_cntr_dash0_dash_hp_drop_pkt_cnt {
      type oc-yang:counter64;
      description
        "FIFO Full packet Count - Partial High Priority packet drops due to no space in FIFO";
    }
    leaf counter_slice6_ifg_ifgbi_rcy_cntr_dash1_dash_hp_drop_pkt_cnt {
      type oc-yang:counter64;
      description
        "FIFO Full packet Count - Partial High Priority packet drops due to no space in FIFO";
    }
    leaf counter_slice7_ifg_ifgbi_rcy_cntr_dash0_dash_hp_drop_pkt_cnt {
      type oc-yang:counter64;
      description
        "FIFO Full packet Count - Partial High Priority packet drops due to no space in FIFO";
    }
    leaf counter_slice7_ifg_ifgbi_rcy_cntr_dash1_dash_hp_drop_pkt_cnt {
      type oc-yang:counter64;
      description
        "FIFO Full packet Count - Partial High Priority packet drops due to no space in FIFO";
    }
    leaf counter_slice8_ifg_ifgbi_rcy_cntr_dash0_dash_hp_drop_pkt_cnt {
      type oc-yang:counter64;
      description
        "FIFO Full packet Count - Partial High Priority packet drops due to no space in FIFO";
    }
    leaf counter_slice8_ifg_ifgbi_rcy_cntr_dash1_dash_hp_drop_pkt_cnt {
      type oc-yang:counter64;
      description
        "FIFO Full packet Count - Partial High Priority packet drops due to no space in FIFO";
    }
    leaf counter_slice9_ifg_ifgbi_rcy_cntr_dash0_dash_hp_drop_pkt_cnt {
      type oc-yang:counter64;
      description
        "FIFO Full packet Count - Partial High Priority packet drops due to no space in FIFO";
    }
    leaf counter_slice9_ifg_ifgbi_rcy_cntr_dash1_dash_hp_drop_pkt_cnt {
      type oc-yang:counter64;
      description
        "FIFO Full packet Count - Partial High Priority packet drops due to no space in FIFO";
    }
    leaf counter_slice10_ifg_ifgbi_rcy_cntr_dash0_dash_hp_drop_pkt_cnt {
      type oc-yang:counter64;
      description
        "FIFO Full packet Count - Partial High Priority packet drops due to no space in FIFO";
    }
    leaf counter_slice10_ifg_ifgbi_rcy_cntr_dash1_dash_hp_drop_pkt_cnt {
      type oc-yang:counter64;
      description
        "FIFO Full packet Count - Partial High Priority packet drops due to no space in FIFO";
    }
    leaf counter_slice11_ifg_ifgbi_rcy_cntr_dash0_dash_hp_drop_pkt_cnt {
      type oc-yang:counter64;
      description
        "FIFO Full packet Count - Partial High Priority packet drops due to no space in FIFO";
    }
    leaf counter_slice11_ifg_ifgbi_rcy_cntr_dash1_dash_hp_drop_pkt_cnt {
      type oc-yang:counter64;
      description
        "FIFO Full packet Count - Partial High Priority packet drops due to no space in FIFO";
    }
    leaf counter_slice12_ifg_ifgbi_rcy_cntr_dash0_dash_hp_drop_pkt_cnt {
      type oc-yang:counter64;
      description
        "FIFO Full packet Count - Partial High Priority packet drops due to no space in FIFO";
    }
    leaf counter_slice12_ifg_ifgbi_rcy_cntr_dash1_dash_hp_drop_pkt_cnt {
      type oc-yang:counter64;
      description
        "FIFO Full packet Count - Partial High Priority packet drops due to no space in FIFO";
    }
    leaf counter_slice13_ifg_ifgbi_rcy_cntr_dash0_dash_hp_drop_pkt_cnt {
      type oc-yang:counter64;
      description
        "FIFO Full packet Count - Partial High Priority packet drops due to no space in FIFO";
    }
    leaf counter_slice13_ifg_ifgbi_rcy_cntr_dash1_dash_hp_drop_pkt_cnt {
      type oc-yang:counter64;
      description
        "FIFO Full packet Count - Partial High Priority packet drops due to no space in FIFO";
    }
    leaf counter_slice14_ifg_ifgbi_rcy_cntr_dash0_dash_hp_drop_pkt_cnt {
      type oc-yang:counter64;
      description
        "FIFO Full packet Count - Partial High Priority packet drops due to no space in FIFO";
    }
    leaf counter_slice14_ifg_ifgbi_rcy_cntr_dash1_dash_hp_drop_pkt_cnt {
      type oc-yang:counter64;
      description
        "FIFO Full packet Count - Partial High Priority packet drops due to no space in FIFO";
    }
    leaf counter_slice15_ifg_ifgbi_rcy_cntr_dash0_dash_hp_drop_pkt_cnt {
      type oc-yang:counter64;
      description
        "FIFO Full packet Count - Partial High Priority packet drops due to no space in FIFO";
    }
    leaf counter_slice15_ifg_ifgbi_rcy_cntr_dash1_dash_hp_drop_pkt_cnt {
      type oc-yang:counter64;
      description
        "FIFO Full packet Count - Partial High Priority packet drops due to no space in FIFO";
    }
    leaf counter_slice0_ifg_ifgbi_rcy_cntr_dash0_dash_hp_drop_word_cnt {
      type oc-yang:counter64;
      description
        "Word Drop Count - Partial High Priority word drops due to no space in FIFO";
    }
    leaf counter_slice0_ifg_ifgbi_rcy_cntr_dash1_dash_hp_drop_word_cnt {
      type oc-yang:counter64;
      description
        "Word Drop Count - Partial High Priority word drops due to no space in FIFO";
    }
    leaf counter_slice1_ifg_ifgbi_rcy_cntr_dash0_dash_hp_drop_word_cnt {
      type oc-yang:counter64;
      description
        "Word Drop Count - Partial High Priority word drops due to no space in FIFO";
    }
    leaf counter_slice1_ifg_ifgbi_rcy_cntr_dash1_dash_hp_drop_word_cnt {
      type oc-yang:counter64;
      description
        "Word Drop Count - Partial High Priority word drops due to no space in FIFO";
    }
    leaf counter_slice2_ifg_ifgbi_rcy_cntr_dash0_dash_hp_drop_word_cnt {
      type oc-yang:counter64;
      description
        "Word Drop Count - Partial High Priority word drops due to no space in FIFO";
    }
    leaf counter_slice2_ifg_ifgbi_rcy_cntr_dash1_dash_hp_drop_word_cnt {
      type oc-yang:counter64;
      description
        "Word Drop Count - Partial High Priority word drops due to no space in FIFO";
    }
    leaf counter_slice3_ifg_ifgbi_rcy_cntr_dash0_dash_hp_drop_word_cnt {
      type oc-yang:counter64;
      description
        "Word Drop Count - Partial High Priority word drops due to no space in FIFO";
    }
    leaf counter_slice3_ifg_ifgbi_rcy_cntr_dash1_dash_hp_drop_word_cnt {
      type oc-yang:counter64;
      description
        "Word Drop Count - Partial High Priority word drops due to no space in FIFO";
    }
    leaf counter_slice4_ifg_ifgbi_rcy_cntr_dash0_dash_hp_drop_word_cnt {
      type oc-yang:counter64;
      description
        "Word Drop Count - Partial High Priority word drops due to no space in FIFO";
    }
    leaf counter_slice4_ifg_ifgbi_rcy_cntr_dash1_dash_hp_drop_word_cnt {
      type oc-yang:counter64;
      description
        "Word Drop Count - Partial High Priority word drops due to no space in FIFO";
    }
    leaf counter_slice5_ifg_ifgbi_rcy_cntr_dash0_dash_hp_drop_word_cnt {
      type oc-yang:counter64;
      description
        "Word Drop Count - Partial High Priority word drops due to no space in FIFO";
    }
    leaf counter_slice5_ifg_ifgbi_rcy_cntr_dash1_dash_hp_drop_word_cnt {
      type oc-yang:counter64;
      description
        "Word Drop Count - Partial High Priority word drops due to no space in FIFO";
    }
    leaf counter_slice6_ifg_ifgbi_rcy_cntr_dash0_dash_hp_drop_word_cnt {
      type oc-yang:counter64;
      description
        "Word Drop Count - Partial High Priority word drops due to no space in FIFO";
    }
    leaf counter_slice6_ifg_ifgbi_rcy_cntr_dash1_dash_hp_drop_word_cnt {
      type oc-yang:counter64;
      description
        "Word Drop Count - Partial High Priority word drops due to no space in FIFO";
    }
    leaf counter_slice7_ifg_ifgbi_rcy_cntr_dash0_dash_hp_drop_word_cnt {
      type oc-yang:counter64;
      description
        "Word Drop Count - Partial High Priority word drops due to no space in FIFO";
    }
    leaf counter_slice7_ifg_ifgbi_rcy_cntr_dash1_dash_hp_drop_word_cnt {
      type oc-yang:counter64;
      description
        "Word Drop Count - Partial High Priority word drops due to no space in FIFO";
    }
    leaf counter_slice8_ifg_ifgbi_rcy_cntr_dash0_dash_hp_drop_word_cnt {
      type oc-yang:counter64;
      description
        "Word Drop Count - Partial High Priority word drops due to no space in FIFO";
    }
    leaf counter_slice8_ifg_ifgbi_rcy_cntr_dash1_dash_hp_drop_word_cnt {
      type oc-yang:counter64;
      description
        "Word Drop Count - Partial High Priority word drops due to no space in FIFO";
    }
    leaf counter_slice9_ifg_ifgbi_rcy_cntr_dash0_dash_hp_drop_word_cnt {
      type oc-yang:counter64;
      description
        "Word Drop Count - Partial High Priority word drops due to no space in FIFO";
    }
    leaf counter_slice9_ifg_ifgbi_rcy_cntr_dash1_dash_hp_drop_word_cnt {
      type oc-yang:counter64;
      description
        "Word Drop Count - Partial High Priority word drops due to no space in FIFO";
    }
    leaf counter_slice10_ifg_ifgbi_rcy_cntr_dash0_dash_hp_drop_word_cnt {
      type oc-yang:counter64;
      description
        "Word Drop Count - Partial High Priority word drops due to no space in FIFO";
    }
    leaf counter_slice10_ifg_ifgbi_rcy_cntr_dash1_dash_hp_drop_word_cnt {
      type oc-yang:counter64;
      description
        "Word Drop Count - Partial High Priority word drops due to no space in FIFO";
    }
    leaf counter_slice11_ifg_ifgbi_rcy_cntr_dash0_dash_hp_drop_word_cnt {
      type oc-yang:counter64;
      description
        "Word Drop Count - Partial High Priority word drops due to no space in FIFO";
    }
    leaf counter_slice11_ifg_ifgbi_rcy_cntr_dash1_dash_hp_drop_word_cnt {
      type oc-yang:counter64;
      description
        "Word Drop Count - Partial High Priority word drops due to no space in FIFO";
    }
    leaf counter_slice12_ifg_ifgbi_rcy_cntr_dash0_dash_hp_drop_word_cnt {
      type oc-yang:counter64;
      description
        "Word Drop Count - Partial High Priority word drops due to no space in FIFO";
    }
    leaf counter_slice12_ifg_ifgbi_rcy_cntr_dash1_dash_hp_drop_word_cnt {
      type oc-yang:counter64;
      description
        "Word Drop Count - Partial High Priority word drops due to no space in FIFO";
    }
    leaf counter_slice13_ifg_ifgbi_rcy_cntr_dash0_dash_hp_drop_word_cnt {
      type oc-yang:counter64;
      description
        "Word Drop Count - Partial High Priority word drops due to no space in FIFO";
    }
    leaf counter_slice13_ifg_ifgbi_rcy_cntr_dash1_dash_hp_drop_word_cnt {
      type oc-yang:counter64;
      description
        "Word Drop Count - Partial High Priority word drops due to no space in FIFO";
    }
    leaf counter_slice14_ifg_ifgbi_rcy_cntr_dash0_dash_hp_drop_word_cnt {
      type oc-yang:counter64;
      description
        "Word Drop Count - Partial High Priority word drops due to no space in FIFO";
    }
    leaf counter_slice14_ifg_ifgbi_rcy_cntr_dash1_dash_hp_drop_word_cnt {
      type oc-yang:counter64;
      description
        "Word Drop Count - Partial High Priority word drops due to no space in FIFO";
    }
    leaf counter_slice15_ifg_ifgbi_rcy_cntr_dash0_dash_hp_drop_word_cnt {
      type oc-yang:counter64;
      description
        "Word Drop Count - Partial High Priority word drops due to no space in FIFO";
    }
    leaf counter_slice15_ifg_ifgbi_rcy_cntr_dash1_dash_hp_drop_word_cnt {
      type oc-yang:counter64;
      description
        "Word Drop Count - Partial High Priority word drops due to no space in FIFO";
    }
    leaf counter_slice0_ifg_ifgbi_rcy_cntr_dash0_dash_lp_drop_full_pkt_cnt {
      type oc-yang:counter64;
      description
        "SOP Drop packet Count - Full Low Priority packet drops based on WrSopThd";
    }
    leaf counter_slice0_ifg_ifgbi_rcy_cntr_dash1_dash_lp_drop_full_pkt_cnt {
      type oc-yang:counter64;
      description
        "SOP Drop packet Count - Full Low Priority packet drops based on WrSopThd";
    }
    leaf counter_slice1_ifg_ifgbi_rcy_cntr_dash0_dash_lp_drop_full_pkt_cnt {
      type oc-yang:counter64;
      description
        "SOP Drop packet Count - Full Low Priority packet drops based on WrSopThd";
    }
    leaf counter_slice1_ifg_ifgbi_rcy_cntr_dash1_dash_lp_drop_full_pkt_cnt {
      type oc-yang:counter64;
      description
        "SOP Drop packet Count - Full Low Priority packet drops based on WrSopThd";
    }
    leaf counter_slice2_ifg_ifgbi_rcy_cntr_dash0_dash_lp_drop_full_pkt_cnt {
      type oc-yang:counter64;
      description
        "SOP Drop packet Count - Full Low Priority packet drops based on WrSopThd";
    }
    leaf counter_slice2_ifg_ifgbi_rcy_cntr_dash1_dash_lp_drop_full_pkt_cnt {
      type oc-yang:counter64;
      description
        "SOP Drop packet Count - Full Low Priority packet drops based on WrSopThd";
    }
    leaf counter_slice3_ifg_ifgbi_rcy_cntr_dash0_dash_lp_drop_full_pkt_cnt {
      type oc-yang:counter64;
      description
        "SOP Drop packet Count - Full Low Priority packet drops based on WrSopThd";
    }
    leaf counter_slice3_ifg_ifgbi_rcy_cntr_dash1_dash_lp_drop_full_pkt_cnt {
      type oc-yang:counter64;
      description
        "SOP Drop packet Count - Full Low Priority packet drops based on WrSopThd";
    }
    leaf counter_slice4_ifg_ifgbi_rcy_cntr_dash0_dash_lp_drop_full_pkt_cnt {
      type oc-yang:counter64;
      description
        "SOP Drop packet Count - Full Low Priority packet drops based on WrSopThd";
    }
    leaf counter_slice4_ifg_ifgbi_rcy_cntr_dash1_dash_lp_drop_full_pkt_cnt {
      type oc-yang:counter64;
      description
        "SOP Drop packet Count - Full Low Priority packet drops based on WrSopThd";
    }
    leaf counter_slice5_ifg_ifgbi_rcy_cntr_dash0_dash_lp_drop_full_pkt_cnt {
      type oc-yang:counter64;
      description
        "SOP Drop packet Count - Full Low Priority packet drops based on WrSopThd";
    }
    leaf counter_slice5_ifg_ifgbi_rcy_cntr_dash1_dash_lp_drop_full_pkt_cnt {
      type oc-yang:counter64;
      description
        "SOP Drop packet Count - Full Low Priority packet drops based on WrSopThd";
    }
    leaf counter_slice6_ifg_ifgbi_rcy_cntr_dash0_dash_lp_drop_full_pkt_cnt {
      type oc-yang:counter64;
      description
        "SOP Drop packet Count - Full Low Priority packet drops based on WrSopThd";
    }
    leaf counter_slice6_ifg_ifgbi_rcy_cntr_dash1_dash_lp_drop_full_pkt_cnt {
      type oc-yang:counter64;
      description
        "SOP Drop packet Count - Full Low Priority packet drops based on WrSopThd";
    }
    leaf counter_slice7_ifg_ifgbi_rcy_cntr_dash0_dash_lp_drop_full_pkt_cnt {
      type oc-yang:counter64;
      description
        "SOP Drop packet Count - Full Low Priority packet drops based on WrSopThd";
    }
    leaf counter_slice7_ifg_ifgbi_rcy_cntr_dash1_dash_lp_drop_full_pkt_cnt {
      type oc-yang:counter64;
      description
        "SOP Drop packet Count - Full Low Priority packet drops based on WrSopThd";
    }
    leaf counter_slice8_ifg_ifgbi_rcy_cntr_dash0_dash_lp_drop_full_pkt_cnt {
      type oc-yang:counter64;
      description
        "SOP Drop packet Count - Full Low Priority packet drops based on WrSopThd";
    }
    leaf counter_slice8_ifg_ifgbi_rcy_cntr_dash1_dash_lp_drop_full_pkt_cnt {
      type oc-yang:counter64;
      description
        "SOP Drop packet Count - Full Low Priority packet drops based on WrSopThd";
    }
    leaf counter_slice9_ifg_ifgbi_rcy_cntr_dash0_dash_lp_drop_full_pkt_cnt {
      type oc-yang:counter64;
      description
        "SOP Drop packet Count - Full Low Priority packet drops based on WrSopThd";
    }
    leaf counter_slice9_ifg_ifgbi_rcy_cntr_dash1_dash_lp_drop_full_pkt_cnt {
      type oc-yang:counter64;
      description
        "SOP Drop packet Count - Full Low Priority packet drops based on WrSopThd";
    }
    leaf counter_slice10_ifg_ifgbi_rcy_cntr_dash0_dash_lp_drop_full_pkt_cnt {
      type oc-yang:counter64;
      description
        "SOP Drop packet Count - Full Low Priority packet drops based on WrSopThd";
    }
    leaf counter_slice10_ifg_ifgbi_rcy_cntr_dash1_dash_lp_drop_full_pkt_cnt {
      type oc-yang:counter64;
      description
        "SOP Drop packet Count - Full Low Priority packet drops based on WrSopThd";
    }
    leaf counter_slice11_ifg_ifgbi_rcy_cntr_dash0_dash_lp_drop_full_pkt_cnt {
      type oc-yang:counter64;
      description
        "SOP Drop packet Count - Full Low Priority packet drops based on WrSopThd";
    }
    leaf counter_slice11_ifg_ifgbi_rcy_cntr_dash1_dash_lp_drop_full_pkt_cnt {
      type oc-yang:counter64;
      description
        "SOP Drop packet Count - Full Low Priority packet drops based on WrSopThd";
    }
    leaf counter_slice12_ifg_ifgbi_rcy_cntr_dash0_dash_lp_drop_full_pkt_cnt {
      type oc-yang:counter64;
      description
        "SOP Drop packet Count - Full Low Priority packet drops based on WrSopThd";
    }
    leaf counter_slice12_ifg_ifgbi_rcy_cntr_dash1_dash_lp_drop_full_pkt_cnt {
      type oc-yang:counter64;
      description
        "SOP Drop packet Count - Full Low Priority packet drops based on WrSopThd";
    }
    leaf counter_slice13_ifg_ifgbi_rcy_cntr_dash0_dash_lp_drop_full_pkt_cnt {
      type oc-yang:counter64;
      description
        "SOP Drop packet Count - Full Low Priority packet drops based on WrSopThd";
    }
    leaf counter_slice13_ifg_ifgbi_rcy_cntr_dash1_dash_lp_drop_full_pkt_cnt {
      type oc-yang:counter64;
      description
        "SOP Drop packet Count - Full Low Priority packet drops based on WrSopThd";
    }
    leaf counter_slice14_ifg_ifgbi_rcy_cntr_dash0_dash_lp_drop_full_pkt_cnt {
      type oc-yang:counter64;
      description
        "SOP Drop packet Count - Full Low Priority packet drops based on WrSopThd";
    }
    leaf counter_slice14_ifg_ifgbi_rcy_cntr_dash1_dash_lp_drop_full_pkt_cnt {
      type oc-yang:counter64;
      description
        "SOP Drop packet Count - Full Low Priority packet drops based on WrSopThd";
    }
    leaf counter_slice15_ifg_ifgbi_rcy_cntr_dash0_dash_lp_drop_full_pkt_cnt {
      type oc-yang:counter64;
      description
        "SOP Drop packet Count - Full Low Priority packet drops based on WrSopThd";
    }
    leaf counter_slice15_ifg_ifgbi_rcy_cntr_dash1_dash_lp_drop_full_pkt_cnt {
      type oc-yang:counter64;
      description
        "SOP Drop packet Count - Full Low Priority packet drops based on WrSopThd";
    }
    leaf counter_slice0_ifg_ifgbi_rcy_cntr_dash0_dash_lp_drop_pkt_cnt {
      type oc-yang:counter64;
      description
        "FIFO Full packet Count - Partial Low Priority packet drops due to no space in FIFO";
    }
    leaf counter_slice0_ifg_ifgbi_rcy_cntr_dash1_dash_lp_drop_pkt_cnt {
      type oc-yang:counter64;
      description
        "FIFO Full packet Count - Partial Low Priority packet drops due to no space in FIFO";
    }
    leaf counter_slice1_ifg_ifgbi_rcy_cntr_dash0_dash_lp_drop_pkt_cnt {
      type oc-yang:counter64;
      description
        "FIFO Full packet Count - Partial Low Priority packet drops due to no space in FIFO";
    }
    leaf counter_slice1_ifg_ifgbi_rcy_cntr_dash1_dash_lp_drop_pkt_cnt {
      type oc-yang:counter64;
      description
        "FIFO Full packet Count - Partial Low Priority packet drops due to no space in FIFO";
    }
    leaf counter_slice2_ifg_ifgbi_rcy_cntr_dash0_dash_lp_drop_pkt_cnt {
      type oc-yang:counter64;
      description
        "FIFO Full packet Count - Partial Low Priority packet drops due to no space in FIFO";
    }
    leaf counter_slice2_ifg_ifgbi_rcy_cntr_dash1_dash_lp_drop_pkt_cnt {
      type oc-yang:counter64;
      description
        "FIFO Full packet Count - Partial Low Priority packet drops due to no space in FIFO";
    }
    leaf counter_slice3_ifg_ifgbi_rcy_cntr_dash0_dash_lp_drop_pkt_cnt {
      type oc-yang:counter64;
      description
        "FIFO Full packet Count - Partial Low Priority packet drops due to no space in FIFO";
    }
    leaf counter_slice3_ifg_ifgbi_rcy_cntr_dash1_dash_lp_drop_pkt_cnt {
      type oc-yang:counter64;
      description
        "FIFO Full packet Count - Partial Low Priority packet drops due to no space in FIFO";
    }
    leaf counter_slice4_ifg_ifgbi_rcy_cntr_dash0_dash_lp_drop_pkt_cnt {
      type oc-yang:counter64;
      description
        "FIFO Full packet Count - Partial Low Priority packet drops due to no space in FIFO";
    }
    leaf counter_slice4_ifg_ifgbi_rcy_cntr_dash1_dash_lp_drop_pkt_cnt {
      type oc-yang:counter64;
      description
        "FIFO Full packet Count - Partial Low Priority packet drops due to no space in FIFO";
    }
    leaf counter_slice5_ifg_ifgbi_rcy_cntr_dash0_dash_lp_drop_pkt_cnt {
      type oc-yang:counter64;
      description
        "FIFO Full packet Count - Partial Low Priority packet drops due to no space in FIFO";
    }
    leaf counter_slice5_ifg_ifgbi_rcy_cntr_dash1_dash_lp_drop_pkt_cnt {
      type oc-yang:counter64;
      description
        "FIFO Full packet Count - Partial Low Priority packet drops due to no space in FIFO";
    }
    leaf counter_slice6_ifg_ifgbi_rcy_cntr_dash0_dash_lp_drop_pkt_cnt {
      type oc-yang:counter64;
      description
        "FIFO Full packet Count - Partial Low Priority packet drops due to no space in FIFO";
    }
    leaf counter_slice6_ifg_ifgbi_rcy_cntr_dash1_dash_lp_drop_pkt_cnt {
      type oc-yang:counter64;
      description
        "FIFO Full packet Count - Partial Low Priority packet drops due to no space in FIFO";
    }
    leaf counter_slice7_ifg_ifgbi_rcy_cntr_dash0_dash_lp_drop_pkt_cnt {
      type oc-yang:counter64;
      description
        "FIFO Full packet Count - Partial Low Priority packet drops due to no space in FIFO";
    }
    leaf counter_slice7_ifg_ifgbi_rcy_cntr_dash1_dash_lp_drop_pkt_cnt {
      type oc-yang:counter64;
      description
        "FIFO Full packet Count - Partial Low Priority packet drops due to no space in FIFO";
    }
    leaf counter_slice8_ifg_ifgbi_rcy_cntr_dash0_dash_lp_drop_pkt_cnt {
      type oc-yang:counter64;
      description
        "FIFO Full packet Count - Partial Low Priority packet drops due to no space in FIFO";
    }
    leaf counter_slice8_ifg_ifgbi_rcy_cntr_dash1_dash_lp_drop_pkt_cnt {
      type oc-yang:counter64;
      description
        "FIFO Full packet Count - Partial Low Priority packet drops due to no space in FIFO";
    }
    leaf counter_slice9_ifg_ifgbi_rcy_cntr_dash0_dash_lp_drop_pkt_cnt {
      type oc-yang:counter64;
      description
        "FIFO Full packet Count - Partial Low Priority packet drops due to no space in FIFO";
    }
    leaf counter_slice9_ifg_ifgbi_rcy_cntr_dash1_dash_lp_drop_pkt_cnt {
      type oc-yang:counter64;
      description
        "FIFO Full packet Count - Partial Low Priority packet drops due to no space in FIFO";
    }
    leaf counter_slice10_ifg_ifgbi_rcy_cntr_dash0_dash_lp_drop_pkt_cnt {
      type oc-yang:counter64;
      description
        "FIFO Full packet Count - Partial Low Priority packet drops due to no space in FIFO";
    }
    leaf counter_slice10_ifg_ifgbi_rcy_cntr_dash1_dash_lp_drop_pkt_cnt {
      type oc-yang:counter64;
      description
        "FIFO Full packet Count - Partial Low Priority packet drops due to no space in FIFO";
    }
    leaf counter_slice11_ifg_ifgbi_rcy_cntr_dash0_dash_lp_drop_pkt_cnt {
      type oc-yang:counter64;
      description
        "FIFO Full packet Count - Partial Low Priority packet drops due to no space in FIFO";
    }
    leaf counter_slice11_ifg_ifgbi_rcy_cntr_dash1_dash_lp_drop_pkt_cnt {
      type oc-yang:counter64;
      description
        "FIFO Full packet Count - Partial Low Priority packet drops due to no space in FIFO";
    }
    leaf counter_slice12_ifg_ifgbi_rcy_cntr_dash0_dash_lp_drop_pkt_cnt {
      type oc-yang:counter64;
      description
        "FIFO Full packet Count - Partial Low Priority packet drops due to no space in FIFO";
    }
    leaf counter_slice12_ifg_ifgbi_rcy_cntr_dash1_dash_lp_drop_pkt_cnt {
      type oc-yang:counter64;
      description
        "FIFO Full packet Count - Partial Low Priority packet drops due to no space in FIFO";
    }
    leaf counter_slice13_ifg_ifgbi_rcy_cntr_dash0_dash_lp_drop_pkt_cnt {
      type oc-yang:counter64;
      description
        "FIFO Full packet Count - Partial Low Priority packet drops due to no space in FIFO";
    }
    leaf counter_slice13_ifg_ifgbi_rcy_cntr_dash1_dash_lp_drop_pkt_cnt {
      type oc-yang:counter64;
      description
        "FIFO Full packet Count - Partial Low Priority packet drops due to no space in FIFO";
    }
    leaf counter_slice14_ifg_ifgbi_rcy_cntr_dash0_dash_lp_drop_pkt_cnt {
      type oc-yang:counter64;
      description
        "FIFO Full packet Count - Partial Low Priority packet drops due to no space in FIFO";
    }
    leaf counter_slice14_ifg_ifgbi_rcy_cntr_dash1_dash_lp_drop_pkt_cnt {
      type oc-yang:counter64;
      description
        "FIFO Full packet Count - Partial Low Priority packet drops due to no space in FIFO";
    }
    leaf counter_slice15_ifg_ifgbi_rcy_cntr_dash0_dash_lp_drop_pkt_cnt {
      type oc-yang:counter64;
      description
        "FIFO Full packet Count - Partial Low Priority packet drops due to no space in FIFO";
    }
    leaf counter_slice15_ifg_ifgbi_rcy_cntr_dash1_dash_lp_drop_pkt_cnt {
      type oc-yang:counter64;
      description
        "FIFO Full packet Count - Partial Low Priority packet drops due to no space in FIFO";
    }
    leaf counter_slice0_ifg_ifgbi_rcy_cntr_dash0_dash_lp_drop_word_cnt {
      type oc-yang:counter64;
      description
        "Word Drop Count - Partial Low Priority word drops due to no space in FIFO";
    }
    leaf counter_slice0_ifg_ifgbi_rcy_cntr_dash1_dash_lp_drop_word_cnt {
      type oc-yang:counter64;
      description
        "Word Drop Count - Partial Low Priority word drops due to no space in FIFO";
    }
    leaf counter_slice1_ifg_ifgbi_rcy_cntr_dash0_dash_lp_drop_word_cnt {
      type oc-yang:counter64;
      description
        "Word Drop Count - Partial Low Priority word drops due to no space in FIFO";
    }
    leaf counter_slice1_ifg_ifgbi_rcy_cntr_dash1_dash_lp_drop_word_cnt {
      type oc-yang:counter64;
      description
        "Word Drop Count - Partial Low Priority word drops due to no space in FIFO";
    }
    leaf counter_slice2_ifg_ifgbi_rcy_cntr_dash0_dash_lp_drop_word_cnt {
      type oc-yang:counter64;
      description
        "Word Drop Count - Partial Low Priority word drops due to no space in FIFO";
    }
    leaf counter_slice2_ifg_ifgbi_rcy_cntr_dash1_dash_lp_drop_word_cnt {
      type oc-yang:counter64;
      description
        "Word Drop Count - Partial Low Priority word drops due to no space in FIFO";
    }
    leaf counter_slice3_ifg_ifgbi_rcy_cntr_dash0_dash_lp_drop_word_cnt {
      type oc-yang:counter64;
      description
        "Word Drop Count - Partial Low Priority word drops due to no space in FIFO";
    }
    leaf counter_slice3_ifg_ifgbi_rcy_cntr_dash1_dash_lp_drop_word_cnt {
      type oc-yang:counter64;
      description
        "Word Drop Count - Partial Low Priority word drops due to no space in FIFO";
    }
    leaf counter_slice4_ifg_ifgbi_rcy_cntr_dash0_dash_lp_drop_word_cnt {
      type oc-yang:counter64;
      description
        "Word Drop Count - Partial Low Priority word drops due to no space in FIFO";
    }
    leaf counter_slice4_ifg_ifgbi_rcy_cntr_dash1_dash_lp_drop_word_cnt {
      type oc-yang:counter64;
      description
        "Word Drop Count - Partial Low Priority word drops due to no space in FIFO";
    }
    leaf counter_slice5_ifg_ifgbi_rcy_cntr_dash0_dash_lp_drop_word_cnt {
      type oc-yang:counter64;
      description
        "Word Drop Count - Partial Low Priority word drops due to no space in FIFO";
    }
    leaf counter_slice5_ifg_ifgbi_rcy_cntr_dash1_dash_lp_drop_word_cnt {
      type oc-yang:counter64;
      description
        "Word Drop Count - Partial Low Priority word drops due to no space in FIFO";
    }
    leaf counter_slice6_ifg_ifgbi_rcy_cntr_dash0_dash_lp_drop_word_cnt {
      type oc-yang:counter64;
      description
        "Word Drop Count - Partial Low Priority word drops due to no space in FIFO";
    }
    leaf counter_slice6_ifg_ifgbi_rcy_cntr_dash1_dash_lp_drop_word_cnt {
      type oc-yang:counter64;
      description
        "Word Drop Count - Partial Low Priority word drops due to no space in FIFO";
    }
    leaf counter_slice7_ifg_ifgbi_rcy_cntr_dash0_dash_lp_drop_word_cnt {
      type oc-yang:counter64;
      description
        "Word Drop Count - Partial Low Priority word drops due to no space in FIFO";
    }
    leaf counter_slice7_ifg_ifgbi_rcy_cntr_dash1_dash_lp_drop_word_cnt {
      type oc-yang:counter64;
      description
        "Word Drop Count - Partial Low Priority word drops due to no space in FIFO";
    }
    leaf counter_slice8_ifg_ifgbi_rcy_cntr_dash0_dash_lp_drop_word_cnt {
      type oc-yang:counter64;
      description
        "Word Drop Count - Partial Low Priority word drops due to no space in FIFO";
    }
    leaf counter_slice8_ifg_ifgbi_rcy_cntr_dash1_dash_lp_drop_word_cnt {
      type oc-yang:counter64;
      description
        "Word Drop Count - Partial Low Priority word drops due to no space in FIFO";
    }
    leaf counter_slice9_ifg_ifgbi_rcy_cntr_dash0_dash_lp_drop_word_cnt {
      type oc-yang:counter64;
      description
        "Word Drop Count - Partial Low Priority word drops due to no space in FIFO";
    }
    leaf counter_slice9_ifg_ifgbi_rcy_cntr_dash1_dash_lp_drop_word_cnt {
      type oc-yang:counter64;
      description
        "Word Drop Count - Partial Low Priority word drops due to no space in FIFO";
    }
    leaf counter_slice10_ifg_ifgbi_rcy_cntr_dash0_dash_lp_drop_word_cnt {
      type oc-yang:counter64;
      description
        "Word Drop Count - Partial Low Priority word drops due to no space in FIFO";
    }
    leaf counter_slice10_ifg_ifgbi_rcy_cntr_dash1_dash_lp_drop_word_cnt {
      type oc-yang:counter64;
      description
        "Word Drop Count - Partial Low Priority word drops due to no space in FIFO";
    }
    leaf counter_slice11_ifg_ifgbi_rcy_cntr_dash0_dash_lp_drop_word_cnt {
      type oc-yang:counter64;
      description
        "Word Drop Count - Partial Low Priority word drops due to no space in FIFO";
    }
    leaf counter_slice11_ifg_ifgbi_rcy_cntr_dash1_dash_lp_drop_word_cnt {
      type oc-yang:counter64;
      description
        "Word Drop Count - Partial Low Priority word drops due to no space in FIFO";
    }
    leaf counter_slice12_ifg_ifgbi_rcy_cntr_dash0_dash_lp_drop_word_cnt {
      type oc-yang:counter64;
      description
        "Word Drop Count - Partial Low Priority word drops due to no space in FIFO";
    }
    leaf counter_slice12_ifg_ifgbi_rcy_cntr_dash1_dash_lp_drop_word_cnt {
      type oc-yang:counter64;
      description
        "Word Drop Count - Partial Low Priority word drops due to no space in FIFO";
    }
    leaf counter_slice13_ifg_ifgbi_rcy_cntr_dash0_dash_lp_drop_word_cnt {
      type oc-yang:counter64;
      description
        "Word Drop Count - Partial Low Priority word drops due to no space in FIFO";
    }
    leaf counter_slice13_ifg_ifgbi_rcy_cntr_dash1_dash_lp_drop_word_cnt {
      type oc-yang:counter64;
      description
        "Word Drop Count - Partial Low Priority word drops due to no space in FIFO";
    }
    leaf counter_slice14_ifg_ifgbi_rcy_cntr_dash0_dash_lp_drop_word_cnt {
      type oc-yang:counter64;
      description
        "Word Drop Count - Partial Low Priority word drops due to no space in FIFO";
    }
    leaf counter_slice14_ifg_ifgbi_rcy_cntr_dash1_dash_lp_drop_word_cnt {
      type oc-yang:counter64;
      description
        "Word Drop Count - Partial Low Priority word drops due to no space in FIFO";
    }
    leaf counter_slice15_ifg_ifgbi_rcy_cntr_dash0_dash_lp_drop_word_cnt {
      type oc-yang:counter64;
      description
        "Word Drop Count - Partial Low Priority word drops due to no space in FIFO";
    }
    leaf counter_slice15_ifg_ifgbi_rcy_cntr_dash1_dash_lp_drop_word_cnt {
      type oc-yang:counter64;
      description
        "Word Drop Count - Partial Low Priority word drops due to no space in FIFO";
    }
    leaf counter_slice0_ifg_ifgbi_rx_prot_pkt_terminate_abnormally_counter_rx_prot_pkt_terminate_abnormally_cnt {
      type oc-yang:counter64;
      description
        "RXPP interface protection packets terminate abnormally counter";
    }
    leaf counter_slice1_ifg_ifgbi_rx_prot_pkt_terminate_abnormally_counter_rx_prot_pkt_terminate_abnormally_cnt {
      type oc-yang:counter64;
      description
        "RXPP interface protection packets terminate abnormally counter";
    }
    leaf counter_slice2_ifg_ifgbi_rx_prot_pkt_terminate_abnormally_counter_rx_prot_pkt_terminate_abnormally_cnt {
      type oc-yang:counter64;
      description
        "RXPP interface protection packets terminate abnormally counter";
    }
    leaf counter_slice3_ifg_ifgbi_rx_prot_pkt_terminate_abnormally_counter_rx_prot_pkt_terminate_abnormally_cnt {
      type oc-yang:counter64;
      description
        "RXPP interface protection packets terminate abnormally counter";
    }
    leaf counter_slice4_ifg_ifgbi_rx_prot_pkt_terminate_abnormally_counter_rx_prot_pkt_terminate_abnormally_cnt {
      type oc-yang:counter64;
      description
        "RXPP interface protection packets terminate abnormally counter";
    }
    leaf counter_slice5_ifg_ifgbi_rx_prot_pkt_terminate_abnormally_counter_rx_prot_pkt_terminate_abnormally_cnt {
      type oc-yang:counter64;
      description
        "RXPP interface protection packets terminate abnormally counter";
    }
    leaf counter_slice6_ifg_ifgbi_rx_prot_pkt_terminate_abnormally_counter_rx_prot_pkt_terminate_abnormally_cnt {
      type oc-yang:counter64;
      description
        "RXPP interface protection packets terminate abnormally counter";
    }
    leaf counter_slice7_ifg_ifgbi_rx_prot_pkt_terminate_abnormally_counter_rx_prot_pkt_terminate_abnormally_cnt {
      type oc-yang:counter64;
      description
        "RXPP interface protection packets terminate abnormally counter";
    }
    leaf counter_slice8_ifg_ifgbi_rx_prot_pkt_terminate_abnormally_counter_rx_prot_pkt_terminate_abnormally_cnt {
      type oc-yang:counter64;
      description
        "RXPP interface protection packets terminate abnormally counter";
    }
    leaf counter_slice9_ifg_ifgbi_rx_prot_pkt_terminate_abnormally_counter_rx_prot_pkt_terminate_abnormally_cnt {
      type oc-yang:counter64;
      description
        "RXPP interface protection packets terminate abnormally counter";
    }
    leaf counter_slice10_ifg_ifgbi_rx_prot_pkt_terminate_abnormally_counter_rx_prot_pkt_terminate_abnormally_cnt {
      type oc-yang:counter64;
      description
        "RXPP interface protection packets terminate abnormally counter";
    }
    leaf counter_slice11_ifg_ifgbi_rx_prot_pkt_terminate_abnormally_counter_rx_prot_pkt_terminate_abnormally_cnt {
      type oc-yang:counter64;
      description
        "RXPP interface protection packets terminate abnormally counter";
    }
    leaf counter_slice12_ifg_ifgbi_rx_prot_pkt_terminate_abnormally_counter_rx_prot_pkt_terminate_abnormally_cnt {
      type oc-yang:counter64;
      description
        "RXPP interface protection packets terminate abnormally counter";
    }
    leaf counter_slice13_ifg_ifgbi_rx_prot_pkt_terminate_abnormally_counter_rx_prot_pkt_terminate_abnormally_cnt {
      type oc-yang:counter64;
      description
        "RXPP interface protection packets terminate abnormally counter";
    }
    leaf counter_slice14_ifg_ifgbi_rx_prot_pkt_terminate_abnormally_counter_rx_prot_pkt_terminate_abnormally_cnt {
      type oc-yang:counter64;
      description
        "RXPP interface protection packets terminate abnormally counter";
    }
    leaf counter_slice15_ifg_ifgbi_rx_prot_pkt_terminate_abnormally_counter_rx_prot_pkt_terminate_abnormally_cnt {
      type oc-yang:counter64;
      description
        "RXPP interface protection packets terminate abnormally counter";
    }
    leaf counter_slice0_ifg_ifgbi_tx_prot_pkt_drop_counter_tx_prot_pkt_drop_cnt {
      type oc-yang:counter64;
      description
        "TXPP interface protection packet drop counter.";
    }
    leaf counter_slice1_ifg_ifgbi_tx_prot_pkt_drop_counter_tx_prot_pkt_drop_cnt {
      type oc-yang:counter64;
      description
        "TXPP interface protection packet drop counter.";
    }
    leaf counter_slice2_ifg_ifgbi_tx_prot_pkt_drop_counter_tx_prot_pkt_drop_cnt {
      type oc-yang:counter64;
      description
        "TXPP interface protection packet drop counter.";
    }
    leaf counter_slice3_ifg_ifgbi_tx_prot_pkt_drop_counter_tx_prot_pkt_drop_cnt {
      type oc-yang:counter64;
      description
        "TXPP interface protection packet drop counter.";
    }
    leaf counter_slice4_ifg_ifgbi_tx_prot_pkt_drop_counter_tx_prot_pkt_drop_cnt {
      type oc-yang:counter64;
      description
        "TXPP interface protection packet drop counter.";
    }
    leaf counter_slice5_ifg_ifgbi_tx_prot_pkt_drop_counter_tx_prot_pkt_drop_cnt {
      type oc-yang:counter64;
      description
        "TXPP interface protection packet drop counter.";
    }
    leaf counter_slice6_ifg_ifgbi_tx_prot_pkt_drop_counter_tx_prot_pkt_drop_cnt {
      type oc-yang:counter64;
      description
        "TXPP interface protection packet drop counter.";
    }
    leaf counter_slice7_ifg_ifgbi_tx_prot_pkt_drop_counter_tx_prot_pkt_drop_cnt {
      type oc-yang:counter64;
      description
        "TXPP interface protection packet drop counter.";
    }
    leaf counter_slice8_ifg_ifgbi_tx_prot_pkt_drop_counter_tx_prot_pkt_drop_cnt {
      type oc-yang:counter64;
      description
        "TXPP interface protection packet drop counter.";
    }
    leaf counter_slice9_ifg_ifgbi_tx_prot_pkt_drop_counter_tx_prot_pkt_drop_cnt {
      type oc-yang:counter64;
      description
        "TXPP interface protection packet drop counter.";
    }
    leaf counter_slice10_ifg_ifgbi_tx_prot_pkt_drop_counter_tx_prot_pkt_drop_cnt {
      type oc-yang:counter64;
      description
        "TXPP interface protection packet drop counter.";
    }
    leaf counter_slice11_ifg_ifgbi_tx_prot_pkt_drop_counter_tx_prot_pkt_drop_cnt {
      type oc-yang:counter64;
      description
        "TXPP interface protection packet drop counter.";
    }
    leaf counter_slice12_ifg_ifgbi_tx_prot_pkt_drop_counter_tx_prot_pkt_drop_cnt {
      type oc-yang:counter64;
      description
        "TXPP interface protection packet drop counter.";
    }
    leaf counter_slice13_ifg_ifgbi_tx_prot_pkt_drop_counter_tx_prot_pkt_drop_cnt {
      type oc-yang:counter64;
      description
        "TXPP interface protection packet drop counter.";
    }
    leaf counter_slice14_ifg_ifgbi_tx_prot_pkt_drop_counter_tx_prot_pkt_drop_cnt {
      type oc-yang:counter64;
      description
        "TXPP interface protection packet drop counter.";
    }
    leaf counter_slice15_ifg_ifgbi_tx_prot_pkt_drop_counter_tx_prot_pkt_drop_cnt {
      type oc-yang:counter64;
      description
        "TXPP interface protection packet drop counter.";
    }
    leaf counter_slice0_ifg_ifgbi_tx_prot_word_drop_counter_tx_prot_word_drop_cnt {
      type oc-yang:counter64;
      description
        "TXPP interface protection words drop counter.";
    }
    leaf counter_slice1_ifg_ifgbi_tx_prot_word_drop_counter_tx_prot_word_drop_cnt {
      type oc-yang:counter64;
      description
        "TXPP interface protection words drop counter.";
    }
    leaf counter_slice2_ifg_ifgbi_tx_prot_word_drop_counter_tx_prot_word_drop_cnt {
      type oc-yang:counter64;
      description
        "TXPP interface protection words drop counter.";
    }
    leaf counter_slice3_ifg_ifgbi_tx_prot_word_drop_counter_tx_prot_word_drop_cnt {
      type oc-yang:counter64;
      description
        "TXPP interface protection words drop counter.";
    }
    leaf counter_slice4_ifg_ifgbi_tx_prot_word_drop_counter_tx_prot_word_drop_cnt {
      type oc-yang:counter64;
      description
        "TXPP interface protection words drop counter.";
    }
    leaf counter_slice5_ifg_ifgbi_tx_prot_word_drop_counter_tx_prot_word_drop_cnt {
      type oc-yang:counter64;
      description
        "TXPP interface protection words drop counter.";
    }
    leaf counter_slice6_ifg_ifgbi_tx_prot_word_drop_counter_tx_prot_word_drop_cnt {
      type oc-yang:counter64;
      description
        "TXPP interface protection words drop counter.";
    }
    leaf counter_slice7_ifg_ifgbi_tx_prot_word_drop_counter_tx_prot_word_drop_cnt {
      type oc-yang:counter64;
      description
        "TXPP interface protection words drop counter.";
    }
    leaf counter_slice8_ifg_ifgbi_tx_prot_word_drop_counter_tx_prot_word_drop_cnt {
      type oc-yang:counter64;
      description
        "TXPP interface protection words drop counter.";
    }
    leaf counter_slice9_ifg_ifgbi_tx_prot_word_drop_counter_tx_prot_word_drop_cnt {
      type oc-yang:counter64;
      description
        "TXPP interface protection words drop counter.";
    }
    leaf counter_slice10_ifg_ifgbi_tx_prot_word_drop_counter_tx_prot_word_drop_cnt {
      type oc-yang:counter64;
      description
        "TXPP interface protection words drop counter.";
    }
    leaf counter_slice11_ifg_ifgbi_tx_prot_word_drop_counter_tx_prot_word_drop_cnt {
      type oc-yang:counter64;
      description
        "TXPP interface protection words drop counter.";
    }
    leaf counter_slice12_ifg_ifgbi_tx_prot_word_drop_counter_tx_prot_word_drop_cnt {
      type oc-yang:counter64;
      description
        "TXPP interface protection words drop counter.";
    }
    leaf counter_slice13_ifg_ifgbi_tx_prot_word_drop_counter_tx_prot_word_drop_cnt {
      type oc-yang:counter64;
      description
        "TXPP interface protection words drop counter.";
    }
    leaf counter_slice14_ifg_ifgbi_tx_prot_word_drop_counter_tx_prot_word_drop_cnt {
      type oc-yang:counter64;
      description
        "TXPP interface protection words drop counter.";
    }
    leaf counter_slice15_ifg_ifgbi_tx_prot_word_drop_counter_tx_prot_word_drop_cnt {
      type oc-yang:counter64;
      description
        "TXPP interface protection words drop counter.";
    }
    leaf counter_slice0_ifg_mac_pool80_port_mib_counter0_tx_mac_missing_eop_err_cnt {
      type oc-yang:counter64;
      description
        "MAC TX missing eop errors count.";
    }
    leaf counter_slice0_ifg_mac_pool80_port_mib_counter1_tx_mac_missing_eop_err_cnt {
      type oc-yang:counter64;
      description
        "MAC TX missing eop errors count.";
    }
    leaf counter_slice0_ifg_mac_pool80_port_mib_counter2_tx_mac_missing_eop_err_cnt {
      type oc-yang:counter64;
      description
        "MAC TX missing eop errors count.";
    }
    leaf counter_slice0_ifg_mac_pool80_port_mib_counter3_tx_mac_missing_eop_err_cnt {
      type oc-yang:counter64;
      description
        "MAC TX missing eop errors count.";
    }
    leaf counter_slice0_ifg_mac_pool80_port_mib_counter4_tx_mac_missing_eop_err_cnt {
      type oc-yang:counter64;
      description
        "MAC TX missing eop errors count.";
    }
    leaf counter_slice0_ifg_mac_pool80_port_mib_counter5_tx_mac_missing_eop_err_cnt {
      type oc-yang:counter64;
      description
        "MAC TX missing eop errors count.";
    }
    leaf counter_slice0_ifg_mac_pool80_port_mib_counter6_tx_mac_missing_eop_err_cnt {
      type oc-yang:counter64;
      description
        "MAC TX missing eop errors count.";
    }
    leaf counter_slice0_ifg_mac_pool80_port_mib_counter7_tx_mac_missing_eop_err_cnt {
      type oc-yang:counter64;
      description
        "MAC TX missing eop errors count.";
    }
    leaf counter_slice0_ifg_mac_pool81_port_mib_counter0_tx_mac_missing_eop_err_cnt {
      type oc-yang:counter64;
      description
        "MAC TX missing eop errors count.";
    }
    leaf counter_slice0_ifg_mac_pool81_port_mib_counter1_tx_mac_missing_eop_err_cnt {
      type oc-yang:counter64;
      description
        "MAC TX missing eop errors count.";
    }
    leaf counter_slice0_ifg_mac_pool81_port_mib_counter2_tx_mac_missing_eop_err_cnt {
      type oc-yang:counter64;
      description
        "MAC TX missing eop errors count.";
    }
    leaf counter_slice0_ifg_mac_pool81_port_mib_counter3_tx_mac_missing_eop_err_cnt {
      type oc-yang:counter64;
      description
        "MAC TX missing eop errors count.";
    }
    leaf counter_slice0_ifg_mac_pool81_port_mib_counter4_tx_mac_missing_eop_err_cnt {
      type oc-yang:counter64;
      description
        "MAC TX missing eop errors count.";
    }
    leaf counter_slice0_ifg_mac_pool81_port_mib_counter5_tx_mac_missing_eop_err_cnt {
      type oc-yang:counter64;
      description
        "MAC TX missing eop errors count.";
    }
    leaf counter_slice0_ifg_mac_pool81_port_mib_counter6_tx_mac_missing_eop_err_cnt {
      type oc-yang:counter64;
      description
        "MAC TX missing eop errors count.";
    }
    leaf counter_slice0_ifg_mac_pool81_port_mib_counter7_tx_mac_missing_eop_err_cnt {
      type oc-yang:counter64;
      description
        "MAC TX missing eop errors count.";
    }
    leaf counter_slice0_ifg_mac_pool82_port_mib_counter0_tx_mac_missing_eop_err_cnt {
      type oc-yang:counter64;
      description
        "MAC TX missing eop errors count.";
    }
    leaf counter_slice0_ifg_mac_pool82_port_mib_counter1_tx_mac_missing_eop_err_cnt {
      type oc-yang:counter64;
      description
        "MAC TX missing eop errors count.";
    }
    leaf counter_slice0_ifg_mac_pool82_port_mib_counter2_tx_mac_missing_eop_err_cnt {
      type oc-yang:counter64;
      description
        "MAC TX missing eop errors count.";
    }
    leaf counter_slice0_ifg_mac_pool82_port_mib_counter3_tx_mac_missing_eop_err_cnt {
      type oc-yang:counter64;
      description
        "MAC TX missing eop errors count.";
    }
    leaf counter_slice0_ifg_mac_pool82_port_mib_counter4_tx_mac_missing_eop_err_cnt {
      type oc-yang:counter64;
      description
        "MAC TX missing eop errors count.";
    }
    leaf counter_slice0_ifg_mac_pool82_port_mib_counter5_tx_mac_missing_eop_err_cnt {
      type oc-yang:counter64;
      description
        "MAC TX missing eop errors count.";
    }
    leaf counter_slice0_ifg_mac_pool82_port_mib_counter6_tx_mac_missing_eop_err_cnt {
      type oc-yang:counter64;
      description
        "MAC TX missing eop errors count.";
    }
    leaf counter_slice0_ifg_mac_pool82_port_mib_counter7_tx_mac_missing_eop_err_cnt {
      type oc-yang:counter64;
      description
        "MAC TX missing eop errors count.";
    }
    leaf counter_slice0_ifg_mac_pool83_port_mib_counter0_tx_mac_missing_eop_err_cnt {
      type oc-yang:counter64;
      description
        "MAC TX missing eop errors count.";
    }
    leaf counter_slice0_ifg_mac_pool83_port_mib_counter1_tx_mac_missing_eop_err_cnt {
      type oc-yang:counter64;
      description
        "MAC TX missing eop errors count.";
    }
    leaf counter_slice0_ifg_mac_pool83_port_mib_counter2_tx_mac_missing_eop_err_cnt {
      type oc-yang:counter64;
      description
        "MAC TX missing eop errors count.";
    }
    leaf counter_slice0_ifg_mac_pool83_port_mib_counter3_tx_mac_missing_eop_err_cnt {
      type oc-yang:counter64;
      description
        "MAC TX missing eop errors count.";
    }
    leaf counter_slice0_ifg_mac_pool83_port_mib_counter4_tx_mac_missing_eop_err_cnt {
      type oc-yang:counter64;
      description
        "MAC TX missing eop errors count.";
    }
    leaf counter_slice0_ifg_mac_pool83_port_mib_counter5_tx_mac_missing_eop_err_cnt {
      type oc-yang:counter64;
      description
        "MAC TX missing eop errors count.";
    }
    leaf counter_slice0_ifg_mac_pool83_port_mib_counter6_tx_mac_missing_eop_err_cnt {
      type oc-yang:counter64;
      description
        "MAC TX missing eop errors count.";
    }
    leaf counter_slice0_ifg_mac_pool83_port_mib_counter7_tx_mac_missing_eop_err_cnt {
      type oc-yang:counter64;
      description
        "MAC TX missing eop errors count.";
    }
    leaf counter_slice0_ifg_mac_pool84_port_mib_counter0_tx_mac_missing_eop_err_cnt {
      type oc-yang:counter64;
      description
        "MAC TX missing eop errors count.";
    }
    leaf counter_slice0_ifg_mac_pool84_port_mib_counter1_tx_mac_missing_eop_err_cnt {
      type oc-yang:counter64;
      description
        "MAC TX missing eop errors count.";
    }
    leaf counter_slice0_ifg_mac_pool84_port_mib_counter2_tx_mac_missing_eop_err_cnt {
      type oc-yang:counter64;
      description
        "MAC TX missing eop errors count.";
    }
    leaf counter_slice0_ifg_mac_pool84_port_mib_counter3_tx_mac_missing_eop_err_cnt {
      type oc-yang:counter64;
      description
        "MAC TX missing eop errors count.";
    }
    leaf counter_slice0_ifg_mac_pool84_port_mib_counter4_tx_mac_missing_eop_err_cnt {
      type oc-yang:counter64;
      description
        "MAC TX missing eop errors count.";
    }
    leaf counter_slice0_ifg_mac_pool84_port_mib_counter5_tx_mac_missing_eop_err_cnt {
      type oc-yang:counter64;
      description
        "MAC TX missing eop errors count.";
    }
    leaf counter_slice0_ifg_mac_pool84_port_mib_counter6_tx_mac_missing_eop_err_cnt {
      type oc-yang:counter64;
      description
        "MAC TX missing eop errors count.";
    }
    leaf counter_slice0_ifg_mac_pool84_port_mib_counter7_tx_mac_missing_eop_err_cnt {
      type oc-yang:counter64;
      description
        "MAC TX missing eop errors count.";
    }
    leaf counter_slice0_ifg_mac_pool85_port_mib_counter0_tx_mac_missing_eop_err_cnt {
      type oc-yang:counter64;
      description
        "MAC TX missing eop errors count.";
    }
    leaf counter_slice0_ifg_mac_pool85_port_mib_counter1_tx_mac_missing_eop_err_cnt {
      type oc-yang:counter64;
      description
        "MAC TX missing eop errors count.";
    }
    leaf counter_slice0_ifg_mac_pool85_port_mib_counter2_tx_mac_missing_eop_err_cnt {
      type oc-yang:counter64;
      description
        "MAC TX missing eop errors count.";
    }
    leaf counter_slice0_ifg_mac_pool85_port_mib_counter3_tx_mac_missing_eop_err_cnt {
      type oc-yang:counter64;
      description
        "MAC TX missing eop errors count.";
    }
    leaf counter_slice0_ifg_mac_pool85_port_mib_counter4_tx_mac_missing_eop_err_cnt {
      type oc-yang:counter64;
      description
        "MAC TX missing eop errors count.";
    }
    leaf counter_slice0_ifg_mac_pool85_port_mib_counter5_tx_mac_missing_eop_err_cnt {
      type oc-yang:counter64;
      description
        "MAC TX missing eop errors count.";
    }
    leaf counter_slice0_ifg_mac_pool85_port_mib_counter6_tx_mac_missing_eop_err_cnt {
      type oc-yang:counter64;
      description
        "MAC TX missing eop errors count.";
    }
    leaf counter_slice0_ifg_mac_pool85_port_mib_counter7_tx_mac_missing_eop_err_cnt {
      type oc-yang:counter64;
      description
        "MAC TX missing eop errors count.";
    }
    leaf counter_slice0_ifg_mac_pool86_port_mib_counter0_tx_mac_missing_eop_err_cnt {
      type oc-yang:counter64;
      description
        "MAC TX missing eop errors count.";
    }
    leaf counter_slice0_ifg_mac_pool86_port_mib_counter1_tx_mac_missing_eop_err_cnt {
      type oc-yang:counter64;
      description
        "MAC TX missing eop errors count.";
    }
    leaf counter_slice0_ifg_mac_pool86_port_mib_counter2_tx_mac_missing_eop_err_cnt {
      type oc-yang:counter64;
      description
        "MAC TX missing eop errors count.";
    }
    leaf counter_slice0_ifg_mac_pool86_port_mib_counter3_tx_mac_missing_eop_err_cnt {
      type oc-yang:counter64;
      description
        "MAC TX missing eop errors count.";
    }
    leaf counter_slice0_ifg_mac_pool86_port_mib_counter4_tx_mac_missing_eop_err_cnt {
      type oc-yang:counter64;
      description
        "MAC TX missing eop errors count.";
    }
    leaf counter_slice0_ifg_mac_pool86_port_mib_counter5_tx_mac_missing_eop_err_cnt {
      type oc-yang:counter64;
      description
        "MAC TX missing eop errors count.";
    }
    leaf counter_slice0_ifg_mac_pool86_port_mib_counter6_tx_mac_missing_eop_err_cnt {
      type oc-yang:counter64;
      description
        "MAC TX missing eop errors count.";
    }
    leaf counter_slice0_ifg_mac_pool86_port_mib_counter7_tx_mac_missing_eop_err_cnt {
      type oc-yang:counter64;
      description
        "MAC TX missing eop errors count.";
    }
    leaf counter_slice0_ifg_mac_pool87_port_mib_counter0_tx_mac_missing_eop_err_cnt {
      type oc-yang:counter64;
      description
        "MAC TX missing eop errors count.";
    }
    leaf counter_slice0_ifg_mac_pool87_port_mib_counter1_tx_mac_missing_eop_err_cnt {
      type oc-yang:counter64;
      description
        "MAC TX missing eop errors count.";
    }
    leaf counter_slice0_ifg_mac_pool87_port_mib_counter2_tx_mac_missing_eop_err_cnt {
      type oc-yang:counter64;
      description
        "MAC TX missing eop errors count.";
    }
    leaf counter_slice0_ifg_mac_pool87_port_mib_counter3_tx_mac_missing_eop_err_cnt {
      type oc-yang:counter64;
      description
        "MAC TX missing eop errors count.";
    }
    leaf counter_slice0_ifg_mac_pool87_port_mib_counter4_tx_mac_missing_eop_err_cnt {
      type oc-yang:counter64;
      description
        "MAC TX missing eop errors count.";
    }
    leaf counter_slice0_ifg_mac_pool87_port_mib_counter5_tx_mac_missing_eop_err_cnt {
      type oc-yang:counter64;
      description
        "MAC TX missing eop errors count.";
    }
    leaf counter_slice0_ifg_mac_pool87_port_mib_counter6_tx_mac_missing_eop_err_cnt {
      type oc-yang:counter64;
      description
        "MAC TX missing eop errors count.";
    }
    leaf counter_slice0_ifg_mac_pool87_port_mib_counter7_tx_mac_missing_eop_err_cnt {
      type oc-yang:counter64;
      description
        "MAC TX missing eop errors count.";
    }
    leaf counter_slice1_ifg_mac_pool80_port_mib_counter0_tx_mac_missing_eop_err_cnt {
      type oc-yang:counter64;
      description
        "MAC TX missing eop errors count.";
    }
    leaf counter_slice1_ifg_mac_pool80_port_mib_counter1_tx_mac_missing_eop_err_cnt {
      type oc-yang:counter64;
      description
        "MAC TX missing eop errors count.";
    }
    leaf counter_slice1_ifg_mac_pool80_port_mib_counter2_tx_mac_missing_eop_err_cnt {
      type oc-yang:counter64;
      description
        "MAC TX missing eop errors count.";
    }
    leaf counter_slice1_ifg_mac_pool80_port_mib_counter3_tx_mac_missing_eop_err_cnt {
      type oc-yang:counter64;
      description
        "MAC TX missing eop errors count.";
    }
    leaf counter_slice1_ifg_mac_pool80_port_mib_counter4_tx_mac_missing_eop_err_cnt {
      type oc-yang:counter64;
      description
        "MAC TX missing eop errors count.";
    }
    leaf counter_slice1_ifg_mac_pool80_port_mib_counter5_tx_mac_missing_eop_err_cnt {
      type oc-yang:counter64;
      description
        "MAC TX missing eop errors count.";
    }
    leaf counter_slice1_ifg_mac_pool80_port_mib_counter6_tx_mac_missing_eop_err_cnt {
      type oc-yang:counter64;
      description
        "MAC TX missing eop errors count.";
    }
    leaf counter_slice1_ifg_mac_pool80_port_mib_counter7_tx_mac_missing_eop_err_cnt {
      type oc-yang:counter64;
      description
        "MAC TX missing eop errors count.";
    }
    leaf counter_slice1_ifg_mac_pool81_port_mib_counter0_tx_mac_missing_eop_err_cnt {
      type oc-yang:counter64;
      description
        "MAC TX missing eop errors count.";
    }
    leaf counter_slice1_ifg_mac_pool81_port_mib_counter1_tx_mac_missing_eop_err_cnt {
      type oc-yang:counter64;
      description
        "MAC TX missing eop errors count.";
    }
    leaf counter_slice1_ifg_mac_pool81_port_mib_counter2_tx_mac_missing_eop_err_cnt {
      type oc-yang:counter64;
      description
        "MAC TX missing eop errors count.";
    }
    leaf counter_slice1_ifg_mac_pool81_port_mib_counter3_tx_mac_missing_eop_err_cnt {
      type oc-yang:counter64;
      description
        "MAC TX missing eop errors count.";
    }
    leaf counter_slice1_ifg_mac_pool81_port_mib_counter4_tx_mac_missing_eop_err_cnt {
      type oc-yang:counter64;
      description
        "MAC TX missing eop errors count.";
    }
    leaf counter_slice1_ifg_mac_pool81_port_mib_counter5_tx_mac_missing_eop_err_cnt {
      type oc-yang:counter64;
      description
        "MAC TX missing eop errors count.";
    }
    leaf counter_slice1_ifg_mac_pool81_port_mib_counter6_tx_mac_missing_eop_err_cnt {
      type oc-yang:counter64;
      description
        "MAC TX missing eop errors count.";
    }
    leaf counter_slice1_ifg_mac_pool81_port_mib_counter7_tx_mac_missing_eop_err_cnt {
      type oc-yang:counter64;
      description
        "MAC TX missing eop errors count.";
    }
    leaf counter_slice1_ifg_mac_pool82_port_mib_counter0_tx_mac_missing_eop_err_cnt {
      type oc-yang:counter64;
      description
        "MAC TX missing eop errors count.";
    }
    leaf counter_slice1_ifg_mac_pool82_port_mib_counter1_tx_mac_missing_eop_err_cnt {
      type oc-yang:counter64;
      description
        "MAC TX missing eop errors count.";
    }
    leaf counter_slice1_ifg_mac_pool82_port_mib_counter2_tx_mac_missing_eop_err_cnt {
      type oc-yang:counter64;
      description
        "MAC TX missing eop errors count.";
    }
    leaf counter_slice1_ifg_mac_pool82_port_mib_counter3_tx_mac_missing_eop_err_cnt {
      type oc-yang:counter64;
      description
        "MAC TX missing eop errors count.";
    }
    leaf counter_slice1_ifg_mac_pool82_port_mib_counter4_tx_mac_missing_eop_err_cnt {
      type oc-yang:counter64;
      description
        "MAC TX missing eop errors count.";
    }
    leaf counter_slice1_ifg_mac_pool82_port_mib_counter5_tx_mac_missing_eop_err_cnt {
      type oc-yang:counter64;
      description
        "MAC TX missing eop errors count.";
    }
    leaf counter_slice1_ifg_mac_pool82_port_mib_counter6_tx_mac_missing_eop_err_cnt {
      type oc-yang:counter64;
      description
        "MAC TX missing eop errors count.";
    }
    leaf counter_slice1_ifg_mac_pool82_port_mib_counter7_tx_mac_missing_eop_err_cnt {
      type oc-yang:counter64;
      description
        "MAC TX missing eop errors count.";
    }
    leaf counter_slice1_ifg_mac_pool83_port_mib_counter0_tx_mac_missing_eop_err_cnt {
      type oc-yang:counter64;
      description
        "MAC TX missing eop errors count.";
    }
    leaf counter_slice1_ifg_mac_pool83_port_mib_counter1_tx_mac_missing_eop_err_cnt {
      type oc-yang:counter64;
      description
        "MAC TX missing eop errors count.";
    }
    leaf counter_slice1_ifg_mac_pool83_port_mib_counter2_tx_mac_missing_eop_err_cnt {
      type oc-yang:counter64;
      description
        "MAC TX missing eop errors count.";
    }
    leaf counter_slice1_ifg_mac_pool83_port_mib_counter3_tx_mac_missing_eop_err_cnt {
      type oc-yang:counter64;
      description
        "MAC TX missing eop errors count.";
    }
    leaf counter_slice1_ifg_mac_pool83_port_mib_counter4_tx_mac_missing_eop_err_cnt {
      type oc-yang:counter64;
      description
        "MAC TX missing eop errors count.";
    }
    leaf counter_slice1_ifg_mac_pool83_port_mib_counter5_tx_mac_missing_eop_err_cnt {
      type oc-yang:counter64;
      description
        "MAC TX missing eop errors count.";
    }
    leaf counter_slice1_ifg_mac_pool83_port_mib_counter6_tx_mac_missing_eop_err_cnt {
      type oc-yang:counter64;
      description
        "MAC TX missing eop errors count.";
    }
    leaf counter_slice1_ifg_mac_pool83_port_mib_counter7_tx_mac_missing_eop_err_cnt {
      type oc-yang:counter64;
      description
        "MAC TX missing eop errors count.";
    }
    leaf counter_slice1_ifg_mac_pool84_port_mib_counter0_tx_mac_missing_eop_err_cnt {
      type oc-yang:counter64;
      description
        "MAC TX missing eop errors count.";
    }
    leaf counter_slice1_ifg_mac_pool84_port_mib_counter1_tx_mac_missing_eop_err_cnt {
      type oc-yang:counter64;
      description
        "MAC TX missing eop errors count.";
    }
    leaf counter_slice1_ifg_mac_pool84_port_mib_counter2_tx_mac_missing_eop_err_cnt {
      type oc-yang:counter64;
      description
        "MAC TX missing eop errors count.";
    }
    leaf counter_slice1_ifg_mac_pool84_port_mib_counter3_tx_mac_missing_eop_err_cnt {
      type oc-yang:counter64;
      description
        "MAC TX missing eop errors count.";
    }
    leaf counter_slice1_ifg_mac_pool84_port_mib_counter4_tx_mac_missing_eop_err_cnt {
      type oc-yang:counter64;
      description
        "MAC TX missing eop errors count.";
    }
    leaf counter_slice1_ifg_mac_pool84_port_mib_counter5_tx_mac_missing_eop_err_cnt {
      type oc-yang:counter64;
      description
        "MAC TX missing eop errors count.";
    }
    leaf counter_slice1_ifg_mac_pool84_port_mib_counter6_tx_mac_missing_eop_err_cnt {
      type oc-yang:counter64;
      description
        "MAC TX missing eop errors count.";
    }
    leaf counter_slice1_ifg_mac_pool84_port_mib_counter7_tx_mac_missing_eop_err_cnt {
      type oc-yang:counter64;
      description
        "MAC TX missing eop errors count.";
    }
    leaf counter_slice1_ifg_mac_pool85_port_mib_counter0_tx_mac_missing_eop_err_cnt {
      type oc-yang:counter64;
      description
        "MAC TX missing eop errors count.";
    }
    leaf counter_slice1_ifg_mac_pool85_port_mib_counter1_tx_mac_missing_eop_err_cnt {
      type oc-yang:counter64;
      description
        "MAC TX missing eop errors count.";
    }
    leaf counter_slice1_ifg_mac_pool85_port_mib_counter2_tx_mac_missing_eop_err_cnt {
      type oc-yang:counter64;
      description
        "MAC TX missing eop errors count.";
    }
    leaf counter_slice1_ifg_mac_pool85_port_mib_counter3_tx_mac_missing_eop_err_cnt {
      type oc-yang:counter64;
      description
        "MAC TX missing eop errors count.";
    }
    leaf counter_slice1_ifg_mac_pool85_port_mib_counter4_tx_mac_missing_eop_err_cnt {
      type oc-yang:counter64;
      description
        "MAC TX missing eop errors count.";
    }
    leaf counter_slice1_ifg_mac_pool85_port_mib_counter5_tx_mac_missing_eop_err_cnt {
      type oc-yang:counter64;
      description
        "MAC TX missing eop errors count.";
    }
    leaf counter_slice1_ifg_mac_pool85_port_mib_counter6_tx_mac_missing_eop_err_cnt {
      type oc-yang:counter64;
      description
        "MAC TX missing eop errors count.";
    }
    leaf counter_slice1_ifg_mac_pool85_port_mib_counter7_tx_mac_missing_eop_err_cnt {
      type oc-yang:counter64;
      description
        "MAC TX missing eop errors count.";
    }
    leaf counter_slice1_ifg_mac_pool86_port_mib_counter0_tx_mac_missing_eop_err_cnt {
      type oc-yang:counter64;
      description
        "MAC TX missing eop errors count.";
    }
    leaf counter_slice1_ifg_mac_pool86_port_mib_counter1_tx_mac_missing_eop_err_cnt {
      type oc-yang:counter64;
      description
        "MAC TX missing eop errors count.";
    }
    leaf counter_slice1_ifg_mac_pool86_port_mib_counter2_tx_mac_missing_eop_err_cnt {
      type oc-yang:counter64;
      description
        "MAC TX missing eop errors count.";
    }
    leaf counter_slice1_ifg_mac_pool86_port_mib_counter3_tx_mac_missing_eop_err_cnt {
      type oc-yang:counter64;
      description
        "MAC TX missing eop errors count.";
    }
    leaf counter_slice1_ifg_mac_pool86_port_mib_counter4_tx_mac_missing_eop_err_cnt {
      type oc-yang:counter64;
      description
        "MAC TX missing eop errors count.";
    }
    leaf counter_slice1_ifg_mac_pool86_port_mib_counter5_tx_mac_missing_eop_err_cnt {
      type oc-yang:counter64;
      description
        "MAC TX missing eop errors count.";
    }
    leaf counter_slice1_ifg_mac_pool86_port_mib_counter6_tx_mac_missing_eop_err_cnt {
      type oc-yang:counter64;
      description
        "MAC TX missing eop errors count.";
    }
    leaf counter_slice1_ifg_mac_pool86_port_mib_counter7_tx_mac_missing_eop_err_cnt {
      type oc-yang:counter64;
      description
        "MAC TX missing eop errors count.";
    }
    leaf counter_slice1_ifg_mac_pool87_port_mib_counter0_tx_mac_missing_eop_err_cnt {
      type oc-yang:counter64;
      description
        "MAC TX missing eop errors count.";
    }
    leaf counter_slice1_ifg_mac_pool87_port_mib_counter1_tx_mac_missing_eop_err_cnt {
      type oc-yang:counter64;
      description
        "MAC TX missing eop errors count.";
    }
    leaf counter_slice1_ifg_mac_pool87_port_mib_counter2_tx_mac_missing_eop_err_cnt {
      type oc-yang:counter64;
      description
        "MAC TX missing eop errors count.";
    }
    leaf counter_slice1_ifg_mac_pool87_port_mib_counter3_tx_mac_missing_eop_err_cnt {
      type oc-yang:counter64;
      description
        "MAC TX missing eop errors count.";
    }
    leaf counter_slice1_ifg_mac_pool87_port_mib_counter4_tx_mac_missing_eop_err_cnt {
      type oc-yang:counter64;
      description
        "MAC TX missing eop errors count.";
    }
    leaf counter_slice1_ifg_mac_pool87_port_mib_counter5_tx_mac_missing_eop_err_cnt {
      type oc-yang:counter64;
      description
        "MAC TX missing eop errors count.";
    }
    leaf counter_slice1_ifg_mac_pool87_port_mib_counter6_tx_mac_missing_eop_err_cnt {
      type oc-yang:counter64;
      description
        "MAC TX missing eop errors count.";
    }
    leaf counter_slice1_ifg_mac_pool87_port_mib_counter7_tx_mac_missing_eop_err_cnt {
      type oc-yang:counter64;
      description
        "MAC TX missing eop errors count.";
    }
    leaf counter_slice2_ifg_mac_pool80_port_mib_counter0_tx_mac_missing_eop_err_cnt {
      type oc-yang:counter64;
      description
        "MAC TX missing eop errors count.";
    }
    leaf counter_slice2_ifg_mac_pool80_port_mib_counter1_tx_mac_missing_eop_err_cnt {
      type oc-yang:counter64;
      description
        "MAC TX missing eop errors count.";
    }
    leaf counter_slice2_ifg_mac_pool80_port_mib_counter2_tx_mac_missing_eop_err_cnt {
      type oc-yang:counter64;
      description
        "MAC TX missing eop errors count.";
    }
    leaf counter_slice2_ifg_mac_pool80_port_mib_counter3_tx_mac_missing_eop_err_cnt {
      type oc-yang:counter64;
      description
        "MAC TX missing eop errors count.";
    }
    leaf counter_slice2_ifg_mac_pool80_port_mib_counter4_tx_mac_missing_eop_err_cnt {
      type oc-yang:counter64;
      description
        "MAC TX missing eop errors count.";
    }
    leaf counter_slice2_ifg_mac_pool80_port_mib_counter5_tx_mac_missing_eop_err_cnt {
      type oc-yang:counter64;
      description
        "MAC TX missing eop errors count.";
    }
    leaf counter_slice2_ifg_mac_pool80_port_mib_counter6_tx_mac_missing_eop_err_cnt {
      type oc-yang:counter64;
      description
        "MAC TX missing eop errors count.";
    }
    leaf counter_slice2_ifg_mac_pool80_port_mib_counter7_tx_mac_missing_eop_err_cnt {
      type oc-yang:counter64;
      description
        "MAC TX missing eop errors count.";
    }
    leaf counter_slice2_ifg_mac_pool81_port_mib_counter0_tx_mac_missing_eop_err_cnt {
      type oc-yang:counter64;
      description
        "MAC TX missing eop errors count.";
    }
    leaf counter_slice2_ifg_mac_pool81_port_mib_counter1_tx_mac_missing_eop_err_cnt {
      type oc-yang:counter64;
      description
        "MAC TX missing eop errors count.";
    }
    leaf counter_slice2_ifg_mac_pool81_port_mib_counter2_tx_mac_missing_eop_err_cnt {
      type oc-yang:counter64;
      description
        "MAC TX missing eop errors count.";
    }
    leaf counter_slice2_ifg_mac_pool81_port_mib_counter3_tx_mac_missing_eop_err_cnt {
      type oc-yang:counter64;
      description
        "MAC TX missing eop errors count.";
    }
    leaf counter_slice2_ifg_mac_pool81_port_mib_counter4_tx_mac_missing_eop_err_cnt {
      type oc-yang:counter64;
      description
        "MAC TX missing eop errors count.";
    }
    leaf counter_slice2_ifg_mac_pool81_port_mib_counter5_tx_mac_missing_eop_err_cnt {
      type oc-yang:counter64;
      description
        "MAC TX missing eop errors count.";
    }
    leaf counter_slice2_ifg_mac_pool81_port_mib_counter6_tx_mac_missing_eop_err_cnt {
      type oc-yang:counter64;
      description
        "MAC TX missing eop errors count.";
    }
    leaf counter_slice2_ifg_mac_pool81_port_mib_counter7_tx_mac_missing_eop_err_cnt {
      type oc-yang:counter64;
      description
        "MAC TX missing eop errors count.";
    }
    leaf counter_slice2_ifg_mac_pool82_port_mib_counter0_tx_mac_missing_eop_err_cnt {
      type oc-yang:counter64;
      description
        "MAC TX missing eop errors count.";
    }
    leaf counter_slice2_ifg_mac_pool82_port_mib_counter1_tx_mac_missing_eop_err_cnt {
      type oc-yang:counter64;
      description
        "MAC TX missing eop errors count.";
    }
    leaf counter_slice2_ifg_mac_pool82_port_mib_counter2_tx_mac_missing_eop_err_cnt {
      type oc-yang:counter64;
      description
        "MAC TX missing eop errors count.";
    }
    leaf counter_slice2_ifg_mac_pool82_port_mib_counter3_tx_mac_missing_eop_err_cnt {
      type oc-yang:counter64;
      description
        "MAC TX missing eop errors count.";
    }
    leaf counter_slice2_ifg_mac_pool82_port_mib_counter4_tx_mac_missing_eop_err_cnt {
      type oc-yang:counter64;
      description
        "MAC TX missing eop errors count.";
    }
    leaf counter_slice2_ifg_mac_pool82_port_mib_counter5_tx_mac_missing_eop_err_cnt {
      type oc-yang:counter64;
      description
        "MAC TX missing eop errors count.";
    }
    leaf counter_slice2_ifg_mac_pool82_port_mib_counter6_tx_mac_missing_eop_err_cnt {
      type oc-yang:counter64;
      description
        "MAC TX missing eop errors count.";
    }
    leaf counter_slice2_ifg_mac_pool82_port_mib_counter7_tx_mac_missing_eop_err_cnt {
      type oc-yang:counter64;
      description
        "MAC TX missing eop errors count.";
    }
    leaf counter_slice2_ifg_mac_pool83_port_mib_counter0_tx_mac_missing_eop_err_cnt {
      type oc-yang:counter64;
      description
        "MAC TX missing eop errors count.";
    }
    leaf counter_slice2_ifg_mac_pool83_port_mib_counter1_tx_mac_missing_eop_err_cnt {
      type oc-yang:counter64;
      description
        "MAC TX missing eop errors count.";
    }
    leaf counter_slice2_ifg_mac_pool83_port_mib_counter2_tx_mac_missing_eop_err_cnt {
      type oc-yang:counter64;
      description
        "MAC TX missing eop errors count.";
    }
    leaf counter_slice2_ifg_mac_pool83_port_mib_counter3_tx_mac_missing_eop_err_cnt {
      type oc-yang:counter64;
      description
        "MAC TX missing eop errors count.";
    }
    leaf counter_slice2_ifg_mac_pool83_port_mib_counter4_tx_mac_missing_eop_err_cnt {
      type oc-yang:counter64;
      description
        "MAC TX missing eop errors count.";
    }
    leaf counter_slice2_ifg_mac_pool83_port_mib_counter5_tx_mac_missing_eop_err_cnt {
      type oc-yang:counter64;
      description
        "MAC TX missing eop errors count.";
    }
    leaf counter_slice2_ifg_mac_pool83_port_mib_counter6_tx_mac_missing_eop_err_cnt {
      type oc-yang:counter64;
      description
        "MAC TX missing eop errors count.";
    }
    leaf counter_slice2_ifg_mac_pool83_port_mib_counter7_tx_mac_missing_eop_err_cnt {
      type oc-yang:counter64;
      description
        "MAC TX missing eop errors count.";
    }
    leaf counter_slice2_ifg_mac_pool84_port_mib_counter0_tx_mac_missing_eop_err_cnt {
      type oc-yang:counter64;
      description
        "MAC TX missing eop errors count.";
    }
    leaf counter_slice2_ifg_mac_pool84_port_mib_counter1_tx_mac_missing_eop_err_cnt {
      type oc-yang:counter64;
      description
        "MAC TX missing eop errors count.";
    }
    leaf counter_slice2_ifg_mac_pool84_port_mib_counter2_tx_mac_missing_eop_err_cnt {
      type oc-yang:counter64;
      description
        "MAC TX missing eop errors count.";
    }
    leaf counter_slice2_ifg_mac_pool84_port_mib_counter3_tx_mac_missing_eop_err_cnt {
      type oc-yang:counter64;
      description
        "MAC TX missing eop errors count.";
    }
    leaf counter_slice2_ifg_mac_pool84_port_mib_counter4_tx_mac_missing_eop_err_cnt {
      type oc-yang:counter64;
      description
        "MAC TX missing eop errors count.";
    }
    leaf counter_slice2_ifg_mac_pool84_port_mib_counter5_tx_mac_missing_eop_err_cnt {
      type oc-yang:counter64;
      description
        "MAC TX missing eop errors count.";
    }
    leaf counter_slice2_ifg_mac_pool84_port_mib_counter6_tx_mac_missing_eop_err_cnt {
      type oc-yang:counter64;
      description
        "MAC TX missing eop errors count.";
    }
    leaf counter_slice2_ifg_mac_pool84_port_mib_counter7_tx_mac_missing_eop_err_cnt {
      type oc-yang:counter64;
      description
        "MAC TX missing eop errors count.";
    }
    leaf counter_slice2_ifg_mac_pool85_port_mib_counter0_tx_mac_missing_eop_err_cnt {
      type oc-yang:counter64;
      description
        "MAC TX missing eop errors count.";
    }
    leaf counter_slice2_ifg_mac_pool85_port_mib_counter1_tx_mac_missing_eop_err_cnt {
      type oc-yang:counter64;
      description
        "MAC TX missing eop errors count.";
    }
    leaf counter_slice2_ifg_mac_pool85_port_mib_counter2_tx_mac_missing_eop_err_cnt {
      type oc-yang:counter64;
      description
        "MAC TX missing eop errors count.";
    }
    leaf counter_slice2_ifg_mac_pool85_port_mib_counter3_tx_mac_missing_eop_err_cnt {
      type oc-yang:counter64;
      description
        "MAC TX missing eop errors count.";
    }
    leaf counter_slice2_ifg_mac_pool85_port_mib_counter4_tx_mac_missing_eop_err_cnt {
      type oc-yang:counter64;
      description
        "MAC TX missing eop errors count.";
    }
    leaf counter_slice2_ifg_mac_pool85_port_mib_counter5_tx_mac_missing_eop_err_cnt {
      type oc-yang:counter64;
      description
        "MAC TX missing eop errors count.";
    }
    leaf counter_slice2_ifg_mac_pool85_port_mib_counter6_tx_mac_missing_eop_err_cnt {
      type oc-yang:counter64;
      description
        "MAC TX missing eop errors count.";
    }
    leaf counter_slice2_ifg_mac_pool85_port_mib_counter7_tx_mac_missing_eop_err_cnt {
      type oc-yang:counter64;
      description
        "MAC TX missing eop errors count.";
    }
    leaf counter_slice2_ifg_mac_pool86_port_mib_counter0_tx_mac_missing_eop_err_cnt {
      type oc-yang:counter64;
      description
        "MAC TX missing eop errors count.";
    }
    leaf counter_slice2_ifg_mac_pool86_port_mib_counter1_tx_mac_missing_eop_err_cnt {
      type oc-yang:counter64;
      description
        "MAC TX missing eop errors count.";
    }
    leaf counter_slice2_ifg_mac_pool86_port_mib_counter2_tx_mac_missing_eop_err_cnt {
      type oc-yang:counter64;
      description
        "MAC TX missing eop errors count.";
    }
    leaf counter_slice2_ifg_mac_pool86_port_mib_counter3_tx_mac_missing_eop_err_cnt {
      type oc-yang:counter64;
      description
        "MAC TX missing eop errors count.";
    }
    leaf counter_slice2_ifg_mac_pool86_port_mib_counter4_tx_mac_missing_eop_err_cnt {
      type oc-yang:counter64;
      description
        "MAC TX missing eop errors count.";
    }
    leaf counter_slice2_ifg_mac_pool86_port_mib_counter5_tx_mac_missing_eop_err_cnt {
      type oc-yang:counter64;
      description
        "MAC TX missing eop errors count.";
    }
    leaf counter_slice2_ifg_mac_pool86_port_mib_counter6_tx_mac_missing_eop_err_cnt {
      type oc-yang:counter64;
      description
        "MAC TX missing eop errors count.";
    }
    leaf counter_slice2_ifg_mac_pool86_port_mib_counter7_tx_mac_missing_eop_err_cnt {
      type oc-yang:counter64;
      description
        "MAC TX missing eop errors count.";
    }
    leaf counter_slice2_ifg_mac_pool87_port_mib_counter0_tx_mac_missing_eop_err_cnt {
      type oc-yang:counter64;
      description
        "MAC TX missing eop errors count.";
    }
    leaf counter_slice2_ifg_mac_pool87_port_mib_counter1_tx_mac_missing_eop_err_cnt {
      type oc-yang:counter64;
      description
        "MAC TX missing eop errors count.";
    }
    leaf counter_slice2_ifg_mac_pool87_port_mib_counter2_tx_mac_missing_eop_err_cnt {
      type oc-yang:counter64;
      description
        "MAC TX missing eop errors count.";
    }
    leaf counter_slice2_ifg_mac_pool87_port_mib_counter3_tx_mac_missing_eop_err_cnt {
      type oc-yang:counter64;
      description
        "MAC TX missing eop errors count.";
    }
    leaf counter_slice2_ifg_mac_pool87_port_mib_counter4_tx_mac_missing_eop_err_cnt {
      type oc-yang:counter64;
      description
        "MAC TX missing eop errors count.";
    }
    leaf counter_slice2_ifg_mac_pool87_port_mib_counter5_tx_mac_missing_eop_err_cnt {
      type oc-yang:counter64;
      description
        "MAC TX missing eop errors count.";
    }
    leaf counter_slice2_ifg_mac_pool87_port_mib_counter6_tx_mac_missing_eop_err_cnt {
      type oc-yang:counter64;
      description
        "MAC TX missing eop errors count.";
    }
    leaf counter_slice2_ifg_mac_pool87_port_mib_counter7_tx_mac_missing_eop_err_cnt {
      type oc-yang:counter64;
      description
        "MAC TX missing eop errors count.";
    }
    leaf counter_slice3_ifg_mac_pool80_port_mib_counter0_tx_mac_missing_eop_err_cnt {
      type oc-yang:counter64;
      description
        "MAC TX missing eop errors count.";
    }
    leaf counter_slice3_ifg_mac_pool80_port_mib_counter1_tx_mac_missing_eop_err_cnt {
      type oc-yang:counter64;
      description
        "MAC TX missing eop errors count.";
    }
    leaf counter_slice3_ifg_mac_pool80_port_mib_counter2_tx_mac_missing_eop_err_cnt {
      type oc-yang:counter64;
      description
        "MAC TX missing eop errors count.";
    }
    leaf counter_slice3_ifg_mac_pool80_port_mib_counter3_tx_mac_missing_eop_err_cnt {
      type oc-yang:counter64;
      description
        "MAC TX missing eop errors count.";
    }
    leaf counter_slice3_ifg_mac_pool80_port_mib_counter4_tx_mac_missing_eop_err_cnt {
      type oc-yang:counter64;
      description
        "MAC TX missing eop errors count.";
    }
    leaf counter_slice3_ifg_mac_pool80_port_mib_counter5_tx_mac_missing_eop_err_cnt {
      type oc-yang:counter64;
      description
        "MAC TX missing eop errors count.";
    }
    leaf counter_slice3_ifg_mac_pool80_port_mib_counter6_tx_mac_missing_eop_err_cnt {
      type oc-yang:counter64;
      description
        "MAC TX missing eop errors count.";
    }
    leaf counter_slice3_ifg_mac_pool80_port_mib_counter7_tx_mac_missing_eop_err_cnt {
      type oc-yang:counter64;
      description
        "MAC TX missing eop errors count.";
    }
    leaf counter_slice3_ifg_mac_pool81_port_mib_counter0_tx_mac_missing_eop_err_cnt {
      type oc-yang:counter64;
      description
        "MAC TX missing eop errors count.";
    }
    leaf counter_slice3_ifg_mac_pool81_port_mib_counter1_tx_mac_missing_eop_err_cnt {
      type oc-yang:counter64;
      description
        "MAC TX missing eop errors count.";
    }
    leaf counter_slice3_ifg_mac_pool81_port_mib_counter2_tx_mac_missing_eop_err_cnt {
      type oc-yang:counter64;
      description
        "MAC TX missing eop errors count.";
    }
    leaf counter_slice3_ifg_mac_pool81_port_mib_counter3_tx_mac_missing_eop_err_cnt {
      type oc-yang:counter64;
      description
        "MAC TX missing eop errors count.";
    }
    leaf counter_slice3_ifg_mac_pool81_port_mib_counter4_tx_mac_missing_eop_err_cnt {
      type oc-yang:counter64;
      description
        "MAC TX missing eop errors count.";
    }
    leaf counter_slice3_ifg_mac_pool81_port_mib_counter5_tx_mac_missing_eop_err_cnt {
      type oc-yang:counter64;
      description
        "MAC TX missing eop errors count.";
    }
    leaf counter_slice3_ifg_mac_pool81_port_mib_counter6_tx_mac_missing_eop_err_cnt {
      type oc-yang:counter64;
      description
        "MAC TX missing eop errors count.";
    }
    leaf counter_slice3_ifg_mac_pool81_port_mib_counter7_tx_mac_missing_eop_err_cnt {
      type oc-yang:counter64;
      description
        "MAC TX missing eop errors count.";
    }
    leaf counter_slice3_ifg_mac_pool82_port_mib_counter0_tx_mac_missing_eop_err_cnt {
      type oc-yang:counter64;
      description
        "MAC TX missing eop errors count.";
    }
    leaf counter_slice3_ifg_mac_pool82_port_mib_counter1_tx_mac_missing_eop_err_cnt {
      type oc-yang:counter64;
      description
        "MAC TX missing eop errors count.";
    }
    leaf counter_slice3_ifg_mac_pool82_port_mib_counter2_tx_mac_missing_eop_err_cnt {
      type oc-yang:counter64;
      description
        "MAC TX missing eop errors count.";
    }
    leaf counter_slice3_ifg_mac_pool82_port_mib_counter3_tx_mac_missing_eop_err_cnt {
      type oc-yang:counter64;
      description
        "MAC TX missing eop errors count.";
    }
    leaf counter_slice3_ifg_mac_pool82_port_mib_counter4_tx_mac_missing_eop_err_cnt {
      type oc-yang:counter64;
      description
        "MAC TX missing eop errors count.";
    }
    leaf counter_slice3_ifg_mac_pool82_port_mib_counter5_tx_mac_missing_eop_err_cnt {
      type oc-yang:counter64;
      description
        "MAC TX missing eop errors count.";
    }
    leaf counter_slice3_ifg_mac_pool82_port_mib_counter6_tx_mac_missing_eop_err_cnt {
      type oc-yang:counter64;
      description
        "MAC TX missing eop errors count.";
    }
    leaf counter_slice3_ifg_mac_pool82_port_mib_counter7_tx_mac_missing_eop_err_cnt {
      type oc-yang:counter64;
      description
        "MAC TX missing eop errors count.";
    }
    leaf counter_slice3_ifg_mac_pool83_port_mib_counter0_tx_mac_missing_eop_err_cnt {
      type oc-yang:counter64;
      description
        "MAC TX missing eop errors count.";
    }
    leaf counter_slice3_ifg_mac_pool83_port_mib_counter1_tx_mac_missing_eop_err_cnt {
      type oc-yang:counter64;
      description
        "MAC TX missing eop errors count.";
    }
    leaf counter_slice3_ifg_mac_pool83_port_mib_counter2_tx_mac_missing_eop_err_cnt {
      type oc-yang:counter64;
      description
        "MAC TX missing eop errors count.";
    }
    leaf counter_slice3_ifg_mac_pool83_port_mib_counter3_tx_mac_missing_eop_err_cnt {
      type oc-yang:counter64;
      description
        "MAC TX missing eop errors count.";
    }
    leaf counter_slice3_ifg_mac_pool83_port_mib_counter4_tx_mac_missing_eop_err_cnt {
      type oc-yang:counter64;
      description
        "MAC TX missing eop errors count.";
    }
    leaf counter_slice3_ifg_mac_pool83_port_mib_counter5_tx_mac_missing_eop_err_cnt {
      type oc-yang:counter64;
      description
        "MAC TX missing eop errors count.";
    }
    leaf counter_slice3_ifg_mac_pool83_port_mib_counter6_tx_mac_missing_eop_err_cnt {
      type oc-yang:counter64;
      description
        "MAC TX missing eop errors count.";
    }
    leaf counter_slice3_ifg_mac_pool83_port_mib_counter7_tx_mac_missing_eop_err_cnt {
      type oc-yang:counter64;
      description
        "MAC TX missing eop errors count.";
    }
    leaf counter_slice3_ifg_mac_pool84_port_mib_counter0_tx_mac_missing_eop_err_cnt {
      type oc-yang:counter64;
      description
        "MAC TX missing eop errors count.";
    }
    leaf counter_slice3_ifg_mac_pool84_port_mib_counter1_tx_mac_missing_eop_err_cnt {
      type oc-yang:counter64;
      description
        "MAC TX missing eop errors count.";
    }
    leaf counter_slice3_ifg_mac_pool84_port_mib_counter2_tx_mac_missing_eop_err_cnt {
      type oc-yang:counter64;
      description
        "MAC TX missing eop errors count.";
    }
    leaf counter_slice3_ifg_mac_pool84_port_mib_counter3_tx_mac_missing_eop_err_cnt {
      type oc-yang:counter64;
      description
        "MAC TX missing eop errors count.";
    }
    leaf counter_slice3_ifg_mac_pool84_port_mib_counter4_tx_mac_missing_eop_err_cnt {
      type oc-yang:counter64;
      description
        "MAC TX missing eop errors count.";
    }
    leaf counter_slice3_ifg_mac_pool84_port_mib_counter5_tx_mac_missing_eop_err_cnt {
      type oc-yang:counter64;
      description
        "MAC TX missing eop errors count.";
    }
    leaf counter_slice3_ifg_mac_pool84_port_mib_counter6_tx_mac_missing_eop_err_cnt {
      type oc-yang:counter64;
      description
        "MAC TX missing eop errors count.";
    }
    leaf counter_slice3_ifg_mac_pool84_port_mib_counter7_tx_mac_missing_eop_err_cnt {
      type oc-yang:counter64;
      description
        "MAC TX missing eop errors count.";
    }
    leaf counter_slice3_ifg_mac_pool85_port_mib_counter0_tx_mac_missing_eop_err_cnt {
      type oc-yang:counter64;
      description
        "MAC TX missing eop errors count.";
    }
    leaf counter_slice3_ifg_mac_pool85_port_mib_counter1_tx_mac_missing_eop_err_cnt {
      type oc-yang:counter64;
      description
        "MAC TX missing eop errors count.";
    }
    leaf counter_slice3_ifg_mac_pool85_port_mib_counter2_tx_mac_missing_eop_err_cnt {
      type oc-yang:counter64;
      description
        "MAC TX missing eop errors count.";
    }
    leaf counter_slice3_ifg_mac_pool85_port_mib_counter3_tx_mac_missing_eop_err_cnt {
      type oc-yang:counter64;
      description
        "MAC TX missing eop errors count.";
    }
    leaf counter_slice3_ifg_mac_pool85_port_mib_counter4_tx_mac_missing_eop_err_cnt {
      type oc-yang:counter64;
      description
        "MAC TX missing eop errors count.";
    }
    leaf counter_slice3_ifg_mac_pool85_port_mib_counter5_tx_mac_missing_eop_err_cnt {
      type oc-yang:counter64;
      description
        "MAC TX missing eop errors count.";
    }
    leaf counter_slice3_ifg_mac_pool85_port_mib_counter6_tx_mac_missing_eop_err_cnt {
      type oc-yang:counter64;
      description
        "MAC TX missing eop errors count.";
    }
    leaf counter_slice3_ifg_mac_pool85_port_mib_counter7_tx_mac_missing_eop_err_cnt {
      type oc-yang:counter64;
      description
        "MAC TX missing eop errors count.";
    }
    leaf counter_slice3_ifg_mac_pool86_port_mib_counter0_tx_mac_missing_eop_err_cnt {
      type oc-yang:counter64;
      description
        "MAC TX missing eop errors count.";
    }
    leaf counter_slice3_ifg_mac_pool86_port_mib_counter1_tx_mac_missing_eop_err_cnt {
      type oc-yang:counter64;
      description
        "MAC TX missing eop errors count.";
    }
    leaf counter_slice3_ifg_mac_pool86_port_mib_counter2_tx_mac_missing_eop_err_cnt {
      type oc-yang:counter64;
      description
        "MAC TX missing eop errors count.";
    }
    leaf counter_slice3_ifg_mac_pool86_port_mib_counter3_tx_mac_missing_eop_err_cnt {
      type oc-yang:counter64;
      description
        "MAC TX missing eop errors count.";
    }
    leaf counter_slice3_ifg_mac_pool86_port_mib_counter4_tx_mac_missing_eop_err_cnt {
      type oc-yang:counter64;
      description
        "MAC TX missing eop errors count.";
    }
    leaf counter_slice3_ifg_mac_pool86_port_mib_counter5_tx_mac_missing_eop_err_cnt {
      type oc-yang:counter64;
      description
        "MAC TX missing eop errors count.";
    }
    leaf counter_slice3_ifg_mac_pool86_port_mib_counter6_tx_mac_missing_eop_err_cnt {
      type oc-yang:counter64;
      description
        "MAC TX missing eop errors count.";
    }
    leaf counter_slice3_ifg_mac_pool86_port_mib_counter7_tx_mac_missing_eop_err_cnt {
      type oc-yang:counter64;
      description
        "MAC TX missing eop errors count.";
    }
    leaf counter_slice3_ifg_mac_pool87_port_mib_counter0_tx_mac_missing_eop_err_cnt {
      type oc-yang:counter64;
      description
        "MAC TX missing eop errors count.";
    }
    leaf counter_slice3_ifg_mac_pool87_port_mib_counter1_tx_mac_missing_eop_err_cnt {
      type oc-yang:counter64;
      description
        "MAC TX missing eop errors count.";
    }
    leaf counter_slice3_ifg_mac_pool87_port_mib_counter2_tx_mac_missing_eop_err_cnt {
      type oc-yang:counter64;
      description
        "MAC TX missing eop errors count.";
    }
    leaf counter_slice3_ifg_mac_pool87_port_mib_counter3_tx_mac_missing_eop_err_cnt {
      type oc-yang:counter64;
      description
        "MAC TX missing eop errors count.";
    }
    leaf counter_slice3_ifg_mac_pool87_port_mib_counter4_tx_mac_missing_eop_err_cnt {
      type oc-yang:counter64;
      description
        "MAC TX missing eop errors count.";
    }
    leaf counter_slice3_ifg_mac_pool87_port_mib_counter5_tx_mac_missing_eop_err_cnt {
      type oc-yang:counter64;
      description
        "MAC TX missing eop errors count.";
    }
    leaf counter_slice3_ifg_mac_pool87_port_mib_counter6_tx_mac_missing_eop_err_cnt {
      type oc-yang:counter64;
      description
        "MAC TX missing eop errors count.";
    }
    leaf counter_slice3_ifg_mac_pool87_port_mib_counter7_tx_mac_missing_eop_err_cnt {
      type oc-yang:counter64;
      description
        "MAC TX missing eop errors count.";
    }
    leaf counter_slice4_ifg_mac_pool80_port_mib_counter0_tx_mac_missing_eop_err_cnt {
      type oc-yang:counter64;
      description
        "MAC TX missing eop errors count.";
    }
    leaf counter_slice4_ifg_mac_pool80_port_mib_counter1_tx_mac_missing_eop_err_cnt {
      type oc-yang:counter64;
      description
        "MAC TX missing eop errors count.";
    }
    leaf counter_slice4_ifg_mac_pool80_port_mib_counter2_tx_mac_missing_eop_err_cnt {
      type oc-yang:counter64;
      description
        "MAC TX missing eop errors count.";
    }
    leaf counter_slice4_ifg_mac_pool80_port_mib_counter3_tx_mac_missing_eop_err_cnt {
      type oc-yang:counter64;
      description
        "MAC TX missing eop errors count.";
    }
    leaf counter_slice4_ifg_mac_pool80_port_mib_counter4_tx_mac_missing_eop_err_cnt {
      type oc-yang:counter64;
      description
        "MAC TX missing eop errors count.";
    }
    leaf counter_slice4_ifg_mac_pool80_port_mib_counter5_tx_mac_missing_eop_err_cnt {
      type oc-yang:counter64;
      description
        "MAC TX missing eop errors count.";
    }
    leaf counter_slice4_ifg_mac_pool80_port_mib_counter6_tx_mac_missing_eop_err_cnt {
      type oc-yang:counter64;
      description
        "MAC TX missing eop errors count.";
    }
    leaf counter_slice4_ifg_mac_pool80_port_mib_counter7_tx_mac_missing_eop_err_cnt {
      type oc-yang:counter64;
      description
        "MAC TX missing eop errors count.";
    }
    leaf counter_slice4_ifg_mac_pool81_port_mib_counter0_tx_mac_missing_eop_err_cnt {
      type oc-yang:counter64;
      description
        "MAC TX missing eop errors count.";
    }
    leaf counter_slice4_ifg_mac_pool81_port_mib_counter1_tx_mac_missing_eop_err_cnt {
      type oc-yang:counter64;
      description
        "MAC TX missing eop errors count.";
    }
    leaf counter_slice4_ifg_mac_pool81_port_mib_counter2_tx_mac_missing_eop_err_cnt {
      type oc-yang:counter64;
      description
        "MAC TX missing eop errors count.";
    }
    leaf counter_slice4_ifg_mac_pool81_port_mib_counter3_tx_mac_missing_eop_err_cnt {
      type oc-yang:counter64;
      description
        "MAC TX missing eop errors count.";
    }
    leaf counter_slice4_ifg_mac_pool81_port_mib_counter4_tx_mac_missing_eop_err_cnt {
      type oc-yang:counter64;
      description
        "MAC TX missing eop errors count.";
    }
    leaf counter_slice4_ifg_mac_pool81_port_mib_counter5_tx_mac_missing_eop_err_cnt {
      type oc-yang:counter64;
      description
        "MAC TX missing eop errors count.";
    }
    leaf counter_slice4_ifg_mac_pool81_port_mib_counter6_tx_mac_missing_eop_err_cnt {
      type oc-yang:counter64;
      description
        "MAC TX missing eop errors count.";
    }
    leaf counter_slice4_ifg_mac_pool81_port_mib_counter7_tx_mac_missing_eop_err_cnt {
      type oc-yang:counter64;
      description
        "MAC TX missing eop errors count.";
    }
    leaf counter_slice4_ifg_mac_pool82_port_mib_counter0_tx_mac_missing_eop_err_cnt {
      type oc-yang:counter64;
      description
        "MAC TX missing eop errors count.";
    }
    leaf counter_slice4_ifg_mac_pool82_port_mib_counter1_tx_mac_missing_eop_err_cnt {
      type oc-yang:counter64;
      description
        "MAC TX missing eop errors count.";
    }
    leaf counter_slice4_ifg_mac_pool82_port_mib_counter2_tx_mac_missing_eop_err_cnt {
      type oc-yang:counter64;
      description
        "MAC TX missing eop errors count.";
    }
    leaf counter_slice4_ifg_mac_pool82_port_mib_counter3_tx_mac_missing_eop_err_cnt {
      type oc-yang:counter64;
      description
        "MAC TX missing eop errors count.";
    }
    leaf counter_slice4_ifg_mac_pool82_port_mib_counter4_tx_mac_missing_eop_err_cnt {
      type oc-yang:counter64;
      description
        "MAC TX missing eop errors count.";
    }
    leaf counter_slice4_ifg_mac_pool82_port_mib_counter5_tx_mac_missing_eop_err_cnt {
      type oc-yang:counter64;
      description
        "MAC TX missing eop errors count.";
    }
    leaf counter_slice4_ifg_mac_pool82_port_mib_counter6_tx_mac_missing_eop_err_cnt {
      type oc-yang:counter64;
      description
        "MAC TX missing eop errors count.";
    }
    leaf counter_slice4_ifg_mac_pool82_port_mib_counter7_tx_mac_missing_eop_err_cnt {
      type oc-yang:counter64;
      description
        "MAC TX missing eop errors count.";
    }
    leaf counter_slice4_ifg_mac_pool83_port_mib_counter0_tx_mac_missing_eop_err_cnt {
      type oc-yang:counter64;
      description
        "MAC TX missing eop errors count.";
    }
    leaf counter_slice4_ifg_mac_pool83_port_mib_counter1_tx_mac_missing_eop_err_cnt {
      type oc-yang:counter64;
      description
        "MAC TX missing eop errors count.";
    }
    leaf counter_slice4_ifg_mac_pool83_port_mib_counter2_tx_mac_missing_eop_err_cnt {
      type oc-yang:counter64;
      description
        "MAC TX missing eop errors count.";
    }
    leaf counter_slice4_ifg_mac_pool83_port_mib_counter3_tx_mac_missing_eop_err_cnt {
      type oc-yang:counter64;
      description
        "MAC TX missing eop errors count.";
    }
    leaf counter_slice4_ifg_mac_pool83_port_mib_counter4_tx_mac_missing_eop_err_cnt {
      type oc-yang:counter64;
      description
        "MAC TX missing eop errors count.";
    }
    leaf counter_slice4_ifg_mac_pool83_port_mib_counter5_tx_mac_missing_eop_err_cnt {
      type oc-yang:counter64;
      description
        "MAC TX missing eop errors count.";
    }
    leaf counter_slice4_ifg_mac_pool83_port_mib_counter6_tx_mac_missing_eop_err_cnt {
      type oc-yang:counter64;
      description
        "MAC TX missing eop errors count.";
    }
    leaf counter_slice4_ifg_mac_pool83_port_mib_counter7_tx_mac_missing_eop_err_cnt {
      type oc-yang:counter64;
      description
        "MAC TX missing eop errors count.";
    }
    leaf counter_slice4_ifg_mac_pool84_port_mib_counter0_tx_mac_missing_eop_err_cnt {
      type oc-yang:counter64;
      description
        "MAC TX missing eop errors count.";
    }
    leaf counter_slice4_ifg_mac_pool84_port_mib_counter1_tx_mac_missing_eop_err_cnt {
      type oc-yang:counter64;
      description
        "MAC TX missing eop errors count.";
    }
    leaf counter_slice4_ifg_mac_pool84_port_mib_counter2_tx_mac_missing_eop_err_cnt {
      type oc-yang:counter64;
      description
        "MAC TX missing eop errors count.";
    }
    leaf counter_slice4_ifg_mac_pool84_port_mib_counter3_tx_mac_missing_eop_err_cnt {
      type oc-yang:counter64;
      description
        "MAC TX missing eop errors count.";
    }
    leaf counter_slice4_ifg_mac_pool84_port_mib_counter4_tx_mac_missing_eop_err_cnt {
      type oc-yang:counter64;
      description
        "MAC TX missing eop errors count.";
    }
    leaf counter_slice4_ifg_mac_pool84_port_mib_counter5_tx_mac_missing_eop_err_cnt {
      type oc-yang:counter64;
      description
        "MAC TX missing eop errors count.";
    }
    leaf counter_slice4_ifg_mac_pool84_port_mib_counter6_tx_mac_missing_eop_err_cnt {
      type oc-yang:counter64;
      description
        "MAC TX missing eop errors count.";
    }
    leaf counter_slice4_ifg_mac_pool84_port_mib_counter7_tx_mac_missing_eop_err_cnt {
      type oc-yang:counter64;
      description
        "MAC TX missing eop errors count.";
    }
    leaf counter_slice4_ifg_mac_pool85_port_mib_counter0_tx_mac_missing_eop_err_cnt {
      type oc-yang:counter64;
      description
        "MAC TX missing eop errors count.";
    }
    leaf counter_slice4_ifg_mac_pool85_port_mib_counter1_tx_mac_missing_eop_err_cnt {
      type oc-yang:counter64;
      description
        "MAC TX missing eop errors count.";
    }
    leaf counter_slice4_ifg_mac_pool85_port_mib_counter2_tx_mac_missing_eop_err_cnt {
      type oc-yang:counter64;
      description
        "MAC TX missing eop errors count.";
    }
    leaf counter_slice4_ifg_mac_pool85_port_mib_counter3_tx_mac_missing_eop_err_cnt {
      type oc-yang:counter64;
      description
        "MAC TX missing eop errors count.";
    }
    leaf counter_slice4_ifg_mac_pool85_port_mib_counter4_tx_mac_missing_eop_err_cnt {
      type oc-yang:counter64;
      description
        "MAC TX missing eop errors count.";
    }
    leaf counter_slice4_ifg_mac_pool85_port_mib_counter5_tx_mac_missing_eop_err_cnt {
      type oc-yang:counter64;
      description
        "MAC TX missing eop errors count.";
    }
    leaf counter_slice4_ifg_mac_pool85_port_mib_counter6_tx_mac_missing_eop_err_cnt {
      type oc-yang:counter64;
      description
        "MAC TX missing eop errors count.";
    }
    leaf counter_slice4_ifg_mac_pool85_port_mib_counter7_tx_mac_missing_eop_err_cnt {
      type oc-yang:counter64;
      description
        "MAC TX missing eop errors count.";
    }
    leaf counter_slice4_ifg_mac_pool86_port_mib_counter0_tx_mac_missing_eop_err_cnt {
      type oc-yang:counter64;
      description
        "MAC TX missing eop errors count.";
    }
    leaf counter_slice4_ifg_mac_pool86_port_mib_counter1_tx_mac_missing_eop_err_cnt {
      type oc-yang:counter64;
      description
        "MAC TX missing eop errors count.";
    }
    leaf counter_slice4_ifg_mac_pool86_port_mib_counter2_tx_mac_missing_eop_err_cnt {
      type oc-yang:counter64;
      description
        "MAC TX missing eop errors count.";
    }
    leaf counter_slice4_ifg_mac_pool86_port_mib_counter3_tx_mac_missing_eop_err_cnt {
      type oc-yang:counter64;
      description
        "MAC TX missing eop errors count.";
    }
    leaf counter_slice4_ifg_mac_pool86_port_mib_counter4_tx_mac_missing_eop_err_cnt {
      type oc-yang:counter64;
      description
        "MAC TX missing eop errors count.";
    }
    leaf counter_slice4_ifg_mac_pool86_port_mib_counter5_tx_mac_missing_eop_err_cnt {
      type oc-yang:counter64;
      description
        "MAC TX missing eop errors count.";
    }
    leaf counter_slice4_ifg_mac_pool86_port_mib_counter6_tx_mac_missing_eop_err_cnt {
      type oc-yang:counter64;
      description
        "MAC TX missing eop errors count.";
    }
    leaf counter_slice4_ifg_mac_pool86_port_mib_counter7_tx_mac_missing_eop_err_cnt {
      type oc-yang:counter64;
      description
        "MAC TX missing eop errors count.";
    }
    leaf counter_slice4_ifg_mac_pool87_port_mib_counter0_tx_mac_missing_eop_err_cnt {
      type oc-yang:counter64;
      description
        "MAC TX missing eop errors count.";
    }
    leaf counter_slice4_ifg_mac_pool87_port_mib_counter1_tx_mac_missing_eop_err_cnt {
      type oc-yang:counter64;
      description
        "MAC TX missing eop errors count.";
    }
    leaf counter_slice4_ifg_mac_pool87_port_mib_counter2_tx_mac_missing_eop_err_cnt {
      type oc-yang:counter64;
      description
        "MAC TX missing eop errors count.";
    }
    leaf counter_slice4_ifg_mac_pool87_port_mib_counter3_tx_mac_missing_eop_err_cnt {
      type oc-yang:counter64;
      description
        "MAC TX missing eop errors count.";
    }
    leaf counter_slice4_ifg_mac_pool87_port_mib_counter4_tx_mac_missing_eop_err_cnt {
      type oc-yang:counter64;
      description
        "MAC TX missing eop errors count.";
    }
    leaf counter_slice4_ifg_mac_pool87_port_mib_counter5_tx_mac_missing_eop_err_cnt {
      type oc-yang:counter64;
      description
        "MAC TX missing eop errors count.";
    }
    leaf counter_slice4_ifg_mac_pool87_port_mib_counter6_tx_mac_missing_eop_err_cnt {
      type oc-yang:counter64;
      description
        "MAC TX missing eop errors count.";
    }
    leaf counter_slice4_ifg_mac_pool87_port_mib_counter7_tx_mac_missing_eop_err_cnt {
      type oc-yang:counter64;
      description
        "MAC TX missing eop errors count.";
    }
    leaf counter_slice5_ifg_mac_pool80_port_mib_counter0_tx_mac_missing_eop_err_cnt {
      type oc-yang:counter64;
      description
        "MAC TX missing eop errors count.";
    }
    leaf counter_slice5_ifg_mac_pool80_port_mib_counter1_tx_mac_missing_eop_err_cnt {
      type oc-yang:counter64;
      description
        "MAC TX missing eop errors count.";
    }
    leaf counter_slice5_ifg_mac_pool80_port_mib_counter2_tx_mac_missing_eop_err_cnt {
      type oc-yang:counter64;
      description
        "MAC TX missing eop errors count.";
    }
    leaf counter_slice5_ifg_mac_pool80_port_mib_counter3_tx_mac_missing_eop_err_cnt {
      type oc-yang:counter64;
      description
        "MAC TX missing eop errors count.";
    }
    leaf counter_slice5_ifg_mac_pool80_port_mib_counter4_tx_mac_missing_eop_err_cnt {
      type oc-yang:counter64;
      description
        "MAC TX missing eop errors count.";
    }
    leaf counter_slice5_ifg_mac_pool80_port_mib_counter5_tx_mac_missing_eop_err_cnt {
      type oc-yang:counter64;
      description
        "MAC TX missing eop errors count.";
    }
    leaf counter_slice5_ifg_mac_pool80_port_mib_counter6_tx_mac_missing_eop_err_cnt {
      type oc-yang:counter64;
      description
        "MAC TX missing eop errors count.";
    }
    leaf counter_slice5_ifg_mac_pool80_port_mib_counter7_tx_mac_missing_eop_err_cnt {
      type oc-yang:counter64;
      description
        "MAC TX missing eop errors count.";
    }
    leaf counter_slice5_ifg_mac_pool81_port_mib_counter0_tx_mac_missing_eop_err_cnt {
      type oc-yang:counter64;
      description
        "MAC TX missing eop errors count.";
    }
    leaf counter_slice5_ifg_mac_pool81_port_mib_counter1_tx_mac_missing_eop_err_cnt {
      type oc-yang:counter64;
      description
        "MAC TX missing eop errors count.";
    }
    leaf counter_slice5_ifg_mac_pool81_port_mib_counter2_tx_mac_missing_eop_err_cnt {
      type oc-yang:counter64;
      description
        "MAC TX missing eop errors count.";
    }
    leaf counter_slice5_ifg_mac_pool81_port_mib_counter3_tx_mac_missing_eop_err_cnt {
      type oc-yang:counter64;
      description
        "MAC TX missing eop errors count.";
    }
    leaf counter_slice5_ifg_mac_pool81_port_mib_counter4_tx_mac_missing_eop_err_cnt {
      type oc-yang:counter64;
      description
        "MAC TX missing eop errors count.";
    }
    leaf counter_slice5_ifg_mac_pool81_port_mib_counter5_tx_mac_missing_eop_err_cnt {
      type oc-yang:counter64;
      description
        "MAC TX missing eop errors count.";
    }
    leaf counter_slice5_ifg_mac_pool81_port_mib_counter6_tx_mac_missing_eop_err_cnt {
      type oc-yang:counter64;
      description
        "MAC TX missing eop errors count.";
    }
    leaf counter_slice5_ifg_mac_pool81_port_mib_counter7_tx_mac_missing_eop_err_cnt {
      type oc-yang:counter64;
      description
        "MAC TX missing eop errors count.";
    }
    leaf counter_slice5_ifg_mac_pool82_port_mib_counter0_tx_mac_missing_eop_err_cnt {
      type oc-yang:counter64;
      description
        "MAC TX missing eop errors count.";
    }
    leaf counter_slice5_ifg_mac_pool82_port_mib_counter1_tx_mac_missing_eop_err_cnt {
      type oc-yang:counter64;
      description
        "MAC TX missing eop errors count.";
    }
    leaf counter_slice5_ifg_mac_pool82_port_mib_counter2_tx_mac_missing_eop_err_cnt {
      type oc-yang:counter64;
      description
        "MAC TX missing eop errors count.";
    }
    leaf counter_slice5_ifg_mac_pool82_port_mib_counter3_tx_mac_missing_eop_err_cnt {
      type oc-yang:counter64;
      description
        "MAC TX missing eop errors count.";
    }
    leaf counter_slice5_ifg_mac_pool82_port_mib_counter4_tx_mac_missing_eop_err_cnt {
      type oc-yang:counter64;
      description
        "MAC TX missing eop errors count.";
    }
    leaf counter_slice5_ifg_mac_pool82_port_mib_counter5_tx_mac_missing_eop_err_cnt {
      type oc-yang:counter64;
      description
        "MAC TX missing eop errors count.";
    }
    leaf counter_slice5_ifg_mac_pool82_port_mib_counter6_tx_mac_missing_eop_err_cnt {
      type oc-yang:counter64;
      description
        "MAC TX missing eop errors count.";
    }
    leaf counter_slice5_ifg_mac_pool82_port_mib_counter7_tx_mac_missing_eop_err_cnt {
      type oc-yang:counter64;
      description
        "MAC TX missing eop errors count.";
    }
    leaf counter_slice5_ifg_mac_pool83_port_mib_counter0_tx_mac_missing_eop_err_cnt {
      type oc-yang:counter64;
      description
        "MAC TX missing eop errors count.";
    }
    leaf counter_slice5_ifg_mac_pool83_port_mib_counter1_tx_mac_missing_eop_err_cnt {
      type oc-yang:counter64;
      description
        "MAC TX missing eop errors count.";
    }
    leaf counter_slice5_ifg_mac_pool83_port_mib_counter2_tx_mac_missing_eop_err_cnt {
      type oc-yang:counter64;
      description
        "MAC TX missing eop errors count.";
    }
    leaf counter_slice5_ifg_mac_pool83_port_mib_counter3_tx_mac_missing_eop_err_cnt {
      type oc-yang:counter64;
      description
        "MAC TX missing eop errors count.";
    }
    leaf counter_slice5_ifg_mac_pool83_port_mib_counter4_tx_mac_missing_eop_err_cnt {
      type oc-yang:counter64;
      description
        "MAC TX missing eop errors count.";
    }
    leaf counter_slice5_ifg_mac_pool83_port_mib_counter5_tx_mac_missing_eop_err_cnt {
      type oc-yang:counter64;
      description
        "MAC TX missing eop errors count.";
    }
    leaf counter_slice5_ifg_mac_pool83_port_mib_counter6_tx_mac_missing_eop_err_cnt {
      type oc-yang:counter64;
      description
        "MAC TX missing eop errors count.";
    }
    leaf counter_slice5_ifg_mac_pool83_port_mib_counter7_tx_mac_missing_eop_err_cnt {
      type oc-yang:counter64;
      description
        "MAC TX missing eop errors count.";
    }
    leaf counter_slice5_ifg_mac_pool84_port_mib_counter0_tx_mac_missing_eop_err_cnt {
      type oc-yang:counter64;
      description
        "MAC TX missing eop errors count.";
    }
    leaf counter_slice5_ifg_mac_pool84_port_mib_counter1_tx_mac_missing_eop_err_cnt {
      type oc-yang:counter64;
      description
        "MAC TX missing eop errors count.";
    }
    leaf counter_slice5_ifg_mac_pool84_port_mib_counter2_tx_mac_missing_eop_err_cnt {
      type oc-yang:counter64;
      description
        "MAC TX missing eop errors count.";
    }
    leaf counter_slice5_ifg_mac_pool84_port_mib_counter3_tx_mac_missing_eop_err_cnt {
      type oc-yang:counter64;
      description
        "MAC TX missing eop errors count.";
    }
    leaf counter_slice5_ifg_mac_pool84_port_mib_counter4_tx_mac_missing_eop_err_cnt {
      type oc-yang:counter64;
      description
        "MAC TX missing eop errors count.";
    }
    leaf counter_slice5_ifg_mac_pool84_port_mib_counter5_tx_mac_missing_eop_err_cnt {
      type oc-yang:counter64;
      description
        "MAC TX missing eop errors count.";
    }
    leaf counter_slice5_ifg_mac_pool84_port_mib_counter6_tx_mac_missing_eop_err_cnt {
      type oc-yang:counter64;
      description
        "MAC TX missing eop errors count.";
    }
    leaf counter_slice5_ifg_mac_pool84_port_mib_counter7_tx_mac_missing_eop_err_cnt {
      type oc-yang:counter64;
      description
        "MAC TX missing eop errors count.";
    }
    leaf counter_slice5_ifg_mac_pool85_port_mib_counter0_tx_mac_missing_eop_err_cnt {
      type oc-yang:counter64;
      description
        "MAC TX missing eop errors count.";
    }
    leaf counter_slice5_ifg_mac_pool85_port_mib_counter1_tx_mac_missing_eop_err_cnt {
      type oc-yang:counter64;
      description
        "MAC TX missing eop errors count.";
    }
    leaf counter_slice5_ifg_mac_pool85_port_mib_counter2_tx_mac_missing_eop_err_cnt {
      type oc-yang:counter64;
      description
        "MAC TX missing eop errors count.";
    }
    leaf counter_slice5_ifg_mac_pool85_port_mib_counter3_tx_mac_missing_eop_err_cnt {
      type oc-yang:counter64;
      description
        "MAC TX missing eop errors count.";
    }
    leaf counter_slice5_ifg_mac_pool85_port_mib_counter4_tx_mac_missing_eop_err_cnt {
      type oc-yang:counter64;
      description
        "MAC TX missing eop errors count.";
    }
    leaf counter_slice5_ifg_mac_pool85_port_mib_counter5_tx_mac_missing_eop_err_cnt {
      type oc-yang:counter64;
      description
        "MAC TX missing eop errors count.";
    }
    leaf counter_slice5_ifg_mac_pool85_port_mib_counter6_tx_mac_missing_eop_err_cnt {
      type oc-yang:counter64;
      description
        "MAC TX missing eop errors count.";
    }
    leaf counter_slice5_ifg_mac_pool85_port_mib_counter7_tx_mac_missing_eop_err_cnt {
      type oc-yang:counter64;
      description
        "MAC TX missing eop errors count.";
    }
    leaf counter_slice5_ifg_mac_pool86_port_mib_counter0_tx_mac_missing_eop_err_cnt {
      type oc-yang:counter64;
      description
        "MAC TX missing eop errors count.";
    }
    leaf counter_slice5_ifg_mac_pool86_port_mib_counter1_tx_mac_missing_eop_err_cnt {
      type oc-yang:counter64;
      description
        "MAC TX missing eop errors count.";
    }
    leaf counter_slice5_ifg_mac_pool86_port_mib_counter2_tx_mac_missing_eop_err_cnt {
      type oc-yang:counter64;
      description
        "MAC TX missing eop errors count.";
    }
    leaf counter_slice5_ifg_mac_pool86_port_mib_counter3_tx_mac_missing_eop_err_cnt {
      type oc-yang:counter64;
      description
        "MAC TX missing eop errors count.";
    }
    leaf counter_slice5_ifg_mac_pool86_port_mib_counter4_tx_mac_missing_eop_err_cnt {
      type oc-yang:counter64;
      description
        "MAC TX missing eop errors count.";
    }
    leaf counter_slice5_ifg_mac_pool86_port_mib_counter5_tx_mac_missing_eop_err_cnt {
      type oc-yang:counter64;
      description
        "MAC TX missing eop errors count.";
    }
    leaf counter_slice5_ifg_mac_pool86_port_mib_counter6_tx_mac_missing_eop_err_cnt {
      type oc-yang:counter64;
      description
        "MAC TX missing eop errors count.";
    }
    leaf counter_slice5_ifg_mac_pool86_port_mib_counter7_tx_mac_missing_eop_err_cnt {
      type oc-yang:counter64;
      description
        "MAC TX missing eop errors count.";
    }
    leaf counter_slice5_ifg_mac_pool87_port_mib_counter0_tx_mac_missing_eop_err_cnt {
      type oc-yang:counter64;
      description
        "MAC TX missing eop errors count.";
    }
    leaf counter_slice5_ifg_mac_pool87_port_mib_counter1_tx_mac_missing_eop_err_cnt {
      type oc-yang:counter64;
      description
        "MAC TX missing eop errors count.";
    }
    leaf counter_slice5_ifg_mac_pool87_port_mib_counter2_tx_mac_missing_eop_err_cnt {
      type oc-yang:counter64;
      description
        "MAC TX missing eop errors count.";
    }
    leaf counter_slice5_ifg_mac_pool87_port_mib_counter3_tx_mac_missing_eop_err_cnt {
      type oc-yang:counter64;
      description
        "MAC TX missing eop errors count.";
    }
    leaf counter_slice5_ifg_mac_pool87_port_mib_counter4_tx_mac_missing_eop_err_cnt {
      type oc-yang:counter64;
      description
        "MAC TX missing eop errors count.";
    }
    leaf counter_slice5_ifg_mac_pool87_port_mib_counter5_tx_mac_missing_eop_err_cnt {
      type oc-yang:counter64;
      description
        "MAC TX missing eop errors count.";
    }
    leaf counter_slice5_ifg_mac_pool87_port_mib_counter6_tx_mac_missing_eop_err_cnt {
      type oc-yang:counter64;
      description
        "MAC TX missing eop errors count.";
    }
    leaf counter_slice5_ifg_mac_pool87_port_mib_counter7_tx_mac_missing_eop_err_cnt {
      type oc-yang:counter64;
      description
        "MAC TX missing eop errors count.";
    }
    leaf counter_slice6_ifg_mac_pool80_port_mib_counter0_tx_mac_missing_eop_err_cnt {
      type oc-yang:counter64;
      description
        "MAC TX missing eop errors count.";
    }
    leaf counter_slice6_ifg_mac_pool80_port_mib_counter1_tx_mac_missing_eop_err_cnt {
      type oc-yang:counter64;
      description
        "MAC TX missing eop errors count.";
    }
    leaf counter_slice6_ifg_mac_pool80_port_mib_counter2_tx_mac_missing_eop_err_cnt {
      type oc-yang:counter64;
      description
        "MAC TX missing eop errors count.";
    }
    leaf counter_slice6_ifg_mac_pool80_port_mib_counter3_tx_mac_missing_eop_err_cnt {
      type oc-yang:counter64;
      description
        "MAC TX missing eop errors count.";
    }
    leaf counter_slice6_ifg_mac_pool80_port_mib_counter4_tx_mac_missing_eop_err_cnt {
      type oc-yang:counter64;
      description
        "MAC TX missing eop errors count.";
    }
    leaf counter_slice6_ifg_mac_pool80_port_mib_counter5_tx_mac_missing_eop_err_cnt {
      type oc-yang:counter64;
      description
        "MAC TX missing eop errors count.";
    }
    leaf counter_slice6_ifg_mac_pool80_port_mib_counter6_tx_mac_missing_eop_err_cnt {
      type oc-yang:counter64;
      description
        "MAC TX missing eop errors count.";
    }
    leaf counter_slice6_ifg_mac_pool80_port_mib_counter7_tx_mac_missing_eop_err_cnt {
      type oc-yang:counter64;
      description
        "MAC TX missing eop errors count.";
    }
    leaf counter_slice6_ifg_mac_pool81_port_mib_counter0_tx_mac_missing_eop_err_cnt {
      type oc-yang:counter64;
      description
        "MAC TX missing eop errors count.";
    }
    leaf counter_slice6_ifg_mac_pool81_port_mib_counter1_tx_mac_missing_eop_err_cnt {
      type oc-yang:counter64;
      description
        "MAC TX missing eop errors count.";
    }
    leaf counter_slice6_ifg_mac_pool81_port_mib_counter2_tx_mac_missing_eop_err_cnt {
      type oc-yang:counter64;
      description
        "MAC TX missing eop errors count.";
    }
    leaf counter_slice6_ifg_mac_pool81_port_mib_counter3_tx_mac_missing_eop_err_cnt {
      type oc-yang:counter64;
      description
        "MAC TX missing eop errors count.";
    }
    leaf counter_slice6_ifg_mac_pool81_port_mib_counter4_tx_mac_missing_eop_err_cnt {
      type oc-yang:counter64;
      description
        "MAC TX missing eop errors count.";
    }
    leaf counter_slice6_ifg_mac_pool81_port_mib_counter5_tx_mac_missing_eop_err_cnt {
      type oc-yang:counter64;
      description
        "MAC TX missing eop errors count.";
    }
    leaf counter_slice6_ifg_mac_pool81_port_mib_counter6_tx_mac_missing_eop_err_cnt {
      type oc-yang:counter64;
      description
        "MAC TX missing eop errors count.";
    }
    leaf counter_slice6_ifg_mac_pool81_port_mib_counter7_tx_mac_missing_eop_err_cnt {
      type oc-yang:counter64;
      description
        "MAC TX missing eop errors count.";
    }
    leaf counter_slice6_ifg_mac_pool82_port_mib_counter0_tx_mac_missing_eop_err_cnt {
      type oc-yang:counter64;
      description
        "MAC TX missing eop errors count.";
    }
    leaf counter_slice6_ifg_mac_pool82_port_mib_counter1_tx_mac_missing_eop_err_cnt {
      type oc-yang:counter64;
      description
        "MAC TX missing eop errors count.";
    }
    leaf counter_slice6_ifg_mac_pool82_port_mib_counter2_tx_mac_missing_eop_err_cnt {
      type oc-yang:counter64;
      description
        "MAC TX missing eop errors count.";
    }
    leaf counter_slice6_ifg_mac_pool82_port_mib_counter3_tx_mac_missing_eop_err_cnt {
      type oc-yang:counter64;
      description
        "MAC TX missing eop errors count.";
    }
    leaf counter_slice6_ifg_mac_pool82_port_mib_counter4_tx_mac_missing_eop_err_cnt {
      type oc-yang:counter64;
      description
        "MAC TX missing eop errors count.";
    }
    leaf counter_slice6_ifg_mac_pool82_port_mib_counter5_tx_mac_missing_eop_err_cnt {
      type oc-yang:counter64;
      description
        "MAC TX missing eop errors count.";
    }
    leaf counter_slice6_ifg_mac_pool82_port_mib_counter6_tx_mac_missing_eop_err_cnt {
      type oc-yang:counter64;
      description
        "MAC TX missing eop errors count.";
    }
    leaf counter_slice6_ifg_mac_pool82_port_mib_counter7_tx_mac_missing_eop_err_cnt {
      type oc-yang:counter64;
      description
        "MAC TX missing eop errors count.";
    }
    leaf counter_slice6_ifg_mac_pool83_port_mib_counter0_tx_mac_missing_eop_err_cnt {
      type oc-yang:counter64;
      description
        "MAC TX missing eop errors count.";
    }
    leaf counter_slice6_ifg_mac_pool83_port_mib_counter1_tx_mac_missing_eop_err_cnt {
      type oc-yang:counter64;
      description
        "MAC TX missing eop errors count.";
    }
    leaf counter_slice6_ifg_mac_pool83_port_mib_counter2_tx_mac_missing_eop_err_cnt {
      type oc-yang:counter64;
      description
        "MAC TX missing eop errors count.";
    }
    leaf counter_slice6_ifg_mac_pool83_port_mib_counter3_tx_mac_missing_eop_err_cnt {
      type oc-yang:counter64;
      description
        "MAC TX missing eop errors count.";
    }
    leaf counter_slice6_ifg_mac_pool83_port_mib_counter4_tx_mac_missing_eop_err_cnt {
      type oc-yang:counter64;
      description
        "MAC TX missing eop errors count.";
    }
    leaf counter_slice6_ifg_mac_pool83_port_mib_counter5_tx_mac_missing_eop_err_cnt {
      type oc-yang:counter64;
      description
        "MAC TX missing eop errors count.";
    }
    leaf counter_slice6_ifg_mac_pool83_port_mib_counter6_tx_mac_missing_eop_err_cnt {
      type oc-yang:counter64;
      description
        "MAC TX missing eop errors count.";
    }
    leaf counter_slice6_ifg_mac_pool83_port_mib_counter7_tx_mac_missing_eop_err_cnt {
      type oc-yang:counter64;
      description
        "MAC TX missing eop errors count.";
    }
    leaf counter_slice6_ifg_mac_pool84_port_mib_counter0_tx_mac_missing_eop_err_cnt {
      type oc-yang:counter64;
      description
        "MAC TX missing eop errors count.";
    }
    leaf counter_slice6_ifg_mac_pool84_port_mib_counter1_tx_mac_missing_eop_err_cnt {
      type oc-yang:counter64;
      description
        "MAC TX missing eop errors count.";
    }
    leaf counter_slice6_ifg_mac_pool84_port_mib_counter2_tx_mac_missing_eop_err_cnt {
      type oc-yang:counter64;
      description
        "MAC TX missing eop errors count.";
    }
    leaf counter_slice6_ifg_mac_pool84_port_mib_counter3_tx_mac_missing_eop_err_cnt {
      type oc-yang:counter64;
      description
        "MAC TX missing eop errors count.";
    }
    leaf counter_slice6_ifg_mac_pool84_port_mib_counter4_tx_mac_missing_eop_err_cnt {
      type oc-yang:counter64;
      description
        "MAC TX missing eop errors count.";
    }
    leaf counter_slice6_ifg_mac_pool84_port_mib_counter5_tx_mac_missing_eop_err_cnt {
      type oc-yang:counter64;
      description
        "MAC TX missing eop errors count.";
    }
    leaf counter_slice6_ifg_mac_pool84_port_mib_counter6_tx_mac_missing_eop_err_cnt {
      type oc-yang:counter64;
      description
        "MAC TX missing eop errors count.";
    }
    leaf counter_slice6_ifg_mac_pool84_port_mib_counter7_tx_mac_missing_eop_err_cnt {
      type oc-yang:counter64;
      description
        "MAC TX missing eop errors count.";
    }
    leaf counter_slice6_ifg_mac_pool85_port_mib_counter0_tx_mac_missing_eop_err_cnt {
      type oc-yang:counter64;
      description
        "MAC TX missing eop errors count.";
    }
    leaf counter_slice6_ifg_mac_pool85_port_mib_counter1_tx_mac_missing_eop_err_cnt {
      type oc-yang:counter64;
      description
        "MAC TX missing eop errors count.";
    }
    leaf counter_slice6_ifg_mac_pool85_port_mib_counter2_tx_mac_missing_eop_err_cnt {
      type oc-yang:counter64;
      description
        "MAC TX missing eop errors count.";
    }
    leaf counter_slice6_ifg_mac_pool85_port_mib_counter3_tx_mac_missing_eop_err_cnt {
      type oc-yang:counter64;
      description
        "MAC TX missing eop errors count.";
    }
    leaf counter_slice6_ifg_mac_pool85_port_mib_counter4_tx_mac_missing_eop_err_cnt {
      type oc-yang:counter64;
      description
        "MAC TX missing eop errors count.";
    }
    leaf counter_slice6_ifg_mac_pool85_port_mib_counter5_tx_mac_missing_eop_err_cnt {
      type oc-yang:counter64;
      description
        "MAC TX missing eop errors count.";
    }
    leaf counter_slice6_ifg_mac_pool85_port_mib_counter6_tx_mac_missing_eop_err_cnt {
      type oc-yang:counter64;
      description
        "MAC TX missing eop errors count.";
    }
    leaf counter_slice6_ifg_mac_pool85_port_mib_counter7_tx_mac_missing_eop_err_cnt {
      type oc-yang:counter64;
      description
        "MAC TX missing eop errors count.";
    }
    leaf counter_slice6_ifg_mac_pool86_port_mib_counter0_tx_mac_missing_eop_err_cnt {
      type oc-yang:counter64;
      description
        "MAC TX missing eop errors count.";
    }
    leaf counter_slice6_ifg_mac_pool86_port_mib_counter1_tx_mac_missing_eop_err_cnt {
      type oc-yang:counter64;
      description
        "MAC TX missing eop errors count.";
    }
    leaf counter_slice6_ifg_mac_pool86_port_mib_counter2_tx_mac_missing_eop_err_cnt {
      type oc-yang:counter64;
      description
        "MAC TX missing eop errors count.";
    }
    leaf counter_slice6_ifg_mac_pool86_port_mib_counter3_tx_mac_missing_eop_err_cnt {
      type oc-yang:counter64;
      description
        "MAC TX missing eop errors count.";
    }
    leaf counter_slice6_ifg_mac_pool86_port_mib_counter4_tx_mac_missing_eop_err_cnt {
      type oc-yang:counter64;
      description
        "MAC TX missing eop errors count.";
    }
    leaf counter_slice6_ifg_mac_pool86_port_mib_counter5_tx_mac_missing_eop_err_cnt {
      type oc-yang:counter64;
      description
        "MAC TX missing eop errors count.";
    }
    leaf counter_slice6_ifg_mac_pool86_port_mib_counter6_tx_mac_missing_eop_err_cnt {
      type oc-yang:counter64;
      description
        "MAC TX missing eop errors count.";
    }
    leaf counter_slice6_ifg_mac_pool86_port_mib_counter7_tx_mac_missing_eop_err_cnt {
      type oc-yang:counter64;
      description
        "MAC TX missing eop errors count.";
    }
    leaf counter_slice6_ifg_mac_pool87_port_mib_counter0_tx_mac_missing_eop_err_cnt {
      type oc-yang:counter64;
      description
        "MAC TX missing eop errors count.";
    }
    leaf counter_slice6_ifg_mac_pool87_port_mib_counter1_tx_mac_missing_eop_err_cnt {
      type oc-yang:counter64;
      description
        "MAC TX missing eop errors count.";
    }
    leaf counter_slice6_ifg_mac_pool87_port_mib_counter2_tx_mac_missing_eop_err_cnt {
      type oc-yang:counter64;
      description
        "MAC TX missing eop errors count.";
    }
    leaf counter_slice6_ifg_mac_pool87_port_mib_counter3_tx_mac_missing_eop_err_cnt {
      type oc-yang:counter64;
      description
        "MAC TX missing eop errors count.";
    }
    leaf counter_slice6_ifg_mac_pool87_port_mib_counter4_tx_mac_missing_eop_err_cnt {
      type oc-yang:counter64;
      description
        "MAC TX missing eop errors count.";
    }
    leaf counter_slice6_ifg_mac_pool87_port_mib_counter5_tx_mac_missing_eop_err_cnt {
      type oc-yang:counter64;
      description
        "MAC TX missing eop errors count.";
    }
    leaf counter_slice6_ifg_mac_pool87_port_mib_counter6_tx_mac_missing_eop_err_cnt {
      type oc-yang:counter64;
      description
        "MAC TX missing eop errors count.";
    }
    leaf counter_slice6_ifg_mac_pool87_port_mib_counter7_tx_mac_missing_eop_err_cnt {
      type oc-yang:counter64;
      description
        "MAC TX missing eop errors count.";
    }
    leaf counter_slice7_ifg_mac_pool80_port_mib_counter0_tx_mac_missing_eop_err_cnt {
      type oc-yang:counter64;
      description
        "MAC TX missing eop errors count.";
    }
    leaf counter_slice7_ifg_mac_pool80_port_mib_counter1_tx_mac_missing_eop_err_cnt {
      type oc-yang:counter64;
      description
        "MAC TX missing eop errors count.";
    }
    leaf counter_slice7_ifg_mac_pool80_port_mib_counter2_tx_mac_missing_eop_err_cnt {
      type oc-yang:counter64;
      description
        "MAC TX missing eop errors count.";
    }
    leaf counter_slice7_ifg_mac_pool80_port_mib_counter3_tx_mac_missing_eop_err_cnt {
      type oc-yang:counter64;
      description
        "MAC TX missing eop errors count.";
    }
    leaf counter_slice7_ifg_mac_pool80_port_mib_counter4_tx_mac_missing_eop_err_cnt {
      type oc-yang:counter64;
      description
        "MAC TX missing eop errors count.";
    }
    leaf counter_slice7_ifg_mac_pool80_port_mib_counter5_tx_mac_missing_eop_err_cnt {
      type oc-yang:counter64;
      description
        "MAC TX missing eop errors count.";
    }
    leaf counter_slice7_ifg_mac_pool80_port_mib_counter6_tx_mac_missing_eop_err_cnt {
      type oc-yang:counter64;
      description
        "MAC TX missing eop errors count.";
    }
    leaf counter_slice7_ifg_mac_pool80_port_mib_counter7_tx_mac_missing_eop_err_cnt {
      type oc-yang:counter64;
      description
        "MAC TX missing eop errors count.";
    }
    leaf counter_slice7_ifg_mac_pool81_port_mib_counter0_tx_mac_missing_eop_err_cnt {
      type oc-yang:counter64;
      description
        "MAC TX missing eop errors count.";
    }
    leaf counter_slice7_ifg_mac_pool81_port_mib_counter1_tx_mac_missing_eop_err_cnt {
      type oc-yang:counter64;
      description
        "MAC TX missing eop errors count.";
    }
    leaf counter_slice7_ifg_mac_pool81_port_mib_counter2_tx_mac_missing_eop_err_cnt {
      type oc-yang:counter64;
      description
        "MAC TX missing eop errors count.";
    }
    leaf counter_slice7_ifg_mac_pool81_port_mib_counter3_tx_mac_missing_eop_err_cnt {
      type oc-yang:counter64;
      description
        "MAC TX missing eop errors count.";
    }
    leaf counter_slice7_ifg_mac_pool81_port_mib_counter4_tx_mac_missing_eop_err_cnt {
      type oc-yang:counter64;
      description
        "MAC TX missing eop errors count.";
    }
    leaf counter_slice7_ifg_mac_pool81_port_mib_counter5_tx_mac_missing_eop_err_cnt {
      type oc-yang:counter64;
      description
        "MAC TX missing eop errors count.";
    }
    leaf counter_slice7_ifg_mac_pool81_port_mib_counter6_tx_mac_missing_eop_err_cnt {
      type oc-yang:counter64;
      description
        "MAC TX missing eop errors count.";
    }
    leaf counter_slice7_ifg_mac_pool81_port_mib_counter7_tx_mac_missing_eop_err_cnt {
      type oc-yang:counter64;
      description
        "MAC TX missing eop errors count.";
    }
    leaf counter_slice7_ifg_mac_pool82_port_mib_counter0_tx_mac_missing_eop_err_cnt {
      type oc-yang:counter64;
      description
        "MAC TX missing eop errors count.";
    }
    leaf counter_slice7_ifg_mac_pool82_port_mib_counter1_tx_mac_missing_eop_err_cnt {
      type oc-yang:counter64;
      description
        "MAC TX missing eop errors count.";
    }
    leaf counter_slice7_ifg_mac_pool82_port_mib_counter2_tx_mac_missing_eop_err_cnt {
      type oc-yang:counter64;
      description
        "MAC TX missing eop errors count.";
    }
    leaf counter_slice7_ifg_mac_pool82_port_mib_counter3_tx_mac_missing_eop_err_cnt {
      type oc-yang:counter64;
      description
        "MAC TX missing eop errors count.";
    }
    leaf counter_slice7_ifg_mac_pool82_port_mib_counter4_tx_mac_missing_eop_err_cnt {
      type oc-yang:counter64;
      description
        "MAC TX missing eop errors count.";
    }
    leaf counter_slice7_ifg_mac_pool82_port_mib_counter5_tx_mac_missing_eop_err_cnt {
      type oc-yang:counter64;
      description
        "MAC TX missing eop errors count.";
    }
    leaf counter_slice7_ifg_mac_pool82_port_mib_counter6_tx_mac_missing_eop_err_cnt {
      type oc-yang:counter64;
      description
        "MAC TX missing eop errors count.";
    }
    leaf counter_slice7_ifg_mac_pool82_port_mib_counter7_tx_mac_missing_eop_err_cnt {
      type oc-yang:counter64;
      description
        "MAC TX missing eop errors count.";
    }
    leaf counter_slice7_ifg_mac_pool83_port_mib_counter0_tx_mac_missing_eop_err_cnt {
      type oc-yang:counter64;
      description
        "MAC TX missing eop errors count.";
    }
    leaf counter_slice7_ifg_mac_pool83_port_mib_counter1_tx_mac_missing_eop_err_cnt {
      type oc-yang:counter64;
      description
        "MAC TX missing eop errors count.";
    }
    leaf counter_slice7_ifg_mac_pool83_port_mib_counter2_tx_mac_missing_eop_err_cnt {
      type oc-yang:counter64;
      description
        "MAC TX missing eop errors count.";
    }
    leaf counter_slice7_ifg_mac_pool83_port_mib_counter3_tx_mac_missing_eop_err_cnt {
      type oc-yang:counter64;
      description
        "MAC TX missing eop errors count.";
    }
    leaf counter_slice7_ifg_mac_pool83_port_mib_counter4_tx_mac_missing_eop_err_cnt {
      type oc-yang:counter64;
      description
        "MAC TX missing eop errors count.";
    }
    leaf counter_slice7_ifg_mac_pool83_port_mib_counter5_tx_mac_missing_eop_err_cnt {
      type oc-yang:counter64;
      description
        "MAC TX missing eop errors count.";
    }
    leaf counter_slice7_ifg_mac_pool83_port_mib_counter6_tx_mac_missing_eop_err_cnt {
      type oc-yang:counter64;
      description
        "MAC TX missing eop errors count.";
    }
    leaf counter_slice7_ifg_mac_pool83_port_mib_counter7_tx_mac_missing_eop_err_cnt {
      type oc-yang:counter64;
      description
        "MAC TX missing eop errors count.";
    }
    leaf counter_slice7_ifg_mac_pool84_port_mib_counter0_tx_mac_missing_eop_err_cnt {
      type oc-yang:counter64;
      description
        "MAC TX missing eop errors count.";
    }
    leaf counter_slice7_ifg_mac_pool84_port_mib_counter1_tx_mac_missing_eop_err_cnt {
      type oc-yang:counter64;
      description
        "MAC TX missing eop errors count.";
    }
    leaf counter_slice7_ifg_mac_pool84_port_mib_counter2_tx_mac_missing_eop_err_cnt {
      type oc-yang:counter64;
      description
        "MAC TX missing eop errors count.";
    }
    leaf counter_slice7_ifg_mac_pool84_port_mib_counter3_tx_mac_missing_eop_err_cnt {
      type oc-yang:counter64;
      description
        "MAC TX missing eop errors count.";
    }
    leaf counter_slice7_ifg_mac_pool84_port_mib_counter4_tx_mac_missing_eop_err_cnt {
      type oc-yang:counter64;
      description
        "MAC TX missing eop errors count.";
    }
    leaf counter_slice7_ifg_mac_pool84_port_mib_counter5_tx_mac_missing_eop_err_cnt {
      type oc-yang:counter64;
      description
        "MAC TX missing eop errors count.";
    }
    leaf counter_slice7_ifg_mac_pool84_port_mib_counter6_tx_mac_missing_eop_err_cnt {
      type oc-yang:counter64;
      description
        "MAC TX missing eop errors count.";
    }
    leaf counter_slice7_ifg_mac_pool84_port_mib_counter7_tx_mac_missing_eop_err_cnt {
      type oc-yang:counter64;
      description
        "MAC TX missing eop errors count.";
    }
    leaf counter_slice7_ifg_mac_pool85_port_mib_counter0_tx_mac_missing_eop_err_cnt {
      type oc-yang:counter64;
      description
        "MAC TX missing eop errors count.";
    }
    leaf counter_slice7_ifg_mac_pool85_port_mib_counter1_tx_mac_missing_eop_err_cnt {
      type oc-yang:counter64;
      description
        "MAC TX missing eop errors count.";
    }
    leaf counter_slice7_ifg_mac_pool85_port_mib_counter2_tx_mac_missing_eop_err_cnt {
      type oc-yang:counter64;
      description
        "MAC TX missing eop errors count.";
    }
    leaf counter_slice7_ifg_mac_pool85_port_mib_counter3_tx_mac_missing_eop_err_cnt {
      type oc-yang:counter64;
      description
        "MAC TX missing eop errors count.";
    }
    leaf counter_slice7_ifg_mac_pool85_port_mib_counter4_tx_mac_missing_eop_err_cnt {
      type oc-yang:counter64;
      description
        "MAC TX missing eop errors count.";
    }
    leaf counter_slice7_ifg_mac_pool85_port_mib_counter5_tx_mac_missing_eop_err_cnt {
      type oc-yang:counter64;
      description
        "MAC TX missing eop errors count.";
    }
    leaf counter_slice7_ifg_mac_pool85_port_mib_counter6_tx_mac_missing_eop_err_cnt {
      type oc-yang:counter64;
      description
        "MAC TX missing eop errors count.";
    }
    leaf counter_slice7_ifg_mac_pool85_port_mib_counter7_tx_mac_missing_eop_err_cnt {
      type oc-yang:counter64;
      description
        "MAC TX missing eop errors count.";
    }
    leaf counter_slice7_ifg_mac_pool86_port_mib_counter0_tx_mac_missing_eop_err_cnt {
      type oc-yang:counter64;
      description
        "MAC TX missing eop errors count.";
    }
    leaf counter_slice7_ifg_mac_pool86_port_mib_counter1_tx_mac_missing_eop_err_cnt {
      type oc-yang:counter64;
      description
        "MAC TX missing eop errors count.";
    }
    leaf counter_slice7_ifg_mac_pool86_port_mib_counter2_tx_mac_missing_eop_err_cnt {
      type oc-yang:counter64;
      description
        "MAC TX missing eop errors count.";
    }
    leaf counter_slice7_ifg_mac_pool86_port_mib_counter3_tx_mac_missing_eop_err_cnt {
      type oc-yang:counter64;
      description
        "MAC TX missing eop errors count.";
    }
    leaf counter_slice7_ifg_mac_pool86_port_mib_counter4_tx_mac_missing_eop_err_cnt {
      type oc-yang:counter64;
      description
        "MAC TX missing eop errors count.";
    }
    leaf counter_slice7_ifg_mac_pool86_port_mib_counter5_tx_mac_missing_eop_err_cnt {
      type oc-yang:counter64;
      description
        "MAC TX missing eop errors count.";
    }
    leaf counter_slice7_ifg_mac_pool86_port_mib_counter6_tx_mac_missing_eop_err_cnt {
      type oc-yang:counter64;
      description
        "MAC TX missing eop errors count.";
    }
    leaf counter_slice7_ifg_mac_pool86_port_mib_counter7_tx_mac_missing_eop_err_cnt {
      type oc-yang:counter64;
      description
        "MAC TX missing eop errors count.";
    }
    leaf counter_slice7_ifg_mac_pool87_port_mib_counter0_tx_mac_missing_eop_err_cnt {
      type oc-yang:counter64;
      description
        "MAC TX missing eop errors count.";
    }
    leaf counter_slice7_ifg_mac_pool87_port_mib_counter1_tx_mac_missing_eop_err_cnt {
      type oc-yang:counter64;
      description
        "MAC TX missing eop errors count.";
    }
    leaf counter_slice7_ifg_mac_pool87_port_mib_counter2_tx_mac_missing_eop_err_cnt {
      type oc-yang:counter64;
      description
        "MAC TX missing eop errors count.";
    }
    leaf counter_slice7_ifg_mac_pool87_port_mib_counter3_tx_mac_missing_eop_err_cnt {
      type oc-yang:counter64;
      description
        "MAC TX missing eop errors count.";
    }
    leaf counter_slice7_ifg_mac_pool87_port_mib_counter4_tx_mac_missing_eop_err_cnt {
      type oc-yang:counter64;
      description
        "MAC TX missing eop errors count.";
    }
    leaf counter_slice7_ifg_mac_pool87_port_mib_counter5_tx_mac_missing_eop_err_cnt {
      type oc-yang:counter64;
      description
        "MAC TX missing eop errors count.";
    }
    leaf counter_slice7_ifg_mac_pool87_port_mib_counter6_tx_mac_missing_eop_err_cnt {
      type oc-yang:counter64;
      description
        "MAC TX missing eop errors count.";
    }
    leaf counter_slice7_ifg_mac_pool87_port_mib_counter7_tx_mac_missing_eop_err_cnt {
      type oc-yang:counter64;
      description
        "MAC TX missing eop errors count.";
    }
    leaf counter_slice8_ifg_mac_pool80_port_mib_counter0_tx_mac_missing_eop_err_cnt {
      type oc-yang:counter64;
      description
        "MAC TX missing eop errors count.";
    }
    leaf counter_slice8_ifg_mac_pool80_port_mib_counter1_tx_mac_missing_eop_err_cnt {
      type oc-yang:counter64;
      description
        "MAC TX missing eop errors count.";
    }
    leaf counter_slice8_ifg_mac_pool80_port_mib_counter2_tx_mac_missing_eop_err_cnt {
      type oc-yang:counter64;
      description
        "MAC TX missing eop errors count.";
    }
    leaf counter_slice8_ifg_mac_pool80_port_mib_counter3_tx_mac_missing_eop_err_cnt {
      type oc-yang:counter64;
      description
        "MAC TX missing eop errors count.";
    }
    leaf counter_slice8_ifg_mac_pool80_port_mib_counter4_tx_mac_missing_eop_err_cnt {
      type oc-yang:counter64;
      description
        "MAC TX missing eop errors count.";
    }
    leaf counter_slice8_ifg_mac_pool80_port_mib_counter5_tx_mac_missing_eop_err_cnt {
      type oc-yang:counter64;
      description
        "MAC TX missing eop errors count.";
    }
    leaf counter_slice8_ifg_mac_pool80_port_mib_counter6_tx_mac_missing_eop_err_cnt {
      type oc-yang:counter64;
      description
        "MAC TX missing eop errors count.";
    }
    leaf counter_slice8_ifg_mac_pool80_port_mib_counter7_tx_mac_missing_eop_err_cnt {
      type oc-yang:counter64;
      description
        "MAC TX missing eop errors count.";
    }
    leaf counter_slice8_ifg_mac_pool81_port_mib_counter0_tx_mac_missing_eop_err_cnt {
      type oc-yang:counter64;
      description
        "MAC TX missing eop errors count.";
    }
    leaf counter_slice8_ifg_mac_pool81_port_mib_counter1_tx_mac_missing_eop_err_cnt {
      type oc-yang:counter64;
      description
        "MAC TX missing eop errors count.";
    }
    leaf counter_slice8_ifg_mac_pool81_port_mib_counter2_tx_mac_missing_eop_err_cnt {
      type oc-yang:counter64;
      description
        "MAC TX missing eop errors count.";
    }
    leaf counter_slice8_ifg_mac_pool81_port_mib_counter3_tx_mac_missing_eop_err_cnt {
      type oc-yang:counter64;
      description
        "MAC TX missing eop errors count.";
    }
    leaf counter_slice8_ifg_mac_pool81_port_mib_counter4_tx_mac_missing_eop_err_cnt {
      type oc-yang:counter64;
      description
        "MAC TX missing eop errors count.";
    }
    leaf counter_slice8_ifg_mac_pool81_port_mib_counter5_tx_mac_missing_eop_err_cnt {
      type oc-yang:counter64;
      description
        "MAC TX missing eop errors count.";
    }
    leaf counter_slice8_ifg_mac_pool81_port_mib_counter6_tx_mac_missing_eop_err_cnt {
      type oc-yang:counter64;
      description
        "MAC TX missing eop errors count.";
    }
    leaf counter_slice8_ifg_mac_pool81_port_mib_counter7_tx_mac_missing_eop_err_cnt {
      type oc-yang:counter64;
      description
        "MAC TX missing eop errors count.";
    }
    leaf counter_slice8_ifg_mac_pool82_port_mib_counter0_tx_mac_missing_eop_err_cnt {
      type oc-yang:counter64;
      description
        "MAC TX missing eop errors count.";
    }
    leaf counter_slice8_ifg_mac_pool82_port_mib_counter1_tx_mac_missing_eop_err_cnt {
      type oc-yang:counter64;
      description
        "MAC TX missing eop errors count.";
    }
    leaf counter_slice8_ifg_mac_pool82_port_mib_counter2_tx_mac_missing_eop_err_cnt {
      type oc-yang:counter64;
      description
        "MAC TX missing eop errors count.";
    }
    leaf counter_slice8_ifg_mac_pool82_port_mib_counter3_tx_mac_missing_eop_err_cnt {
      type oc-yang:counter64;
      description
        "MAC TX missing eop errors count.";
    }
    leaf counter_slice8_ifg_mac_pool82_port_mib_counter4_tx_mac_missing_eop_err_cnt {
      type oc-yang:counter64;
      description
        "MAC TX missing eop errors count.";
    }
    leaf counter_slice8_ifg_mac_pool82_port_mib_counter5_tx_mac_missing_eop_err_cnt {
      type oc-yang:counter64;
      description
        "MAC TX missing eop errors count.";
    }
    leaf counter_slice8_ifg_mac_pool82_port_mib_counter6_tx_mac_missing_eop_err_cnt {
      type oc-yang:counter64;
      description
        "MAC TX missing eop errors count.";
    }
    leaf counter_slice8_ifg_mac_pool82_port_mib_counter7_tx_mac_missing_eop_err_cnt {
      type oc-yang:counter64;
      description
        "MAC TX missing eop errors count.";
    }
    leaf counter_slice8_ifg_mac_pool83_port_mib_counter0_tx_mac_missing_eop_err_cnt {
      type oc-yang:counter64;
      description
        "MAC TX missing eop errors count.";
    }
    leaf counter_slice8_ifg_mac_pool83_port_mib_counter1_tx_mac_missing_eop_err_cnt {
      type oc-yang:counter64;
      description
        "MAC TX missing eop errors count.";
    }
    leaf counter_slice8_ifg_mac_pool83_port_mib_counter2_tx_mac_missing_eop_err_cnt {
      type oc-yang:counter64;
      description
        "MAC TX missing eop errors count.";
    }
    leaf counter_slice8_ifg_mac_pool83_port_mib_counter3_tx_mac_missing_eop_err_cnt {
      type oc-yang:counter64;
      description
        "MAC TX missing eop errors count.";
    }
    leaf counter_slice8_ifg_mac_pool83_port_mib_counter4_tx_mac_missing_eop_err_cnt {
      type oc-yang:counter64;
      description
        "MAC TX missing eop errors count.";
    }
    leaf counter_slice8_ifg_mac_pool83_port_mib_counter5_tx_mac_missing_eop_err_cnt {
      type oc-yang:counter64;
      description
        "MAC TX missing eop errors count.";
    }
    leaf counter_slice8_ifg_mac_pool83_port_mib_counter6_tx_mac_missing_eop_err_cnt {
      type oc-yang:counter64;
      description
        "MAC TX missing eop errors count.";
    }
    leaf counter_slice8_ifg_mac_pool83_port_mib_counter7_tx_mac_missing_eop_err_cnt {
      type oc-yang:counter64;
      description
        "MAC TX missing eop errors count.";
    }
    leaf counter_slice8_ifg_mac_pool84_port_mib_counter0_tx_mac_missing_eop_err_cnt {
      type oc-yang:counter64;
      description
        "MAC TX missing eop errors count.";
    }
    leaf counter_slice8_ifg_mac_pool84_port_mib_counter1_tx_mac_missing_eop_err_cnt {
      type oc-yang:counter64;
      description
        "MAC TX missing eop errors count.";
    }
    leaf counter_slice8_ifg_mac_pool84_port_mib_counter2_tx_mac_missing_eop_err_cnt {
      type oc-yang:counter64;
      description
        "MAC TX missing eop errors count.";
    }
    leaf counter_slice8_ifg_mac_pool84_port_mib_counter3_tx_mac_missing_eop_err_cnt {
      type oc-yang:counter64;
      description
        "MAC TX missing eop errors count.";
    }
    leaf counter_slice8_ifg_mac_pool84_port_mib_counter4_tx_mac_missing_eop_err_cnt {
      type oc-yang:counter64;
      description
        "MAC TX missing eop errors count.";
    }
    leaf counter_slice8_ifg_mac_pool84_port_mib_counter5_tx_mac_missing_eop_err_cnt {
      type oc-yang:counter64;
      description
        "MAC TX missing eop errors count.";
    }
    leaf counter_slice8_ifg_mac_pool84_port_mib_counter6_tx_mac_missing_eop_err_cnt {
      type oc-yang:counter64;
      description
        "MAC TX missing eop errors count.";
    }
    leaf counter_slice8_ifg_mac_pool84_port_mib_counter7_tx_mac_missing_eop_err_cnt {
      type oc-yang:counter64;
      description
        "MAC TX missing eop errors count.";
    }
    leaf counter_slice8_ifg_mac_pool85_port_mib_counter0_tx_mac_missing_eop_err_cnt {
      type oc-yang:counter64;
      description
        "MAC TX missing eop errors count.";
    }
    leaf counter_slice8_ifg_mac_pool85_port_mib_counter1_tx_mac_missing_eop_err_cnt {
      type oc-yang:counter64;
      description
        "MAC TX missing eop errors count.";
    }
    leaf counter_slice8_ifg_mac_pool85_port_mib_counter2_tx_mac_missing_eop_err_cnt {
      type oc-yang:counter64;
      description
        "MAC TX missing eop errors count.";
    }
    leaf counter_slice8_ifg_mac_pool85_port_mib_counter3_tx_mac_missing_eop_err_cnt {
      type oc-yang:counter64;
      description
        "MAC TX missing eop errors count.";
    }
    leaf counter_slice8_ifg_mac_pool85_port_mib_counter4_tx_mac_missing_eop_err_cnt {
      type oc-yang:counter64;
      description
        "MAC TX missing eop errors count.";
    }
    leaf counter_slice8_ifg_mac_pool85_port_mib_counter5_tx_mac_missing_eop_err_cnt {
      type oc-yang:counter64;
      description
        "MAC TX missing eop errors count.";
    }
    leaf counter_slice8_ifg_mac_pool85_port_mib_counter6_tx_mac_missing_eop_err_cnt {
      type oc-yang:counter64;
      description
        "MAC TX missing eop errors count.";
    }
    leaf counter_slice8_ifg_mac_pool85_port_mib_counter7_tx_mac_missing_eop_err_cnt {
      type oc-yang:counter64;
      description
        "MAC TX missing eop errors count.";
    }
    leaf counter_slice8_ifg_mac_pool86_port_mib_counter0_tx_mac_missing_eop_err_cnt {
      type oc-yang:counter64;
      description
        "MAC TX missing eop errors count.";
    }
    leaf counter_slice8_ifg_mac_pool86_port_mib_counter1_tx_mac_missing_eop_err_cnt {
      type oc-yang:counter64;
      description
        "MAC TX missing eop errors count.";
    }
    leaf counter_slice8_ifg_mac_pool86_port_mib_counter2_tx_mac_missing_eop_err_cnt {
      type oc-yang:counter64;
      description
        "MAC TX missing eop errors count.";
    }
    leaf counter_slice8_ifg_mac_pool86_port_mib_counter3_tx_mac_missing_eop_err_cnt {
      type oc-yang:counter64;
      description
        "MAC TX missing eop errors count.";
    }
    leaf counter_slice8_ifg_mac_pool86_port_mib_counter4_tx_mac_missing_eop_err_cnt {
      type oc-yang:counter64;
      description
        "MAC TX missing eop errors count.";
    }
    leaf counter_slice8_ifg_mac_pool86_port_mib_counter5_tx_mac_missing_eop_err_cnt {
      type oc-yang:counter64;
      description
        "MAC TX missing eop errors count.";
    }
    leaf counter_slice8_ifg_mac_pool86_port_mib_counter6_tx_mac_missing_eop_err_cnt {
      type oc-yang:counter64;
      description
        "MAC TX missing eop errors count.";
    }
    leaf counter_slice8_ifg_mac_pool86_port_mib_counter7_tx_mac_missing_eop_err_cnt {
      type oc-yang:counter64;
      description
        "MAC TX missing eop errors count.";
    }
    leaf counter_slice8_ifg_mac_pool87_port_mib_counter0_tx_mac_missing_eop_err_cnt {
      type oc-yang:counter64;
      description
        "MAC TX missing eop errors count.";
    }
    leaf counter_slice8_ifg_mac_pool87_port_mib_counter1_tx_mac_missing_eop_err_cnt {
      type oc-yang:counter64;
      description
        "MAC TX missing eop errors count.";
    }
    leaf counter_slice8_ifg_mac_pool87_port_mib_counter2_tx_mac_missing_eop_err_cnt {
      type oc-yang:counter64;
      description
        "MAC TX missing eop errors count.";
    }
    leaf counter_slice8_ifg_mac_pool87_port_mib_counter3_tx_mac_missing_eop_err_cnt {
      type oc-yang:counter64;
      description
        "MAC TX missing eop errors count.";
    }
    leaf counter_slice8_ifg_mac_pool87_port_mib_counter4_tx_mac_missing_eop_err_cnt {
      type oc-yang:counter64;
      description
        "MAC TX missing eop errors count.";
    }
    leaf counter_slice8_ifg_mac_pool87_port_mib_counter5_tx_mac_missing_eop_err_cnt {
      type oc-yang:counter64;
      description
        "MAC TX missing eop errors count.";
    }
    leaf counter_slice8_ifg_mac_pool87_port_mib_counter6_tx_mac_missing_eop_err_cnt {
      type oc-yang:counter64;
      description
        "MAC TX missing eop errors count.";
    }
    leaf counter_slice8_ifg_mac_pool87_port_mib_counter7_tx_mac_missing_eop_err_cnt {
      type oc-yang:counter64;
      description
        "MAC TX missing eop errors count.";
    }
    leaf counter_slice9_ifg_mac_pool80_port_mib_counter0_tx_mac_missing_eop_err_cnt {
      type oc-yang:counter64;
      description
        "MAC TX missing eop errors count.";
    }
    leaf counter_slice9_ifg_mac_pool80_port_mib_counter1_tx_mac_missing_eop_err_cnt {
      type oc-yang:counter64;
      description
        "MAC TX missing eop errors count.";
    }
    leaf counter_slice9_ifg_mac_pool80_port_mib_counter2_tx_mac_missing_eop_err_cnt {
      type oc-yang:counter64;
      description
        "MAC TX missing eop errors count.";
    }
    leaf counter_slice9_ifg_mac_pool80_port_mib_counter3_tx_mac_missing_eop_err_cnt {
      type oc-yang:counter64;
      description
        "MAC TX missing eop errors count.";
    }
    leaf counter_slice9_ifg_mac_pool80_port_mib_counter4_tx_mac_missing_eop_err_cnt {
      type oc-yang:counter64;
      description
        "MAC TX missing eop errors count.";
    }
    leaf counter_slice9_ifg_mac_pool80_port_mib_counter5_tx_mac_missing_eop_err_cnt {
      type oc-yang:counter64;
      description
        "MAC TX missing eop errors count.";
    }
    leaf counter_slice9_ifg_mac_pool80_port_mib_counter6_tx_mac_missing_eop_err_cnt {
      type oc-yang:counter64;
      description
        "MAC TX missing eop errors count.";
    }
    leaf counter_slice9_ifg_mac_pool80_port_mib_counter7_tx_mac_missing_eop_err_cnt {
      type oc-yang:counter64;
      description
        "MAC TX missing eop errors count.";
    }
    leaf counter_slice9_ifg_mac_pool81_port_mib_counter0_tx_mac_missing_eop_err_cnt {
      type oc-yang:counter64;
      description
        "MAC TX missing eop errors count.";
    }
    leaf counter_slice9_ifg_mac_pool81_port_mib_counter1_tx_mac_missing_eop_err_cnt {
      type oc-yang:counter64;
      description
        "MAC TX missing eop errors count.";
    }
    leaf counter_slice9_ifg_mac_pool81_port_mib_counter2_tx_mac_missing_eop_err_cnt {
      type oc-yang:counter64;
      description
        "MAC TX missing eop errors count.";
    }
    leaf counter_slice9_ifg_mac_pool81_port_mib_counter3_tx_mac_missing_eop_err_cnt {
      type oc-yang:counter64;
      description
        "MAC TX missing eop errors count.";
    }
    leaf counter_slice9_ifg_mac_pool81_port_mib_counter4_tx_mac_missing_eop_err_cnt {
      type oc-yang:counter64;
      description
        "MAC TX missing eop errors count.";
    }
    leaf counter_slice9_ifg_mac_pool81_port_mib_counter5_tx_mac_missing_eop_err_cnt {
      type oc-yang:counter64;
      description
        "MAC TX missing eop errors count.";
    }
    leaf counter_slice9_ifg_mac_pool81_port_mib_counter6_tx_mac_missing_eop_err_cnt {
      type oc-yang:counter64;
      description
        "MAC TX missing eop errors count.";
    }
    leaf counter_slice9_ifg_mac_pool81_port_mib_counter7_tx_mac_missing_eop_err_cnt {
      type oc-yang:counter64;
      description
        "MAC TX missing eop errors count.";
    }
    leaf counter_slice9_ifg_mac_pool82_port_mib_counter0_tx_mac_missing_eop_err_cnt {
      type oc-yang:counter64;
      description
        "MAC TX missing eop errors count.";
    }
    leaf counter_slice9_ifg_mac_pool82_port_mib_counter1_tx_mac_missing_eop_err_cnt {
      type oc-yang:counter64;
      description
        "MAC TX missing eop errors count.";
    }
    leaf counter_slice9_ifg_mac_pool82_port_mib_counter2_tx_mac_missing_eop_err_cnt {
      type oc-yang:counter64;
      description
        "MAC TX missing eop errors count.";
    }
    leaf counter_slice9_ifg_mac_pool82_port_mib_counter3_tx_mac_missing_eop_err_cnt {
      type oc-yang:counter64;
      description
        "MAC TX missing eop errors count.";
    }
    leaf counter_slice9_ifg_mac_pool82_port_mib_counter4_tx_mac_missing_eop_err_cnt {
      type oc-yang:counter64;
      description
        "MAC TX missing eop errors count.";
    }
    leaf counter_slice9_ifg_mac_pool82_port_mib_counter5_tx_mac_missing_eop_err_cnt {
      type oc-yang:counter64;
      description
        "MAC TX missing eop errors count.";
    }
    leaf counter_slice9_ifg_mac_pool82_port_mib_counter6_tx_mac_missing_eop_err_cnt {
      type oc-yang:counter64;
      description
        "MAC TX missing eop errors count.";
    }
    leaf counter_slice9_ifg_mac_pool82_port_mib_counter7_tx_mac_missing_eop_err_cnt {
      type oc-yang:counter64;
      description
        "MAC TX missing eop errors count.";
    }
    leaf counter_slice9_ifg_mac_pool83_port_mib_counter0_tx_mac_missing_eop_err_cnt {
      type oc-yang:counter64;
      description
        "MAC TX missing eop errors count.";
    }
    leaf counter_slice9_ifg_mac_pool83_port_mib_counter1_tx_mac_missing_eop_err_cnt {
      type oc-yang:counter64;
      description
        "MAC TX missing eop errors count.";
    }
    leaf counter_slice9_ifg_mac_pool83_port_mib_counter2_tx_mac_missing_eop_err_cnt {
      type oc-yang:counter64;
      description
        "MAC TX missing eop errors count.";
    }
    leaf counter_slice9_ifg_mac_pool83_port_mib_counter3_tx_mac_missing_eop_err_cnt {
      type oc-yang:counter64;
      description
        "MAC TX missing eop errors count.";
    }
    leaf counter_slice9_ifg_mac_pool83_port_mib_counter4_tx_mac_missing_eop_err_cnt {
      type oc-yang:counter64;
      description
        "MAC TX missing eop errors count.";
    }
    leaf counter_slice9_ifg_mac_pool83_port_mib_counter5_tx_mac_missing_eop_err_cnt {
      type oc-yang:counter64;
      description
        "MAC TX missing eop errors count.";
    }
    leaf counter_slice9_ifg_mac_pool83_port_mib_counter6_tx_mac_missing_eop_err_cnt {
      type oc-yang:counter64;
      description
        "MAC TX missing eop errors count.";
    }
    leaf counter_slice9_ifg_mac_pool83_port_mib_counter7_tx_mac_missing_eop_err_cnt {
      type oc-yang:counter64;
      description
        "MAC TX missing eop errors count.";
    }
    leaf counter_slice9_ifg_mac_pool84_port_mib_counter0_tx_mac_missing_eop_err_cnt {
      type oc-yang:counter64;
      description
        "MAC TX missing eop errors count.";
    }
    leaf counter_slice9_ifg_mac_pool84_port_mib_counter1_tx_mac_missing_eop_err_cnt {
      type oc-yang:counter64;
      description
        "MAC TX missing eop errors count.";
    }
    leaf counter_slice9_ifg_mac_pool84_port_mib_counter2_tx_mac_missing_eop_err_cnt {
      type oc-yang:counter64;
      description
        "MAC TX missing eop errors count.";
    }
    leaf counter_slice9_ifg_mac_pool84_port_mib_counter3_tx_mac_missing_eop_err_cnt {
      type oc-yang:counter64;
      description
        "MAC TX missing eop errors count.";
    }
    leaf counter_slice9_ifg_mac_pool84_port_mib_counter4_tx_mac_missing_eop_err_cnt {
      type oc-yang:counter64;
      description
        "MAC TX missing eop errors count.";
    }
    leaf counter_slice9_ifg_mac_pool84_port_mib_counter5_tx_mac_missing_eop_err_cnt {
      type oc-yang:counter64;
      description
        "MAC TX missing eop errors count.";
    }
    leaf counter_slice9_ifg_mac_pool84_port_mib_counter6_tx_mac_missing_eop_err_cnt {
      type oc-yang:counter64;
      description
        "MAC TX missing eop errors count.";
    }
    leaf counter_slice9_ifg_mac_pool84_port_mib_counter7_tx_mac_missing_eop_err_cnt {
      type oc-yang:counter64;
      description
        "MAC TX missing eop errors count.";
    }
    leaf counter_slice9_ifg_mac_pool85_port_mib_counter0_tx_mac_missing_eop_err_cnt {
      type oc-yang:counter64;
      description
        "MAC TX missing eop errors count.";
    }
    leaf counter_slice9_ifg_mac_pool85_port_mib_counter1_tx_mac_missing_eop_err_cnt {
      type oc-yang:counter64;
      description
        "MAC TX missing eop errors count.";
    }
    leaf counter_slice9_ifg_mac_pool85_port_mib_counter2_tx_mac_missing_eop_err_cnt {
      type oc-yang:counter64;
      description
        "MAC TX missing eop errors count.";
    }
    leaf counter_slice9_ifg_mac_pool85_port_mib_counter3_tx_mac_missing_eop_err_cnt {
      type oc-yang:counter64;
      description
        "MAC TX missing eop errors count.";
    }
    leaf counter_slice9_ifg_mac_pool85_port_mib_counter4_tx_mac_missing_eop_err_cnt {
      type oc-yang:counter64;
      description
        "MAC TX missing eop errors count.";
    }
    leaf counter_slice9_ifg_mac_pool85_port_mib_counter5_tx_mac_missing_eop_err_cnt {
      type oc-yang:counter64;
      description
        "MAC TX missing eop errors count.";
    }
    leaf counter_slice9_ifg_mac_pool85_port_mib_counter6_tx_mac_missing_eop_err_cnt {
      type oc-yang:counter64;
      description
        "MAC TX missing eop errors count.";
    }
    leaf counter_slice9_ifg_mac_pool85_port_mib_counter7_tx_mac_missing_eop_err_cnt {
      type oc-yang:counter64;
      description
        "MAC TX missing eop errors count.";
    }
    leaf counter_slice9_ifg_mac_pool86_port_mib_counter0_tx_mac_missing_eop_err_cnt {
      type oc-yang:counter64;
      description
        "MAC TX missing eop errors count.";
    }
    leaf counter_slice9_ifg_mac_pool86_port_mib_counter1_tx_mac_missing_eop_err_cnt {
      type oc-yang:counter64;
      description
        "MAC TX missing eop errors count.";
    }
    leaf counter_slice9_ifg_mac_pool86_port_mib_counter2_tx_mac_missing_eop_err_cnt {
      type oc-yang:counter64;
      description
        "MAC TX missing eop errors count.";
    }
    leaf counter_slice9_ifg_mac_pool86_port_mib_counter3_tx_mac_missing_eop_err_cnt {
      type oc-yang:counter64;
      description
        "MAC TX missing eop errors count.";
    }
    leaf counter_slice9_ifg_mac_pool86_port_mib_counter4_tx_mac_missing_eop_err_cnt {
      type oc-yang:counter64;
      description
        "MAC TX missing eop errors count.";
    }
    leaf counter_slice9_ifg_mac_pool86_port_mib_counter5_tx_mac_missing_eop_err_cnt {
      type oc-yang:counter64;
      description
        "MAC TX missing eop errors count.";
    }
    leaf counter_slice9_ifg_mac_pool86_port_mib_counter6_tx_mac_missing_eop_err_cnt {
      type oc-yang:counter64;
      description
        "MAC TX missing eop errors count.";
    }
    leaf counter_slice9_ifg_mac_pool86_port_mib_counter7_tx_mac_missing_eop_err_cnt {
      type oc-yang:counter64;
      description
        "MAC TX missing eop errors count.";
    }
    leaf counter_slice9_ifg_mac_pool87_port_mib_counter0_tx_mac_missing_eop_err_cnt {
      type oc-yang:counter64;
      description
        "MAC TX missing eop errors count.";
    }
    leaf counter_slice9_ifg_mac_pool87_port_mib_counter1_tx_mac_missing_eop_err_cnt {
      type oc-yang:counter64;
      description
        "MAC TX missing eop errors count.";
    }
    leaf counter_slice9_ifg_mac_pool87_port_mib_counter2_tx_mac_missing_eop_err_cnt {
      type oc-yang:counter64;
      description
        "MAC TX missing eop errors count.";
    }
    leaf counter_slice9_ifg_mac_pool87_port_mib_counter3_tx_mac_missing_eop_err_cnt {
      type oc-yang:counter64;
      description
        "MAC TX missing eop errors count.";
    }
    leaf counter_slice9_ifg_mac_pool87_port_mib_counter4_tx_mac_missing_eop_err_cnt {
      type oc-yang:counter64;
      description
        "MAC TX missing eop errors count.";
    }
    leaf counter_slice9_ifg_mac_pool87_port_mib_counter5_tx_mac_missing_eop_err_cnt {
      type oc-yang:counter64;
      description
        "MAC TX missing eop errors count.";
    }
    leaf counter_slice9_ifg_mac_pool87_port_mib_counter6_tx_mac_missing_eop_err_cnt {
      type oc-yang:counter64;
      description
        "MAC TX missing eop errors count.";
    }
    leaf counter_slice9_ifg_mac_pool87_port_mib_counter7_tx_mac_missing_eop_err_cnt {
      type oc-yang:counter64;
      description
        "MAC TX missing eop errors count.";
    }
    leaf counter_slice10_ifg_mac_pool80_port_mib_counter0_tx_mac_missing_eop_err_cnt {
      type oc-yang:counter64;
      description
        "MAC TX missing eop errors count.";
    }
    leaf counter_slice10_ifg_mac_pool80_port_mib_counter1_tx_mac_missing_eop_err_cnt {
      type oc-yang:counter64;
      description
        "MAC TX missing eop errors count.";
    }
    leaf counter_slice10_ifg_mac_pool80_port_mib_counter2_tx_mac_missing_eop_err_cnt {
      type oc-yang:counter64;
      description
        "MAC TX missing eop errors count.";
    }
    leaf counter_slice10_ifg_mac_pool80_port_mib_counter3_tx_mac_missing_eop_err_cnt {
      type oc-yang:counter64;
      description
        "MAC TX missing eop errors count.";
    }
    leaf counter_slice10_ifg_mac_pool80_port_mib_counter4_tx_mac_missing_eop_err_cnt {
      type oc-yang:counter64;
      description
        "MAC TX missing eop errors count.";
    }
    leaf counter_slice10_ifg_mac_pool80_port_mib_counter5_tx_mac_missing_eop_err_cnt {
      type oc-yang:counter64;
      description
        "MAC TX missing eop errors count.";
    }
    leaf counter_slice10_ifg_mac_pool80_port_mib_counter6_tx_mac_missing_eop_err_cnt {
      type oc-yang:counter64;
      description
        "MAC TX missing eop errors count.";
    }
    leaf counter_slice10_ifg_mac_pool80_port_mib_counter7_tx_mac_missing_eop_err_cnt {
      type oc-yang:counter64;
      description
        "MAC TX missing eop errors count.";
    }
    leaf counter_slice10_ifg_mac_pool81_port_mib_counter0_tx_mac_missing_eop_err_cnt {
      type oc-yang:counter64;
      description
        "MAC TX missing eop errors count.";
    }
    leaf counter_slice10_ifg_mac_pool81_port_mib_counter1_tx_mac_missing_eop_err_cnt {
      type oc-yang:counter64;
      description
        "MAC TX missing eop errors count.";
    }
    leaf counter_slice10_ifg_mac_pool81_port_mib_counter2_tx_mac_missing_eop_err_cnt {
      type oc-yang:counter64;
      description
        "MAC TX missing eop errors count.";
    }
    leaf counter_slice10_ifg_mac_pool81_port_mib_counter3_tx_mac_missing_eop_err_cnt {
      type oc-yang:counter64;
      description
        "MAC TX missing eop errors count.";
    }
    leaf counter_slice10_ifg_mac_pool81_port_mib_counter4_tx_mac_missing_eop_err_cnt {
      type oc-yang:counter64;
      description
        "MAC TX missing eop errors count.";
    }
    leaf counter_slice10_ifg_mac_pool81_port_mib_counter5_tx_mac_missing_eop_err_cnt {
      type oc-yang:counter64;
      description
        "MAC TX missing eop errors count.";
    }
    leaf counter_slice10_ifg_mac_pool81_port_mib_counter6_tx_mac_missing_eop_err_cnt {
      type oc-yang:counter64;
      description
        "MAC TX missing eop errors count.";
    }
    leaf counter_slice10_ifg_mac_pool81_port_mib_counter7_tx_mac_missing_eop_err_cnt {
      type oc-yang:counter64;
      description
        "MAC TX missing eop errors count.";
    }
    leaf counter_slice10_ifg_mac_pool82_port_mib_counter0_tx_mac_missing_eop_err_cnt {
      type oc-yang:counter64;
      description
        "MAC TX missing eop errors count.";
    }
    leaf counter_slice10_ifg_mac_pool82_port_mib_counter1_tx_mac_missing_eop_err_cnt {
      type oc-yang:counter64;
      description
        "MAC TX missing eop errors count.";
    }
    leaf counter_slice10_ifg_mac_pool82_port_mib_counter2_tx_mac_missing_eop_err_cnt {
      type oc-yang:counter64;
      description
        "MAC TX missing eop errors count.";
    }
    leaf counter_slice10_ifg_mac_pool82_port_mib_counter3_tx_mac_missing_eop_err_cnt {
      type oc-yang:counter64;
      description
        "MAC TX missing eop errors count.";
    }
    leaf counter_slice10_ifg_mac_pool82_port_mib_counter4_tx_mac_missing_eop_err_cnt {
      type oc-yang:counter64;
      description
        "MAC TX missing eop errors count.";
    }
    leaf counter_slice10_ifg_mac_pool82_port_mib_counter5_tx_mac_missing_eop_err_cnt {
      type oc-yang:counter64;
      description
        "MAC TX missing eop errors count.";
    }
    leaf counter_slice10_ifg_mac_pool82_port_mib_counter6_tx_mac_missing_eop_err_cnt {
      type oc-yang:counter64;
      description
        "MAC TX missing eop errors count.";
    }
    leaf counter_slice10_ifg_mac_pool82_port_mib_counter7_tx_mac_missing_eop_err_cnt {
      type oc-yang:counter64;
      description
        "MAC TX missing eop errors count.";
    }
    leaf counter_slice10_ifg_mac_pool83_port_mib_counter0_tx_mac_missing_eop_err_cnt {
      type oc-yang:counter64;
      description
        "MAC TX missing eop errors count.";
    }
    leaf counter_slice10_ifg_mac_pool83_port_mib_counter1_tx_mac_missing_eop_err_cnt {
      type oc-yang:counter64;
      description
        "MAC TX missing eop errors count.";
    }
    leaf counter_slice10_ifg_mac_pool83_port_mib_counter2_tx_mac_missing_eop_err_cnt {
      type oc-yang:counter64;
      description
        "MAC TX missing eop errors count.";
    }
    leaf counter_slice10_ifg_mac_pool83_port_mib_counter3_tx_mac_missing_eop_err_cnt {
      type oc-yang:counter64;
      description
        "MAC TX missing eop errors count.";
    }
    leaf counter_slice10_ifg_mac_pool83_port_mib_counter4_tx_mac_missing_eop_err_cnt {
      type oc-yang:counter64;
      description
        "MAC TX missing eop errors count.";
    }
    leaf counter_slice10_ifg_mac_pool83_port_mib_counter5_tx_mac_missing_eop_err_cnt {
      type oc-yang:counter64;
      description
        "MAC TX missing eop errors count.";
    }
    leaf counter_slice10_ifg_mac_pool83_port_mib_counter6_tx_mac_missing_eop_err_cnt {
      type oc-yang:counter64;
      description
        "MAC TX missing eop errors count.";
    }
    leaf counter_slice10_ifg_mac_pool83_port_mib_counter7_tx_mac_missing_eop_err_cnt {
      type oc-yang:counter64;
      description
        "MAC TX missing eop errors count.";
    }
    leaf counter_slice10_ifg_mac_pool84_port_mib_counter0_tx_mac_missing_eop_err_cnt {
      type oc-yang:counter64;
      description
        "MAC TX missing eop errors count.";
    }
    leaf counter_slice10_ifg_mac_pool84_port_mib_counter1_tx_mac_missing_eop_err_cnt {
      type oc-yang:counter64;
      description
        "MAC TX missing eop errors count.";
    }
    leaf counter_slice10_ifg_mac_pool84_port_mib_counter2_tx_mac_missing_eop_err_cnt {
      type oc-yang:counter64;
      description
        "MAC TX missing eop errors count.";
    }
    leaf counter_slice10_ifg_mac_pool84_port_mib_counter3_tx_mac_missing_eop_err_cnt {
      type oc-yang:counter64;
      description
        "MAC TX missing eop errors count.";
    }
    leaf counter_slice10_ifg_mac_pool84_port_mib_counter4_tx_mac_missing_eop_err_cnt {
      type oc-yang:counter64;
      description
        "MAC TX missing eop errors count.";
    }
    leaf counter_slice10_ifg_mac_pool84_port_mib_counter5_tx_mac_missing_eop_err_cnt {
      type oc-yang:counter64;
      description
        "MAC TX missing eop errors count.";
    }
    leaf counter_slice10_ifg_mac_pool84_port_mib_counter6_tx_mac_missing_eop_err_cnt {
      type oc-yang:counter64;
      description
        "MAC TX missing eop errors count.";
    }
    leaf counter_slice10_ifg_mac_pool84_port_mib_counter7_tx_mac_missing_eop_err_cnt {
      type oc-yang:counter64;
      description
        "MAC TX missing eop errors count.";
    }
    leaf counter_slice10_ifg_mac_pool85_port_mib_counter0_tx_mac_missing_eop_err_cnt {
      type oc-yang:counter64;
      description
        "MAC TX missing eop errors count.";
    }
    leaf counter_slice10_ifg_mac_pool85_port_mib_counter1_tx_mac_missing_eop_err_cnt {
      type oc-yang:counter64;
      description
        "MAC TX missing eop errors count.";
    }
    leaf counter_slice10_ifg_mac_pool85_port_mib_counter2_tx_mac_missing_eop_err_cnt {
      type oc-yang:counter64;
      description
        "MAC TX missing eop errors count.";
    }
    leaf counter_slice10_ifg_mac_pool85_port_mib_counter3_tx_mac_missing_eop_err_cnt {
      type oc-yang:counter64;
      description
        "MAC TX missing eop errors count.";
    }
    leaf counter_slice10_ifg_mac_pool85_port_mib_counter4_tx_mac_missing_eop_err_cnt {
      type oc-yang:counter64;
      description
        "MAC TX missing eop errors count.";
    }
    leaf counter_slice10_ifg_mac_pool85_port_mib_counter5_tx_mac_missing_eop_err_cnt {
      type oc-yang:counter64;
      description
        "MAC TX missing eop errors count.";
    }
    leaf counter_slice10_ifg_mac_pool85_port_mib_counter6_tx_mac_missing_eop_err_cnt {
      type oc-yang:counter64;
      description
        "MAC TX missing eop errors count.";
    }
    leaf counter_slice10_ifg_mac_pool85_port_mib_counter7_tx_mac_missing_eop_err_cnt {
      type oc-yang:counter64;
      description
        "MAC TX missing eop errors count.";
    }
    leaf counter_slice10_ifg_mac_pool86_port_mib_counter0_tx_mac_missing_eop_err_cnt {
      type oc-yang:counter64;
      description
        "MAC TX missing eop errors count.";
    }
    leaf counter_slice10_ifg_mac_pool86_port_mib_counter1_tx_mac_missing_eop_err_cnt {
      type oc-yang:counter64;
      description
        "MAC TX missing eop errors count.";
    }
    leaf counter_slice10_ifg_mac_pool86_port_mib_counter2_tx_mac_missing_eop_err_cnt {
      type oc-yang:counter64;
      description
        "MAC TX missing eop errors count.";
    }
    leaf counter_slice10_ifg_mac_pool86_port_mib_counter3_tx_mac_missing_eop_err_cnt {
      type oc-yang:counter64;
      description
        "MAC TX missing eop errors count.";
    }
    leaf counter_slice10_ifg_mac_pool86_port_mib_counter4_tx_mac_missing_eop_err_cnt {
      type oc-yang:counter64;
      description
        "MAC TX missing eop errors count.";
    }
    leaf counter_slice10_ifg_mac_pool86_port_mib_counter5_tx_mac_missing_eop_err_cnt {
      type oc-yang:counter64;
      description
        "MAC TX missing eop errors count.";
    }
    leaf counter_slice10_ifg_mac_pool86_port_mib_counter6_tx_mac_missing_eop_err_cnt {
      type oc-yang:counter64;
      description
        "MAC TX missing eop errors count.";
    }
    leaf counter_slice10_ifg_mac_pool86_port_mib_counter7_tx_mac_missing_eop_err_cnt {
      type oc-yang:counter64;
      description
        "MAC TX missing eop errors count.";
    }
    leaf counter_slice10_ifg_mac_pool87_port_mib_counter0_tx_mac_missing_eop_err_cnt {
      type oc-yang:counter64;
      description
        "MAC TX missing eop errors count.";
    }
    leaf counter_slice10_ifg_mac_pool87_port_mib_counter1_tx_mac_missing_eop_err_cnt {
      type oc-yang:counter64;
      description
        "MAC TX missing eop errors count.";
    }
    leaf counter_slice10_ifg_mac_pool87_port_mib_counter2_tx_mac_missing_eop_err_cnt {
      type oc-yang:counter64;
      description
        "MAC TX missing eop errors count.";
    }
    leaf counter_slice10_ifg_mac_pool87_port_mib_counter3_tx_mac_missing_eop_err_cnt {
      type oc-yang:counter64;
      description
        "MAC TX missing eop errors count.";
    }
    leaf counter_slice10_ifg_mac_pool87_port_mib_counter4_tx_mac_missing_eop_err_cnt {
      type oc-yang:counter64;
      description
        "MAC TX missing eop errors count.";
    }
    leaf counter_slice10_ifg_mac_pool87_port_mib_counter5_tx_mac_missing_eop_err_cnt {
      type oc-yang:counter64;
      description
        "MAC TX missing eop errors count.";
    }
    leaf counter_slice10_ifg_mac_pool87_port_mib_counter6_tx_mac_missing_eop_err_cnt {
      type oc-yang:counter64;
      description
        "MAC TX missing eop errors count.";
    }
    leaf counter_slice10_ifg_mac_pool87_port_mib_counter7_tx_mac_missing_eop_err_cnt {
      type oc-yang:counter64;
      description
        "MAC TX missing eop errors count.";
    }
    leaf counter_slice11_ifg_mac_pool80_port_mib_counter0_tx_mac_missing_eop_err_cnt {
      type oc-yang:counter64;
      description
        "MAC TX missing eop errors count.";
    }
    leaf counter_slice11_ifg_mac_pool80_port_mib_counter1_tx_mac_missing_eop_err_cnt {
      type oc-yang:counter64;
      description
        "MAC TX missing eop errors count.";
    }
    leaf counter_slice11_ifg_mac_pool80_port_mib_counter2_tx_mac_missing_eop_err_cnt {
      type oc-yang:counter64;
      description
        "MAC TX missing eop errors count.";
    }
    leaf counter_slice11_ifg_mac_pool80_port_mib_counter3_tx_mac_missing_eop_err_cnt {
      type oc-yang:counter64;
      description
        "MAC TX missing eop errors count.";
    }
    leaf counter_slice11_ifg_mac_pool80_port_mib_counter4_tx_mac_missing_eop_err_cnt {
      type oc-yang:counter64;
      description
        "MAC TX missing eop errors count.";
    }
    leaf counter_slice11_ifg_mac_pool80_port_mib_counter5_tx_mac_missing_eop_err_cnt {
      type oc-yang:counter64;
      description
        "MAC TX missing eop errors count.";
    }
    leaf counter_slice11_ifg_mac_pool80_port_mib_counter6_tx_mac_missing_eop_err_cnt {
      type oc-yang:counter64;
      description
        "MAC TX missing eop errors count.";
    }
    leaf counter_slice11_ifg_mac_pool80_port_mib_counter7_tx_mac_missing_eop_err_cnt {
      type oc-yang:counter64;
      description
        "MAC TX missing eop errors count.";
    }
    leaf counter_slice11_ifg_mac_pool81_port_mib_counter0_tx_mac_missing_eop_err_cnt {
      type oc-yang:counter64;
      description
        "MAC TX missing eop errors count.";
    }
    leaf counter_slice11_ifg_mac_pool81_port_mib_counter1_tx_mac_missing_eop_err_cnt {
      type oc-yang:counter64;
      description
        "MAC TX missing eop errors count.";
    }
    leaf counter_slice11_ifg_mac_pool81_port_mib_counter2_tx_mac_missing_eop_err_cnt {
      type oc-yang:counter64;
      description
        "MAC TX missing eop errors count.";
    }
    leaf counter_slice11_ifg_mac_pool81_port_mib_counter3_tx_mac_missing_eop_err_cnt {
      type oc-yang:counter64;
      description
        "MAC TX missing eop errors count.";
    }
    leaf counter_slice11_ifg_mac_pool81_port_mib_counter4_tx_mac_missing_eop_err_cnt {
      type oc-yang:counter64;
      description
        "MAC TX missing eop errors count.";
    }
    leaf counter_slice11_ifg_mac_pool81_port_mib_counter5_tx_mac_missing_eop_err_cnt {
      type oc-yang:counter64;
      description
        "MAC TX missing eop errors count.";
    }
    leaf counter_slice11_ifg_mac_pool81_port_mib_counter6_tx_mac_missing_eop_err_cnt {
      type oc-yang:counter64;
      description
        "MAC TX missing eop errors count.";
    }
    leaf counter_slice11_ifg_mac_pool81_port_mib_counter7_tx_mac_missing_eop_err_cnt {
      type oc-yang:counter64;
      description
        "MAC TX missing eop errors count.";
    }
    leaf counter_slice11_ifg_mac_pool82_port_mib_counter0_tx_mac_missing_eop_err_cnt {
      type oc-yang:counter64;
      description
        "MAC TX missing eop errors count.";
    }
    leaf counter_slice11_ifg_mac_pool82_port_mib_counter1_tx_mac_missing_eop_err_cnt {
      type oc-yang:counter64;
      description
        "MAC TX missing eop errors count.";
    }
    leaf counter_slice11_ifg_mac_pool82_port_mib_counter2_tx_mac_missing_eop_err_cnt {
      type oc-yang:counter64;
      description
        "MAC TX missing eop errors count.";
    }
    leaf counter_slice11_ifg_mac_pool82_port_mib_counter3_tx_mac_missing_eop_err_cnt {
      type oc-yang:counter64;
      description
        "MAC TX missing eop errors count.";
    }
    leaf counter_slice11_ifg_mac_pool82_port_mib_counter4_tx_mac_missing_eop_err_cnt {
      type oc-yang:counter64;
      description
        "MAC TX missing eop errors count.";
    }
    leaf counter_slice11_ifg_mac_pool82_port_mib_counter5_tx_mac_missing_eop_err_cnt {
      type oc-yang:counter64;
      description
        "MAC TX missing eop errors count.";
    }
    leaf counter_slice11_ifg_mac_pool82_port_mib_counter6_tx_mac_missing_eop_err_cnt {
      type oc-yang:counter64;
      description
        "MAC TX missing eop errors count.";
    }
    leaf counter_slice11_ifg_mac_pool82_port_mib_counter7_tx_mac_missing_eop_err_cnt {
      type oc-yang:counter64;
      description
        "MAC TX missing eop errors count.";
    }
    leaf counter_slice11_ifg_mac_pool83_port_mib_counter0_tx_mac_missing_eop_err_cnt {
      type oc-yang:counter64;
      description
        "MAC TX missing eop errors count.";
    }
    leaf counter_slice11_ifg_mac_pool83_port_mib_counter1_tx_mac_missing_eop_err_cnt {
      type oc-yang:counter64;
      description
        "MAC TX missing eop errors count.";
    }
    leaf counter_slice11_ifg_mac_pool83_port_mib_counter2_tx_mac_missing_eop_err_cnt {
      type oc-yang:counter64;
      description
        "MAC TX missing eop errors count.";
    }
    leaf counter_slice11_ifg_mac_pool83_port_mib_counter3_tx_mac_missing_eop_err_cnt {
      type oc-yang:counter64;
      description
        "MAC TX missing eop errors count.";
    }
    leaf counter_slice11_ifg_mac_pool83_port_mib_counter4_tx_mac_missing_eop_err_cnt {
      type oc-yang:counter64;
      description
        "MAC TX missing eop errors count.";
    }
    leaf counter_slice11_ifg_mac_pool83_port_mib_counter5_tx_mac_missing_eop_err_cnt {
      type oc-yang:counter64;
      description
        "MAC TX missing eop errors count.";
    }
    leaf counter_slice11_ifg_mac_pool83_port_mib_counter6_tx_mac_missing_eop_err_cnt {
      type oc-yang:counter64;
      description
        "MAC TX missing eop errors count.";
    }
    leaf counter_slice11_ifg_mac_pool83_port_mib_counter7_tx_mac_missing_eop_err_cnt {
      type oc-yang:counter64;
      description
        "MAC TX missing eop errors count.";
    }
    leaf counter_slice11_ifg_mac_pool84_port_mib_counter0_tx_mac_missing_eop_err_cnt {
      type oc-yang:counter64;
      description
        "MAC TX missing eop errors count.";
    }
    leaf counter_slice11_ifg_mac_pool84_port_mib_counter1_tx_mac_missing_eop_err_cnt {
      type oc-yang:counter64;
      description
        "MAC TX missing eop errors count.";
    }
    leaf counter_slice11_ifg_mac_pool84_port_mib_counter2_tx_mac_missing_eop_err_cnt {
      type oc-yang:counter64;
      description
        "MAC TX missing eop errors count.";
    }
    leaf counter_slice11_ifg_mac_pool84_port_mib_counter3_tx_mac_missing_eop_err_cnt {
      type oc-yang:counter64;
      description
        "MAC TX missing eop errors count.";
    }
    leaf counter_slice11_ifg_mac_pool84_port_mib_counter4_tx_mac_missing_eop_err_cnt {
      type oc-yang:counter64;
      description
        "MAC TX missing eop errors count.";
    }
    leaf counter_slice11_ifg_mac_pool84_port_mib_counter5_tx_mac_missing_eop_err_cnt {
      type oc-yang:counter64;
      description
        "MAC TX missing eop errors count.";
    }
    leaf counter_slice11_ifg_mac_pool84_port_mib_counter6_tx_mac_missing_eop_err_cnt {
      type oc-yang:counter64;
      description
        "MAC TX missing eop errors count.";
    }
    leaf counter_slice11_ifg_mac_pool84_port_mib_counter7_tx_mac_missing_eop_err_cnt {
      type oc-yang:counter64;
      description
        "MAC TX missing eop errors count.";
    }
    leaf counter_slice11_ifg_mac_pool85_port_mib_counter0_tx_mac_missing_eop_err_cnt {
      type oc-yang:counter64;
      description
        "MAC TX missing eop errors count.";
    }
    leaf counter_slice11_ifg_mac_pool85_port_mib_counter1_tx_mac_missing_eop_err_cnt {
      type oc-yang:counter64;
      description
        "MAC TX missing eop errors count.";
    }
    leaf counter_slice11_ifg_mac_pool85_port_mib_counter2_tx_mac_missing_eop_err_cnt {
      type oc-yang:counter64;
      description
        "MAC TX missing eop errors count.";
    }
    leaf counter_slice11_ifg_mac_pool85_port_mib_counter3_tx_mac_missing_eop_err_cnt {
      type oc-yang:counter64;
      description
        "MAC TX missing eop errors count.";
    }
    leaf counter_slice11_ifg_mac_pool85_port_mib_counter4_tx_mac_missing_eop_err_cnt {
      type oc-yang:counter64;
      description
        "MAC TX missing eop errors count.";
    }
    leaf counter_slice11_ifg_mac_pool85_port_mib_counter5_tx_mac_missing_eop_err_cnt {
      type oc-yang:counter64;
      description
        "MAC TX missing eop errors count.";
    }
    leaf counter_slice11_ifg_mac_pool85_port_mib_counter6_tx_mac_missing_eop_err_cnt {
      type oc-yang:counter64;
      description
        "MAC TX missing eop errors count.";
    }
    leaf counter_slice11_ifg_mac_pool85_port_mib_counter7_tx_mac_missing_eop_err_cnt {
      type oc-yang:counter64;
      description
        "MAC TX missing eop errors count.";
    }
    leaf counter_slice11_ifg_mac_pool86_port_mib_counter0_tx_mac_missing_eop_err_cnt {
      type oc-yang:counter64;
      description
        "MAC TX missing eop errors count.";
    }
    leaf counter_slice11_ifg_mac_pool86_port_mib_counter1_tx_mac_missing_eop_err_cnt {
      type oc-yang:counter64;
      description
        "MAC TX missing eop errors count.";
    }
    leaf counter_slice11_ifg_mac_pool86_port_mib_counter2_tx_mac_missing_eop_err_cnt {
      type oc-yang:counter64;
      description
        "MAC TX missing eop errors count.";
    }
    leaf counter_slice11_ifg_mac_pool86_port_mib_counter3_tx_mac_missing_eop_err_cnt {
      type oc-yang:counter64;
      description
        "MAC TX missing eop errors count.";
    }
    leaf counter_slice11_ifg_mac_pool86_port_mib_counter4_tx_mac_missing_eop_err_cnt {
      type oc-yang:counter64;
      description
        "MAC TX missing eop errors count.";
    }
    leaf counter_slice11_ifg_mac_pool86_port_mib_counter5_tx_mac_missing_eop_err_cnt {
      type oc-yang:counter64;
      description
        "MAC TX missing eop errors count.";
    }
    leaf counter_slice11_ifg_mac_pool86_port_mib_counter6_tx_mac_missing_eop_err_cnt {
      type oc-yang:counter64;
      description
        "MAC TX missing eop errors count.";
    }
    leaf counter_slice11_ifg_mac_pool86_port_mib_counter7_tx_mac_missing_eop_err_cnt {
      type oc-yang:counter64;
      description
        "MAC TX missing eop errors count.";
    }
    leaf counter_slice11_ifg_mac_pool87_port_mib_counter0_tx_mac_missing_eop_err_cnt {
      type oc-yang:counter64;
      description
        "MAC TX missing eop errors count.";
    }
    leaf counter_slice11_ifg_mac_pool87_port_mib_counter1_tx_mac_missing_eop_err_cnt {
      type oc-yang:counter64;
      description
        "MAC TX missing eop errors count.";
    }
    leaf counter_slice11_ifg_mac_pool87_port_mib_counter2_tx_mac_missing_eop_err_cnt {
      type oc-yang:counter64;
      description
        "MAC TX missing eop errors count.";
    }
    leaf counter_slice11_ifg_mac_pool87_port_mib_counter3_tx_mac_missing_eop_err_cnt {
      type oc-yang:counter64;
      description
        "MAC TX missing eop errors count.";
    }
    leaf counter_slice11_ifg_mac_pool87_port_mib_counter4_tx_mac_missing_eop_err_cnt {
      type oc-yang:counter64;
      description
        "MAC TX missing eop errors count.";
    }
    leaf counter_slice11_ifg_mac_pool87_port_mib_counter5_tx_mac_missing_eop_err_cnt {
      type oc-yang:counter64;
      description
        "MAC TX missing eop errors count.";
    }
    leaf counter_slice11_ifg_mac_pool87_port_mib_counter6_tx_mac_missing_eop_err_cnt {
      type oc-yang:counter64;
      description
        "MAC TX missing eop errors count.";
    }
    leaf counter_slice11_ifg_mac_pool87_port_mib_counter7_tx_mac_missing_eop_err_cnt {
      type oc-yang:counter64;
      description
        "MAC TX missing eop errors count.";
    }
    leaf counter_slice12_ifg_mac_pool80_port_mib_counter0_tx_mac_missing_eop_err_cnt {
      type oc-yang:counter64;
      description
        "MAC TX missing eop errors count.";
    }
    leaf counter_slice12_ifg_mac_pool80_port_mib_counter1_tx_mac_missing_eop_err_cnt {
      type oc-yang:counter64;
      description
        "MAC TX missing eop errors count.";
    }
    leaf counter_slice12_ifg_mac_pool80_port_mib_counter2_tx_mac_missing_eop_err_cnt {
      type oc-yang:counter64;
      description
        "MAC TX missing eop errors count.";
    }
    leaf counter_slice12_ifg_mac_pool80_port_mib_counter3_tx_mac_missing_eop_err_cnt {
      type oc-yang:counter64;
      description
        "MAC TX missing eop errors count.";
    }
    leaf counter_slice12_ifg_mac_pool80_port_mib_counter4_tx_mac_missing_eop_err_cnt {
      type oc-yang:counter64;
      description
        "MAC TX missing eop errors count.";
    }
    leaf counter_slice12_ifg_mac_pool80_port_mib_counter5_tx_mac_missing_eop_err_cnt {
      type oc-yang:counter64;
      description
        "MAC TX missing eop errors count.";
    }
    leaf counter_slice12_ifg_mac_pool80_port_mib_counter6_tx_mac_missing_eop_err_cnt {
      type oc-yang:counter64;
      description
        "MAC TX missing eop errors count.";
    }
    leaf counter_slice12_ifg_mac_pool80_port_mib_counter7_tx_mac_missing_eop_err_cnt {
      type oc-yang:counter64;
      description
        "MAC TX missing eop errors count.";
    }
    leaf counter_slice12_ifg_mac_pool81_port_mib_counter0_tx_mac_missing_eop_err_cnt {
      type oc-yang:counter64;
      description
        "MAC TX missing eop errors count.";
    }
    leaf counter_slice12_ifg_mac_pool81_port_mib_counter1_tx_mac_missing_eop_err_cnt {
      type oc-yang:counter64;
      description
        "MAC TX missing eop errors count.";
    }
    leaf counter_slice12_ifg_mac_pool81_port_mib_counter2_tx_mac_missing_eop_err_cnt {
      type oc-yang:counter64;
      description
        "MAC TX missing eop errors count.";
    }
    leaf counter_slice12_ifg_mac_pool81_port_mib_counter3_tx_mac_missing_eop_err_cnt {
      type oc-yang:counter64;
      description
        "MAC TX missing eop errors count.";
    }
    leaf counter_slice12_ifg_mac_pool81_port_mib_counter4_tx_mac_missing_eop_err_cnt {
      type oc-yang:counter64;
      description
        "MAC TX missing eop errors count.";
    }
    leaf counter_slice12_ifg_mac_pool81_port_mib_counter5_tx_mac_missing_eop_err_cnt {
      type oc-yang:counter64;
      description
        "MAC TX missing eop errors count.";
    }
    leaf counter_slice12_ifg_mac_pool81_port_mib_counter6_tx_mac_missing_eop_err_cnt {
      type oc-yang:counter64;
      description
        "MAC TX missing eop errors count.";
    }
    leaf counter_slice12_ifg_mac_pool81_port_mib_counter7_tx_mac_missing_eop_err_cnt {
      type oc-yang:counter64;
      description
        "MAC TX missing eop errors count.";
    }
    leaf counter_slice12_ifg_mac_pool82_port_mib_counter0_tx_mac_missing_eop_err_cnt {
      type oc-yang:counter64;
      description
        "MAC TX missing eop errors count.";
    }
    leaf counter_slice12_ifg_mac_pool82_port_mib_counter1_tx_mac_missing_eop_err_cnt {
      type oc-yang:counter64;
      description
        "MAC TX missing eop errors count.";
    }
    leaf counter_slice12_ifg_mac_pool82_port_mib_counter2_tx_mac_missing_eop_err_cnt {
      type oc-yang:counter64;
      description
        "MAC TX missing eop errors count.";
    }
    leaf counter_slice12_ifg_mac_pool82_port_mib_counter3_tx_mac_missing_eop_err_cnt {
      type oc-yang:counter64;
      description
        "MAC TX missing eop errors count.";
    }
    leaf counter_slice12_ifg_mac_pool82_port_mib_counter4_tx_mac_missing_eop_err_cnt {
      type oc-yang:counter64;
      description
        "MAC TX missing eop errors count.";
    }
    leaf counter_slice12_ifg_mac_pool82_port_mib_counter5_tx_mac_missing_eop_err_cnt {
      type oc-yang:counter64;
      description
        "MAC TX missing eop errors count.";
    }
    leaf counter_slice12_ifg_mac_pool82_port_mib_counter6_tx_mac_missing_eop_err_cnt {
      type oc-yang:counter64;
      description
        "MAC TX missing eop errors count.";
    }
    leaf counter_slice12_ifg_mac_pool82_port_mib_counter7_tx_mac_missing_eop_err_cnt {
      type oc-yang:counter64;
      description
        "MAC TX missing eop errors count.";
    }
    leaf counter_slice12_ifg_mac_pool83_port_mib_counter0_tx_mac_missing_eop_err_cnt {
      type oc-yang:counter64;
      description
        "MAC TX missing eop errors count.";
    }
    leaf counter_slice12_ifg_mac_pool83_port_mib_counter1_tx_mac_missing_eop_err_cnt {
      type oc-yang:counter64;
      description
        "MAC TX missing eop errors count.";
    }
    leaf counter_slice12_ifg_mac_pool83_port_mib_counter2_tx_mac_missing_eop_err_cnt {
      type oc-yang:counter64;
      description
        "MAC TX missing eop errors count.";
    }
    leaf counter_slice12_ifg_mac_pool83_port_mib_counter3_tx_mac_missing_eop_err_cnt {
      type oc-yang:counter64;
      description
        "MAC TX missing eop errors count.";
    }
    leaf counter_slice12_ifg_mac_pool83_port_mib_counter4_tx_mac_missing_eop_err_cnt {
      type oc-yang:counter64;
      description
        "MAC TX missing eop errors count.";
    }
    leaf counter_slice12_ifg_mac_pool83_port_mib_counter5_tx_mac_missing_eop_err_cnt {
      type oc-yang:counter64;
      description
        "MAC TX missing eop errors count.";
    }
    leaf counter_slice12_ifg_mac_pool83_port_mib_counter6_tx_mac_missing_eop_err_cnt {
      type oc-yang:counter64;
      description
        "MAC TX missing eop errors count.";
    }
    leaf counter_slice12_ifg_mac_pool83_port_mib_counter7_tx_mac_missing_eop_err_cnt {
      type oc-yang:counter64;
      description
        "MAC TX missing eop errors count.";
    }
    leaf counter_slice12_ifg_mac_pool84_port_mib_counter0_tx_mac_missing_eop_err_cnt {
      type oc-yang:counter64;
      description
        "MAC TX missing eop errors count.";
    }
    leaf counter_slice12_ifg_mac_pool84_port_mib_counter1_tx_mac_missing_eop_err_cnt {
      type oc-yang:counter64;
      description
        "MAC TX missing eop errors count.";
    }
    leaf counter_slice12_ifg_mac_pool84_port_mib_counter2_tx_mac_missing_eop_err_cnt {
      type oc-yang:counter64;
      description
        "MAC TX missing eop errors count.";
    }
    leaf counter_slice12_ifg_mac_pool84_port_mib_counter3_tx_mac_missing_eop_err_cnt {
      type oc-yang:counter64;
      description
        "MAC TX missing eop errors count.";
    }
    leaf counter_slice12_ifg_mac_pool84_port_mib_counter4_tx_mac_missing_eop_err_cnt {
      type oc-yang:counter64;
      description
        "MAC TX missing eop errors count.";
    }
    leaf counter_slice12_ifg_mac_pool84_port_mib_counter5_tx_mac_missing_eop_err_cnt {
      type oc-yang:counter64;
      description
        "MAC TX missing eop errors count.";
    }
    leaf counter_slice12_ifg_mac_pool84_port_mib_counter6_tx_mac_missing_eop_err_cnt {
      type oc-yang:counter64;
      description
        "MAC TX missing eop errors count.";
    }
    leaf counter_slice12_ifg_mac_pool84_port_mib_counter7_tx_mac_missing_eop_err_cnt {
      type oc-yang:counter64;
      description
        "MAC TX missing eop errors count.";
    }
    leaf counter_slice12_ifg_mac_pool85_port_mib_counter0_tx_mac_missing_eop_err_cnt {
      type oc-yang:counter64;
      description
        "MAC TX missing eop errors count.";
    }
    leaf counter_slice12_ifg_mac_pool85_port_mib_counter1_tx_mac_missing_eop_err_cnt {
      type oc-yang:counter64;
      description
        "MAC TX missing eop errors count.";
    }
    leaf counter_slice12_ifg_mac_pool85_port_mib_counter2_tx_mac_missing_eop_err_cnt {
      type oc-yang:counter64;
      description
        "MAC TX missing eop errors count.";
    }
    leaf counter_slice12_ifg_mac_pool85_port_mib_counter3_tx_mac_missing_eop_err_cnt {
      type oc-yang:counter64;
      description
        "MAC TX missing eop errors count.";
    }
    leaf counter_slice12_ifg_mac_pool85_port_mib_counter4_tx_mac_missing_eop_err_cnt {
      type oc-yang:counter64;
      description
        "MAC TX missing eop errors count.";
    }
    leaf counter_slice12_ifg_mac_pool85_port_mib_counter5_tx_mac_missing_eop_err_cnt {
      type oc-yang:counter64;
      description
        "MAC TX missing eop errors count.";
    }
    leaf counter_slice12_ifg_mac_pool85_port_mib_counter6_tx_mac_missing_eop_err_cnt {
      type oc-yang:counter64;
      description
        "MAC TX missing eop errors count.";
    }
    leaf counter_slice12_ifg_mac_pool85_port_mib_counter7_tx_mac_missing_eop_err_cnt {
      type oc-yang:counter64;
      description
        "MAC TX missing eop errors count.";
    }
    leaf counter_slice12_ifg_mac_pool86_port_mib_counter0_tx_mac_missing_eop_err_cnt {
      type oc-yang:counter64;
      description
        "MAC TX missing eop errors count.";
    }
    leaf counter_slice12_ifg_mac_pool86_port_mib_counter1_tx_mac_missing_eop_err_cnt {
      type oc-yang:counter64;
      description
        "MAC TX missing eop errors count.";
    }
    leaf counter_slice12_ifg_mac_pool86_port_mib_counter2_tx_mac_missing_eop_err_cnt {
      type oc-yang:counter64;
      description
        "MAC TX missing eop errors count.";
    }
    leaf counter_slice12_ifg_mac_pool86_port_mib_counter3_tx_mac_missing_eop_err_cnt {
      type oc-yang:counter64;
      description
        "MAC TX missing eop errors count.";
    }
    leaf counter_slice12_ifg_mac_pool86_port_mib_counter4_tx_mac_missing_eop_err_cnt {
      type oc-yang:counter64;
      description
        "MAC TX missing eop errors count.";
    }
    leaf counter_slice12_ifg_mac_pool86_port_mib_counter5_tx_mac_missing_eop_err_cnt {
      type oc-yang:counter64;
      description
        "MAC TX missing eop errors count.";
    }
    leaf counter_slice12_ifg_mac_pool86_port_mib_counter6_tx_mac_missing_eop_err_cnt {
      type oc-yang:counter64;
      description
        "MAC TX missing eop errors count.";
    }
    leaf counter_slice12_ifg_mac_pool86_port_mib_counter7_tx_mac_missing_eop_err_cnt {
      type oc-yang:counter64;
      description
        "MAC TX missing eop errors count.";
    }
    leaf counter_slice12_ifg_mac_pool87_port_mib_counter0_tx_mac_missing_eop_err_cnt {
      type oc-yang:counter64;
      description
        "MAC TX missing eop errors count.";
    }
    leaf counter_slice12_ifg_mac_pool87_port_mib_counter1_tx_mac_missing_eop_err_cnt {
      type oc-yang:counter64;
      description
        "MAC TX missing eop errors count.";
    }
    leaf counter_slice12_ifg_mac_pool87_port_mib_counter2_tx_mac_missing_eop_err_cnt {
      type oc-yang:counter64;
      description
        "MAC TX missing eop errors count.";
    }
    leaf counter_slice12_ifg_mac_pool87_port_mib_counter3_tx_mac_missing_eop_err_cnt {
      type oc-yang:counter64;
      description
        "MAC TX missing eop errors count.";
    }
    leaf counter_slice12_ifg_mac_pool87_port_mib_counter4_tx_mac_missing_eop_err_cnt {
      type oc-yang:counter64;
      description
        "MAC TX missing eop errors count.";
    }
    leaf counter_slice12_ifg_mac_pool87_port_mib_counter5_tx_mac_missing_eop_err_cnt {
      type oc-yang:counter64;
      description
        "MAC TX missing eop errors count.";
    }
    leaf counter_slice12_ifg_mac_pool87_port_mib_counter6_tx_mac_missing_eop_err_cnt {
      type oc-yang:counter64;
      description
        "MAC TX missing eop errors count.";
    }
    leaf counter_slice12_ifg_mac_pool87_port_mib_counter7_tx_mac_missing_eop_err_cnt {
      type oc-yang:counter64;
      description
        "MAC TX missing eop errors count.";
    }
    leaf counter_slice13_ifg_mac_pool80_port_mib_counter0_tx_mac_missing_eop_err_cnt {
      type oc-yang:counter64;
      description
        "MAC TX missing eop errors count.";
    }
    leaf counter_slice13_ifg_mac_pool80_port_mib_counter1_tx_mac_missing_eop_err_cnt {
      type oc-yang:counter64;
      description
        "MAC TX missing eop errors count.";
    }
    leaf counter_slice13_ifg_mac_pool80_port_mib_counter2_tx_mac_missing_eop_err_cnt {
      type oc-yang:counter64;
      description
        "MAC TX missing eop errors count.";
    }
    leaf counter_slice13_ifg_mac_pool80_port_mib_counter3_tx_mac_missing_eop_err_cnt {
      type oc-yang:counter64;
      description
        "MAC TX missing eop errors count.";
    }
    leaf counter_slice13_ifg_mac_pool80_port_mib_counter4_tx_mac_missing_eop_err_cnt {
      type oc-yang:counter64;
      description
        "MAC TX missing eop errors count.";
    }
    leaf counter_slice13_ifg_mac_pool80_port_mib_counter5_tx_mac_missing_eop_err_cnt {
      type oc-yang:counter64;
      description
        "MAC TX missing eop errors count.";
    }
    leaf counter_slice13_ifg_mac_pool80_port_mib_counter6_tx_mac_missing_eop_err_cnt {
      type oc-yang:counter64;
      description
        "MAC TX missing eop errors count.";
    }
    leaf counter_slice13_ifg_mac_pool80_port_mib_counter7_tx_mac_missing_eop_err_cnt {
      type oc-yang:counter64;
      description
        "MAC TX missing eop errors count.";
    }
    leaf counter_slice13_ifg_mac_pool81_port_mib_counter0_tx_mac_missing_eop_err_cnt {
      type oc-yang:counter64;
      description
        "MAC TX missing eop errors count.";
    }
    leaf counter_slice13_ifg_mac_pool81_port_mib_counter1_tx_mac_missing_eop_err_cnt {
      type oc-yang:counter64;
      description
        "MAC TX missing eop errors count.";
    }
    leaf counter_slice13_ifg_mac_pool81_port_mib_counter2_tx_mac_missing_eop_err_cnt {
      type oc-yang:counter64;
      description
        "MAC TX missing eop errors count.";
    }
    leaf counter_slice13_ifg_mac_pool81_port_mib_counter3_tx_mac_missing_eop_err_cnt {
      type oc-yang:counter64;
      description
        "MAC TX missing eop errors count.";
    }
    leaf counter_slice13_ifg_mac_pool81_port_mib_counter4_tx_mac_missing_eop_err_cnt {
      type oc-yang:counter64;
      description
        "MAC TX missing eop errors count.";
    }
    leaf counter_slice13_ifg_mac_pool81_port_mib_counter5_tx_mac_missing_eop_err_cnt {
      type oc-yang:counter64;
      description
        "MAC TX missing eop errors count.";
    }
    leaf counter_slice13_ifg_mac_pool81_port_mib_counter6_tx_mac_missing_eop_err_cnt {
      type oc-yang:counter64;
      description
        "MAC TX missing eop errors count.";
    }
    leaf counter_slice13_ifg_mac_pool81_port_mib_counter7_tx_mac_missing_eop_err_cnt {
      type oc-yang:counter64;
      description
        "MAC TX missing eop errors count.";
    }
    leaf counter_slice13_ifg_mac_pool82_port_mib_counter0_tx_mac_missing_eop_err_cnt {
      type oc-yang:counter64;
      description
        "MAC TX missing eop errors count.";
    }
    leaf counter_slice13_ifg_mac_pool82_port_mib_counter1_tx_mac_missing_eop_err_cnt {
      type oc-yang:counter64;
      description
        "MAC TX missing eop errors count.";
    }
    leaf counter_slice13_ifg_mac_pool82_port_mib_counter2_tx_mac_missing_eop_err_cnt {
      type oc-yang:counter64;
      description
        "MAC TX missing eop errors count.";
    }
    leaf counter_slice13_ifg_mac_pool82_port_mib_counter3_tx_mac_missing_eop_err_cnt {
      type oc-yang:counter64;
      description
        "MAC TX missing eop errors count.";
    }
    leaf counter_slice13_ifg_mac_pool82_port_mib_counter4_tx_mac_missing_eop_err_cnt {
      type oc-yang:counter64;
      description
        "MAC TX missing eop errors count.";
    }
    leaf counter_slice13_ifg_mac_pool82_port_mib_counter5_tx_mac_missing_eop_err_cnt {
      type oc-yang:counter64;
      description
        "MAC TX missing eop errors count.";
    }
    leaf counter_slice13_ifg_mac_pool82_port_mib_counter6_tx_mac_missing_eop_err_cnt {
      type oc-yang:counter64;
      description
        "MAC TX missing eop errors count.";
    }
    leaf counter_slice13_ifg_mac_pool82_port_mib_counter7_tx_mac_missing_eop_err_cnt {
      type oc-yang:counter64;
      description
        "MAC TX missing eop errors count.";
    }
    leaf counter_slice13_ifg_mac_pool83_port_mib_counter0_tx_mac_missing_eop_err_cnt {
      type oc-yang:counter64;
      description
        "MAC TX missing eop errors count.";
    }
    leaf counter_slice13_ifg_mac_pool83_port_mib_counter1_tx_mac_missing_eop_err_cnt {
      type oc-yang:counter64;
      description
        "MAC TX missing eop errors count.";
    }
    leaf counter_slice13_ifg_mac_pool83_port_mib_counter2_tx_mac_missing_eop_err_cnt {
      type oc-yang:counter64;
      description
        "MAC TX missing eop errors count.";
    }
    leaf counter_slice13_ifg_mac_pool83_port_mib_counter3_tx_mac_missing_eop_err_cnt {
      type oc-yang:counter64;
      description
        "MAC TX missing eop errors count.";
    }
    leaf counter_slice13_ifg_mac_pool83_port_mib_counter4_tx_mac_missing_eop_err_cnt {
      type oc-yang:counter64;
      description
        "MAC TX missing eop errors count.";
    }
    leaf counter_slice13_ifg_mac_pool83_port_mib_counter5_tx_mac_missing_eop_err_cnt {
      type oc-yang:counter64;
      description
        "MAC TX missing eop errors count.";
    }
    leaf counter_slice13_ifg_mac_pool83_port_mib_counter6_tx_mac_missing_eop_err_cnt {
      type oc-yang:counter64;
      description
        "MAC TX missing eop errors count.";
    }
    leaf counter_slice13_ifg_mac_pool83_port_mib_counter7_tx_mac_missing_eop_err_cnt {
      type oc-yang:counter64;
      description
        "MAC TX missing eop errors count.";
    }
    leaf counter_slice13_ifg_mac_pool84_port_mib_counter0_tx_mac_missing_eop_err_cnt {
      type oc-yang:counter64;
      description
        "MAC TX missing eop errors count.";
    }
    leaf counter_slice13_ifg_mac_pool84_port_mib_counter1_tx_mac_missing_eop_err_cnt {
      type oc-yang:counter64;
      description
        "MAC TX missing eop errors count.";
    }
    leaf counter_slice13_ifg_mac_pool84_port_mib_counter2_tx_mac_missing_eop_err_cnt {
      type oc-yang:counter64;
      description
        "MAC TX missing eop errors count.";
    }
    leaf counter_slice13_ifg_mac_pool84_port_mib_counter3_tx_mac_missing_eop_err_cnt {
      type oc-yang:counter64;
      description
        "MAC TX missing eop errors count.";
    }
    leaf counter_slice13_ifg_mac_pool84_port_mib_counter4_tx_mac_missing_eop_err_cnt {
      type oc-yang:counter64;
      description
        "MAC TX missing eop errors count.";
    }
    leaf counter_slice13_ifg_mac_pool84_port_mib_counter5_tx_mac_missing_eop_err_cnt {
      type oc-yang:counter64;
      description
        "MAC TX missing eop errors count.";
    }
    leaf counter_slice13_ifg_mac_pool84_port_mib_counter6_tx_mac_missing_eop_err_cnt {
      type oc-yang:counter64;
      description
        "MAC TX missing eop errors count.";
    }
    leaf counter_slice13_ifg_mac_pool84_port_mib_counter7_tx_mac_missing_eop_err_cnt {
      type oc-yang:counter64;
      description
        "MAC TX missing eop errors count.";
    }
    leaf counter_slice13_ifg_mac_pool85_port_mib_counter0_tx_mac_missing_eop_err_cnt {
      type oc-yang:counter64;
      description
        "MAC TX missing eop errors count.";
    }
    leaf counter_slice13_ifg_mac_pool85_port_mib_counter1_tx_mac_missing_eop_err_cnt {
      type oc-yang:counter64;
      description
        "MAC TX missing eop errors count.";
    }
    leaf counter_slice13_ifg_mac_pool85_port_mib_counter2_tx_mac_missing_eop_err_cnt {
      type oc-yang:counter64;
      description
        "MAC TX missing eop errors count.";
    }
    leaf counter_slice13_ifg_mac_pool85_port_mib_counter3_tx_mac_missing_eop_err_cnt {
      type oc-yang:counter64;
      description
        "MAC TX missing eop errors count.";
    }
    leaf counter_slice13_ifg_mac_pool85_port_mib_counter4_tx_mac_missing_eop_err_cnt {
      type oc-yang:counter64;
      description
        "MAC TX missing eop errors count.";
    }
    leaf counter_slice13_ifg_mac_pool85_port_mib_counter5_tx_mac_missing_eop_err_cnt {
      type oc-yang:counter64;
      description
        "MAC TX missing eop errors count.";
    }
    leaf counter_slice13_ifg_mac_pool85_port_mib_counter6_tx_mac_missing_eop_err_cnt {
      type oc-yang:counter64;
      description
        "MAC TX missing eop errors count.";
    }
    leaf counter_slice13_ifg_mac_pool85_port_mib_counter7_tx_mac_missing_eop_err_cnt {
      type oc-yang:counter64;
      description
        "MAC TX missing eop errors count.";
    }
    leaf counter_slice13_ifg_mac_pool86_port_mib_counter0_tx_mac_missing_eop_err_cnt {
      type oc-yang:counter64;
      description
        "MAC TX missing eop errors count.";
    }
    leaf counter_slice13_ifg_mac_pool86_port_mib_counter1_tx_mac_missing_eop_err_cnt {
      type oc-yang:counter64;
      description
        "MAC TX missing eop errors count.";
    }
    leaf counter_slice13_ifg_mac_pool86_port_mib_counter2_tx_mac_missing_eop_err_cnt {
      type oc-yang:counter64;
      description
        "MAC TX missing eop errors count.";
    }
    leaf counter_slice13_ifg_mac_pool86_port_mib_counter3_tx_mac_missing_eop_err_cnt {
      type oc-yang:counter64;
      description
        "MAC TX missing eop errors count.";
    }
    leaf counter_slice13_ifg_mac_pool86_port_mib_counter4_tx_mac_missing_eop_err_cnt {
      type oc-yang:counter64;
      description
        "MAC TX missing eop errors count.";
    }
    leaf counter_slice13_ifg_mac_pool86_port_mib_counter5_tx_mac_missing_eop_err_cnt {
      type oc-yang:counter64;
      description
        "MAC TX missing eop errors count.";
    }
    leaf counter_slice13_ifg_mac_pool86_port_mib_counter6_tx_mac_missing_eop_err_cnt {
      type oc-yang:counter64;
      description
        "MAC TX missing eop errors count.";
    }
    leaf counter_slice13_ifg_mac_pool86_port_mib_counter7_tx_mac_missing_eop_err_cnt {
      type oc-yang:counter64;
      description
        "MAC TX missing eop errors count.";
    }
    leaf counter_slice13_ifg_mac_pool87_port_mib_counter0_tx_mac_missing_eop_err_cnt {
      type oc-yang:counter64;
      description
        "MAC TX missing eop errors count.";
    }
    leaf counter_slice13_ifg_mac_pool87_port_mib_counter1_tx_mac_missing_eop_err_cnt {
      type oc-yang:counter64;
      description
        "MAC TX missing eop errors count.";
    }
    leaf counter_slice13_ifg_mac_pool87_port_mib_counter2_tx_mac_missing_eop_err_cnt {
      type oc-yang:counter64;
      description
        "MAC TX missing eop errors count.";
    }
    leaf counter_slice13_ifg_mac_pool87_port_mib_counter3_tx_mac_missing_eop_err_cnt {
      type oc-yang:counter64;
      description
        "MAC TX missing eop errors count.";
    }
    leaf counter_slice13_ifg_mac_pool87_port_mib_counter4_tx_mac_missing_eop_err_cnt {
      type oc-yang:counter64;
      description
        "MAC TX missing eop errors count.";
    }
    leaf counter_slice13_ifg_mac_pool87_port_mib_counter5_tx_mac_missing_eop_err_cnt {
      type oc-yang:counter64;
      description
        "MAC TX missing eop errors count.";
    }
    leaf counter_slice13_ifg_mac_pool87_port_mib_counter6_tx_mac_missing_eop_err_cnt {
      type oc-yang:counter64;
      description
        "MAC TX missing eop errors count.";
    }
    leaf counter_slice13_ifg_mac_pool87_port_mib_counter7_tx_mac_missing_eop_err_cnt {
      type oc-yang:counter64;
      description
        "MAC TX missing eop errors count.";
    }
    leaf counter_slice14_ifg_mac_pool80_port_mib_counter0_tx_mac_missing_eop_err_cnt {
      type oc-yang:counter64;
      description
        "MAC TX missing eop errors count.";
    }
    leaf counter_slice14_ifg_mac_pool80_port_mib_counter1_tx_mac_missing_eop_err_cnt {
      type oc-yang:counter64;
      description
        "MAC TX missing eop errors count.";
    }
    leaf counter_slice14_ifg_mac_pool80_port_mib_counter2_tx_mac_missing_eop_err_cnt {
      type oc-yang:counter64;
      description
        "MAC TX missing eop errors count.";
    }
    leaf counter_slice14_ifg_mac_pool80_port_mib_counter3_tx_mac_missing_eop_err_cnt {
      type oc-yang:counter64;
      description
        "MAC TX missing eop errors count.";
    }
    leaf counter_slice14_ifg_mac_pool80_port_mib_counter4_tx_mac_missing_eop_err_cnt {
      type oc-yang:counter64;
      description
        "MAC TX missing eop errors count.";
    }
    leaf counter_slice14_ifg_mac_pool80_port_mib_counter5_tx_mac_missing_eop_err_cnt {
      type oc-yang:counter64;
      description
        "MAC TX missing eop errors count.";
    }
    leaf counter_slice14_ifg_mac_pool80_port_mib_counter6_tx_mac_missing_eop_err_cnt {
      type oc-yang:counter64;
      description
        "MAC TX missing eop errors count.";
    }
    leaf counter_slice14_ifg_mac_pool80_port_mib_counter7_tx_mac_missing_eop_err_cnt {
      type oc-yang:counter64;
      description
        "MAC TX missing eop errors count.";
    }
    leaf counter_slice14_ifg_mac_pool81_port_mib_counter0_tx_mac_missing_eop_err_cnt {
      type oc-yang:counter64;
      description
        "MAC TX missing eop errors count.";
    }
    leaf counter_slice14_ifg_mac_pool81_port_mib_counter1_tx_mac_missing_eop_err_cnt {
      type oc-yang:counter64;
      description
        "MAC TX missing eop errors count.";
    }
    leaf counter_slice14_ifg_mac_pool81_port_mib_counter2_tx_mac_missing_eop_err_cnt {
      type oc-yang:counter64;
      description
        "MAC TX missing eop errors count.";
    }
    leaf counter_slice14_ifg_mac_pool81_port_mib_counter3_tx_mac_missing_eop_err_cnt {
      type oc-yang:counter64;
      description
        "MAC TX missing eop errors count.";
    }
    leaf counter_slice14_ifg_mac_pool81_port_mib_counter4_tx_mac_missing_eop_err_cnt {
      type oc-yang:counter64;
      description
        "MAC TX missing eop errors count.";
    }
    leaf counter_slice14_ifg_mac_pool81_port_mib_counter5_tx_mac_missing_eop_err_cnt {
      type oc-yang:counter64;
      description
        "MAC TX missing eop errors count.";
    }
    leaf counter_slice14_ifg_mac_pool81_port_mib_counter6_tx_mac_missing_eop_err_cnt {
      type oc-yang:counter64;
      description
        "MAC TX missing eop errors count.";
    }
    leaf counter_slice14_ifg_mac_pool81_port_mib_counter7_tx_mac_missing_eop_err_cnt {
      type oc-yang:counter64;
      description
        "MAC TX missing eop errors count.";
    }
    leaf counter_slice14_ifg_mac_pool82_port_mib_counter0_tx_mac_missing_eop_err_cnt {
      type oc-yang:counter64;
      description
        "MAC TX missing eop errors count.";
    }
    leaf counter_slice14_ifg_mac_pool82_port_mib_counter1_tx_mac_missing_eop_err_cnt {
      type oc-yang:counter64;
      description
        "MAC TX missing eop errors count.";
    }
    leaf counter_slice14_ifg_mac_pool82_port_mib_counter2_tx_mac_missing_eop_err_cnt {
      type oc-yang:counter64;
      description
        "MAC TX missing eop errors count.";
    }
    leaf counter_slice14_ifg_mac_pool82_port_mib_counter3_tx_mac_missing_eop_err_cnt {
      type oc-yang:counter64;
      description
        "MAC TX missing eop errors count.";
    }
    leaf counter_slice14_ifg_mac_pool82_port_mib_counter4_tx_mac_missing_eop_err_cnt {
      type oc-yang:counter64;
      description
        "MAC TX missing eop errors count.";
    }
    leaf counter_slice14_ifg_mac_pool82_port_mib_counter5_tx_mac_missing_eop_err_cnt {
      type oc-yang:counter64;
      description
        "MAC TX missing eop errors count.";
    }
    leaf counter_slice14_ifg_mac_pool82_port_mib_counter6_tx_mac_missing_eop_err_cnt {
      type oc-yang:counter64;
      description
        "MAC TX missing eop errors count.";
    }
    leaf counter_slice14_ifg_mac_pool82_port_mib_counter7_tx_mac_missing_eop_err_cnt {
      type oc-yang:counter64;
      description
        "MAC TX missing eop errors count.";
    }
    leaf counter_slice14_ifg_mac_pool83_port_mib_counter0_tx_mac_missing_eop_err_cnt {
      type oc-yang:counter64;
      description
        "MAC TX missing eop errors count.";
    }
    leaf counter_slice14_ifg_mac_pool83_port_mib_counter1_tx_mac_missing_eop_err_cnt {
      type oc-yang:counter64;
      description
        "MAC TX missing eop errors count.";
    }
    leaf counter_slice14_ifg_mac_pool83_port_mib_counter2_tx_mac_missing_eop_err_cnt {
      type oc-yang:counter64;
      description
        "MAC TX missing eop errors count.";
    }
    leaf counter_slice14_ifg_mac_pool83_port_mib_counter3_tx_mac_missing_eop_err_cnt {
      type oc-yang:counter64;
      description
        "MAC TX missing eop errors count.";
    }
    leaf counter_slice14_ifg_mac_pool83_port_mib_counter4_tx_mac_missing_eop_err_cnt {
      type oc-yang:counter64;
      description
        "MAC TX missing eop errors count.";
    }
    leaf counter_slice14_ifg_mac_pool83_port_mib_counter5_tx_mac_missing_eop_err_cnt {
      type oc-yang:counter64;
      description
        "MAC TX missing eop errors count.";
    }
    leaf counter_slice14_ifg_mac_pool83_port_mib_counter6_tx_mac_missing_eop_err_cnt {
      type oc-yang:counter64;
      description
        "MAC TX missing eop errors count.";
    }
    leaf counter_slice14_ifg_mac_pool83_port_mib_counter7_tx_mac_missing_eop_err_cnt {
      type oc-yang:counter64;
      description
        "MAC TX missing eop errors count.";
    }
    leaf counter_slice14_ifg_mac_pool84_port_mib_counter0_tx_mac_missing_eop_err_cnt {
      type oc-yang:counter64;
      description
        "MAC TX missing eop errors count.";
    }
    leaf counter_slice14_ifg_mac_pool84_port_mib_counter1_tx_mac_missing_eop_err_cnt {
      type oc-yang:counter64;
      description
        "MAC TX missing eop errors count.";
    }
    leaf counter_slice14_ifg_mac_pool84_port_mib_counter2_tx_mac_missing_eop_err_cnt {
      type oc-yang:counter64;
      description
        "MAC TX missing eop errors count.";
    }
    leaf counter_slice14_ifg_mac_pool84_port_mib_counter3_tx_mac_missing_eop_err_cnt {
      type oc-yang:counter64;
      description
        "MAC TX missing eop errors count.";
    }
    leaf counter_slice14_ifg_mac_pool84_port_mib_counter4_tx_mac_missing_eop_err_cnt {
      type oc-yang:counter64;
      description
        "MAC TX missing eop errors count.";
    }
    leaf counter_slice14_ifg_mac_pool84_port_mib_counter5_tx_mac_missing_eop_err_cnt {
      type oc-yang:counter64;
      description
        "MAC TX missing eop errors count.";
    }
    leaf counter_slice14_ifg_mac_pool84_port_mib_counter6_tx_mac_missing_eop_err_cnt {
      type oc-yang:counter64;
      description
        "MAC TX missing eop errors count.";
    }
    leaf counter_slice14_ifg_mac_pool84_port_mib_counter7_tx_mac_missing_eop_err_cnt {
      type oc-yang:counter64;
      description
        "MAC TX missing eop errors count.";
    }
    leaf counter_slice14_ifg_mac_pool85_port_mib_counter0_tx_mac_missing_eop_err_cnt {
      type oc-yang:counter64;
      description
        "MAC TX missing eop errors count.";
    }
    leaf counter_slice14_ifg_mac_pool85_port_mib_counter1_tx_mac_missing_eop_err_cnt {
      type oc-yang:counter64;
      description
        "MAC TX missing eop errors count.";
    }
    leaf counter_slice14_ifg_mac_pool85_port_mib_counter2_tx_mac_missing_eop_err_cnt {
      type oc-yang:counter64;
      description
        "MAC TX missing eop errors count.";
    }
    leaf counter_slice14_ifg_mac_pool85_port_mib_counter3_tx_mac_missing_eop_err_cnt {
      type oc-yang:counter64;
      description
        "MAC TX missing eop errors count.";
    }
    leaf counter_slice14_ifg_mac_pool85_port_mib_counter4_tx_mac_missing_eop_err_cnt {
      type oc-yang:counter64;
      description
        "MAC TX missing eop errors count.";
    }
    leaf counter_slice14_ifg_mac_pool85_port_mib_counter5_tx_mac_missing_eop_err_cnt {
      type oc-yang:counter64;
      description
        "MAC TX missing eop errors count.";
    }
    leaf counter_slice14_ifg_mac_pool85_port_mib_counter6_tx_mac_missing_eop_err_cnt {
      type oc-yang:counter64;
      description
        "MAC TX missing eop errors count.";
    }
    leaf counter_slice14_ifg_mac_pool85_port_mib_counter7_tx_mac_missing_eop_err_cnt {
      type oc-yang:counter64;
      description
        "MAC TX missing eop errors count.";
    }
    leaf counter_slice14_ifg_mac_pool86_port_mib_counter0_tx_mac_missing_eop_err_cnt {
      type oc-yang:counter64;
      description
        "MAC TX missing eop errors count.";
    }
    leaf counter_slice14_ifg_mac_pool86_port_mib_counter1_tx_mac_missing_eop_err_cnt {
      type oc-yang:counter64;
      description
        "MAC TX missing eop errors count.";
    }
    leaf counter_slice14_ifg_mac_pool86_port_mib_counter2_tx_mac_missing_eop_err_cnt {
      type oc-yang:counter64;
      description
        "MAC TX missing eop errors count.";
    }
    leaf counter_slice14_ifg_mac_pool86_port_mib_counter3_tx_mac_missing_eop_err_cnt {
      type oc-yang:counter64;
      description
        "MAC TX missing eop errors count.";
    }
    leaf counter_slice14_ifg_mac_pool86_port_mib_counter4_tx_mac_missing_eop_err_cnt {
      type oc-yang:counter64;
      description
        "MAC TX missing eop errors count.";
    }
    leaf counter_slice14_ifg_mac_pool86_port_mib_counter5_tx_mac_missing_eop_err_cnt {
      type oc-yang:counter64;
      description
        "MAC TX missing eop errors count.";
    }
    leaf counter_slice14_ifg_mac_pool86_port_mib_counter6_tx_mac_missing_eop_err_cnt {
      type oc-yang:counter64;
      description
        "MAC TX missing eop errors count.";
    }
    leaf counter_slice14_ifg_mac_pool86_port_mib_counter7_tx_mac_missing_eop_err_cnt {
      type oc-yang:counter64;
      description
        "MAC TX missing eop errors count.";
    }
    leaf counter_slice14_ifg_mac_pool87_port_mib_counter0_tx_mac_missing_eop_err_cnt {
      type oc-yang:counter64;
      description
        "MAC TX missing eop errors count.";
    }
    leaf counter_slice14_ifg_mac_pool87_port_mib_counter1_tx_mac_missing_eop_err_cnt {
      type oc-yang:counter64;
      description
        "MAC TX missing eop errors count.";
    }
    leaf counter_slice14_ifg_mac_pool87_port_mib_counter2_tx_mac_missing_eop_err_cnt {
      type oc-yang:counter64;
      description
        "MAC TX missing eop errors count.";
    }
    leaf counter_slice14_ifg_mac_pool87_port_mib_counter3_tx_mac_missing_eop_err_cnt {
      type oc-yang:counter64;
      description
        "MAC TX missing eop errors count.";
    }
    leaf counter_slice14_ifg_mac_pool87_port_mib_counter4_tx_mac_missing_eop_err_cnt {
      type oc-yang:counter64;
      description
        "MAC TX missing eop errors count.";
    }
    leaf counter_slice14_ifg_mac_pool87_port_mib_counter5_tx_mac_missing_eop_err_cnt {
      type oc-yang:counter64;
      description
        "MAC TX missing eop errors count.";
    }
    leaf counter_slice14_ifg_mac_pool87_port_mib_counter6_tx_mac_missing_eop_err_cnt {
      type oc-yang:counter64;
      description
        "MAC TX missing eop errors count.";
    }
    leaf counter_slice14_ifg_mac_pool87_port_mib_counter7_tx_mac_missing_eop_err_cnt {
      type oc-yang:counter64;
      description
        "MAC TX missing eop errors count.";
    }
    leaf counter_slice15_ifg_mac_pool80_port_mib_counter0_tx_mac_missing_eop_err_cnt {
      type oc-yang:counter64;
      description
        "MAC TX missing eop errors count.";
    }
    leaf counter_slice15_ifg_mac_pool80_port_mib_counter1_tx_mac_missing_eop_err_cnt {
      type oc-yang:counter64;
      description
        "MAC TX missing eop errors count.";
    }
    leaf counter_slice15_ifg_mac_pool80_port_mib_counter2_tx_mac_missing_eop_err_cnt {
      type oc-yang:counter64;
      description
        "MAC TX missing eop errors count.";
    }
    leaf counter_slice15_ifg_mac_pool80_port_mib_counter3_tx_mac_missing_eop_err_cnt {
      type oc-yang:counter64;
      description
        "MAC TX missing eop errors count.";
    }
    leaf counter_slice15_ifg_mac_pool80_port_mib_counter4_tx_mac_missing_eop_err_cnt {
      type oc-yang:counter64;
      description
        "MAC TX missing eop errors count.";
    }
    leaf counter_slice15_ifg_mac_pool80_port_mib_counter5_tx_mac_missing_eop_err_cnt {
      type oc-yang:counter64;
      description
        "MAC TX missing eop errors count.";
    }
    leaf counter_slice15_ifg_mac_pool80_port_mib_counter6_tx_mac_missing_eop_err_cnt {
      type oc-yang:counter64;
      description
        "MAC TX missing eop errors count.";
    }
    leaf counter_slice15_ifg_mac_pool80_port_mib_counter7_tx_mac_missing_eop_err_cnt {
      type oc-yang:counter64;
      description
        "MAC TX missing eop errors count.";
    }
    leaf counter_slice15_ifg_mac_pool81_port_mib_counter0_tx_mac_missing_eop_err_cnt {
      type oc-yang:counter64;
      description
        "MAC TX missing eop errors count.";
    }
    leaf counter_slice15_ifg_mac_pool81_port_mib_counter1_tx_mac_missing_eop_err_cnt {
      type oc-yang:counter64;
      description
        "MAC TX missing eop errors count.";
    }
    leaf counter_slice15_ifg_mac_pool81_port_mib_counter2_tx_mac_missing_eop_err_cnt {
      type oc-yang:counter64;
      description
        "MAC TX missing eop errors count.";
    }
    leaf counter_slice15_ifg_mac_pool81_port_mib_counter3_tx_mac_missing_eop_err_cnt {
      type oc-yang:counter64;
      description
        "MAC TX missing eop errors count.";
    }
    leaf counter_slice15_ifg_mac_pool81_port_mib_counter4_tx_mac_missing_eop_err_cnt {
      type oc-yang:counter64;
      description
        "MAC TX missing eop errors count.";
    }
    leaf counter_slice15_ifg_mac_pool81_port_mib_counter5_tx_mac_missing_eop_err_cnt {
      type oc-yang:counter64;
      description
        "MAC TX missing eop errors count.";
    }
    leaf counter_slice15_ifg_mac_pool81_port_mib_counter6_tx_mac_missing_eop_err_cnt {
      type oc-yang:counter64;
      description
        "MAC TX missing eop errors count.";
    }
    leaf counter_slice15_ifg_mac_pool81_port_mib_counter7_tx_mac_missing_eop_err_cnt {
      type oc-yang:counter64;
      description
        "MAC TX missing eop errors count.";
    }
    leaf counter_slice15_ifg_mac_pool82_port_mib_counter0_tx_mac_missing_eop_err_cnt {
      type oc-yang:counter64;
      description
        "MAC TX missing eop errors count.";
    }
    leaf counter_slice15_ifg_mac_pool82_port_mib_counter1_tx_mac_missing_eop_err_cnt {
      type oc-yang:counter64;
      description
        "MAC TX missing eop errors count.";
    }
    leaf counter_slice15_ifg_mac_pool82_port_mib_counter2_tx_mac_missing_eop_err_cnt {
      type oc-yang:counter64;
      description
        "MAC TX missing eop errors count.";
    }
    leaf counter_slice15_ifg_mac_pool82_port_mib_counter3_tx_mac_missing_eop_err_cnt {
      type oc-yang:counter64;
      description
        "MAC TX missing eop errors count.";
    }
    leaf counter_slice15_ifg_mac_pool82_port_mib_counter4_tx_mac_missing_eop_err_cnt {
      type oc-yang:counter64;
      description
        "MAC TX missing eop errors count.";
    }
    leaf counter_slice15_ifg_mac_pool82_port_mib_counter5_tx_mac_missing_eop_err_cnt {
      type oc-yang:counter64;
      description
        "MAC TX missing eop errors count.";
    }
    leaf counter_slice15_ifg_mac_pool82_port_mib_counter6_tx_mac_missing_eop_err_cnt {
      type oc-yang:counter64;
      description
        "MAC TX missing eop errors count.";
    }
    leaf counter_slice15_ifg_mac_pool82_port_mib_counter7_tx_mac_missing_eop_err_cnt {
      type oc-yang:counter64;
      description
        "MAC TX missing eop errors count.";
    }
    leaf counter_slice15_ifg_mac_pool83_port_mib_counter0_tx_mac_missing_eop_err_cnt {
      type oc-yang:counter64;
      description
        "MAC TX missing eop errors count.";
    }
    leaf counter_slice15_ifg_mac_pool83_port_mib_counter1_tx_mac_missing_eop_err_cnt {
      type oc-yang:counter64;
      description
        "MAC TX missing eop errors count.";
    }
    leaf counter_slice15_ifg_mac_pool83_port_mib_counter2_tx_mac_missing_eop_err_cnt {
      type oc-yang:counter64;
      description
        "MAC TX missing eop errors count.";
    }
    leaf counter_slice15_ifg_mac_pool83_port_mib_counter3_tx_mac_missing_eop_err_cnt {
      type oc-yang:counter64;
      description
        "MAC TX missing eop errors count.";
    }
    leaf counter_slice15_ifg_mac_pool83_port_mib_counter4_tx_mac_missing_eop_err_cnt {
      type oc-yang:counter64;
      description
        "MAC TX missing eop errors count.";
    }
    leaf counter_slice15_ifg_mac_pool83_port_mib_counter5_tx_mac_missing_eop_err_cnt {
      type oc-yang:counter64;
      description
        "MAC TX missing eop errors count.";
    }
    leaf counter_slice15_ifg_mac_pool83_port_mib_counter6_tx_mac_missing_eop_err_cnt {
      type oc-yang:counter64;
      description
        "MAC TX missing eop errors count.";
    }
    leaf counter_slice15_ifg_mac_pool83_port_mib_counter7_tx_mac_missing_eop_err_cnt {
      type oc-yang:counter64;
      description
        "MAC TX missing eop errors count.";
    }
    leaf counter_slice15_ifg_mac_pool84_port_mib_counter0_tx_mac_missing_eop_err_cnt {
      type oc-yang:counter64;
      description
        "MAC TX missing eop errors count.";
    }
    leaf counter_slice15_ifg_mac_pool84_port_mib_counter1_tx_mac_missing_eop_err_cnt {
      type oc-yang:counter64;
      description
        "MAC TX missing eop errors count.";
    }
    leaf counter_slice15_ifg_mac_pool84_port_mib_counter2_tx_mac_missing_eop_err_cnt {
      type oc-yang:counter64;
      description
        "MAC TX missing eop errors count.";
    }
    leaf counter_slice15_ifg_mac_pool84_port_mib_counter3_tx_mac_missing_eop_err_cnt {
      type oc-yang:counter64;
      description
        "MAC TX missing eop errors count.";
    }
    leaf counter_slice15_ifg_mac_pool84_port_mib_counter4_tx_mac_missing_eop_err_cnt {
      type oc-yang:counter64;
      description
        "MAC TX missing eop errors count.";
    }
    leaf counter_slice15_ifg_mac_pool84_port_mib_counter5_tx_mac_missing_eop_err_cnt {
      type oc-yang:counter64;
      description
        "MAC TX missing eop errors count.";
    }
    leaf counter_slice15_ifg_mac_pool84_port_mib_counter6_tx_mac_missing_eop_err_cnt {
      type oc-yang:counter64;
      description
        "MAC TX missing eop errors count.";
    }
    leaf counter_slice15_ifg_mac_pool84_port_mib_counter7_tx_mac_missing_eop_err_cnt {
      type oc-yang:counter64;
      description
        "MAC TX missing eop errors count.";
    }
    leaf counter_slice15_ifg_mac_pool85_port_mib_counter0_tx_mac_missing_eop_err_cnt {
      type oc-yang:counter64;
      description
        "MAC TX missing eop errors count.";
    }
    leaf counter_slice15_ifg_mac_pool85_port_mib_counter1_tx_mac_missing_eop_err_cnt {
      type oc-yang:counter64;
      description
        "MAC TX missing eop errors count.";
    }
    leaf counter_slice15_ifg_mac_pool85_port_mib_counter2_tx_mac_missing_eop_err_cnt {
      type oc-yang:counter64;
      description
        "MAC TX missing eop errors count.";
    }
    leaf counter_slice15_ifg_mac_pool85_port_mib_counter3_tx_mac_missing_eop_err_cnt {
      type oc-yang:counter64;
      description
        "MAC TX missing eop errors count.";
    }
    leaf counter_slice15_ifg_mac_pool85_port_mib_counter4_tx_mac_missing_eop_err_cnt {
      type oc-yang:counter64;
      description
        "MAC TX missing eop errors count.";
    }
    leaf counter_slice15_ifg_mac_pool85_port_mib_counter5_tx_mac_missing_eop_err_cnt {
      type oc-yang:counter64;
      description
        "MAC TX missing eop errors count.";
    }
    leaf counter_slice15_ifg_mac_pool85_port_mib_counter6_tx_mac_missing_eop_err_cnt {
      type oc-yang:counter64;
      description
        "MAC TX missing eop errors count.";
    }
    leaf counter_slice15_ifg_mac_pool85_port_mib_counter7_tx_mac_missing_eop_err_cnt {
      type oc-yang:counter64;
      description
        "MAC TX missing eop errors count.";
    }
    leaf counter_slice15_ifg_mac_pool86_port_mib_counter0_tx_mac_missing_eop_err_cnt {
      type oc-yang:counter64;
      description
        "MAC TX missing eop errors count.";
    }
    leaf counter_slice15_ifg_mac_pool86_port_mib_counter1_tx_mac_missing_eop_err_cnt {
      type oc-yang:counter64;
      description
        "MAC TX missing eop errors count.";
    }
    leaf counter_slice15_ifg_mac_pool86_port_mib_counter2_tx_mac_missing_eop_err_cnt {
      type oc-yang:counter64;
      description
        "MAC TX missing eop errors count.";
    }
    leaf counter_slice15_ifg_mac_pool86_port_mib_counter3_tx_mac_missing_eop_err_cnt {
      type oc-yang:counter64;
      description
        "MAC TX missing eop errors count.";
    }
    leaf counter_slice15_ifg_mac_pool86_port_mib_counter4_tx_mac_missing_eop_err_cnt {
      type oc-yang:counter64;
      description
        "MAC TX missing eop errors count.";
    }
    leaf counter_slice15_ifg_mac_pool86_port_mib_counter5_tx_mac_missing_eop_err_cnt {
      type oc-yang:counter64;
      description
        "MAC TX missing eop errors count.";
    }
    leaf counter_slice15_ifg_mac_pool86_port_mib_counter6_tx_mac_missing_eop_err_cnt {
      type oc-yang:counter64;
      description
        "MAC TX missing eop errors count.";
    }
    leaf counter_slice15_ifg_mac_pool86_port_mib_counter7_tx_mac_missing_eop_err_cnt {
      type oc-yang:counter64;
      description
        "MAC TX missing eop errors count.";
    }
    leaf counter_slice15_ifg_mac_pool87_port_mib_counter0_tx_mac_missing_eop_err_cnt {
      type oc-yang:counter64;
      description
        "MAC TX missing eop errors count.";
    }
    leaf counter_slice15_ifg_mac_pool87_port_mib_counter1_tx_mac_missing_eop_err_cnt {
      type oc-yang:counter64;
      description
        "MAC TX missing eop errors count.";
    }
    leaf counter_slice15_ifg_mac_pool87_port_mib_counter2_tx_mac_missing_eop_err_cnt {
      type oc-yang:counter64;
      description
        "MAC TX missing eop errors count.";
    }
    leaf counter_slice15_ifg_mac_pool87_port_mib_counter3_tx_mac_missing_eop_err_cnt {
      type oc-yang:counter64;
      description
        "MAC TX missing eop errors count.";
    }
    leaf counter_slice15_ifg_mac_pool87_port_mib_counter4_tx_mac_missing_eop_err_cnt {
      type oc-yang:counter64;
      description
        "MAC TX missing eop errors count.";
    }
    leaf counter_slice15_ifg_mac_pool87_port_mib_counter5_tx_mac_missing_eop_err_cnt {
      type oc-yang:counter64;
      description
        "MAC TX missing eop errors count.";
    }
    leaf counter_slice15_ifg_mac_pool87_port_mib_counter6_tx_mac_missing_eop_err_cnt {
      type oc-yang:counter64;
      description
        "MAC TX missing eop errors count.";
    }
    leaf counter_slice15_ifg_mac_pool87_port_mib_counter7_tx_mac_missing_eop_err_cnt {
      type oc-yang:counter64;
      description
        "MAC TX missing eop errors count.";
    }
    leaf counter_slice0_ifg_mac_pool80_port_mib_counter0_tx_mac_underrun_err_cnt {
      type oc-yang:counter64;
      description
        "MAC TX underrun errors count.";
    }
    leaf counter_slice0_ifg_mac_pool80_port_mib_counter1_tx_mac_underrun_err_cnt {
      type oc-yang:counter64;
      description
        "MAC TX underrun errors count.";
    }
    leaf counter_slice0_ifg_mac_pool80_port_mib_counter2_tx_mac_underrun_err_cnt {
      type oc-yang:counter64;
      description
        "MAC TX underrun errors count.";
    }
    leaf counter_slice0_ifg_mac_pool80_port_mib_counter3_tx_mac_underrun_err_cnt {
      type oc-yang:counter64;
      description
        "MAC TX underrun errors count.";
    }
    leaf counter_slice0_ifg_mac_pool80_port_mib_counter4_tx_mac_underrun_err_cnt {
      type oc-yang:counter64;
      description
        "MAC TX underrun errors count.";
    }
    leaf counter_slice0_ifg_mac_pool80_port_mib_counter5_tx_mac_underrun_err_cnt {
      type oc-yang:counter64;
      description
        "MAC TX underrun errors count.";
    }
    leaf counter_slice0_ifg_mac_pool80_port_mib_counter6_tx_mac_underrun_err_cnt {
      type oc-yang:counter64;
      description
        "MAC TX underrun errors count.";
    }
    leaf counter_slice0_ifg_mac_pool80_port_mib_counter7_tx_mac_underrun_err_cnt {
      type oc-yang:counter64;
      description
        "MAC TX underrun errors count.";
    }
    leaf counter_slice0_ifg_mac_pool81_port_mib_counter0_tx_mac_underrun_err_cnt {
      type oc-yang:counter64;
      description
        "MAC TX underrun errors count.";
    }
    leaf counter_slice0_ifg_mac_pool81_port_mib_counter1_tx_mac_underrun_err_cnt {
      type oc-yang:counter64;
      description
        "MAC TX underrun errors count.";
    }
    leaf counter_slice0_ifg_mac_pool81_port_mib_counter2_tx_mac_underrun_err_cnt {
      type oc-yang:counter64;
      description
        "MAC TX underrun errors count.";
    }
    leaf counter_slice0_ifg_mac_pool81_port_mib_counter3_tx_mac_underrun_err_cnt {
      type oc-yang:counter64;
      description
        "MAC TX underrun errors count.";
    }
    leaf counter_slice0_ifg_mac_pool81_port_mib_counter4_tx_mac_underrun_err_cnt {
      type oc-yang:counter64;
      description
        "MAC TX underrun errors count.";
    }
    leaf counter_slice0_ifg_mac_pool81_port_mib_counter5_tx_mac_underrun_err_cnt {
      type oc-yang:counter64;
      description
        "MAC TX underrun errors count.";
    }
    leaf counter_slice0_ifg_mac_pool81_port_mib_counter6_tx_mac_underrun_err_cnt {
      type oc-yang:counter64;
      description
        "MAC TX underrun errors count.";
    }
    leaf counter_slice0_ifg_mac_pool81_port_mib_counter7_tx_mac_underrun_err_cnt {
      type oc-yang:counter64;
      description
        "MAC TX underrun errors count.";
    }
    leaf counter_slice0_ifg_mac_pool82_port_mib_counter0_tx_mac_underrun_err_cnt {
      type oc-yang:counter64;
      description
        "MAC TX underrun errors count.";
    }
    leaf counter_slice0_ifg_mac_pool82_port_mib_counter1_tx_mac_underrun_err_cnt {
      type oc-yang:counter64;
      description
        "MAC TX underrun errors count.";
    }
    leaf counter_slice0_ifg_mac_pool82_port_mib_counter2_tx_mac_underrun_err_cnt {
      type oc-yang:counter64;
      description
        "MAC TX underrun errors count.";
    }
    leaf counter_slice0_ifg_mac_pool82_port_mib_counter3_tx_mac_underrun_err_cnt {
      type oc-yang:counter64;
      description
        "MAC TX underrun errors count.";
    }
    leaf counter_slice0_ifg_mac_pool82_port_mib_counter4_tx_mac_underrun_err_cnt {
      type oc-yang:counter64;
      description
        "MAC TX underrun errors count.";
    }
    leaf counter_slice0_ifg_mac_pool82_port_mib_counter5_tx_mac_underrun_err_cnt {
      type oc-yang:counter64;
      description
        "MAC TX underrun errors count.";
    }
    leaf counter_slice0_ifg_mac_pool82_port_mib_counter6_tx_mac_underrun_err_cnt {
      type oc-yang:counter64;
      description
        "MAC TX underrun errors count.";
    }
    leaf counter_slice0_ifg_mac_pool82_port_mib_counter7_tx_mac_underrun_err_cnt {
      type oc-yang:counter64;
      description
        "MAC TX underrun errors count.";
    }
    leaf counter_slice0_ifg_mac_pool83_port_mib_counter0_tx_mac_underrun_err_cnt {
      type oc-yang:counter64;
      description
        "MAC TX underrun errors count.";
    }
    leaf counter_slice0_ifg_mac_pool83_port_mib_counter1_tx_mac_underrun_err_cnt {
      type oc-yang:counter64;
      description
        "MAC TX underrun errors count.";
    }
    leaf counter_slice0_ifg_mac_pool83_port_mib_counter2_tx_mac_underrun_err_cnt {
      type oc-yang:counter64;
      description
        "MAC TX underrun errors count.";
    }
    leaf counter_slice0_ifg_mac_pool83_port_mib_counter3_tx_mac_underrun_err_cnt {
      type oc-yang:counter64;
      description
        "MAC TX underrun errors count.";
    }
    leaf counter_slice0_ifg_mac_pool83_port_mib_counter4_tx_mac_underrun_err_cnt {
      type oc-yang:counter64;
      description
        "MAC TX underrun errors count.";
    }
    leaf counter_slice0_ifg_mac_pool83_port_mib_counter5_tx_mac_underrun_err_cnt {
      type oc-yang:counter64;
      description
        "MAC TX underrun errors count.";
    }
    leaf counter_slice0_ifg_mac_pool83_port_mib_counter6_tx_mac_underrun_err_cnt {
      type oc-yang:counter64;
      description
        "MAC TX underrun errors count.";
    }
    leaf counter_slice0_ifg_mac_pool83_port_mib_counter7_tx_mac_underrun_err_cnt {
      type oc-yang:counter64;
      description
        "MAC TX underrun errors count.";
    }
    leaf counter_slice0_ifg_mac_pool84_port_mib_counter0_tx_mac_underrun_err_cnt {
      type oc-yang:counter64;
      description
        "MAC TX underrun errors count.";
    }
    leaf counter_slice0_ifg_mac_pool84_port_mib_counter1_tx_mac_underrun_err_cnt {
      type oc-yang:counter64;
      description
        "MAC TX underrun errors count.";
    }
    leaf counter_slice0_ifg_mac_pool84_port_mib_counter2_tx_mac_underrun_err_cnt {
      type oc-yang:counter64;
      description
        "MAC TX underrun errors count.";
    }
    leaf counter_slice0_ifg_mac_pool84_port_mib_counter3_tx_mac_underrun_err_cnt {
      type oc-yang:counter64;
      description
        "MAC TX underrun errors count.";
    }
    leaf counter_slice0_ifg_mac_pool84_port_mib_counter4_tx_mac_underrun_err_cnt {
      type oc-yang:counter64;
      description
        "MAC TX underrun errors count.";
    }
    leaf counter_slice0_ifg_mac_pool84_port_mib_counter5_tx_mac_underrun_err_cnt {
      type oc-yang:counter64;
      description
        "MAC TX underrun errors count.";
    }
    leaf counter_slice0_ifg_mac_pool84_port_mib_counter6_tx_mac_underrun_err_cnt {
      type oc-yang:counter64;
      description
        "MAC TX underrun errors count.";
    }
    leaf counter_slice0_ifg_mac_pool84_port_mib_counter7_tx_mac_underrun_err_cnt {
      type oc-yang:counter64;
      description
        "MAC TX underrun errors count.";
    }
    leaf counter_slice0_ifg_mac_pool85_port_mib_counter0_tx_mac_underrun_err_cnt {
      type oc-yang:counter64;
      description
        "MAC TX underrun errors count.";
    }
    leaf counter_slice0_ifg_mac_pool85_port_mib_counter1_tx_mac_underrun_err_cnt {
      type oc-yang:counter64;
      description
        "MAC TX underrun errors count.";
    }
    leaf counter_slice0_ifg_mac_pool85_port_mib_counter2_tx_mac_underrun_err_cnt {
      type oc-yang:counter64;
      description
        "MAC TX underrun errors count.";
    }
    leaf counter_slice0_ifg_mac_pool85_port_mib_counter3_tx_mac_underrun_err_cnt {
      type oc-yang:counter64;
      description
        "MAC TX underrun errors count.";
    }
    leaf counter_slice0_ifg_mac_pool85_port_mib_counter4_tx_mac_underrun_err_cnt {
      type oc-yang:counter64;
      description
        "MAC TX underrun errors count.";
    }
    leaf counter_slice0_ifg_mac_pool85_port_mib_counter5_tx_mac_underrun_err_cnt {
      type oc-yang:counter64;
      description
        "MAC TX underrun errors count.";
    }
    leaf counter_slice0_ifg_mac_pool85_port_mib_counter6_tx_mac_underrun_err_cnt {
      type oc-yang:counter64;
      description
        "MAC TX underrun errors count.";
    }
    leaf counter_slice0_ifg_mac_pool85_port_mib_counter7_tx_mac_underrun_err_cnt {
      type oc-yang:counter64;
      description
        "MAC TX underrun errors count.";
    }
    leaf counter_slice0_ifg_mac_pool86_port_mib_counter0_tx_mac_underrun_err_cnt {
      type oc-yang:counter64;
      description
        "MAC TX underrun errors count.";
    }
    leaf counter_slice0_ifg_mac_pool86_port_mib_counter1_tx_mac_underrun_err_cnt {
      type oc-yang:counter64;
      description
        "MAC TX underrun errors count.";
    }
    leaf counter_slice0_ifg_mac_pool86_port_mib_counter2_tx_mac_underrun_err_cnt {
      type oc-yang:counter64;
      description
        "MAC TX underrun errors count.";
    }
    leaf counter_slice0_ifg_mac_pool86_port_mib_counter3_tx_mac_underrun_err_cnt {
      type oc-yang:counter64;
      description
        "MAC TX underrun errors count.";
    }
    leaf counter_slice0_ifg_mac_pool86_port_mib_counter4_tx_mac_underrun_err_cnt {
      type oc-yang:counter64;
      description
        "MAC TX underrun errors count.";
    }
    leaf counter_slice0_ifg_mac_pool86_port_mib_counter5_tx_mac_underrun_err_cnt {
      type oc-yang:counter64;
      description
        "MAC TX underrun errors count.";
    }
    leaf counter_slice0_ifg_mac_pool86_port_mib_counter6_tx_mac_underrun_err_cnt {
      type oc-yang:counter64;
      description
        "MAC TX underrun errors count.";
    }
    leaf counter_slice0_ifg_mac_pool86_port_mib_counter7_tx_mac_underrun_err_cnt {
      type oc-yang:counter64;
      description
        "MAC TX underrun errors count.";
    }
    leaf counter_slice0_ifg_mac_pool87_port_mib_counter0_tx_mac_underrun_err_cnt {
      type oc-yang:counter64;
      description
        "MAC TX underrun errors count.";
    }
    leaf counter_slice0_ifg_mac_pool87_port_mib_counter1_tx_mac_underrun_err_cnt {
      type oc-yang:counter64;
      description
        "MAC TX underrun errors count.";
    }
    leaf counter_slice0_ifg_mac_pool87_port_mib_counter2_tx_mac_underrun_err_cnt {
      type oc-yang:counter64;
      description
        "MAC TX underrun errors count.";
    }
    leaf counter_slice0_ifg_mac_pool87_port_mib_counter3_tx_mac_underrun_err_cnt {
      type oc-yang:counter64;
      description
        "MAC TX underrun errors count.";
    }
    leaf counter_slice0_ifg_mac_pool87_port_mib_counter4_tx_mac_underrun_err_cnt {
      type oc-yang:counter64;
      description
        "MAC TX underrun errors count.";
    }
    leaf counter_slice0_ifg_mac_pool87_port_mib_counter5_tx_mac_underrun_err_cnt {
      type oc-yang:counter64;
      description
        "MAC TX underrun errors count.";
    }
    leaf counter_slice0_ifg_mac_pool87_port_mib_counter6_tx_mac_underrun_err_cnt {
      type oc-yang:counter64;
      description
        "MAC TX underrun errors count.";
    }
    leaf counter_slice0_ifg_mac_pool87_port_mib_counter7_tx_mac_underrun_err_cnt {
      type oc-yang:counter64;
      description
        "MAC TX underrun errors count.";
    }
    leaf counter_slice1_ifg_mac_pool80_port_mib_counter0_tx_mac_underrun_err_cnt {
      type oc-yang:counter64;
      description
        "MAC TX underrun errors count.";
    }
    leaf counter_slice1_ifg_mac_pool80_port_mib_counter1_tx_mac_underrun_err_cnt {
      type oc-yang:counter64;
      description
        "MAC TX underrun errors count.";
    }
    leaf counter_slice1_ifg_mac_pool80_port_mib_counter2_tx_mac_underrun_err_cnt {
      type oc-yang:counter64;
      description
        "MAC TX underrun errors count.";
    }
    leaf counter_slice1_ifg_mac_pool80_port_mib_counter3_tx_mac_underrun_err_cnt {
      type oc-yang:counter64;
      description
        "MAC TX underrun errors count.";
    }
    leaf counter_slice1_ifg_mac_pool80_port_mib_counter4_tx_mac_underrun_err_cnt {
      type oc-yang:counter64;
      description
        "MAC TX underrun errors count.";
    }
    leaf counter_slice1_ifg_mac_pool80_port_mib_counter5_tx_mac_underrun_err_cnt {
      type oc-yang:counter64;
      description
        "MAC TX underrun errors count.";
    }
    leaf counter_slice1_ifg_mac_pool80_port_mib_counter6_tx_mac_underrun_err_cnt {
      type oc-yang:counter64;
      description
        "MAC TX underrun errors count.";
    }
    leaf counter_slice1_ifg_mac_pool80_port_mib_counter7_tx_mac_underrun_err_cnt {
      type oc-yang:counter64;
      description
        "MAC TX underrun errors count.";
    }
    leaf counter_slice1_ifg_mac_pool81_port_mib_counter0_tx_mac_underrun_err_cnt {
      type oc-yang:counter64;
      description
        "MAC TX underrun errors count.";
    }
    leaf counter_slice1_ifg_mac_pool81_port_mib_counter1_tx_mac_underrun_err_cnt {
      type oc-yang:counter64;
      description
        "MAC TX underrun errors count.";
    }
    leaf counter_slice1_ifg_mac_pool81_port_mib_counter2_tx_mac_underrun_err_cnt {
      type oc-yang:counter64;
      description
        "MAC TX underrun errors count.";
    }
    leaf counter_slice1_ifg_mac_pool81_port_mib_counter3_tx_mac_underrun_err_cnt {
      type oc-yang:counter64;
      description
        "MAC TX underrun errors count.";
    }
    leaf counter_slice1_ifg_mac_pool81_port_mib_counter4_tx_mac_underrun_err_cnt {
      type oc-yang:counter64;
      description
        "MAC TX underrun errors count.";
    }
    leaf counter_slice1_ifg_mac_pool81_port_mib_counter5_tx_mac_underrun_err_cnt {
      type oc-yang:counter64;
      description
        "MAC TX underrun errors count.";
    }
    leaf counter_slice1_ifg_mac_pool81_port_mib_counter6_tx_mac_underrun_err_cnt {
      type oc-yang:counter64;
      description
        "MAC TX underrun errors count.";
    }
    leaf counter_slice1_ifg_mac_pool81_port_mib_counter7_tx_mac_underrun_err_cnt {
      type oc-yang:counter64;
      description
        "MAC TX underrun errors count.";
    }
    leaf counter_slice1_ifg_mac_pool82_port_mib_counter0_tx_mac_underrun_err_cnt {
      type oc-yang:counter64;
      description
        "MAC TX underrun errors count.";
    }
    leaf counter_slice1_ifg_mac_pool82_port_mib_counter1_tx_mac_underrun_err_cnt {
      type oc-yang:counter64;
      description
        "MAC TX underrun errors count.";
    }
    leaf counter_slice1_ifg_mac_pool82_port_mib_counter2_tx_mac_underrun_err_cnt {
      type oc-yang:counter64;
      description
        "MAC TX underrun errors count.";
    }
    leaf counter_slice1_ifg_mac_pool82_port_mib_counter3_tx_mac_underrun_err_cnt {
      type oc-yang:counter64;
      description
        "MAC TX underrun errors count.";
    }
    leaf counter_slice1_ifg_mac_pool82_port_mib_counter4_tx_mac_underrun_err_cnt {
      type oc-yang:counter64;
      description
        "MAC TX underrun errors count.";
    }
    leaf counter_slice1_ifg_mac_pool82_port_mib_counter5_tx_mac_underrun_err_cnt {
      type oc-yang:counter64;
      description
        "MAC TX underrun errors count.";
    }
    leaf counter_slice1_ifg_mac_pool82_port_mib_counter6_tx_mac_underrun_err_cnt {
      type oc-yang:counter64;
      description
        "MAC TX underrun errors count.";
    }
    leaf counter_slice1_ifg_mac_pool82_port_mib_counter7_tx_mac_underrun_err_cnt {
      type oc-yang:counter64;
      description
        "MAC TX underrun errors count.";
    }
    leaf counter_slice1_ifg_mac_pool83_port_mib_counter0_tx_mac_underrun_err_cnt {
      type oc-yang:counter64;
      description
        "MAC TX underrun errors count.";
    }
    leaf counter_slice1_ifg_mac_pool83_port_mib_counter1_tx_mac_underrun_err_cnt {
      type oc-yang:counter64;
      description
        "MAC TX underrun errors count.";
    }
    leaf counter_slice1_ifg_mac_pool83_port_mib_counter2_tx_mac_underrun_err_cnt {
      type oc-yang:counter64;
      description
        "MAC TX underrun errors count.";
    }
    leaf counter_slice1_ifg_mac_pool83_port_mib_counter3_tx_mac_underrun_err_cnt {
      type oc-yang:counter64;
      description
        "MAC TX underrun errors count.";
    }
    leaf counter_slice1_ifg_mac_pool83_port_mib_counter4_tx_mac_underrun_err_cnt {
      type oc-yang:counter64;
      description
        "MAC TX underrun errors count.";
    }
    leaf counter_slice1_ifg_mac_pool83_port_mib_counter5_tx_mac_underrun_err_cnt {
      type oc-yang:counter64;
      description
        "MAC TX underrun errors count.";
    }
    leaf counter_slice1_ifg_mac_pool83_port_mib_counter6_tx_mac_underrun_err_cnt {
      type oc-yang:counter64;
      description
        "MAC TX underrun errors count.";
    }
    leaf counter_slice1_ifg_mac_pool83_port_mib_counter7_tx_mac_underrun_err_cnt {
      type oc-yang:counter64;
      description
        "MAC TX underrun errors count.";
    }
    leaf counter_slice1_ifg_mac_pool84_port_mib_counter0_tx_mac_underrun_err_cnt {
      type oc-yang:counter64;
      description
        "MAC TX underrun errors count.";
    }
    leaf counter_slice1_ifg_mac_pool84_port_mib_counter1_tx_mac_underrun_err_cnt {
      type oc-yang:counter64;
      description
        "MAC TX underrun errors count.";
    }
    leaf counter_slice1_ifg_mac_pool84_port_mib_counter2_tx_mac_underrun_err_cnt {
      type oc-yang:counter64;
      description
        "MAC TX underrun errors count.";
    }
    leaf counter_slice1_ifg_mac_pool84_port_mib_counter3_tx_mac_underrun_err_cnt {
      type oc-yang:counter64;
      description
        "MAC TX underrun errors count.";
    }
    leaf counter_slice1_ifg_mac_pool84_port_mib_counter4_tx_mac_underrun_err_cnt {
      type oc-yang:counter64;
      description
        "MAC TX underrun errors count.";
    }
    leaf counter_slice1_ifg_mac_pool84_port_mib_counter5_tx_mac_underrun_err_cnt {
      type oc-yang:counter64;
      description
        "MAC TX underrun errors count.";
    }
    leaf counter_slice1_ifg_mac_pool84_port_mib_counter6_tx_mac_underrun_err_cnt {
      type oc-yang:counter64;
      description
        "MAC TX underrun errors count.";
    }
    leaf counter_slice1_ifg_mac_pool84_port_mib_counter7_tx_mac_underrun_err_cnt {
      type oc-yang:counter64;
      description
        "MAC TX underrun errors count.";
    }
    leaf counter_slice1_ifg_mac_pool85_port_mib_counter0_tx_mac_underrun_err_cnt {
      type oc-yang:counter64;
      description
        "MAC TX underrun errors count.";
    }
    leaf counter_slice1_ifg_mac_pool85_port_mib_counter1_tx_mac_underrun_err_cnt {
      type oc-yang:counter64;
      description
        "MAC TX underrun errors count.";
    }
    leaf counter_slice1_ifg_mac_pool85_port_mib_counter2_tx_mac_underrun_err_cnt {
      type oc-yang:counter64;
      description
        "MAC TX underrun errors count.";
    }
    leaf counter_slice1_ifg_mac_pool85_port_mib_counter3_tx_mac_underrun_err_cnt {
      type oc-yang:counter64;
      description
        "MAC TX underrun errors count.";
    }
    leaf counter_slice1_ifg_mac_pool85_port_mib_counter4_tx_mac_underrun_err_cnt {
      type oc-yang:counter64;
      description
        "MAC TX underrun errors count.";
    }
    leaf counter_slice1_ifg_mac_pool85_port_mib_counter5_tx_mac_underrun_err_cnt {
      type oc-yang:counter64;
      description
        "MAC TX underrun errors count.";
    }
    leaf counter_slice1_ifg_mac_pool85_port_mib_counter6_tx_mac_underrun_err_cnt {
      type oc-yang:counter64;
      description
        "MAC TX underrun errors count.";
    }
    leaf counter_slice1_ifg_mac_pool85_port_mib_counter7_tx_mac_underrun_err_cnt {
      type oc-yang:counter64;
      description
        "MAC TX underrun errors count.";
    }
    leaf counter_slice1_ifg_mac_pool86_port_mib_counter0_tx_mac_underrun_err_cnt {
      type oc-yang:counter64;
      description
        "MAC TX underrun errors count.";
    }
    leaf counter_slice1_ifg_mac_pool86_port_mib_counter1_tx_mac_underrun_err_cnt {
      type oc-yang:counter64;
      description
        "MAC TX underrun errors count.";
    }
    leaf counter_slice1_ifg_mac_pool86_port_mib_counter2_tx_mac_underrun_err_cnt {
      type oc-yang:counter64;
      description
        "MAC TX underrun errors count.";
    }
    leaf counter_slice1_ifg_mac_pool86_port_mib_counter3_tx_mac_underrun_err_cnt {
      type oc-yang:counter64;
      description
        "MAC TX underrun errors count.";
    }
    leaf counter_slice1_ifg_mac_pool86_port_mib_counter4_tx_mac_underrun_err_cnt {
      type oc-yang:counter64;
      description
        "MAC TX underrun errors count.";
    }
    leaf counter_slice1_ifg_mac_pool86_port_mib_counter5_tx_mac_underrun_err_cnt {
      type oc-yang:counter64;
      description
        "MAC TX underrun errors count.";
    }
    leaf counter_slice1_ifg_mac_pool86_port_mib_counter6_tx_mac_underrun_err_cnt {
      type oc-yang:counter64;
      description
        "MAC TX underrun errors count.";
    }
    leaf counter_slice1_ifg_mac_pool86_port_mib_counter7_tx_mac_underrun_err_cnt {
      type oc-yang:counter64;
      description
        "MAC TX underrun errors count.";
    }
    leaf counter_slice1_ifg_mac_pool87_port_mib_counter0_tx_mac_underrun_err_cnt {
      type oc-yang:counter64;
      description
        "MAC TX underrun errors count.";
    }
    leaf counter_slice1_ifg_mac_pool87_port_mib_counter1_tx_mac_underrun_err_cnt {
      type oc-yang:counter64;
      description
        "MAC TX underrun errors count.";
    }
    leaf counter_slice1_ifg_mac_pool87_port_mib_counter2_tx_mac_underrun_err_cnt {
      type oc-yang:counter64;
      description
        "MAC TX underrun errors count.";
    }
    leaf counter_slice1_ifg_mac_pool87_port_mib_counter3_tx_mac_underrun_err_cnt {
      type oc-yang:counter64;
      description
        "MAC TX underrun errors count.";
    }
    leaf counter_slice1_ifg_mac_pool87_port_mib_counter4_tx_mac_underrun_err_cnt {
      type oc-yang:counter64;
      description
        "MAC TX underrun errors count.";
    }
    leaf counter_slice1_ifg_mac_pool87_port_mib_counter5_tx_mac_underrun_err_cnt {
      type oc-yang:counter64;
      description
        "MAC TX underrun errors count.";
    }
    leaf counter_slice1_ifg_mac_pool87_port_mib_counter6_tx_mac_underrun_err_cnt {
      type oc-yang:counter64;
      description
        "MAC TX underrun errors count.";
    }
    leaf counter_slice1_ifg_mac_pool87_port_mib_counter7_tx_mac_underrun_err_cnt {
      type oc-yang:counter64;
      description
        "MAC TX underrun errors count.";
    }
    leaf counter_slice2_ifg_mac_pool80_port_mib_counter0_tx_mac_underrun_err_cnt {
      type oc-yang:counter64;
      description
        "MAC TX underrun errors count.";
    }
    leaf counter_slice2_ifg_mac_pool80_port_mib_counter1_tx_mac_underrun_err_cnt {
      type oc-yang:counter64;
      description
        "MAC TX underrun errors count.";
    }
    leaf counter_slice2_ifg_mac_pool80_port_mib_counter2_tx_mac_underrun_err_cnt {
      type oc-yang:counter64;
      description
        "MAC TX underrun errors count.";
    }
    leaf counter_slice2_ifg_mac_pool80_port_mib_counter3_tx_mac_underrun_err_cnt {
      type oc-yang:counter64;
      description
        "MAC TX underrun errors count.";
    }
    leaf counter_slice2_ifg_mac_pool80_port_mib_counter4_tx_mac_underrun_err_cnt {
      type oc-yang:counter64;
      description
        "MAC TX underrun errors count.";
    }
    leaf counter_slice2_ifg_mac_pool80_port_mib_counter5_tx_mac_underrun_err_cnt {
      type oc-yang:counter64;
      description
        "MAC TX underrun errors count.";
    }
    leaf counter_slice2_ifg_mac_pool80_port_mib_counter6_tx_mac_underrun_err_cnt {
      type oc-yang:counter64;
      description
        "MAC TX underrun errors count.";
    }
    leaf counter_slice2_ifg_mac_pool80_port_mib_counter7_tx_mac_underrun_err_cnt {
      type oc-yang:counter64;
      description
        "MAC TX underrun errors count.";
    }
    leaf counter_slice2_ifg_mac_pool81_port_mib_counter0_tx_mac_underrun_err_cnt {
      type oc-yang:counter64;
      description
        "MAC TX underrun errors count.";
    }
    leaf counter_slice2_ifg_mac_pool81_port_mib_counter1_tx_mac_underrun_err_cnt {
      type oc-yang:counter64;
      description
        "MAC TX underrun errors count.";
    }
    leaf counter_slice2_ifg_mac_pool81_port_mib_counter2_tx_mac_underrun_err_cnt {
      type oc-yang:counter64;
      description
        "MAC TX underrun errors count.";
    }
    leaf counter_slice2_ifg_mac_pool81_port_mib_counter3_tx_mac_underrun_err_cnt {
      type oc-yang:counter64;
      description
        "MAC TX underrun errors count.";
    }
    leaf counter_slice2_ifg_mac_pool81_port_mib_counter4_tx_mac_underrun_err_cnt {
      type oc-yang:counter64;
      description
        "MAC TX underrun errors count.";
    }
    leaf counter_slice2_ifg_mac_pool81_port_mib_counter5_tx_mac_underrun_err_cnt {
      type oc-yang:counter64;
      description
        "MAC TX underrun errors count.";
    }
    leaf counter_slice2_ifg_mac_pool81_port_mib_counter6_tx_mac_underrun_err_cnt {
      type oc-yang:counter64;
      description
        "MAC TX underrun errors count.";
    }
    leaf counter_slice2_ifg_mac_pool81_port_mib_counter7_tx_mac_underrun_err_cnt {
      type oc-yang:counter64;
      description
        "MAC TX underrun errors count.";
    }
    leaf counter_slice2_ifg_mac_pool82_port_mib_counter0_tx_mac_underrun_err_cnt {
      type oc-yang:counter64;
      description
        "MAC TX underrun errors count.";
    }
    leaf counter_slice2_ifg_mac_pool82_port_mib_counter1_tx_mac_underrun_err_cnt {
      type oc-yang:counter64;
      description
        "MAC TX underrun errors count.";
    }
    leaf counter_slice2_ifg_mac_pool82_port_mib_counter2_tx_mac_underrun_err_cnt {
      type oc-yang:counter64;
      description
        "MAC TX underrun errors count.";
    }
    leaf counter_slice2_ifg_mac_pool82_port_mib_counter3_tx_mac_underrun_err_cnt {
      type oc-yang:counter64;
      description
        "MAC TX underrun errors count.";
    }
    leaf counter_slice2_ifg_mac_pool82_port_mib_counter4_tx_mac_underrun_err_cnt {
      type oc-yang:counter64;
      description
        "MAC TX underrun errors count.";
    }
    leaf counter_slice2_ifg_mac_pool82_port_mib_counter5_tx_mac_underrun_err_cnt {
      type oc-yang:counter64;
      description
        "MAC TX underrun errors count.";
    }
    leaf counter_slice2_ifg_mac_pool82_port_mib_counter6_tx_mac_underrun_err_cnt {
      type oc-yang:counter64;
      description
        "MAC TX underrun errors count.";
    }
    leaf counter_slice2_ifg_mac_pool82_port_mib_counter7_tx_mac_underrun_err_cnt {
      type oc-yang:counter64;
      description
        "MAC TX underrun errors count.";
    }
    leaf counter_slice2_ifg_mac_pool83_port_mib_counter0_tx_mac_underrun_err_cnt {
      type oc-yang:counter64;
      description
        "MAC TX underrun errors count.";
    }
    leaf counter_slice2_ifg_mac_pool83_port_mib_counter1_tx_mac_underrun_err_cnt {
      type oc-yang:counter64;
      description
        "MAC TX underrun errors count.";
    }
    leaf counter_slice2_ifg_mac_pool83_port_mib_counter2_tx_mac_underrun_err_cnt {
      type oc-yang:counter64;
      description
        "MAC TX underrun errors count.";
    }
    leaf counter_slice2_ifg_mac_pool83_port_mib_counter3_tx_mac_underrun_err_cnt {
      type oc-yang:counter64;
      description
        "MAC TX underrun errors count.";
    }
    leaf counter_slice2_ifg_mac_pool83_port_mib_counter4_tx_mac_underrun_err_cnt {
      type oc-yang:counter64;
      description
        "MAC TX underrun errors count.";
    }
    leaf counter_slice2_ifg_mac_pool83_port_mib_counter5_tx_mac_underrun_err_cnt {
      type oc-yang:counter64;
      description
        "MAC TX underrun errors count.";
    }
    leaf counter_slice2_ifg_mac_pool83_port_mib_counter6_tx_mac_underrun_err_cnt {
      type oc-yang:counter64;
      description
        "MAC TX underrun errors count.";
    }
    leaf counter_slice2_ifg_mac_pool83_port_mib_counter7_tx_mac_underrun_err_cnt {
      type oc-yang:counter64;
      description
        "MAC TX underrun errors count.";
    }
    leaf counter_slice2_ifg_mac_pool84_port_mib_counter0_tx_mac_underrun_err_cnt {
      type oc-yang:counter64;
      description
        "MAC TX underrun errors count.";
    }
    leaf counter_slice2_ifg_mac_pool84_port_mib_counter1_tx_mac_underrun_err_cnt {
      type oc-yang:counter64;
      description
        "MAC TX underrun errors count.";
    }
    leaf counter_slice2_ifg_mac_pool84_port_mib_counter2_tx_mac_underrun_err_cnt {
      type oc-yang:counter64;
      description
        "MAC TX underrun errors count.";
    }
    leaf counter_slice2_ifg_mac_pool84_port_mib_counter3_tx_mac_underrun_err_cnt {
      type oc-yang:counter64;
      description
        "MAC TX underrun errors count.";
    }
    leaf counter_slice2_ifg_mac_pool84_port_mib_counter4_tx_mac_underrun_err_cnt {
      type oc-yang:counter64;
      description
        "MAC TX underrun errors count.";
    }
    leaf counter_slice2_ifg_mac_pool84_port_mib_counter5_tx_mac_underrun_err_cnt {
      type oc-yang:counter64;
      description
        "MAC TX underrun errors count.";
    }
    leaf counter_slice2_ifg_mac_pool84_port_mib_counter6_tx_mac_underrun_err_cnt {
      type oc-yang:counter64;
      description
        "MAC TX underrun errors count.";
    }
    leaf counter_slice2_ifg_mac_pool84_port_mib_counter7_tx_mac_underrun_err_cnt {
      type oc-yang:counter64;
      description
        "MAC TX underrun errors count.";
    }
    leaf counter_slice2_ifg_mac_pool85_port_mib_counter0_tx_mac_underrun_err_cnt {
      type oc-yang:counter64;
      description
        "MAC TX underrun errors count.";
    }
    leaf counter_slice2_ifg_mac_pool85_port_mib_counter1_tx_mac_underrun_err_cnt {
      type oc-yang:counter64;
      description
        "MAC TX underrun errors count.";
    }
    leaf counter_slice2_ifg_mac_pool85_port_mib_counter2_tx_mac_underrun_err_cnt {
      type oc-yang:counter64;
      description
        "MAC TX underrun errors count.";
    }
    leaf counter_slice2_ifg_mac_pool85_port_mib_counter3_tx_mac_underrun_err_cnt {
      type oc-yang:counter64;
      description
        "MAC TX underrun errors count.";
    }
    leaf counter_slice2_ifg_mac_pool85_port_mib_counter4_tx_mac_underrun_err_cnt {
      type oc-yang:counter64;
      description
        "MAC TX underrun errors count.";
    }
    leaf counter_slice2_ifg_mac_pool85_port_mib_counter5_tx_mac_underrun_err_cnt {
      type oc-yang:counter64;
      description
        "MAC TX underrun errors count.";
    }
    leaf counter_slice2_ifg_mac_pool85_port_mib_counter6_tx_mac_underrun_err_cnt {
      type oc-yang:counter64;
      description
        "MAC TX underrun errors count.";
    }
    leaf counter_slice2_ifg_mac_pool85_port_mib_counter7_tx_mac_underrun_err_cnt {
      type oc-yang:counter64;
      description
        "MAC TX underrun errors count.";
    }
    leaf counter_slice2_ifg_mac_pool86_port_mib_counter0_tx_mac_underrun_err_cnt {
      type oc-yang:counter64;
      description
        "MAC TX underrun errors count.";
    }
    leaf counter_slice2_ifg_mac_pool86_port_mib_counter1_tx_mac_underrun_err_cnt {
      type oc-yang:counter64;
      description
        "MAC TX underrun errors count.";
    }
    leaf counter_slice2_ifg_mac_pool86_port_mib_counter2_tx_mac_underrun_err_cnt {
      type oc-yang:counter64;
      description
        "MAC TX underrun errors count.";
    }
    leaf counter_slice2_ifg_mac_pool86_port_mib_counter3_tx_mac_underrun_err_cnt {
      type oc-yang:counter64;
      description
        "MAC TX underrun errors count.";
    }
    leaf counter_slice2_ifg_mac_pool86_port_mib_counter4_tx_mac_underrun_err_cnt {
      type oc-yang:counter64;
      description
        "MAC TX underrun errors count.";
    }
    leaf counter_slice2_ifg_mac_pool86_port_mib_counter5_tx_mac_underrun_err_cnt {
      type oc-yang:counter64;
      description
        "MAC TX underrun errors count.";
    }
    leaf counter_slice2_ifg_mac_pool86_port_mib_counter6_tx_mac_underrun_err_cnt {
      type oc-yang:counter64;
      description
        "MAC TX underrun errors count.";
    }
    leaf counter_slice2_ifg_mac_pool86_port_mib_counter7_tx_mac_underrun_err_cnt {
      type oc-yang:counter64;
      description
        "MAC TX underrun errors count.";
    }
    leaf counter_slice2_ifg_mac_pool87_port_mib_counter0_tx_mac_underrun_err_cnt {
      type oc-yang:counter64;
      description
        "MAC TX underrun errors count.";
    }
    leaf counter_slice2_ifg_mac_pool87_port_mib_counter1_tx_mac_underrun_err_cnt {
      type oc-yang:counter64;
      description
        "MAC TX underrun errors count.";
    }
    leaf counter_slice2_ifg_mac_pool87_port_mib_counter2_tx_mac_underrun_err_cnt {
      type oc-yang:counter64;
      description
        "MAC TX underrun errors count.";
    }
    leaf counter_slice2_ifg_mac_pool87_port_mib_counter3_tx_mac_underrun_err_cnt {
      type oc-yang:counter64;
      description
        "MAC TX underrun errors count.";
    }
    leaf counter_slice2_ifg_mac_pool87_port_mib_counter4_tx_mac_underrun_err_cnt {
      type oc-yang:counter64;
      description
        "MAC TX underrun errors count.";
    }
    leaf counter_slice2_ifg_mac_pool87_port_mib_counter5_tx_mac_underrun_err_cnt {
      type oc-yang:counter64;
      description
        "MAC TX underrun errors count.";
    }
    leaf counter_slice2_ifg_mac_pool87_port_mib_counter6_tx_mac_underrun_err_cnt {
      type oc-yang:counter64;
      description
        "MAC TX underrun errors count.";
    }
    leaf counter_slice2_ifg_mac_pool87_port_mib_counter7_tx_mac_underrun_err_cnt {
      type oc-yang:counter64;
      description
        "MAC TX underrun errors count.";
    }
    leaf counter_slice3_ifg_mac_pool80_port_mib_counter0_tx_mac_underrun_err_cnt {
      type oc-yang:counter64;
      description
        "MAC TX underrun errors count.";
    }
    leaf counter_slice3_ifg_mac_pool80_port_mib_counter1_tx_mac_underrun_err_cnt {
      type oc-yang:counter64;
      description
        "MAC TX underrun errors count.";
    }
    leaf counter_slice3_ifg_mac_pool80_port_mib_counter2_tx_mac_underrun_err_cnt {
      type oc-yang:counter64;
      description
        "MAC TX underrun errors count.";
    }
    leaf counter_slice3_ifg_mac_pool80_port_mib_counter3_tx_mac_underrun_err_cnt {
      type oc-yang:counter64;
      description
        "MAC TX underrun errors count.";
    }
    leaf counter_slice3_ifg_mac_pool80_port_mib_counter4_tx_mac_underrun_err_cnt {
      type oc-yang:counter64;
      description
        "MAC TX underrun errors count.";
    }
    leaf counter_slice3_ifg_mac_pool80_port_mib_counter5_tx_mac_underrun_err_cnt {
      type oc-yang:counter64;
      description
        "MAC TX underrun errors count.";
    }
    leaf counter_slice3_ifg_mac_pool80_port_mib_counter6_tx_mac_underrun_err_cnt {
      type oc-yang:counter64;
      description
        "MAC TX underrun errors count.";
    }
    leaf counter_slice3_ifg_mac_pool80_port_mib_counter7_tx_mac_underrun_err_cnt {
      type oc-yang:counter64;
      description
        "MAC TX underrun errors count.";
    }
    leaf counter_slice3_ifg_mac_pool81_port_mib_counter0_tx_mac_underrun_err_cnt {
      type oc-yang:counter64;
      description
        "MAC TX underrun errors count.";
    }
    leaf counter_slice3_ifg_mac_pool81_port_mib_counter1_tx_mac_underrun_err_cnt {
      type oc-yang:counter64;
      description
        "MAC TX underrun errors count.";
    }
    leaf counter_slice3_ifg_mac_pool81_port_mib_counter2_tx_mac_underrun_err_cnt {
      type oc-yang:counter64;
      description
        "MAC TX underrun errors count.";
    }
    leaf counter_slice3_ifg_mac_pool81_port_mib_counter3_tx_mac_underrun_err_cnt {
      type oc-yang:counter64;
      description
        "MAC TX underrun errors count.";
    }
    leaf counter_slice3_ifg_mac_pool81_port_mib_counter4_tx_mac_underrun_err_cnt {
      type oc-yang:counter64;
      description
        "MAC TX underrun errors count.";
    }
    leaf counter_slice3_ifg_mac_pool81_port_mib_counter5_tx_mac_underrun_err_cnt {
      type oc-yang:counter64;
      description
        "MAC TX underrun errors count.";
    }
    leaf counter_slice3_ifg_mac_pool81_port_mib_counter6_tx_mac_underrun_err_cnt {
      type oc-yang:counter64;
      description
        "MAC TX underrun errors count.";
    }
    leaf counter_slice3_ifg_mac_pool81_port_mib_counter7_tx_mac_underrun_err_cnt {
      type oc-yang:counter64;
      description
        "MAC TX underrun errors count.";
    }
    leaf counter_slice3_ifg_mac_pool82_port_mib_counter0_tx_mac_underrun_err_cnt {
      type oc-yang:counter64;
      description
        "MAC TX underrun errors count.";
    }
    leaf counter_slice3_ifg_mac_pool82_port_mib_counter1_tx_mac_underrun_err_cnt {
      type oc-yang:counter64;
      description
        "MAC TX underrun errors count.";
    }
    leaf counter_slice3_ifg_mac_pool82_port_mib_counter2_tx_mac_underrun_err_cnt {
      type oc-yang:counter64;
      description
        "MAC TX underrun errors count.";
    }
    leaf counter_slice3_ifg_mac_pool82_port_mib_counter3_tx_mac_underrun_err_cnt {
      type oc-yang:counter64;
      description
        "MAC TX underrun errors count.";
    }
    leaf counter_slice3_ifg_mac_pool82_port_mib_counter4_tx_mac_underrun_err_cnt {
      type oc-yang:counter64;
      description
        "MAC TX underrun errors count.";
    }
    leaf counter_slice3_ifg_mac_pool82_port_mib_counter5_tx_mac_underrun_err_cnt {
      type oc-yang:counter64;
      description
        "MAC TX underrun errors count.";
    }
    leaf counter_slice3_ifg_mac_pool82_port_mib_counter6_tx_mac_underrun_err_cnt {
      type oc-yang:counter64;
      description
        "MAC TX underrun errors count.";
    }
    leaf counter_slice3_ifg_mac_pool82_port_mib_counter7_tx_mac_underrun_err_cnt {
      type oc-yang:counter64;
      description
        "MAC TX underrun errors count.";
    }
    leaf counter_slice3_ifg_mac_pool83_port_mib_counter0_tx_mac_underrun_err_cnt {
      type oc-yang:counter64;
      description
        "MAC TX underrun errors count.";
    }
    leaf counter_slice3_ifg_mac_pool83_port_mib_counter1_tx_mac_underrun_err_cnt {
      type oc-yang:counter64;
      description
        "MAC TX underrun errors count.";
    }
    leaf counter_slice3_ifg_mac_pool83_port_mib_counter2_tx_mac_underrun_err_cnt {
      type oc-yang:counter64;
      description
        "MAC TX underrun errors count.";
    }
    leaf counter_slice3_ifg_mac_pool83_port_mib_counter3_tx_mac_underrun_err_cnt {
      type oc-yang:counter64;
      description
        "MAC TX underrun errors count.";
    }
    leaf counter_slice3_ifg_mac_pool83_port_mib_counter4_tx_mac_underrun_err_cnt {
      type oc-yang:counter64;
      description
        "MAC TX underrun errors count.";
    }
    leaf counter_slice3_ifg_mac_pool83_port_mib_counter5_tx_mac_underrun_err_cnt {
      type oc-yang:counter64;
      description
        "MAC TX underrun errors count.";
    }
    leaf counter_slice3_ifg_mac_pool83_port_mib_counter6_tx_mac_underrun_err_cnt {
      type oc-yang:counter64;
      description
        "MAC TX underrun errors count.";
    }
    leaf counter_slice3_ifg_mac_pool83_port_mib_counter7_tx_mac_underrun_err_cnt {
      type oc-yang:counter64;
      description
        "MAC TX underrun errors count.";
    }
    leaf counter_slice3_ifg_mac_pool84_port_mib_counter0_tx_mac_underrun_err_cnt {
      type oc-yang:counter64;
      description
        "MAC TX underrun errors count.";
    }
    leaf counter_slice3_ifg_mac_pool84_port_mib_counter1_tx_mac_underrun_err_cnt {
      type oc-yang:counter64;
      description
        "MAC TX underrun errors count.";
    }
    leaf counter_slice3_ifg_mac_pool84_port_mib_counter2_tx_mac_underrun_err_cnt {
      type oc-yang:counter64;
      description
        "MAC TX underrun errors count.";
    }
    leaf counter_slice3_ifg_mac_pool84_port_mib_counter3_tx_mac_underrun_err_cnt {
      type oc-yang:counter64;
      description
        "MAC TX underrun errors count.";
    }
    leaf counter_slice3_ifg_mac_pool84_port_mib_counter4_tx_mac_underrun_err_cnt {
      type oc-yang:counter64;
      description
        "MAC TX underrun errors count.";
    }
    leaf counter_slice3_ifg_mac_pool84_port_mib_counter5_tx_mac_underrun_err_cnt {
      type oc-yang:counter64;
      description
        "MAC TX underrun errors count.";
    }
    leaf counter_slice3_ifg_mac_pool84_port_mib_counter6_tx_mac_underrun_err_cnt {
      type oc-yang:counter64;
      description
        "MAC TX underrun errors count.";
    }
    leaf counter_slice3_ifg_mac_pool84_port_mib_counter7_tx_mac_underrun_err_cnt {
      type oc-yang:counter64;
      description
        "MAC TX underrun errors count.";
    }
    leaf counter_slice3_ifg_mac_pool85_port_mib_counter0_tx_mac_underrun_err_cnt {
      type oc-yang:counter64;
      description
        "MAC TX underrun errors count.";
    }
    leaf counter_slice3_ifg_mac_pool85_port_mib_counter1_tx_mac_underrun_err_cnt {
      type oc-yang:counter64;
      description
        "MAC TX underrun errors count.";
    }
    leaf counter_slice3_ifg_mac_pool85_port_mib_counter2_tx_mac_underrun_err_cnt {
      type oc-yang:counter64;
      description
        "MAC TX underrun errors count.";
    }
    leaf counter_slice3_ifg_mac_pool85_port_mib_counter3_tx_mac_underrun_err_cnt {
      type oc-yang:counter64;
      description
        "MAC TX underrun errors count.";
    }
    leaf counter_slice3_ifg_mac_pool85_port_mib_counter4_tx_mac_underrun_err_cnt {
      type oc-yang:counter64;
      description
        "MAC TX underrun errors count.";
    }
    leaf counter_slice3_ifg_mac_pool85_port_mib_counter5_tx_mac_underrun_err_cnt {
      type oc-yang:counter64;
      description
        "MAC TX underrun errors count.";
    }
    leaf counter_slice3_ifg_mac_pool85_port_mib_counter6_tx_mac_underrun_err_cnt {
      type oc-yang:counter64;
      description
        "MAC TX underrun errors count.";
    }
    leaf counter_slice3_ifg_mac_pool85_port_mib_counter7_tx_mac_underrun_err_cnt {
      type oc-yang:counter64;
      description
        "MAC TX underrun errors count.";
    }
    leaf counter_slice3_ifg_mac_pool86_port_mib_counter0_tx_mac_underrun_err_cnt {
      type oc-yang:counter64;
      description
        "MAC TX underrun errors count.";
    }
    leaf counter_slice3_ifg_mac_pool86_port_mib_counter1_tx_mac_underrun_err_cnt {
      type oc-yang:counter64;
      description
        "MAC TX underrun errors count.";
    }
    leaf counter_slice3_ifg_mac_pool86_port_mib_counter2_tx_mac_underrun_err_cnt {
      type oc-yang:counter64;
      description
        "MAC TX underrun errors count.";
    }
    leaf counter_slice3_ifg_mac_pool86_port_mib_counter3_tx_mac_underrun_err_cnt {
      type oc-yang:counter64;
      description
        "MAC TX underrun errors count.";
    }
    leaf counter_slice3_ifg_mac_pool86_port_mib_counter4_tx_mac_underrun_err_cnt {
      type oc-yang:counter64;
      description
        "MAC TX underrun errors count.";
    }
    leaf counter_slice3_ifg_mac_pool86_port_mib_counter5_tx_mac_underrun_err_cnt {
      type oc-yang:counter64;
      description
        "MAC TX underrun errors count.";
    }
    leaf counter_slice3_ifg_mac_pool86_port_mib_counter6_tx_mac_underrun_err_cnt {
      type oc-yang:counter64;
      description
        "MAC TX underrun errors count.";
    }
    leaf counter_slice3_ifg_mac_pool86_port_mib_counter7_tx_mac_underrun_err_cnt {
      type oc-yang:counter64;
      description
        "MAC TX underrun errors count.";
    }
    leaf counter_slice3_ifg_mac_pool87_port_mib_counter0_tx_mac_underrun_err_cnt {
      type oc-yang:counter64;
      description
        "MAC TX underrun errors count.";
    }
    leaf counter_slice3_ifg_mac_pool87_port_mib_counter1_tx_mac_underrun_err_cnt {
      type oc-yang:counter64;
      description
        "MAC TX underrun errors count.";
    }
    leaf counter_slice3_ifg_mac_pool87_port_mib_counter2_tx_mac_underrun_err_cnt {
      type oc-yang:counter64;
      description
        "MAC TX underrun errors count.";
    }
    leaf counter_slice3_ifg_mac_pool87_port_mib_counter3_tx_mac_underrun_err_cnt {
      type oc-yang:counter64;
      description
        "MAC TX underrun errors count.";
    }
    leaf counter_slice3_ifg_mac_pool87_port_mib_counter4_tx_mac_underrun_err_cnt {
      type oc-yang:counter64;
      description
        "MAC TX underrun errors count.";
    }
    leaf counter_slice3_ifg_mac_pool87_port_mib_counter5_tx_mac_underrun_err_cnt {
      type oc-yang:counter64;
      description
        "MAC TX underrun errors count.";
    }
    leaf counter_slice3_ifg_mac_pool87_port_mib_counter6_tx_mac_underrun_err_cnt {
      type oc-yang:counter64;
      description
        "MAC TX underrun errors count.";
    }
    leaf counter_slice3_ifg_mac_pool87_port_mib_counter7_tx_mac_underrun_err_cnt {
      type oc-yang:counter64;
      description
        "MAC TX underrun errors count.";
    }
    leaf counter_slice4_ifg_mac_pool80_port_mib_counter0_tx_mac_underrun_err_cnt {
      type oc-yang:counter64;
      description
        "MAC TX underrun errors count.";
    }
    leaf counter_slice4_ifg_mac_pool80_port_mib_counter1_tx_mac_underrun_err_cnt {
      type oc-yang:counter64;
      description
        "MAC TX underrun errors count.";
    }
    leaf counter_slice4_ifg_mac_pool80_port_mib_counter2_tx_mac_underrun_err_cnt {
      type oc-yang:counter64;
      description
        "MAC TX underrun errors count.";
    }
    leaf counter_slice4_ifg_mac_pool80_port_mib_counter3_tx_mac_underrun_err_cnt {
      type oc-yang:counter64;
      description
        "MAC TX underrun errors count.";
    }
    leaf counter_slice4_ifg_mac_pool80_port_mib_counter4_tx_mac_underrun_err_cnt {
      type oc-yang:counter64;
      description
        "MAC TX underrun errors count.";
    }
    leaf counter_slice4_ifg_mac_pool80_port_mib_counter5_tx_mac_underrun_err_cnt {
      type oc-yang:counter64;
      description
        "MAC TX underrun errors count.";
    }
    leaf counter_slice4_ifg_mac_pool80_port_mib_counter6_tx_mac_underrun_err_cnt {
      type oc-yang:counter64;
      description
        "MAC TX underrun errors count.";
    }
    leaf counter_slice4_ifg_mac_pool80_port_mib_counter7_tx_mac_underrun_err_cnt {
      type oc-yang:counter64;
      description
        "MAC TX underrun errors count.";
    }
    leaf counter_slice4_ifg_mac_pool81_port_mib_counter0_tx_mac_underrun_err_cnt {
      type oc-yang:counter64;
      description
        "MAC TX underrun errors count.";
    }
    leaf counter_slice4_ifg_mac_pool81_port_mib_counter1_tx_mac_underrun_err_cnt {
      type oc-yang:counter64;
      description
        "MAC TX underrun errors count.";
    }
    leaf counter_slice4_ifg_mac_pool81_port_mib_counter2_tx_mac_underrun_err_cnt {
      type oc-yang:counter64;
      description
        "MAC TX underrun errors count.";
    }
    leaf counter_slice4_ifg_mac_pool81_port_mib_counter3_tx_mac_underrun_err_cnt {
      type oc-yang:counter64;
      description
        "MAC TX underrun errors count.";
    }
    leaf counter_slice4_ifg_mac_pool81_port_mib_counter4_tx_mac_underrun_err_cnt {
      type oc-yang:counter64;
      description
        "MAC TX underrun errors count.";
    }
    leaf counter_slice4_ifg_mac_pool81_port_mib_counter5_tx_mac_underrun_err_cnt {
      type oc-yang:counter64;
      description
        "MAC TX underrun errors count.";
    }
    leaf counter_slice4_ifg_mac_pool81_port_mib_counter6_tx_mac_underrun_err_cnt {
      type oc-yang:counter64;
      description
        "MAC TX underrun errors count.";
    }
    leaf counter_slice4_ifg_mac_pool81_port_mib_counter7_tx_mac_underrun_err_cnt {
      type oc-yang:counter64;
      description
        "MAC TX underrun errors count.";
    }
    leaf counter_slice4_ifg_mac_pool82_port_mib_counter0_tx_mac_underrun_err_cnt {
      type oc-yang:counter64;
      description
        "MAC TX underrun errors count.";
    }
    leaf counter_slice4_ifg_mac_pool82_port_mib_counter1_tx_mac_underrun_err_cnt {
      type oc-yang:counter64;
      description
        "MAC TX underrun errors count.";
    }
    leaf counter_slice4_ifg_mac_pool82_port_mib_counter2_tx_mac_underrun_err_cnt {
      type oc-yang:counter64;
      description
        "MAC TX underrun errors count.";
    }
    leaf counter_slice4_ifg_mac_pool82_port_mib_counter3_tx_mac_underrun_err_cnt {
      type oc-yang:counter64;
      description
        "MAC TX underrun errors count.";
    }
    leaf counter_slice4_ifg_mac_pool82_port_mib_counter4_tx_mac_underrun_err_cnt {
      type oc-yang:counter64;
      description
        "MAC TX underrun errors count.";
    }
    leaf counter_slice4_ifg_mac_pool82_port_mib_counter5_tx_mac_underrun_err_cnt {
      type oc-yang:counter64;
      description
        "MAC TX underrun errors count.";
    }
    leaf counter_slice4_ifg_mac_pool82_port_mib_counter6_tx_mac_underrun_err_cnt {
      type oc-yang:counter64;
      description
        "MAC TX underrun errors count.";
    }
    leaf counter_slice4_ifg_mac_pool82_port_mib_counter7_tx_mac_underrun_err_cnt {
      type oc-yang:counter64;
      description
        "MAC TX underrun errors count.";
    }
    leaf counter_slice4_ifg_mac_pool83_port_mib_counter0_tx_mac_underrun_err_cnt {
      type oc-yang:counter64;
      description
        "MAC TX underrun errors count.";
    }
    leaf counter_slice4_ifg_mac_pool83_port_mib_counter1_tx_mac_underrun_err_cnt {
      type oc-yang:counter64;
      description
        "MAC TX underrun errors count.";
    }
    leaf counter_slice4_ifg_mac_pool83_port_mib_counter2_tx_mac_underrun_err_cnt {
      type oc-yang:counter64;
      description
        "MAC TX underrun errors count.";
    }
    leaf counter_slice4_ifg_mac_pool83_port_mib_counter3_tx_mac_underrun_err_cnt {
      type oc-yang:counter64;
      description
        "MAC TX underrun errors count.";
    }
    leaf counter_slice4_ifg_mac_pool83_port_mib_counter4_tx_mac_underrun_err_cnt {
      type oc-yang:counter64;
      description
        "MAC TX underrun errors count.";
    }
    leaf counter_slice4_ifg_mac_pool83_port_mib_counter5_tx_mac_underrun_err_cnt {
      type oc-yang:counter64;
      description
        "MAC TX underrun errors count.";
    }
    leaf counter_slice4_ifg_mac_pool83_port_mib_counter6_tx_mac_underrun_err_cnt {
      type oc-yang:counter64;
      description
        "MAC TX underrun errors count.";
    }
    leaf counter_slice4_ifg_mac_pool83_port_mib_counter7_tx_mac_underrun_err_cnt {
      type oc-yang:counter64;
      description
        "MAC TX underrun errors count.";
    }
    leaf counter_slice4_ifg_mac_pool84_port_mib_counter0_tx_mac_underrun_err_cnt {
      type oc-yang:counter64;
      description
        "MAC TX underrun errors count.";
    }
    leaf counter_slice4_ifg_mac_pool84_port_mib_counter1_tx_mac_underrun_err_cnt {
      type oc-yang:counter64;
      description
        "MAC TX underrun errors count.";
    }
    leaf counter_slice4_ifg_mac_pool84_port_mib_counter2_tx_mac_underrun_err_cnt {
      type oc-yang:counter64;
      description
        "MAC TX underrun errors count.";
    }
    leaf counter_slice4_ifg_mac_pool84_port_mib_counter3_tx_mac_underrun_err_cnt {
      type oc-yang:counter64;
      description
        "MAC TX underrun errors count.";
    }
    leaf counter_slice4_ifg_mac_pool84_port_mib_counter4_tx_mac_underrun_err_cnt {
      type oc-yang:counter64;
      description
        "MAC TX underrun errors count.";
    }
    leaf counter_slice4_ifg_mac_pool84_port_mib_counter5_tx_mac_underrun_err_cnt {
      type oc-yang:counter64;
      description
        "MAC TX underrun errors count.";
    }
    leaf counter_slice4_ifg_mac_pool84_port_mib_counter6_tx_mac_underrun_err_cnt {
      type oc-yang:counter64;
      description
        "MAC TX underrun errors count.";
    }
    leaf counter_slice4_ifg_mac_pool84_port_mib_counter7_tx_mac_underrun_err_cnt {
      type oc-yang:counter64;
      description
        "MAC TX underrun errors count.";
    }
    leaf counter_slice4_ifg_mac_pool85_port_mib_counter0_tx_mac_underrun_err_cnt {
      type oc-yang:counter64;
      description
        "MAC TX underrun errors count.";
    }
    leaf counter_slice4_ifg_mac_pool85_port_mib_counter1_tx_mac_underrun_err_cnt {
      type oc-yang:counter64;
      description
        "MAC TX underrun errors count.";
    }
    leaf counter_slice4_ifg_mac_pool85_port_mib_counter2_tx_mac_underrun_err_cnt {
      type oc-yang:counter64;
      description
        "MAC TX underrun errors count.";
    }
    leaf counter_slice4_ifg_mac_pool85_port_mib_counter3_tx_mac_underrun_err_cnt {
      type oc-yang:counter64;
      description
        "MAC TX underrun errors count.";
    }
    leaf counter_slice4_ifg_mac_pool85_port_mib_counter4_tx_mac_underrun_err_cnt {
      type oc-yang:counter64;
      description
        "MAC TX underrun errors count.";
    }
    leaf counter_slice4_ifg_mac_pool85_port_mib_counter5_tx_mac_underrun_err_cnt {
      type oc-yang:counter64;
      description
        "MAC TX underrun errors count.";
    }
    leaf counter_slice4_ifg_mac_pool85_port_mib_counter6_tx_mac_underrun_err_cnt {
      type oc-yang:counter64;
      description
        "MAC TX underrun errors count.";
    }
    leaf counter_slice4_ifg_mac_pool85_port_mib_counter7_tx_mac_underrun_err_cnt {
      type oc-yang:counter64;
      description
        "MAC TX underrun errors count.";
    }
    leaf counter_slice4_ifg_mac_pool86_port_mib_counter0_tx_mac_underrun_err_cnt {
      type oc-yang:counter64;
      description
        "MAC TX underrun errors count.";
    }
    leaf counter_slice4_ifg_mac_pool86_port_mib_counter1_tx_mac_underrun_err_cnt {
      type oc-yang:counter64;
      description
        "MAC TX underrun errors count.";
    }
    leaf counter_slice4_ifg_mac_pool86_port_mib_counter2_tx_mac_underrun_err_cnt {
      type oc-yang:counter64;
      description
        "MAC TX underrun errors count.";
    }
    leaf counter_slice4_ifg_mac_pool86_port_mib_counter3_tx_mac_underrun_err_cnt {
      type oc-yang:counter64;
      description
        "MAC TX underrun errors count.";
    }
    leaf counter_slice4_ifg_mac_pool86_port_mib_counter4_tx_mac_underrun_err_cnt {
      type oc-yang:counter64;
      description
        "MAC TX underrun errors count.";
    }
    leaf counter_slice4_ifg_mac_pool86_port_mib_counter5_tx_mac_underrun_err_cnt {
      type oc-yang:counter64;
      description
        "MAC TX underrun errors count.";
    }
    leaf counter_slice4_ifg_mac_pool86_port_mib_counter6_tx_mac_underrun_err_cnt {
      type oc-yang:counter64;
      description
        "MAC TX underrun errors count.";
    }
    leaf counter_slice4_ifg_mac_pool86_port_mib_counter7_tx_mac_underrun_err_cnt {
      type oc-yang:counter64;
      description
        "MAC TX underrun errors count.";
    }
    leaf counter_slice4_ifg_mac_pool87_port_mib_counter0_tx_mac_underrun_err_cnt {
      type oc-yang:counter64;
      description
        "MAC TX underrun errors count.";
    }
    leaf counter_slice4_ifg_mac_pool87_port_mib_counter1_tx_mac_underrun_err_cnt {
      type oc-yang:counter64;
      description
        "MAC TX underrun errors count.";
    }
    leaf counter_slice4_ifg_mac_pool87_port_mib_counter2_tx_mac_underrun_err_cnt {
      type oc-yang:counter64;
      description
        "MAC TX underrun errors count.";
    }
    leaf counter_slice4_ifg_mac_pool87_port_mib_counter3_tx_mac_underrun_err_cnt {
      type oc-yang:counter64;
      description
        "MAC TX underrun errors count.";
    }
    leaf counter_slice4_ifg_mac_pool87_port_mib_counter4_tx_mac_underrun_err_cnt {
      type oc-yang:counter64;
      description
        "MAC TX underrun errors count.";
    }
    leaf counter_slice4_ifg_mac_pool87_port_mib_counter5_tx_mac_underrun_err_cnt {
      type oc-yang:counter64;
      description
        "MAC TX underrun errors count.";
    }
    leaf counter_slice4_ifg_mac_pool87_port_mib_counter6_tx_mac_underrun_err_cnt {
      type oc-yang:counter64;
      description
        "MAC TX underrun errors count.";
    }
    leaf counter_slice4_ifg_mac_pool87_port_mib_counter7_tx_mac_underrun_err_cnt {
      type oc-yang:counter64;
      description
        "MAC TX underrun errors count.";
    }
    leaf counter_slice5_ifg_mac_pool80_port_mib_counter0_tx_mac_underrun_err_cnt {
      type oc-yang:counter64;
      description
        "MAC TX underrun errors count.";
    }
    leaf counter_slice5_ifg_mac_pool80_port_mib_counter1_tx_mac_underrun_err_cnt {
      type oc-yang:counter64;
      description
        "MAC TX underrun errors count.";
    }
    leaf counter_slice5_ifg_mac_pool80_port_mib_counter2_tx_mac_underrun_err_cnt {
      type oc-yang:counter64;
      description
        "MAC TX underrun errors count.";
    }
    leaf counter_slice5_ifg_mac_pool80_port_mib_counter3_tx_mac_underrun_err_cnt {
      type oc-yang:counter64;
      description
        "MAC TX underrun errors count.";
    }
    leaf counter_slice5_ifg_mac_pool80_port_mib_counter4_tx_mac_underrun_err_cnt {
      type oc-yang:counter64;
      description
        "MAC TX underrun errors count.";
    }
    leaf counter_slice5_ifg_mac_pool80_port_mib_counter5_tx_mac_underrun_err_cnt {
      type oc-yang:counter64;
      description
        "MAC TX underrun errors count.";
    }
    leaf counter_slice5_ifg_mac_pool80_port_mib_counter6_tx_mac_underrun_err_cnt {
      type oc-yang:counter64;
      description
        "MAC TX underrun errors count.";
    }
    leaf counter_slice5_ifg_mac_pool80_port_mib_counter7_tx_mac_underrun_err_cnt {
      type oc-yang:counter64;
      description
        "MAC TX underrun errors count.";
    }
    leaf counter_slice5_ifg_mac_pool81_port_mib_counter0_tx_mac_underrun_err_cnt {
      type oc-yang:counter64;
      description
        "MAC TX underrun errors count.";
    }
    leaf counter_slice5_ifg_mac_pool81_port_mib_counter1_tx_mac_underrun_err_cnt {
      type oc-yang:counter64;
      description
        "MAC TX underrun errors count.";
    }
    leaf counter_slice5_ifg_mac_pool81_port_mib_counter2_tx_mac_underrun_err_cnt {
      type oc-yang:counter64;
      description
        "MAC TX underrun errors count.";
    }
    leaf counter_slice5_ifg_mac_pool81_port_mib_counter3_tx_mac_underrun_err_cnt {
      type oc-yang:counter64;
      description
        "MAC TX underrun errors count.";
    }
    leaf counter_slice5_ifg_mac_pool81_port_mib_counter4_tx_mac_underrun_err_cnt {
      type oc-yang:counter64;
      description
        "MAC TX underrun errors count.";
    }
    leaf counter_slice5_ifg_mac_pool81_port_mib_counter5_tx_mac_underrun_err_cnt {
      type oc-yang:counter64;
      description
        "MAC TX underrun errors count.";
    }
    leaf counter_slice5_ifg_mac_pool81_port_mib_counter6_tx_mac_underrun_err_cnt {
      type oc-yang:counter64;
      description
        "MAC TX underrun errors count.";
    }
    leaf counter_slice5_ifg_mac_pool81_port_mib_counter7_tx_mac_underrun_err_cnt {
      type oc-yang:counter64;
      description
        "MAC TX underrun errors count.";
    }
    leaf counter_slice5_ifg_mac_pool82_port_mib_counter0_tx_mac_underrun_err_cnt {
      type oc-yang:counter64;
      description
        "MAC TX underrun errors count.";
    }
    leaf counter_slice5_ifg_mac_pool82_port_mib_counter1_tx_mac_underrun_err_cnt {
      type oc-yang:counter64;
      description
        "MAC TX underrun errors count.";
    }
    leaf counter_slice5_ifg_mac_pool82_port_mib_counter2_tx_mac_underrun_err_cnt {
      type oc-yang:counter64;
      description
        "MAC TX underrun errors count.";
    }
    leaf counter_slice5_ifg_mac_pool82_port_mib_counter3_tx_mac_underrun_err_cnt {
      type oc-yang:counter64;
      description
        "MAC TX underrun errors count.";
    }
    leaf counter_slice5_ifg_mac_pool82_port_mib_counter4_tx_mac_underrun_err_cnt {
      type oc-yang:counter64;
      description
        "MAC TX underrun errors count.";
    }
    leaf counter_slice5_ifg_mac_pool82_port_mib_counter5_tx_mac_underrun_err_cnt {
      type oc-yang:counter64;
      description
        "MAC TX underrun errors count.";
    }
    leaf counter_slice5_ifg_mac_pool82_port_mib_counter6_tx_mac_underrun_err_cnt {
      type oc-yang:counter64;
      description
        "MAC TX underrun errors count.";
    }
    leaf counter_slice5_ifg_mac_pool82_port_mib_counter7_tx_mac_underrun_err_cnt {
      type oc-yang:counter64;
      description
        "MAC TX underrun errors count.";
    }
    leaf counter_slice5_ifg_mac_pool83_port_mib_counter0_tx_mac_underrun_err_cnt {
      type oc-yang:counter64;
      description
        "MAC TX underrun errors count.";
    }
    leaf counter_slice5_ifg_mac_pool83_port_mib_counter1_tx_mac_underrun_err_cnt {
      type oc-yang:counter64;
      description
        "MAC TX underrun errors count.";
    }
    leaf counter_slice5_ifg_mac_pool83_port_mib_counter2_tx_mac_underrun_err_cnt {
      type oc-yang:counter64;
      description
        "MAC TX underrun errors count.";
    }
    leaf counter_slice5_ifg_mac_pool83_port_mib_counter3_tx_mac_underrun_err_cnt {
      type oc-yang:counter64;
      description
        "MAC TX underrun errors count.";
    }
    leaf counter_slice5_ifg_mac_pool83_port_mib_counter4_tx_mac_underrun_err_cnt {
      type oc-yang:counter64;
      description
        "MAC TX underrun errors count.";
    }
    leaf counter_slice5_ifg_mac_pool83_port_mib_counter5_tx_mac_underrun_err_cnt {
      type oc-yang:counter64;
      description
        "MAC TX underrun errors count.";
    }
    leaf counter_slice5_ifg_mac_pool83_port_mib_counter6_tx_mac_underrun_err_cnt {
      type oc-yang:counter64;
      description
        "MAC TX underrun errors count.";
    }
    leaf counter_slice5_ifg_mac_pool83_port_mib_counter7_tx_mac_underrun_err_cnt {
      type oc-yang:counter64;
      description
        "MAC TX underrun errors count.";
    }
    leaf counter_slice5_ifg_mac_pool84_port_mib_counter0_tx_mac_underrun_err_cnt {
      type oc-yang:counter64;
      description
        "MAC TX underrun errors count.";
    }
    leaf counter_slice5_ifg_mac_pool84_port_mib_counter1_tx_mac_underrun_err_cnt {
      type oc-yang:counter64;
      description
        "MAC TX underrun errors count.";
    }
    leaf counter_slice5_ifg_mac_pool84_port_mib_counter2_tx_mac_underrun_err_cnt {
      type oc-yang:counter64;
      description
        "MAC TX underrun errors count.";
    }
    leaf counter_slice5_ifg_mac_pool84_port_mib_counter3_tx_mac_underrun_err_cnt {
      type oc-yang:counter64;
      description
        "MAC TX underrun errors count.";
    }
    leaf counter_slice5_ifg_mac_pool84_port_mib_counter4_tx_mac_underrun_err_cnt {
      type oc-yang:counter64;
      description
        "MAC TX underrun errors count.";
    }
    leaf counter_slice5_ifg_mac_pool84_port_mib_counter5_tx_mac_underrun_err_cnt {
      type oc-yang:counter64;
      description
        "MAC TX underrun errors count.";
    }
    leaf counter_slice5_ifg_mac_pool84_port_mib_counter6_tx_mac_underrun_err_cnt {
      type oc-yang:counter64;
      description
        "MAC TX underrun errors count.";
    }
    leaf counter_slice5_ifg_mac_pool84_port_mib_counter7_tx_mac_underrun_err_cnt {
      type oc-yang:counter64;
      description
        "MAC TX underrun errors count.";
    }
    leaf counter_slice5_ifg_mac_pool85_port_mib_counter0_tx_mac_underrun_err_cnt {
      type oc-yang:counter64;
      description
        "MAC TX underrun errors count.";
    }
    leaf counter_slice5_ifg_mac_pool85_port_mib_counter1_tx_mac_underrun_err_cnt {
      type oc-yang:counter64;
      description
        "MAC TX underrun errors count.";
    }
    leaf counter_slice5_ifg_mac_pool85_port_mib_counter2_tx_mac_underrun_err_cnt {
      type oc-yang:counter64;
      description
        "MAC TX underrun errors count.";
    }
    leaf counter_slice5_ifg_mac_pool85_port_mib_counter3_tx_mac_underrun_err_cnt {
      type oc-yang:counter64;
      description
        "MAC TX underrun errors count.";
    }
    leaf counter_slice5_ifg_mac_pool85_port_mib_counter4_tx_mac_underrun_err_cnt {
      type oc-yang:counter64;
      description
        "MAC TX underrun errors count.";
    }
    leaf counter_slice5_ifg_mac_pool85_port_mib_counter5_tx_mac_underrun_err_cnt {
      type oc-yang:counter64;
      description
        "MAC TX underrun errors count.";
    }
    leaf counter_slice5_ifg_mac_pool85_port_mib_counter6_tx_mac_underrun_err_cnt {
      type oc-yang:counter64;
      description
        "MAC TX underrun errors count.";
    }
    leaf counter_slice5_ifg_mac_pool85_port_mib_counter7_tx_mac_underrun_err_cnt {
      type oc-yang:counter64;
      description
        "MAC TX underrun errors count.";
    }
    leaf counter_slice5_ifg_mac_pool86_port_mib_counter0_tx_mac_underrun_err_cnt {
      type oc-yang:counter64;
      description
        "MAC TX underrun errors count.";
    }
    leaf counter_slice5_ifg_mac_pool86_port_mib_counter1_tx_mac_underrun_err_cnt {
      type oc-yang:counter64;
      description
        "MAC TX underrun errors count.";
    }
    leaf counter_slice5_ifg_mac_pool86_port_mib_counter2_tx_mac_underrun_err_cnt {
      type oc-yang:counter64;
      description
        "MAC TX underrun errors count.";
    }
    leaf counter_slice5_ifg_mac_pool86_port_mib_counter3_tx_mac_underrun_err_cnt {
      type oc-yang:counter64;
      description
        "MAC TX underrun errors count.";
    }
    leaf counter_slice5_ifg_mac_pool86_port_mib_counter4_tx_mac_underrun_err_cnt {
      type oc-yang:counter64;
      description
        "MAC TX underrun errors count.";
    }
    leaf counter_slice5_ifg_mac_pool86_port_mib_counter5_tx_mac_underrun_err_cnt {
      type oc-yang:counter64;
      description
        "MAC TX underrun errors count.";
    }
    leaf counter_slice5_ifg_mac_pool86_port_mib_counter6_tx_mac_underrun_err_cnt {
      type oc-yang:counter64;
      description
        "MAC TX underrun errors count.";
    }
    leaf counter_slice5_ifg_mac_pool86_port_mib_counter7_tx_mac_underrun_err_cnt {
      type oc-yang:counter64;
      description
        "MAC TX underrun errors count.";
    }
    leaf counter_slice5_ifg_mac_pool87_port_mib_counter0_tx_mac_underrun_err_cnt {
      type oc-yang:counter64;
      description
        "MAC TX underrun errors count.";
    }
    leaf counter_slice5_ifg_mac_pool87_port_mib_counter1_tx_mac_underrun_err_cnt {
      type oc-yang:counter64;
      description
        "MAC TX underrun errors count.";
    }
    leaf counter_slice5_ifg_mac_pool87_port_mib_counter2_tx_mac_underrun_err_cnt {
      type oc-yang:counter64;
      description
        "MAC TX underrun errors count.";
    }
    leaf counter_slice5_ifg_mac_pool87_port_mib_counter3_tx_mac_underrun_err_cnt {
      type oc-yang:counter64;
      description
        "MAC TX underrun errors count.";
    }
    leaf counter_slice5_ifg_mac_pool87_port_mib_counter4_tx_mac_underrun_err_cnt {
      type oc-yang:counter64;
      description
        "MAC TX underrun errors count.";
    }
    leaf counter_slice5_ifg_mac_pool87_port_mib_counter5_tx_mac_underrun_err_cnt {
      type oc-yang:counter64;
      description
        "MAC TX underrun errors count.";
    }
    leaf counter_slice5_ifg_mac_pool87_port_mib_counter6_tx_mac_underrun_err_cnt {
      type oc-yang:counter64;
      description
        "MAC TX underrun errors count.";
    }
    leaf counter_slice5_ifg_mac_pool87_port_mib_counter7_tx_mac_underrun_err_cnt {
      type oc-yang:counter64;
      description
        "MAC TX underrun errors count.";
    }
    leaf counter_slice6_ifg_mac_pool80_port_mib_counter0_tx_mac_underrun_err_cnt {
      type oc-yang:counter64;
      description
        "MAC TX underrun errors count.";
    }
    leaf counter_slice6_ifg_mac_pool80_port_mib_counter1_tx_mac_underrun_err_cnt {
      type oc-yang:counter64;
      description
        "MAC TX underrun errors count.";
    }
    leaf counter_slice6_ifg_mac_pool80_port_mib_counter2_tx_mac_underrun_err_cnt {
      type oc-yang:counter64;
      description
        "MAC TX underrun errors count.";
    }
    leaf counter_slice6_ifg_mac_pool80_port_mib_counter3_tx_mac_underrun_err_cnt {
      type oc-yang:counter64;
      description
        "MAC TX underrun errors count.";
    }
    leaf counter_slice6_ifg_mac_pool80_port_mib_counter4_tx_mac_underrun_err_cnt {
      type oc-yang:counter64;
      description
        "MAC TX underrun errors count.";
    }
    leaf counter_slice6_ifg_mac_pool80_port_mib_counter5_tx_mac_underrun_err_cnt {
      type oc-yang:counter64;
      description
        "MAC TX underrun errors count.";
    }
    leaf counter_slice6_ifg_mac_pool80_port_mib_counter6_tx_mac_underrun_err_cnt {
      type oc-yang:counter64;
      description
        "MAC TX underrun errors count.";
    }
    leaf counter_slice6_ifg_mac_pool80_port_mib_counter7_tx_mac_underrun_err_cnt {
      type oc-yang:counter64;
      description
        "MAC TX underrun errors count.";
    }
    leaf counter_slice6_ifg_mac_pool81_port_mib_counter0_tx_mac_underrun_err_cnt {
      type oc-yang:counter64;
      description
        "MAC TX underrun errors count.";
    }
    leaf counter_slice6_ifg_mac_pool81_port_mib_counter1_tx_mac_underrun_err_cnt {
      type oc-yang:counter64;
      description
        "MAC TX underrun errors count.";
    }
    leaf counter_slice6_ifg_mac_pool81_port_mib_counter2_tx_mac_underrun_err_cnt {
      type oc-yang:counter64;
      description
        "MAC TX underrun errors count.";
    }
    leaf counter_slice6_ifg_mac_pool81_port_mib_counter3_tx_mac_underrun_err_cnt {
      type oc-yang:counter64;
      description
        "MAC TX underrun errors count.";
    }
    leaf counter_slice6_ifg_mac_pool81_port_mib_counter4_tx_mac_underrun_err_cnt {
      type oc-yang:counter64;
      description
        "MAC TX underrun errors count.";
    }
    leaf counter_slice6_ifg_mac_pool81_port_mib_counter5_tx_mac_underrun_err_cnt {
      type oc-yang:counter64;
      description
        "MAC TX underrun errors count.";
    }
    leaf counter_slice6_ifg_mac_pool81_port_mib_counter6_tx_mac_underrun_err_cnt {
      type oc-yang:counter64;
      description
        "MAC TX underrun errors count.";
    }
    leaf counter_slice6_ifg_mac_pool81_port_mib_counter7_tx_mac_underrun_err_cnt {
      type oc-yang:counter64;
      description
        "MAC TX underrun errors count.";
    }
    leaf counter_slice6_ifg_mac_pool82_port_mib_counter0_tx_mac_underrun_err_cnt {
      type oc-yang:counter64;
      description
        "MAC TX underrun errors count.";
    }
    leaf counter_slice6_ifg_mac_pool82_port_mib_counter1_tx_mac_underrun_err_cnt {
      type oc-yang:counter64;
      description
        "MAC TX underrun errors count.";
    }
    leaf counter_slice6_ifg_mac_pool82_port_mib_counter2_tx_mac_underrun_err_cnt {
      type oc-yang:counter64;
      description
        "MAC TX underrun errors count.";
    }
    leaf counter_slice6_ifg_mac_pool82_port_mib_counter3_tx_mac_underrun_err_cnt {
      type oc-yang:counter64;
      description
        "MAC TX underrun errors count.";
    }
    leaf counter_slice6_ifg_mac_pool82_port_mib_counter4_tx_mac_underrun_err_cnt {
      type oc-yang:counter64;
      description
        "MAC TX underrun errors count.";
    }
    leaf counter_slice6_ifg_mac_pool82_port_mib_counter5_tx_mac_underrun_err_cnt {
      type oc-yang:counter64;
      description
        "MAC TX underrun errors count.";
    }
    leaf counter_slice6_ifg_mac_pool82_port_mib_counter6_tx_mac_underrun_err_cnt {
      type oc-yang:counter64;
      description
        "MAC TX underrun errors count.";
    }
    leaf counter_slice6_ifg_mac_pool82_port_mib_counter7_tx_mac_underrun_err_cnt {
      type oc-yang:counter64;
      description
        "MAC TX underrun errors count.";
    }
    leaf counter_slice6_ifg_mac_pool83_port_mib_counter0_tx_mac_underrun_err_cnt {
      type oc-yang:counter64;
      description
        "MAC TX underrun errors count.";
    }
    leaf counter_slice6_ifg_mac_pool83_port_mib_counter1_tx_mac_underrun_err_cnt {
      type oc-yang:counter64;
      description
        "MAC TX underrun errors count.";
    }
    leaf counter_slice6_ifg_mac_pool83_port_mib_counter2_tx_mac_underrun_err_cnt {
      type oc-yang:counter64;
      description
        "MAC TX underrun errors count.";
    }
    leaf counter_slice6_ifg_mac_pool83_port_mib_counter3_tx_mac_underrun_err_cnt {
      type oc-yang:counter64;
      description
        "MAC TX underrun errors count.";
    }
    leaf counter_slice6_ifg_mac_pool83_port_mib_counter4_tx_mac_underrun_err_cnt {
      type oc-yang:counter64;
      description
        "MAC TX underrun errors count.";
    }
    leaf counter_slice6_ifg_mac_pool83_port_mib_counter5_tx_mac_underrun_err_cnt {
      type oc-yang:counter64;
      description
        "MAC TX underrun errors count.";
    }
    leaf counter_slice6_ifg_mac_pool83_port_mib_counter6_tx_mac_underrun_err_cnt {
      type oc-yang:counter64;
      description
        "MAC TX underrun errors count.";
    }
    leaf counter_slice6_ifg_mac_pool83_port_mib_counter7_tx_mac_underrun_err_cnt {
      type oc-yang:counter64;
      description
        "MAC TX underrun errors count.";
    }
    leaf counter_slice6_ifg_mac_pool84_port_mib_counter0_tx_mac_underrun_err_cnt {
      type oc-yang:counter64;
      description
        "MAC TX underrun errors count.";
    }
    leaf counter_slice6_ifg_mac_pool84_port_mib_counter1_tx_mac_underrun_err_cnt {
      type oc-yang:counter64;
      description
        "MAC TX underrun errors count.";
    }
    leaf counter_slice6_ifg_mac_pool84_port_mib_counter2_tx_mac_underrun_err_cnt {
      type oc-yang:counter64;
      description
        "MAC TX underrun errors count.";
    }
    leaf counter_slice6_ifg_mac_pool84_port_mib_counter3_tx_mac_underrun_err_cnt {
      type oc-yang:counter64;
      description
        "MAC TX underrun errors count.";
    }
    leaf counter_slice6_ifg_mac_pool84_port_mib_counter4_tx_mac_underrun_err_cnt {
      type oc-yang:counter64;
      description
        "MAC TX underrun errors count.";
    }
    leaf counter_slice6_ifg_mac_pool84_port_mib_counter5_tx_mac_underrun_err_cnt {
      type oc-yang:counter64;
      description
        "MAC TX underrun errors count.";
    }
    leaf counter_slice6_ifg_mac_pool84_port_mib_counter6_tx_mac_underrun_err_cnt {
      type oc-yang:counter64;
      description
        "MAC TX underrun errors count.";
    }
    leaf counter_slice6_ifg_mac_pool84_port_mib_counter7_tx_mac_underrun_err_cnt {
      type oc-yang:counter64;
      description
        "MAC TX underrun errors count.";
    }
    leaf counter_slice6_ifg_mac_pool85_port_mib_counter0_tx_mac_underrun_err_cnt {
      type oc-yang:counter64;
      description
        "MAC TX underrun errors count.";
    }
    leaf counter_slice6_ifg_mac_pool85_port_mib_counter1_tx_mac_underrun_err_cnt {
      type oc-yang:counter64;
      description
        "MAC TX underrun errors count.";
    }
    leaf counter_slice6_ifg_mac_pool85_port_mib_counter2_tx_mac_underrun_err_cnt {
      type oc-yang:counter64;
      description
        "MAC TX underrun errors count.";
    }
    leaf counter_slice6_ifg_mac_pool85_port_mib_counter3_tx_mac_underrun_err_cnt {
      type oc-yang:counter64;
      description
        "MAC TX underrun errors count.";
    }
    leaf counter_slice6_ifg_mac_pool85_port_mib_counter4_tx_mac_underrun_err_cnt {
      type oc-yang:counter64;
      description
        "MAC TX underrun errors count.";
    }
    leaf counter_slice6_ifg_mac_pool85_port_mib_counter5_tx_mac_underrun_err_cnt {
      type oc-yang:counter64;
      description
        "MAC TX underrun errors count.";
    }
    leaf counter_slice6_ifg_mac_pool85_port_mib_counter6_tx_mac_underrun_err_cnt {
      type oc-yang:counter64;
      description
        "MAC TX underrun errors count.";
    }
    leaf counter_slice6_ifg_mac_pool85_port_mib_counter7_tx_mac_underrun_err_cnt {
      type oc-yang:counter64;
      description
        "MAC TX underrun errors count.";
    }
    leaf counter_slice6_ifg_mac_pool86_port_mib_counter0_tx_mac_underrun_err_cnt {
      type oc-yang:counter64;
      description
        "MAC TX underrun errors count.";
    }
    leaf counter_slice6_ifg_mac_pool86_port_mib_counter1_tx_mac_underrun_err_cnt {
      type oc-yang:counter64;
      description
        "MAC TX underrun errors count.";
    }
    leaf counter_slice6_ifg_mac_pool86_port_mib_counter2_tx_mac_underrun_err_cnt {
      type oc-yang:counter64;
      description
        "MAC TX underrun errors count.";
    }
    leaf counter_slice6_ifg_mac_pool86_port_mib_counter3_tx_mac_underrun_err_cnt {
      type oc-yang:counter64;
      description
        "MAC TX underrun errors count.";
    }
    leaf counter_slice6_ifg_mac_pool86_port_mib_counter4_tx_mac_underrun_err_cnt {
      type oc-yang:counter64;
      description
        "MAC TX underrun errors count.";
    }
    leaf counter_slice6_ifg_mac_pool86_port_mib_counter5_tx_mac_underrun_err_cnt {
      type oc-yang:counter64;
      description
        "MAC TX underrun errors count.";
    }
    leaf counter_slice6_ifg_mac_pool86_port_mib_counter6_tx_mac_underrun_err_cnt {
      type oc-yang:counter64;
      description
        "MAC TX underrun errors count.";
    }
    leaf counter_slice6_ifg_mac_pool86_port_mib_counter7_tx_mac_underrun_err_cnt {
      type oc-yang:counter64;
      description
        "MAC TX underrun errors count.";
    }
    leaf counter_slice6_ifg_mac_pool87_port_mib_counter0_tx_mac_underrun_err_cnt {
      type oc-yang:counter64;
      description
        "MAC TX underrun errors count.";
    }
    leaf counter_slice6_ifg_mac_pool87_port_mib_counter1_tx_mac_underrun_err_cnt {
      type oc-yang:counter64;
      description
        "MAC TX underrun errors count.";
    }
    leaf counter_slice6_ifg_mac_pool87_port_mib_counter2_tx_mac_underrun_err_cnt {
      type oc-yang:counter64;
      description
        "MAC TX underrun errors count.";
    }
    leaf counter_slice6_ifg_mac_pool87_port_mib_counter3_tx_mac_underrun_err_cnt {
      type oc-yang:counter64;
      description
        "MAC TX underrun errors count.";
    }
    leaf counter_slice6_ifg_mac_pool87_port_mib_counter4_tx_mac_underrun_err_cnt {
      type oc-yang:counter64;
      description
        "MAC TX underrun errors count.";
    }
    leaf counter_slice6_ifg_mac_pool87_port_mib_counter5_tx_mac_underrun_err_cnt {
      type oc-yang:counter64;
      description
        "MAC TX underrun errors count.";
    }
    leaf counter_slice6_ifg_mac_pool87_port_mib_counter6_tx_mac_underrun_err_cnt {
      type oc-yang:counter64;
      description
        "MAC TX underrun errors count.";
    }
    leaf counter_slice6_ifg_mac_pool87_port_mib_counter7_tx_mac_underrun_err_cnt {
      type oc-yang:counter64;
      description
        "MAC TX underrun errors count.";
    }
    leaf counter_slice7_ifg_mac_pool80_port_mib_counter0_tx_mac_underrun_err_cnt {
      type oc-yang:counter64;
      description
        "MAC TX underrun errors count.";
    }
    leaf counter_slice7_ifg_mac_pool80_port_mib_counter1_tx_mac_underrun_err_cnt {
      type oc-yang:counter64;
      description
        "MAC TX underrun errors count.";
    }
    leaf counter_slice7_ifg_mac_pool80_port_mib_counter2_tx_mac_underrun_err_cnt {
      type oc-yang:counter64;
      description
        "MAC TX underrun errors count.";
    }
    leaf counter_slice7_ifg_mac_pool80_port_mib_counter3_tx_mac_underrun_err_cnt {
      type oc-yang:counter64;
      description
        "MAC TX underrun errors count.";
    }
    leaf counter_slice7_ifg_mac_pool80_port_mib_counter4_tx_mac_underrun_err_cnt {
      type oc-yang:counter64;
      description
        "MAC TX underrun errors count.";
    }
    leaf counter_slice7_ifg_mac_pool80_port_mib_counter5_tx_mac_underrun_err_cnt {
      type oc-yang:counter64;
      description
        "MAC TX underrun errors count.";
    }
    leaf counter_slice7_ifg_mac_pool80_port_mib_counter6_tx_mac_underrun_err_cnt {
      type oc-yang:counter64;
      description
        "MAC TX underrun errors count.";
    }
    leaf counter_slice7_ifg_mac_pool80_port_mib_counter7_tx_mac_underrun_err_cnt {
      type oc-yang:counter64;
      description
        "MAC TX underrun errors count.";
    }
    leaf counter_slice7_ifg_mac_pool81_port_mib_counter0_tx_mac_underrun_err_cnt {
      type oc-yang:counter64;
      description
        "MAC TX underrun errors count.";
    }
    leaf counter_slice7_ifg_mac_pool81_port_mib_counter1_tx_mac_underrun_err_cnt {
      type oc-yang:counter64;
      description
        "MAC TX underrun errors count.";
    }
    leaf counter_slice7_ifg_mac_pool81_port_mib_counter2_tx_mac_underrun_err_cnt {
      type oc-yang:counter64;
      description
        "MAC TX underrun errors count.";
    }
    leaf counter_slice7_ifg_mac_pool81_port_mib_counter3_tx_mac_underrun_err_cnt {
      type oc-yang:counter64;
      description
        "MAC TX underrun errors count.";
    }
    leaf counter_slice7_ifg_mac_pool81_port_mib_counter4_tx_mac_underrun_err_cnt {
      type oc-yang:counter64;
      description
        "MAC TX underrun errors count.";
    }
    leaf counter_slice7_ifg_mac_pool81_port_mib_counter5_tx_mac_underrun_err_cnt {
      type oc-yang:counter64;
      description
        "MAC TX underrun errors count.";
    }
    leaf counter_slice7_ifg_mac_pool81_port_mib_counter6_tx_mac_underrun_err_cnt {
      type oc-yang:counter64;
      description
        "MAC TX underrun errors count.";
    }
    leaf counter_slice7_ifg_mac_pool81_port_mib_counter7_tx_mac_underrun_err_cnt {
      type oc-yang:counter64;
      description
        "MAC TX underrun errors count.";
    }
    leaf counter_slice7_ifg_mac_pool82_port_mib_counter0_tx_mac_underrun_err_cnt {
      type oc-yang:counter64;
      description
        "MAC TX underrun errors count.";
    }
    leaf counter_slice7_ifg_mac_pool82_port_mib_counter1_tx_mac_underrun_err_cnt {
      type oc-yang:counter64;
      description
        "MAC TX underrun errors count.";
    }
    leaf counter_slice7_ifg_mac_pool82_port_mib_counter2_tx_mac_underrun_err_cnt {
      type oc-yang:counter64;
      description
        "MAC TX underrun errors count.";
    }
    leaf counter_slice7_ifg_mac_pool82_port_mib_counter3_tx_mac_underrun_err_cnt {
      type oc-yang:counter64;
      description
        "MAC TX underrun errors count.";
    }
    leaf counter_slice7_ifg_mac_pool82_port_mib_counter4_tx_mac_underrun_err_cnt {
      type oc-yang:counter64;
      description
        "MAC TX underrun errors count.";
    }
    leaf counter_slice7_ifg_mac_pool82_port_mib_counter5_tx_mac_underrun_err_cnt {
      type oc-yang:counter64;
      description
        "MAC TX underrun errors count.";
    }
    leaf counter_slice7_ifg_mac_pool82_port_mib_counter6_tx_mac_underrun_err_cnt {
      type oc-yang:counter64;
      description
        "MAC TX underrun errors count.";
    }
    leaf counter_slice7_ifg_mac_pool82_port_mib_counter7_tx_mac_underrun_err_cnt {
      type oc-yang:counter64;
      description
        "MAC TX underrun errors count.";
    }
    leaf counter_slice7_ifg_mac_pool83_port_mib_counter0_tx_mac_underrun_err_cnt {
      type oc-yang:counter64;
      description
        "MAC TX underrun errors count.";
    }
    leaf counter_slice7_ifg_mac_pool83_port_mib_counter1_tx_mac_underrun_err_cnt {
      type oc-yang:counter64;
      description
        "MAC TX underrun errors count.";
    }
    leaf counter_slice7_ifg_mac_pool83_port_mib_counter2_tx_mac_underrun_err_cnt {
      type oc-yang:counter64;
      description
        "MAC TX underrun errors count.";
    }
    leaf counter_slice7_ifg_mac_pool83_port_mib_counter3_tx_mac_underrun_err_cnt {
      type oc-yang:counter64;
      description
        "MAC TX underrun errors count.";
    }
    leaf counter_slice7_ifg_mac_pool83_port_mib_counter4_tx_mac_underrun_err_cnt {
      type oc-yang:counter64;
      description
        "MAC TX underrun errors count.";
    }
    leaf counter_slice7_ifg_mac_pool83_port_mib_counter5_tx_mac_underrun_err_cnt {
      type oc-yang:counter64;
      description
        "MAC TX underrun errors count.";
    }
    leaf counter_slice7_ifg_mac_pool83_port_mib_counter6_tx_mac_underrun_err_cnt {
      type oc-yang:counter64;
      description
        "MAC TX underrun errors count.";
    }
    leaf counter_slice7_ifg_mac_pool83_port_mib_counter7_tx_mac_underrun_err_cnt {
      type oc-yang:counter64;
      description
        "MAC TX underrun errors count.";
    }
    leaf counter_slice7_ifg_mac_pool84_port_mib_counter0_tx_mac_underrun_err_cnt {
      type oc-yang:counter64;
      description
        "MAC TX underrun errors count.";
    }
    leaf counter_slice7_ifg_mac_pool84_port_mib_counter1_tx_mac_underrun_err_cnt {
      type oc-yang:counter64;
      description
        "MAC TX underrun errors count.";
    }
    leaf counter_slice7_ifg_mac_pool84_port_mib_counter2_tx_mac_underrun_err_cnt {
      type oc-yang:counter64;
      description
        "MAC TX underrun errors count.";
    }
    leaf counter_slice7_ifg_mac_pool84_port_mib_counter3_tx_mac_underrun_err_cnt {
      type oc-yang:counter64;
      description
        "MAC TX underrun errors count.";
    }
    leaf counter_slice7_ifg_mac_pool84_port_mib_counter4_tx_mac_underrun_err_cnt {
      type oc-yang:counter64;
      description
        "MAC TX underrun errors count.";
    }
    leaf counter_slice7_ifg_mac_pool84_port_mib_counter5_tx_mac_underrun_err_cnt {
      type oc-yang:counter64;
      description
        "MAC TX underrun errors count.";
    }
    leaf counter_slice7_ifg_mac_pool84_port_mib_counter6_tx_mac_underrun_err_cnt {
      type oc-yang:counter64;
      description
        "MAC TX underrun errors count.";
    }
    leaf counter_slice7_ifg_mac_pool84_port_mib_counter7_tx_mac_underrun_err_cnt {
      type oc-yang:counter64;
      description
        "MAC TX underrun errors count.";
    }
    leaf counter_slice7_ifg_mac_pool85_port_mib_counter0_tx_mac_underrun_err_cnt {
      type oc-yang:counter64;
      description
        "MAC TX underrun errors count.";
    }
    leaf counter_slice7_ifg_mac_pool85_port_mib_counter1_tx_mac_underrun_err_cnt {
      type oc-yang:counter64;
      description
        "MAC TX underrun errors count.";
    }
    leaf counter_slice7_ifg_mac_pool85_port_mib_counter2_tx_mac_underrun_err_cnt {
      type oc-yang:counter64;
      description
        "MAC TX underrun errors count.";
    }
    leaf counter_slice7_ifg_mac_pool85_port_mib_counter3_tx_mac_underrun_err_cnt {
      type oc-yang:counter64;
      description
        "MAC TX underrun errors count.";
    }
    leaf counter_slice7_ifg_mac_pool85_port_mib_counter4_tx_mac_underrun_err_cnt {
      type oc-yang:counter64;
      description
        "MAC TX underrun errors count.";
    }
    leaf counter_slice7_ifg_mac_pool85_port_mib_counter5_tx_mac_underrun_err_cnt {
      type oc-yang:counter64;
      description
        "MAC TX underrun errors count.";
    }
    leaf counter_slice7_ifg_mac_pool85_port_mib_counter6_tx_mac_underrun_err_cnt {
      type oc-yang:counter64;
      description
        "MAC TX underrun errors count.";
    }
    leaf counter_slice7_ifg_mac_pool85_port_mib_counter7_tx_mac_underrun_err_cnt {
      type oc-yang:counter64;
      description
        "MAC TX underrun errors count.";
    }
    leaf counter_slice7_ifg_mac_pool86_port_mib_counter0_tx_mac_underrun_err_cnt {
      type oc-yang:counter64;
      description
        "MAC TX underrun errors count.";
    }
    leaf counter_slice7_ifg_mac_pool86_port_mib_counter1_tx_mac_underrun_err_cnt {
      type oc-yang:counter64;
      description
        "MAC TX underrun errors count.";
    }
    leaf counter_slice7_ifg_mac_pool86_port_mib_counter2_tx_mac_underrun_err_cnt {
      type oc-yang:counter64;
      description
        "MAC TX underrun errors count.";
    }
    leaf counter_slice7_ifg_mac_pool86_port_mib_counter3_tx_mac_underrun_err_cnt {
      type oc-yang:counter64;
      description
        "MAC TX underrun errors count.";
    }
    leaf counter_slice7_ifg_mac_pool86_port_mib_counter4_tx_mac_underrun_err_cnt {
      type oc-yang:counter64;
      description
        "MAC TX underrun errors count.";
    }
    leaf counter_slice7_ifg_mac_pool86_port_mib_counter5_tx_mac_underrun_err_cnt {
      type oc-yang:counter64;
      description
        "MAC TX underrun errors count.";
    }
    leaf counter_slice7_ifg_mac_pool86_port_mib_counter6_tx_mac_underrun_err_cnt {
      type oc-yang:counter64;
      description
        "MAC TX underrun errors count.";
    }
    leaf counter_slice7_ifg_mac_pool86_port_mib_counter7_tx_mac_underrun_err_cnt {
      type oc-yang:counter64;
      description
        "MAC TX underrun errors count.";
    }
    leaf counter_slice7_ifg_mac_pool87_port_mib_counter0_tx_mac_underrun_err_cnt {
      type oc-yang:counter64;
      description
        "MAC TX underrun errors count.";
    }
    leaf counter_slice7_ifg_mac_pool87_port_mib_counter1_tx_mac_underrun_err_cnt {
      type oc-yang:counter64;
      description
        "MAC TX underrun errors count.";
    }
    leaf counter_slice7_ifg_mac_pool87_port_mib_counter2_tx_mac_underrun_err_cnt {
      type oc-yang:counter64;
      description
        "MAC TX underrun errors count.";
    }
    leaf counter_slice7_ifg_mac_pool87_port_mib_counter3_tx_mac_underrun_err_cnt {
      type oc-yang:counter64;
      description
        "MAC TX underrun errors count.";
    }
    leaf counter_slice7_ifg_mac_pool87_port_mib_counter4_tx_mac_underrun_err_cnt {
      type oc-yang:counter64;
      description
        "MAC TX underrun errors count.";
    }
    leaf counter_slice7_ifg_mac_pool87_port_mib_counter5_tx_mac_underrun_err_cnt {
      type oc-yang:counter64;
      description
        "MAC TX underrun errors count.";
    }
    leaf counter_slice7_ifg_mac_pool87_port_mib_counter6_tx_mac_underrun_err_cnt {
      type oc-yang:counter64;
      description
        "MAC TX underrun errors count.";
    }
    leaf counter_slice7_ifg_mac_pool87_port_mib_counter7_tx_mac_underrun_err_cnt {
      type oc-yang:counter64;
      description
        "MAC TX underrun errors count.";
    }
    leaf counter_slice8_ifg_mac_pool80_port_mib_counter0_tx_mac_underrun_err_cnt {
      type oc-yang:counter64;
      description
        "MAC TX underrun errors count.";
    }
    leaf counter_slice8_ifg_mac_pool80_port_mib_counter1_tx_mac_underrun_err_cnt {
      type oc-yang:counter64;
      description
        "MAC TX underrun errors count.";
    }
    leaf counter_slice8_ifg_mac_pool80_port_mib_counter2_tx_mac_underrun_err_cnt {
      type oc-yang:counter64;
      description
        "MAC TX underrun errors count.";
    }
    leaf counter_slice8_ifg_mac_pool80_port_mib_counter3_tx_mac_underrun_err_cnt {
      type oc-yang:counter64;
      description
        "MAC TX underrun errors count.";
    }
    leaf counter_slice8_ifg_mac_pool80_port_mib_counter4_tx_mac_underrun_err_cnt {
      type oc-yang:counter64;
      description
        "MAC TX underrun errors count.";
    }
    leaf counter_slice8_ifg_mac_pool80_port_mib_counter5_tx_mac_underrun_err_cnt {
      type oc-yang:counter64;
      description
        "MAC TX underrun errors count.";
    }
    leaf counter_slice8_ifg_mac_pool80_port_mib_counter6_tx_mac_underrun_err_cnt {
      type oc-yang:counter64;
      description
        "MAC TX underrun errors count.";
    }
    leaf counter_slice8_ifg_mac_pool80_port_mib_counter7_tx_mac_underrun_err_cnt {
      type oc-yang:counter64;
      description
        "MAC TX underrun errors count.";
    }
    leaf counter_slice8_ifg_mac_pool81_port_mib_counter0_tx_mac_underrun_err_cnt {
      type oc-yang:counter64;
      description
        "MAC TX underrun errors count.";
    }
    leaf counter_slice8_ifg_mac_pool81_port_mib_counter1_tx_mac_underrun_err_cnt {
      type oc-yang:counter64;
      description
        "MAC TX underrun errors count.";
    }
    leaf counter_slice8_ifg_mac_pool81_port_mib_counter2_tx_mac_underrun_err_cnt {
      type oc-yang:counter64;
      description
        "MAC TX underrun errors count.";
    }
    leaf counter_slice8_ifg_mac_pool81_port_mib_counter3_tx_mac_underrun_err_cnt {
      type oc-yang:counter64;
      description
        "MAC TX underrun errors count.";
    }
    leaf counter_slice8_ifg_mac_pool81_port_mib_counter4_tx_mac_underrun_err_cnt {
      type oc-yang:counter64;
      description
        "MAC TX underrun errors count.";
    }
    leaf counter_slice8_ifg_mac_pool81_port_mib_counter5_tx_mac_underrun_err_cnt {
      type oc-yang:counter64;
      description
        "MAC TX underrun errors count.";
    }
    leaf counter_slice8_ifg_mac_pool81_port_mib_counter6_tx_mac_underrun_err_cnt {
      type oc-yang:counter64;
      description
        "MAC TX underrun errors count.";
    }
    leaf counter_slice8_ifg_mac_pool81_port_mib_counter7_tx_mac_underrun_err_cnt {
      type oc-yang:counter64;
      description
        "MAC TX underrun errors count.";
    }
    leaf counter_slice8_ifg_mac_pool82_port_mib_counter0_tx_mac_underrun_err_cnt {
      type oc-yang:counter64;
      description
        "MAC TX underrun errors count.";
    }
    leaf counter_slice8_ifg_mac_pool82_port_mib_counter1_tx_mac_underrun_err_cnt {
      type oc-yang:counter64;
      description
        "MAC TX underrun errors count.";
    }
    leaf counter_slice8_ifg_mac_pool82_port_mib_counter2_tx_mac_underrun_err_cnt {
      type oc-yang:counter64;
      description
        "MAC TX underrun errors count.";
    }
    leaf counter_slice8_ifg_mac_pool82_port_mib_counter3_tx_mac_underrun_err_cnt {
      type oc-yang:counter64;
      description
        "MAC TX underrun errors count.";
    }
    leaf counter_slice8_ifg_mac_pool82_port_mib_counter4_tx_mac_underrun_err_cnt {
      type oc-yang:counter64;
      description
        "MAC TX underrun errors count.";
    }
    leaf counter_slice8_ifg_mac_pool82_port_mib_counter5_tx_mac_underrun_err_cnt {
      type oc-yang:counter64;
      description
        "MAC TX underrun errors count.";
    }
    leaf counter_slice8_ifg_mac_pool82_port_mib_counter6_tx_mac_underrun_err_cnt {
      type oc-yang:counter64;
      description
        "MAC TX underrun errors count.";
    }
    leaf counter_slice8_ifg_mac_pool82_port_mib_counter7_tx_mac_underrun_err_cnt {
      type oc-yang:counter64;
      description
        "MAC TX underrun errors count.";
    }
    leaf counter_slice8_ifg_mac_pool83_port_mib_counter0_tx_mac_underrun_err_cnt {
      type oc-yang:counter64;
      description
        "MAC TX underrun errors count.";
    }
    leaf counter_slice8_ifg_mac_pool83_port_mib_counter1_tx_mac_underrun_err_cnt {
      type oc-yang:counter64;
      description
        "MAC TX underrun errors count.";
    }
    leaf counter_slice8_ifg_mac_pool83_port_mib_counter2_tx_mac_underrun_err_cnt {
      type oc-yang:counter64;
      description
        "MAC TX underrun errors count.";
    }
    leaf counter_slice8_ifg_mac_pool83_port_mib_counter3_tx_mac_underrun_err_cnt {
      type oc-yang:counter64;
      description
        "MAC TX underrun errors count.";
    }
    leaf counter_slice8_ifg_mac_pool83_port_mib_counter4_tx_mac_underrun_err_cnt {
      type oc-yang:counter64;
      description
        "MAC TX underrun errors count.";
    }
    leaf counter_slice8_ifg_mac_pool83_port_mib_counter5_tx_mac_underrun_err_cnt {
      type oc-yang:counter64;
      description
        "MAC TX underrun errors count.";
    }
    leaf counter_slice8_ifg_mac_pool83_port_mib_counter6_tx_mac_underrun_err_cnt {
      type oc-yang:counter64;
      description
        "MAC TX underrun errors count.";
    }
    leaf counter_slice8_ifg_mac_pool83_port_mib_counter7_tx_mac_underrun_err_cnt {
      type oc-yang:counter64;
      description
        "MAC TX underrun errors count.";
    }
    leaf counter_slice8_ifg_mac_pool84_port_mib_counter0_tx_mac_underrun_err_cnt {
      type oc-yang:counter64;
      description
        "MAC TX underrun errors count.";
    }
    leaf counter_slice8_ifg_mac_pool84_port_mib_counter1_tx_mac_underrun_err_cnt {
      type oc-yang:counter64;
      description
        "MAC TX underrun errors count.";
    }
    leaf counter_slice8_ifg_mac_pool84_port_mib_counter2_tx_mac_underrun_err_cnt {
      type oc-yang:counter64;
      description
        "MAC TX underrun errors count.";
    }
    leaf counter_slice8_ifg_mac_pool84_port_mib_counter3_tx_mac_underrun_err_cnt {
      type oc-yang:counter64;
      description
        "MAC TX underrun errors count.";
    }
    leaf counter_slice8_ifg_mac_pool84_port_mib_counter4_tx_mac_underrun_err_cnt {
      type oc-yang:counter64;
      description
        "MAC TX underrun errors count.";
    }
    leaf counter_slice8_ifg_mac_pool84_port_mib_counter5_tx_mac_underrun_err_cnt {
      type oc-yang:counter64;
      description
        "MAC TX underrun errors count.";
    }
    leaf counter_slice8_ifg_mac_pool84_port_mib_counter6_tx_mac_underrun_err_cnt {
      type oc-yang:counter64;
      description
        "MAC TX underrun errors count.";
    }
    leaf counter_slice8_ifg_mac_pool84_port_mib_counter7_tx_mac_underrun_err_cnt {
      type oc-yang:counter64;
      description
        "MAC TX underrun errors count.";
    }
    leaf counter_slice8_ifg_mac_pool85_port_mib_counter0_tx_mac_underrun_err_cnt {
      type oc-yang:counter64;
      description
        "MAC TX underrun errors count.";
    }
    leaf counter_slice8_ifg_mac_pool85_port_mib_counter1_tx_mac_underrun_err_cnt {
      type oc-yang:counter64;
      description
        "MAC TX underrun errors count.";
    }
    leaf counter_slice8_ifg_mac_pool85_port_mib_counter2_tx_mac_underrun_err_cnt {
      type oc-yang:counter64;
      description
        "MAC TX underrun errors count.";
    }
    leaf counter_slice8_ifg_mac_pool85_port_mib_counter3_tx_mac_underrun_err_cnt {
      type oc-yang:counter64;
      description
        "MAC TX underrun errors count.";
    }
    leaf counter_slice8_ifg_mac_pool85_port_mib_counter4_tx_mac_underrun_err_cnt {
      type oc-yang:counter64;
      description
        "MAC TX underrun errors count.";
    }
    leaf counter_slice8_ifg_mac_pool85_port_mib_counter5_tx_mac_underrun_err_cnt {
      type oc-yang:counter64;
      description
        "MAC TX underrun errors count.";
    }
    leaf counter_slice8_ifg_mac_pool85_port_mib_counter6_tx_mac_underrun_err_cnt {
      type oc-yang:counter64;
      description
        "MAC TX underrun errors count.";
    }
    leaf counter_slice8_ifg_mac_pool85_port_mib_counter7_tx_mac_underrun_err_cnt {
      type oc-yang:counter64;
      description
        "MAC TX underrun errors count.";
    }
    leaf counter_slice8_ifg_mac_pool86_port_mib_counter0_tx_mac_underrun_err_cnt {
      type oc-yang:counter64;
      description
        "MAC TX underrun errors count.";
    }
    leaf counter_slice8_ifg_mac_pool86_port_mib_counter1_tx_mac_underrun_err_cnt {
      type oc-yang:counter64;
      description
        "MAC TX underrun errors count.";
    }
    leaf counter_slice8_ifg_mac_pool86_port_mib_counter2_tx_mac_underrun_err_cnt {
      type oc-yang:counter64;
      description
        "MAC TX underrun errors count.";
    }
    leaf counter_slice8_ifg_mac_pool86_port_mib_counter3_tx_mac_underrun_err_cnt {
      type oc-yang:counter64;
      description
        "MAC TX underrun errors count.";
    }
    leaf counter_slice8_ifg_mac_pool86_port_mib_counter4_tx_mac_underrun_err_cnt {
      type oc-yang:counter64;
      description
        "MAC TX underrun errors count.";
    }
    leaf counter_slice8_ifg_mac_pool86_port_mib_counter5_tx_mac_underrun_err_cnt {
      type oc-yang:counter64;
      description
        "MAC TX underrun errors count.";
    }
    leaf counter_slice8_ifg_mac_pool86_port_mib_counter6_tx_mac_underrun_err_cnt {
      type oc-yang:counter64;
      description
        "MAC TX underrun errors count.";
    }
    leaf counter_slice8_ifg_mac_pool86_port_mib_counter7_tx_mac_underrun_err_cnt {
      type oc-yang:counter64;
      description
        "MAC TX underrun errors count.";
    }
    leaf counter_slice8_ifg_mac_pool87_port_mib_counter0_tx_mac_underrun_err_cnt {
      type oc-yang:counter64;
      description
        "MAC TX underrun errors count.";
    }
    leaf counter_slice8_ifg_mac_pool87_port_mib_counter1_tx_mac_underrun_err_cnt {
      type oc-yang:counter64;
      description
        "MAC TX underrun errors count.";
    }
    leaf counter_slice8_ifg_mac_pool87_port_mib_counter2_tx_mac_underrun_err_cnt {
      type oc-yang:counter64;
      description
        "MAC TX underrun errors count.";
    }
    leaf counter_slice8_ifg_mac_pool87_port_mib_counter3_tx_mac_underrun_err_cnt {
      type oc-yang:counter64;
      description
        "MAC TX underrun errors count.";
    }
    leaf counter_slice8_ifg_mac_pool87_port_mib_counter4_tx_mac_underrun_err_cnt {
      type oc-yang:counter64;
      description
        "MAC TX underrun errors count.";
    }
    leaf counter_slice8_ifg_mac_pool87_port_mib_counter5_tx_mac_underrun_err_cnt {
      type oc-yang:counter64;
      description
        "MAC TX underrun errors count.";
    }
    leaf counter_slice8_ifg_mac_pool87_port_mib_counter6_tx_mac_underrun_err_cnt {
      type oc-yang:counter64;
      description
        "MAC TX underrun errors count.";
    }
    leaf counter_slice8_ifg_mac_pool87_port_mib_counter7_tx_mac_underrun_err_cnt {
      type oc-yang:counter64;
      description
        "MAC TX underrun errors count.";
    }
    leaf counter_slice9_ifg_mac_pool80_port_mib_counter0_tx_mac_underrun_err_cnt {
      type oc-yang:counter64;
      description
        "MAC TX underrun errors count.";
    }
    leaf counter_slice9_ifg_mac_pool80_port_mib_counter1_tx_mac_underrun_err_cnt {
      type oc-yang:counter64;
      description
        "MAC TX underrun errors count.";
    }
    leaf counter_slice9_ifg_mac_pool80_port_mib_counter2_tx_mac_underrun_err_cnt {
      type oc-yang:counter64;
      description
        "MAC TX underrun errors count.";
    }
    leaf counter_slice9_ifg_mac_pool80_port_mib_counter3_tx_mac_underrun_err_cnt {
      type oc-yang:counter64;
      description
        "MAC TX underrun errors count.";
    }
    leaf counter_slice9_ifg_mac_pool80_port_mib_counter4_tx_mac_underrun_err_cnt {
      type oc-yang:counter64;
      description
        "MAC TX underrun errors count.";
    }
    leaf counter_slice9_ifg_mac_pool80_port_mib_counter5_tx_mac_underrun_err_cnt {
      type oc-yang:counter64;
      description
        "MAC TX underrun errors count.";
    }
    leaf counter_slice9_ifg_mac_pool80_port_mib_counter6_tx_mac_underrun_err_cnt {
      type oc-yang:counter64;
      description
        "MAC TX underrun errors count.";
    }
    leaf counter_slice9_ifg_mac_pool80_port_mib_counter7_tx_mac_underrun_err_cnt {
      type oc-yang:counter64;
      description
        "MAC TX underrun errors count.";
    }
    leaf counter_slice9_ifg_mac_pool81_port_mib_counter0_tx_mac_underrun_err_cnt {
      type oc-yang:counter64;
      description
        "MAC TX underrun errors count.";
    }
    leaf counter_slice9_ifg_mac_pool81_port_mib_counter1_tx_mac_underrun_err_cnt {
      type oc-yang:counter64;
      description
        "MAC TX underrun errors count.";
    }
    leaf counter_slice9_ifg_mac_pool81_port_mib_counter2_tx_mac_underrun_err_cnt {
      type oc-yang:counter64;
      description
        "MAC TX underrun errors count.";
    }
    leaf counter_slice9_ifg_mac_pool81_port_mib_counter3_tx_mac_underrun_err_cnt {
      type oc-yang:counter64;
      description
        "MAC TX underrun errors count.";
    }
    leaf counter_slice9_ifg_mac_pool81_port_mib_counter4_tx_mac_underrun_err_cnt {
      type oc-yang:counter64;
      description
        "MAC TX underrun errors count.";
    }
    leaf counter_slice9_ifg_mac_pool81_port_mib_counter5_tx_mac_underrun_err_cnt {
      type oc-yang:counter64;
      description
        "MAC TX underrun errors count.";
    }
    leaf counter_slice9_ifg_mac_pool81_port_mib_counter6_tx_mac_underrun_err_cnt {
      type oc-yang:counter64;
      description
        "MAC TX underrun errors count.";
    }
    leaf counter_slice9_ifg_mac_pool81_port_mib_counter7_tx_mac_underrun_err_cnt {
      type oc-yang:counter64;
      description
        "MAC TX underrun errors count.";
    }
    leaf counter_slice9_ifg_mac_pool82_port_mib_counter0_tx_mac_underrun_err_cnt {
      type oc-yang:counter64;
      description
        "MAC TX underrun errors count.";
    }
    leaf counter_slice9_ifg_mac_pool82_port_mib_counter1_tx_mac_underrun_err_cnt {
      type oc-yang:counter64;
      description
        "MAC TX underrun errors count.";
    }
    leaf counter_slice9_ifg_mac_pool82_port_mib_counter2_tx_mac_underrun_err_cnt {
      type oc-yang:counter64;
      description
        "MAC TX underrun errors count.";
    }
    leaf counter_slice9_ifg_mac_pool82_port_mib_counter3_tx_mac_underrun_err_cnt {
      type oc-yang:counter64;
      description
        "MAC TX underrun errors count.";
    }
    leaf counter_slice9_ifg_mac_pool82_port_mib_counter4_tx_mac_underrun_err_cnt {
      type oc-yang:counter64;
      description
        "MAC TX underrun errors count.";
    }
    leaf counter_slice9_ifg_mac_pool82_port_mib_counter5_tx_mac_underrun_err_cnt {
      type oc-yang:counter64;
      description
        "MAC TX underrun errors count.";
    }
    leaf counter_slice9_ifg_mac_pool82_port_mib_counter6_tx_mac_underrun_err_cnt {
      type oc-yang:counter64;
      description
        "MAC TX underrun errors count.";
    }
    leaf counter_slice9_ifg_mac_pool82_port_mib_counter7_tx_mac_underrun_err_cnt {
      type oc-yang:counter64;
      description
        "MAC TX underrun errors count.";
    }
    leaf counter_slice9_ifg_mac_pool83_port_mib_counter0_tx_mac_underrun_err_cnt {
      type oc-yang:counter64;
      description
        "MAC TX underrun errors count.";
    }
    leaf counter_slice9_ifg_mac_pool83_port_mib_counter1_tx_mac_underrun_err_cnt {
      type oc-yang:counter64;
      description
        "MAC TX underrun errors count.";
    }
    leaf counter_slice9_ifg_mac_pool83_port_mib_counter2_tx_mac_underrun_err_cnt {
      type oc-yang:counter64;
      description
        "MAC TX underrun errors count.";
    }
    leaf counter_slice9_ifg_mac_pool83_port_mib_counter3_tx_mac_underrun_err_cnt {
      type oc-yang:counter64;
      description
        "MAC TX underrun errors count.";
    }
    leaf counter_slice9_ifg_mac_pool83_port_mib_counter4_tx_mac_underrun_err_cnt {
      type oc-yang:counter64;
      description
        "MAC TX underrun errors count.";
    }
    leaf counter_slice9_ifg_mac_pool83_port_mib_counter5_tx_mac_underrun_err_cnt {
      type oc-yang:counter64;
      description
        "MAC TX underrun errors count.";
    }
    leaf counter_slice9_ifg_mac_pool83_port_mib_counter6_tx_mac_underrun_err_cnt {
      type oc-yang:counter64;
      description
        "MAC TX underrun errors count.";
    }
    leaf counter_slice9_ifg_mac_pool83_port_mib_counter7_tx_mac_underrun_err_cnt {
      type oc-yang:counter64;
      description
        "MAC TX underrun errors count.";
    }
    leaf counter_slice9_ifg_mac_pool84_port_mib_counter0_tx_mac_underrun_err_cnt {
      type oc-yang:counter64;
      description
        "MAC TX underrun errors count.";
    }
    leaf counter_slice9_ifg_mac_pool84_port_mib_counter1_tx_mac_underrun_err_cnt {
      type oc-yang:counter64;
      description
        "MAC TX underrun errors count.";
    }
    leaf counter_slice9_ifg_mac_pool84_port_mib_counter2_tx_mac_underrun_err_cnt {
      type oc-yang:counter64;
      description
        "MAC TX underrun errors count.";
    }
    leaf counter_slice9_ifg_mac_pool84_port_mib_counter3_tx_mac_underrun_err_cnt {
      type oc-yang:counter64;
      description
        "MAC TX underrun errors count.";
    }
    leaf counter_slice9_ifg_mac_pool84_port_mib_counter4_tx_mac_underrun_err_cnt {
      type oc-yang:counter64;
      description
        "MAC TX underrun errors count.";
    }
    leaf counter_slice9_ifg_mac_pool84_port_mib_counter5_tx_mac_underrun_err_cnt {
      type oc-yang:counter64;
      description
        "MAC TX underrun errors count.";
    }
    leaf counter_slice9_ifg_mac_pool84_port_mib_counter6_tx_mac_underrun_err_cnt {
      type oc-yang:counter64;
      description
        "MAC TX underrun errors count.";
    }
    leaf counter_slice9_ifg_mac_pool84_port_mib_counter7_tx_mac_underrun_err_cnt {
      type oc-yang:counter64;
      description
        "MAC TX underrun errors count.";
    }
    leaf counter_slice9_ifg_mac_pool85_port_mib_counter0_tx_mac_underrun_err_cnt {
      type oc-yang:counter64;
      description
        "MAC TX underrun errors count.";
    }
    leaf counter_slice9_ifg_mac_pool85_port_mib_counter1_tx_mac_underrun_err_cnt {
      type oc-yang:counter64;
      description
        "MAC TX underrun errors count.";
    }
    leaf counter_slice9_ifg_mac_pool85_port_mib_counter2_tx_mac_underrun_err_cnt {
      type oc-yang:counter64;
      description
        "MAC TX underrun errors count.";
    }
    leaf counter_slice9_ifg_mac_pool85_port_mib_counter3_tx_mac_underrun_err_cnt {
      type oc-yang:counter64;
      description
        "MAC TX underrun errors count.";
    }
    leaf counter_slice9_ifg_mac_pool85_port_mib_counter4_tx_mac_underrun_err_cnt {
      type oc-yang:counter64;
      description
        "MAC TX underrun errors count.";
    }
    leaf counter_slice9_ifg_mac_pool85_port_mib_counter5_tx_mac_underrun_err_cnt {
      type oc-yang:counter64;
      description
        "MAC TX underrun errors count.";
    }
    leaf counter_slice9_ifg_mac_pool85_port_mib_counter6_tx_mac_underrun_err_cnt {
      type oc-yang:counter64;
      description
        "MAC TX underrun errors count.";
    }
    leaf counter_slice9_ifg_mac_pool85_port_mib_counter7_tx_mac_underrun_err_cnt {
      type oc-yang:counter64;
      description
        "MAC TX underrun errors count.";
    }
    leaf counter_slice9_ifg_mac_pool86_port_mib_counter0_tx_mac_underrun_err_cnt {
      type oc-yang:counter64;
      description
        "MAC TX underrun errors count.";
    }
    leaf counter_slice9_ifg_mac_pool86_port_mib_counter1_tx_mac_underrun_err_cnt {
      type oc-yang:counter64;
      description
        "MAC TX underrun errors count.";
    }
    leaf counter_slice9_ifg_mac_pool86_port_mib_counter2_tx_mac_underrun_err_cnt {
      type oc-yang:counter64;
      description
        "MAC TX underrun errors count.";
    }
    leaf counter_slice9_ifg_mac_pool86_port_mib_counter3_tx_mac_underrun_err_cnt {
      type oc-yang:counter64;
      description
        "MAC TX underrun errors count.";
    }
    leaf counter_slice9_ifg_mac_pool86_port_mib_counter4_tx_mac_underrun_err_cnt {
      type oc-yang:counter64;
      description
        "MAC TX underrun errors count.";
    }
    leaf counter_slice9_ifg_mac_pool86_port_mib_counter5_tx_mac_underrun_err_cnt {
      type oc-yang:counter64;
      description
        "MAC TX underrun errors count.";
    }
    leaf counter_slice9_ifg_mac_pool86_port_mib_counter6_tx_mac_underrun_err_cnt {
      type oc-yang:counter64;
      description
        "MAC TX underrun errors count.";
    }
    leaf counter_slice9_ifg_mac_pool86_port_mib_counter7_tx_mac_underrun_err_cnt {
      type oc-yang:counter64;
      description
        "MAC TX underrun errors count.";
    }
    leaf counter_slice9_ifg_mac_pool87_port_mib_counter0_tx_mac_underrun_err_cnt {
      type oc-yang:counter64;
      description
        "MAC TX underrun errors count.";
    }
    leaf counter_slice9_ifg_mac_pool87_port_mib_counter1_tx_mac_underrun_err_cnt {
      type oc-yang:counter64;
      description
        "MAC TX underrun errors count.";
    }
    leaf counter_slice9_ifg_mac_pool87_port_mib_counter2_tx_mac_underrun_err_cnt {
      type oc-yang:counter64;
      description
        "MAC TX underrun errors count.";
    }
    leaf counter_slice9_ifg_mac_pool87_port_mib_counter3_tx_mac_underrun_err_cnt {
      type oc-yang:counter64;
      description
        "MAC TX underrun errors count.";
    }
    leaf counter_slice9_ifg_mac_pool87_port_mib_counter4_tx_mac_underrun_err_cnt {
      type oc-yang:counter64;
      description
        "MAC TX underrun errors count.";
    }
    leaf counter_slice9_ifg_mac_pool87_port_mib_counter5_tx_mac_underrun_err_cnt {
      type oc-yang:counter64;
      description
        "MAC TX underrun errors count.";
    }
    leaf counter_slice9_ifg_mac_pool87_port_mib_counter6_tx_mac_underrun_err_cnt {
      type oc-yang:counter64;
      description
        "MAC TX underrun errors count.";
    }
    leaf counter_slice9_ifg_mac_pool87_port_mib_counter7_tx_mac_underrun_err_cnt {
      type oc-yang:counter64;
      description
        "MAC TX underrun errors count.";
    }
    leaf counter_slice10_ifg_mac_pool80_port_mib_counter0_tx_mac_underrun_err_cnt {
      type oc-yang:counter64;
      description
        "MAC TX underrun errors count.";
    }
    leaf counter_slice10_ifg_mac_pool80_port_mib_counter1_tx_mac_underrun_err_cnt {
      type oc-yang:counter64;
      description
        "MAC TX underrun errors count.";
    }
    leaf counter_slice10_ifg_mac_pool80_port_mib_counter2_tx_mac_underrun_err_cnt {
      type oc-yang:counter64;
      description
        "MAC TX underrun errors count.";
    }
    leaf counter_slice10_ifg_mac_pool80_port_mib_counter3_tx_mac_underrun_err_cnt {
      type oc-yang:counter64;
      description
        "MAC TX underrun errors count.";
    }
    leaf counter_slice10_ifg_mac_pool80_port_mib_counter4_tx_mac_underrun_err_cnt {
      type oc-yang:counter64;
      description
        "MAC TX underrun errors count.";
    }
    leaf counter_slice10_ifg_mac_pool80_port_mib_counter5_tx_mac_underrun_err_cnt {
      type oc-yang:counter64;
      description
        "MAC TX underrun errors count.";
    }
    leaf counter_slice10_ifg_mac_pool80_port_mib_counter6_tx_mac_underrun_err_cnt {
      type oc-yang:counter64;
      description
        "MAC TX underrun errors count.";
    }
    leaf counter_slice10_ifg_mac_pool80_port_mib_counter7_tx_mac_underrun_err_cnt {
      type oc-yang:counter64;
      description
        "MAC TX underrun errors count.";
    }
    leaf counter_slice10_ifg_mac_pool81_port_mib_counter0_tx_mac_underrun_err_cnt {
      type oc-yang:counter64;
      description
        "MAC TX underrun errors count.";
    }
    leaf counter_slice10_ifg_mac_pool81_port_mib_counter1_tx_mac_underrun_err_cnt {
      type oc-yang:counter64;
      description
        "MAC TX underrun errors count.";
    }
    leaf counter_slice10_ifg_mac_pool81_port_mib_counter2_tx_mac_underrun_err_cnt {
      type oc-yang:counter64;
      description
        "MAC TX underrun errors count.";
    }
    leaf counter_slice10_ifg_mac_pool81_port_mib_counter3_tx_mac_underrun_err_cnt {
      type oc-yang:counter64;
      description
        "MAC TX underrun errors count.";
    }
    leaf counter_slice10_ifg_mac_pool81_port_mib_counter4_tx_mac_underrun_err_cnt {
      type oc-yang:counter64;
      description
        "MAC TX underrun errors count.";
    }
    leaf counter_slice10_ifg_mac_pool81_port_mib_counter5_tx_mac_underrun_err_cnt {
      type oc-yang:counter64;
      description
        "MAC TX underrun errors count.";
    }
    leaf counter_slice10_ifg_mac_pool81_port_mib_counter6_tx_mac_underrun_err_cnt {
      type oc-yang:counter64;
      description
        "MAC TX underrun errors count.";
    }
    leaf counter_slice10_ifg_mac_pool81_port_mib_counter7_tx_mac_underrun_err_cnt {
      type oc-yang:counter64;
      description
        "MAC TX underrun errors count.";
    }
    leaf counter_slice10_ifg_mac_pool82_port_mib_counter0_tx_mac_underrun_err_cnt {
      type oc-yang:counter64;
      description
        "MAC TX underrun errors count.";
    }
    leaf counter_slice10_ifg_mac_pool82_port_mib_counter1_tx_mac_underrun_err_cnt {
      type oc-yang:counter64;
      description
        "MAC TX underrun errors count.";
    }
    leaf counter_slice10_ifg_mac_pool82_port_mib_counter2_tx_mac_underrun_err_cnt {
      type oc-yang:counter64;
      description
        "MAC TX underrun errors count.";
    }
    leaf counter_slice10_ifg_mac_pool82_port_mib_counter3_tx_mac_underrun_err_cnt {
      type oc-yang:counter64;
      description
        "MAC TX underrun errors count.";
    }
    leaf counter_slice10_ifg_mac_pool82_port_mib_counter4_tx_mac_underrun_err_cnt {
      type oc-yang:counter64;
      description
        "MAC TX underrun errors count.";
    }
    leaf counter_slice10_ifg_mac_pool82_port_mib_counter5_tx_mac_underrun_err_cnt {
      type oc-yang:counter64;
      description
        "MAC TX underrun errors count.";
    }
    leaf counter_slice10_ifg_mac_pool82_port_mib_counter6_tx_mac_underrun_err_cnt {
      type oc-yang:counter64;
      description
        "MAC TX underrun errors count.";
    }
    leaf counter_slice10_ifg_mac_pool82_port_mib_counter7_tx_mac_underrun_err_cnt {
      type oc-yang:counter64;
      description
        "MAC TX underrun errors count.";
    }
    leaf counter_slice10_ifg_mac_pool83_port_mib_counter0_tx_mac_underrun_err_cnt {
      type oc-yang:counter64;
      description
        "MAC TX underrun errors count.";
    }
    leaf counter_slice10_ifg_mac_pool83_port_mib_counter1_tx_mac_underrun_err_cnt {
      type oc-yang:counter64;
      description
        "MAC TX underrun errors count.";
    }
    leaf counter_slice10_ifg_mac_pool83_port_mib_counter2_tx_mac_underrun_err_cnt {
      type oc-yang:counter64;
      description
        "MAC TX underrun errors count.";
    }
    leaf counter_slice10_ifg_mac_pool83_port_mib_counter3_tx_mac_underrun_err_cnt {
      type oc-yang:counter64;
      description
        "MAC TX underrun errors count.";
    }
    leaf counter_slice10_ifg_mac_pool83_port_mib_counter4_tx_mac_underrun_err_cnt {
      type oc-yang:counter64;
      description
        "MAC TX underrun errors count.";
    }
    leaf counter_slice10_ifg_mac_pool83_port_mib_counter5_tx_mac_underrun_err_cnt {
      type oc-yang:counter64;
      description
        "MAC TX underrun errors count.";
    }
    leaf counter_slice10_ifg_mac_pool83_port_mib_counter6_tx_mac_underrun_err_cnt {
      type oc-yang:counter64;
      description
        "MAC TX underrun errors count.";
    }
    leaf counter_slice10_ifg_mac_pool83_port_mib_counter7_tx_mac_underrun_err_cnt {
      type oc-yang:counter64;
      description
        "MAC TX underrun errors count.";
    }
    leaf counter_slice10_ifg_mac_pool84_port_mib_counter0_tx_mac_underrun_err_cnt {
      type oc-yang:counter64;
      description
        "MAC TX underrun errors count.";
    }
    leaf counter_slice10_ifg_mac_pool84_port_mib_counter1_tx_mac_underrun_err_cnt {
      type oc-yang:counter64;
      description
        "MAC TX underrun errors count.";
    }
    leaf counter_slice10_ifg_mac_pool84_port_mib_counter2_tx_mac_underrun_err_cnt {
      type oc-yang:counter64;
      description
        "MAC TX underrun errors count.";
    }
    leaf counter_slice10_ifg_mac_pool84_port_mib_counter3_tx_mac_underrun_err_cnt {
      type oc-yang:counter64;
      description
        "MAC TX underrun errors count.";
    }
    leaf counter_slice10_ifg_mac_pool84_port_mib_counter4_tx_mac_underrun_err_cnt {
      type oc-yang:counter64;
      description
        "MAC TX underrun errors count.";
    }
    leaf counter_slice10_ifg_mac_pool84_port_mib_counter5_tx_mac_underrun_err_cnt {
      type oc-yang:counter64;
      description
        "MAC TX underrun errors count.";
    }
    leaf counter_slice10_ifg_mac_pool84_port_mib_counter6_tx_mac_underrun_err_cnt {
      type oc-yang:counter64;
      description
        "MAC TX underrun errors count.";
    }
    leaf counter_slice10_ifg_mac_pool84_port_mib_counter7_tx_mac_underrun_err_cnt {
      type oc-yang:counter64;
      description
        "MAC TX underrun errors count.";
    }
    leaf counter_slice10_ifg_mac_pool85_port_mib_counter0_tx_mac_underrun_err_cnt {
      type oc-yang:counter64;
      description
        "MAC TX underrun errors count.";
    }
    leaf counter_slice10_ifg_mac_pool85_port_mib_counter1_tx_mac_underrun_err_cnt {
      type oc-yang:counter64;
      description
        "MAC TX underrun errors count.";
    }
    leaf counter_slice10_ifg_mac_pool85_port_mib_counter2_tx_mac_underrun_err_cnt {
      type oc-yang:counter64;
      description
        "MAC TX underrun errors count.";
    }
    leaf counter_slice10_ifg_mac_pool85_port_mib_counter3_tx_mac_underrun_err_cnt {
      type oc-yang:counter64;
      description
        "MAC TX underrun errors count.";
    }
    leaf counter_slice10_ifg_mac_pool85_port_mib_counter4_tx_mac_underrun_err_cnt {
      type oc-yang:counter64;
      description
        "MAC TX underrun errors count.";
    }
    leaf counter_slice10_ifg_mac_pool85_port_mib_counter5_tx_mac_underrun_err_cnt {
      type oc-yang:counter64;
      description
        "MAC TX underrun errors count.";
    }
    leaf counter_slice10_ifg_mac_pool85_port_mib_counter6_tx_mac_underrun_err_cnt {
      type oc-yang:counter64;
      description
        "MAC TX underrun errors count.";
    }
    leaf counter_slice10_ifg_mac_pool85_port_mib_counter7_tx_mac_underrun_err_cnt {
      type oc-yang:counter64;
      description
        "MAC TX underrun errors count.";
    }
    leaf counter_slice10_ifg_mac_pool86_port_mib_counter0_tx_mac_underrun_err_cnt {
      type oc-yang:counter64;
      description
        "MAC TX underrun errors count.";
    }
    leaf counter_slice10_ifg_mac_pool86_port_mib_counter1_tx_mac_underrun_err_cnt {
      type oc-yang:counter64;
      description
        "MAC TX underrun errors count.";
    }
    leaf counter_slice10_ifg_mac_pool86_port_mib_counter2_tx_mac_underrun_err_cnt {
      type oc-yang:counter64;
      description
        "MAC TX underrun errors count.";
    }
    leaf counter_slice10_ifg_mac_pool86_port_mib_counter3_tx_mac_underrun_err_cnt {
      type oc-yang:counter64;
      description
        "MAC TX underrun errors count.";
    }
    leaf counter_slice10_ifg_mac_pool86_port_mib_counter4_tx_mac_underrun_err_cnt {
      type oc-yang:counter64;
      description
        "MAC TX underrun errors count.";
    }
    leaf counter_slice10_ifg_mac_pool86_port_mib_counter5_tx_mac_underrun_err_cnt {
      type oc-yang:counter64;
      description
        "MAC TX underrun errors count.";
    }
    leaf counter_slice10_ifg_mac_pool86_port_mib_counter6_tx_mac_underrun_err_cnt {
      type oc-yang:counter64;
      description
        "MAC TX underrun errors count.";
    }
    leaf counter_slice10_ifg_mac_pool86_port_mib_counter7_tx_mac_underrun_err_cnt {
      type oc-yang:counter64;
      description
        "MAC TX underrun errors count.";
    }
    leaf counter_slice10_ifg_mac_pool87_port_mib_counter0_tx_mac_underrun_err_cnt {
      type oc-yang:counter64;
      description
        "MAC TX underrun errors count.";
    }
    leaf counter_slice10_ifg_mac_pool87_port_mib_counter1_tx_mac_underrun_err_cnt {
      type oc-yang:counter64;
      description
        "MAC TX underrun errors count.";
    }
    leaf counter_slice10_ifg_mac_pool87_port_mib_counter2_tx_mac_underrun_err_cnt {
      type oc-yang:counter64;
      description
        "MAC TX underrun errors count.";
    }
    leaf counter_slice10_ifg_mac_pool87_port_mib_counter3_tx_mac_underrun_err_cnt {
      type oc-yang:counter64;
      description
        "MAC TX underrun errors count.";
    }
    leaf counter_slice10_ifg_mac_pool87_port_mib_counter4_tx_mac_underrun_err_cnt {
      type oc-yang:counter64;
      description
        "MAC TX underrun errors count.";
    }
    leaf counter_slice10_ifg_mac_pool87_port_mib_counter5_tx_mac_underrun_err_cnt {
      type oc-yang:counter64;
      description
        "MAC TX underrun errors count.";
    }
    leaf counter_slice10_ifg_mac_pool87_port_mib_counter6_tx_mac_underrun_err_cnt {
      type oc-yang:counter64;
      description
        "MAC TX underrun errors count.";
    }
    leaf counter_slice10_ifg_mac_pool87_port_mib_counter7_tx_mac_underrun_err_cnt {
      type oc-yang:counter64;
      description
        "MAC TX underrun errors count.";
    }
    leaf counter_slice11_ifg_mac_pool80_port_mib_counter0_tx_mac_underrun_err_cnt {
      type oc-yang:counter64;
      description
        "MAC TX underrun errors count.";
    }
    leaf counter_slice11_ifg_mac_pool80_port_mib_counter1_tx_mac_underrun_err_cnt {
      type oc-yang:counter64;
      description
        "MAC TX underrun errors count.";
    }
    leaf counter_slice11_ifg_mac_pool80_port_mib_counter2_tx_mac_underrun_err_cnt {
      type oc-yang:counter64;
      description
        "MAC TX underrun errors count.";
    }
    leaf counter_slice11_ifg_mac_pool80_port_mib_counter3_tx_mac_underrun_err_cnt {
      type oc-yang:counter64;
      description
        "MAC TX underrun errors count.";
    }
    leaf counter_slice11_ifg_mac_pool80_port_mib_counter4_tx_mac_underrun_err_cnt {
      type oc-yang:counter64;
      description
        "MAC TX underrun errors count.";
    }
    leaf counter_slice11_ifg_mac_pool80_port_mib_counter5_tx_mac_underrun_err_cnt {
      type oc-yang:counter64;
      description
        "MAC TX underrun errors count.";
    }
    leaf counter_slice11_ifg_mac_pool80_port_mib_counter6_tx_mac_underrun_err_cnt {
      type oc-yang:counter64;
      description
        "MAC TX underrun errors count.";
    }
    leaf counter_slice11_ifg_mac_pool80_port_mib_counter7_tx_mac_underrun_err_cnt {
      type oc-yang:counter64;
      description
        "MAC TX underrun errors count.";
    }
    leaf counter_slice11_ifg_mac_pool81_port_mib_counter0_tx_mac_underrun_err_cnt {
      type oc-yang:counter64;
      description
        "MAC TX underrun errors count.";
    }
    leaf counter_slice11_ifg_mac_pool81_port_mib_counter1_tx_mac_underrun_err_cnt {
      type oc-yang:counter64;
      description
        "MAC TX underrun errors count.";
    }
    leaf counter_slice11_ifg_mac_pool81_port_mib_counter2_tx_mac_underrun_err_cnt {
      type oc-yang:counter64;
      description
        "MAC TX underrun errors count.";
    }
    leaf counter_slice11_ifg_mac_pool81_port_mib_counter3_tx_mac_underrun_err_cnt {
      type oc-yang:counter64;
      description
        "MAC TX underrun errors count.";
    }
    leaf counter_slice11_ifg_mac_pool81_port_mib_counter4_tx_mac_underrun_err_cnt {
      type oc-yang:counter64;
      description
        "MAC TX underrun errors count.";
    }
    leaf counter_slice11_ifg_mac_pool81_port_mib_counter5_tx_mac_underrun_err_cnt {
      type oc-yang:counter64;
      description
        "MAC TX underrun errors count.";
    }
    leaf counter_slice11_ifg_mac_pool81_port_mib_counter6_tx_mac_underrun_err_cnt {
      type oc-yang:counter64;
      description
        "MAC TX underrun errors count.";
    }
    leaf counter_slice11_ifg_mac_pool81_port_mib_counter7_tx_mac_underrun_err_cnt {
      type oc-yang:counter64;
      description
        "MAC TX underrun errors count.";
    }
    leaf counter_slice11_ifg_mac_pool82_port_mib_counter0_tx_mac_underrun_err_cnt {
      type oc-yang:counter64;
      description
        "MAC TX underrun errors count.";
    }
    leaf counter_slice11_ifg_mac_pool82_port_mib_counter1_tx_mac_underrun_err_cnt {
      type oc-yang:counter64;
      description
        "MAC TX underrun errors count.";
    }
    leaf counter_slice11_ifg_mac_pool82_port_mib_counter2_tx_mac_underrun_err_cnt {
      type oc-yang:counter64;
      description
        "MAC TX underrun errors count.";
    }
    leaf counter_slice11_ifg_mac_pool82_port_mib_counter3_tx_mac_underrun_err_cnt {
      type oc-yang:counter64;
      description
        "MAC TX underrun errors count.";
    }
    leaf counter_slice11_ifg_mac_pool82_port_mib_counter4_tx_mac_underrun_err_cnt {
      type oc-yang:counter64;
      description
        "MAC TX underrun errors count.";
    }
    leaf counter_slice11_ifg_mac_pool82_port_mib_counter5_tx_mac_underrun_err_cnt {
      type oc-yang:counter64;
      description
        "MAC TX underrun errors count.";
    }
    leaf counter_slice11_ifg_mac_pool82_port_mib_counter6_tx_mac_underrun_err_cnt {
      type oc-yang:counter64;
      description
        "MAC TX underrun errors count.";
    }
    leaf counter_slice11_ifg_mac_pool82_port_mib_counter7_tx_mac_underrun_err_cnt {
      type oc-yang:counter64;
      description
        "MAC TX underrun errors count.";
    }
    leaf counter_slice11_ifg_mac_pool83_port_mib_counter0_tx_mac_underrun_err_cnt {
      type oc-yang:counter64;
      description
        "MAC TX underrun errors count.";
    }
    leaf counter_slice11_ifg_mac_pool83_port_mib_counter1_tx_mac_underrun_err_cnt {
      type oc-yang:counter64;
      description
        "MAC TX underrun errors count.";
    }
    leaf counter_slice11_ifg_mac_pool83_port_mib_counter2_tx_mac_underrun_err_cnt {
      type oc-yang:counter64;
      description
        "MAC TX underrun errors count.";
    }
    leaf counter_slice11_ifg_mac_pool83_port_mib_counter3_tx_mac_underrun_err_cnt {
      type oc-yang:counter64;
      description
        "MAC TX underrun errors count.";
    }
    leaf counter_slice11_ifg_mac_pool83_port_mib_counter4_tx_mac_underrun_err_cnt {
      type oc-yang:counter64;
      description
        "MAC TX underrun errors count.";
    }
    leaf counter_slice11_ifg_mac_pool83_port_mib_counter5_tx_mac_underrun_err_cnt {
      type oc-yang:counter64;
      description
        "MAC TX underrun errors count.";
    }
    leaf counter_slice11_ifg_mac_pool83_port_mib_counter6_tx_mac_underrun_err_cnt {
      type oc-yang:counter64;
      description
        "MAC TX underrun errors count.";
    }
    leaf counter_slice11_ifg_mac_pool83_port_mib_counter7_tx_mac_underrun_err_cnt {
      type oc-yang:counter64;
      description
        "MAC TX underrun errors count.";
    }
    leaf counter_slice11_ifg_mac_pool84_port_mib_counter0_tx_mac_underrun_err_cnt {
      type oc-yang:counter64;
      description
        "MAC TX underrun errors count.";
    }
    leaf counter_slice11_ifg_mac_pool84_port_mib_counter1_tx_mac_underrun_err_cnt {
      type oc-yang:counter64;
      description
        "MAC TX underrun errors count.";
    }
    leaf counter_slice11_ifg_mac_pool84_port_mib_counter2_tx_mac_underrun_err_cnt {
      type oc-yang:counter64;
      description
        "MAC TX underrun errors count.";
    }
    leaf counter_slice11_ifg_mac_pool84_port_mib_counter3_tx_mac_underrun_err_cnt {
      type oc-yang:counter64;
      description
        "MAC TX underrun errors count.";
    }
    leaf counter_slice11_ifg_mac_pool84_port_mib_counter4_tx_mac_underrun_err_cnt {
      type oc-yang:counter64;
      description
        "MAC TX underrun errors count.";
    }
    leaf counter_slice11_ifg_mac_pool84_port_mib_counter5_tx_mac_underrun_err_cnt {
      type oc-yang:counter64;
      description
        "MAC TX underrun errors count.";
    }
    leaf counter_slice11_ifg_mac_pool84_port_mib_counter6_tx_mac_underrun_err_cnt {
      type oc-yang:counter64;
      description
        "MAC TX underrun errors count.";
    }
    leaf counter_slice11_ifg_mac_pool84_port_mib_counter7_tx_mac_underrun_err_cnt {
      type oc-yang:counter64;
      description
        "MAC TX underrun errors count.";
    }
    leaf counter_slice11_ifg_mac_pool85_port_mib_counter0_tx_mac_underrun_err_cnt {
      type oc-yang:counter64;
      description
        "MAC TX underrun errors count.";
    }
    leaf counter_slice11_ifg_mac_pool85_port_mib_counter1_tx_mac_underrun_err_cnt {
      type oc-yang:counter64;
      description
        "MAC TX underrun errors count.";
    }
    leaf counter_slice11_ifg_mac_pool85_port_mib_counter2_tx_mac_underrun_err_cnt {
      type oc-yang:counter64;
      description
        "MAC TX underrun errors count.";
    }
    leaf counter_slice11_ifg_mac_pool85_port_mib_counter3_tx_mac_underrun_err_cnt {
      type oc-yang:counter64;
      description
        "MAC TX underrun errors count.";
    }
    leaf counter_slice11_ifg_mac_pool85_port_mib_counter4_tx_mac_underrun_err_cnt {
      type oc-yang:counter64;
      description
        "MAC TX underrun errors count.";
    }
    leaf counter_slice11_ifg_mac_pool85_port_mib_counter5_tx_mac_underrun_err_cnt {
      type oc-yang:counter64;
      description
        "MAC TX underrun errors count.";
    }
    leaf counter_slice11_ifg_mac_pool85_port_mib_counter6_tx_mac_underrun_err_cnt {
      type oc-yang:counter64;
      description
        "MAC TX underrun errors count.";
    }
    leaf counter_slice11_ifg_mac_pool85_port_mib_counter7_tx_mac_underrun_err_cnt {
      type oc-yang:counter64;
      description
        "MAC TX underrun errors count.";
    }
    leaf counter_slice11_ifg_mac_pool86_port_mib_counter0_tx_mac_underrun_err_cnt {
      type oc-yang:counter64;
      description
        "MAC TX underrun errors count.";
    }
    leaf counter_slice11_ifg_mac_pool86_port_mib_counter1_tx_mac_underrun_err_cnt {
      type oc-yang:counter64;
      description
        "MAC TX underrun errors count.";
    }
    leaf counter_slice11_ifg_mac_pool86_port_mib_counter2_tx_mac_underrun_err_cnt {
      type oc-yang:counter64;
      description
        "MAC TX underrun errors count.";
    }
    leaf counter_slice11_ifg_mac_pool86_port_mib_counter3_tx_mac_underrun_err_cnt {
      type oc-yang:counter64;
      description
        "MAC TX underrun errors count.";
    }
    leaf counter_slice11_ifg_mac_pool86_port_mib_counter4_tx_mac_underrun_err_cnt {
      type oc-yang:counter64;
      description
        "MAC TX underrun errors count.";
    }
    leaf counter_slice11_ifg_mac_pool86_port_mib_counter5_tx_mac_underrun_err_cnt {
      type oc-yang:counter64;
      description
        "MAC TX underrun errors count.";
    }
    leaf counter_slice11_ifg_mac_pool86_port_mib_counter6_tx_mac_underrun_err_cnt {
      type oc-yang:counter64;
      description
        "MAC TX underrun errors count.";
    }
    leaf counter_slice11_ifg_mac_pool86_port_mib_counter7_tx_mac_underrun_err_cnt {
      type oc-yang:counter64;
      description
        "MAC TX underrun errors count.";
    }
    leaf counter_slice11_ifg_mac_pool87_port_mib_counter0_tx_mac_underrun_err_cnt {
      type oc-yang:counter64;
      description
        "MAC TX underrun errors count.";
    }
    leaf counter_slice11_ifg_mac_pool87_port_mib_counter1_tx_mac_underrun_err_cnt {
      type oc-yang:counter64;
      description
        "MAC TX underrun errors count.";
    }
    leaf counter_slice11_ifg_mac_pool87_port_mib_counter2_tx_mac_underrun_err_cnt {
      type oc-yang:counter64;
      description
        "MAC TX underrun errors count.";
    }
    leaf counter_slice11_ifg_mac_pool87_port_mib_counter3_tx_mac_underrun_err_cnt {
      type oc-yang:counter64;
      description
        "MAC TX underrun errors count.";
    }
    leaf counter_slice11_ifg_mac_pool87_port_mib_counter4_tx_mac_underrun_err_cnt {
      type oc-yang:counter64;
      description
        "MAC TX underrun errors count.";
    }
    leaf counter_slice11_ifg_mac_pool87_port_mib_counter5_tx_mac_underrun_err_cnt {
      type oc-yang:counter64;
      description
        "MAC TX underrun errors count.";
    }
    leaf counter_slice11_ifg_mac_pool87_port_mib_counter6_tx_mac_underrun_err_cnt {
      type oc-yang:counter64;
      description
        "MAC TX underrun errors count.";
    }
    leaf counter_slice11_ifg_mac_pool87_port_mib_counter7_tx_mac_underrun_err_cnt {
      type oc-yang:counter64;
      description
        "MAC TX underrun errors count.";
    }
    leaf counter_slice12_ifg_mac_pool80_port_mib_counter0_tx_mac_underrun_err_cnt {
      type oc-yang:counter64;
      description
        "MAC TX underrun errors count.";
    }
    leaf counter_slice12_ifg_mac_pool80_port_mib_counter1_tx_mac_underrun_err_cnt {
      type oc-yang:counter64;
      description
        "MAC TX underrun errors count.";
    }
    leaf counter_slice12_ifg_mac_pool80_port_mib_counter2_tx_mac_underrun_err_cnt {
      type oc-yang:counter64;
      description
        "MAC TX underrun errors count.";
    }
    leaf counter_slice12_ifg_mac_pool80_port_mib_counter3_tx_mac_underrun_err_cnt {
      type oc-yang:counter64;
      description
        "MAC TX underrun errors count.";
    }
    leaf counter_slice12_ifg_mac_pool80_port_mib_counter4_tx_mac_underrun_err_cnt {
      type oc-yang:counter64;
      description
        "MAC TX underrun errors count.";
    }
    leaf counter_slice12_ifg_mac_pool80_port_mib_counter5_tx_mac_underrun_err_cnt {
      type oc-yang:counter64;
      description
        "MAC TX underrun errors count.";
    }
    leaf counter_slice12_ifg_mac_pool80_port_mib_counter6_tx_mac_underrun_err_cnt {
      type oc-yang:counter64;
      description
        "MAC TX underrun errors count.";
    }
    leaf counter_slice12_ifg_mac_pool80_port_mib_counter7_tx_mac_underrun_err_cnt {
      type oc-yang:counter64;
      description
        "MAC TX underrun errors count.";
    }
    leaf counter_slice12_ifg_mac_pool81_port_mib_counter0_tx_mac_underrun_err_cnt {
      type oc-yang:counter64;
      description
        "MAC TX underrun errors count.";
    }
    leaf counter_slice12_ifg_mac_pool81_port_mib_counter1_tx_mac_underrun_err_cnt {
      type oc-yang:counter64;
      description
        "MAC TX underrun errors count.";
    }
    leaf counter_slice12_ifg_mac_pool81_port_mib_counter2_tx_mac_underrun_err_cnt {
      type oc-yang:counter64;
      description
        "MAC TX underrun errors count.";
    }
    leaf counter_slice12_ifg_mac_pool81_port_mib_counter3_tx_mac_underrun_err_cnt {
      type oc-yang:counter64;
      description
        "MAC TX underrun errors count.";
    }
    leaf counter_slice12_ifg_mac_pool81_port_mib_counter4_tx_mac_underrun_err_cnt {
      type oc-yang:counter64;
      description
        "MAC TX underrun errors count.";
    }
    leaf counter_slice12_ifg_mac_pool81_port_mib_counter5_tx_mac_underrun_err_cnt {
      type oc-yang:counter64;
      description
        "MAC TX underrun errors count.";
    }
    leaf counter_slice12_ifg_mac_pool81_port_mib_counter6_tx_mac_underrun_err_cnt {
      type oc-yang:counter64;
      description
        "MAC TX underrun errors count.";
    }
    leaf counter_slice12_ifg_mac_pool81_port_mib_counter7_tx_mac_underrun_err_cnt {
      type oc-yang:counter64;
      description
        "MAC TX underrun errors count.";
    }
    leaf counter_slice12_ifg_mac_pool82_port_mib_counter0_tx_mac_underrun_err_cnt {
      type oc-yang:counter64;
      description
        "MAC TX underrun errors count.";
    }
    leaf counter_slice12_ifg_mac_pool82_port_mib_counter1_tx_mac_underrun_err_cnt {
      type oc-yang:counter64;
      description
        "MAC TX underrun errors count.";
    }
    leaf counter_slice12_ifg_mac_pool82_port_mib_counter2_tx_mac_underrun_err_cnt {
      type oc-yang:counter64;
      description
        "MAC TX underrun errors count.";
    }
    leaf counter_slice12_ifg_mac_pool82_port_mib_counter3_tx_mac_underrun_err_cnt {
      type oc-yang:counter64;
      description
        "MAC TX underrun errors count.";
    }
    leaf counter_slice12_ifg_mac_pool82_port_mib_counter4_tx_mac_underrun_err_cnt {
      type oc-yang:counter64;
      description
        "MAC TX underrun errors count.";
    }
    leaf counter_slice12_ifg_mac_pool82_port_mib_counter5_tx_mac_underrun_err_cnt {
      type oc-yang:counter64;
      description
        "MAC TX underrun errors count.";
    }
    leaf counter_slice12_ifg_mac_pool82_port_mib_counter6_tx_mac_underrun_err_cnt {
      type oc-yang:counter64;
      description
        "MAC TX underrun errors count.";
    }
    leaf counter_slice12_ifg_mac_pool82_port_mib_counter7_tx_mac_underrun_err_cnt {
      type oc-yang:counter64;
      description
        "MAC TX underrun errors count.";
    }
    leaf counter_slice12_ifg_mac_pool83_port_mib_counter0_tx_mac_underrun_err_cnt {
      type oc-yang:counter64;
      description
        "MAC TX underrun errors count.";
    }
    leaf counter_slice12_ifg_mac_pool83_port_mib_counter1_tx_mac_underrun_err_cnt {
      type oc-yang:counter64;
      description
        "MAC TX underrun errors count.";
    }
    leaf counter_slice12_ifg_mac_pool83_port_mib_counter2_tx_mac_underrun_err_cnt {
      type oc-yang:counter64;
      description
        "MAC TX underrun errors count.";
    }
    leaf counter_slice12_ifg_mac_pool83_port_mib_counter3_tx_mac_underrun_err_cnt {
      type oc-yang:counter64;
      description
        "MAC TX underrun errors count.";
    }
    leaf counter_slice12_ifg_mac_pool83_port_mib_counter4_tx_mac_underrun_err_cnt {
      type oc-yang:counter64;
      description
        "MAC TX underrun errors count.";
    }
    leaf counter_slice12_ifg_mac_pool83_port_mib_counter5_tx_mac_underrun_err_cnt {
      type oc-yang:counter64;
      description
        "MAC TX underrun errors count.";
    }
    leaf counter_slice12_ifg_mac_pool83_port_mib_counter6_tx_mac_underrun_err_cnt {
      type oc-yang:counter64;
      description
        "MAC TX underrun errors count.";
    }
    leaf counter_slice12_ifg_mac_pool83_port_mib_counter7_tx_mac_underrun_err_cnt {
      type oc-yang:counter64;
      description
        "MAC TX underrun errors count.";
    }
    leaf counter_slice12_ifg_mac_pool84_port_mib_counter0_tx_mac_underrun_err_cnt {
      type oc-yang:counter64;
      description
        "MAC TX underrun errors count.";
    }
    leaf counter_slice12_ifg_mac_pool84_port_mib_counter1_tx_mac_underrun_err_cnt {
      type oc-yang:counter64;
      description
        "MAC TX underrun errors count.";
    }
    leaf counter_slice12_ifg_mac_pool84_port_mib_counter2_tx_mac_underrun_err_cnt {
      type oc-yang:counter64;
      description
        "MAC TX underrun errors count.";
    }
    leaf counter_slice12_ifg_mac_pool84_port_mib_counter3_tx_mac_underrun_err_cnt {
      type oc-yang:counter64;
      description
        "MAC TX underrun errors count.";
    }
    leaf counter_slice12_ifg_mac_pool84_port_mib_counter4_tx_mac_underrun_err_cnt {
      type oc-yang:counter64;
      description
        "MAC TX underrun errors count.";
    }
    leaf counter_slice12_ifg_mac_pool84_port_mib_counter5_tx_mac_underrun_err_cnt {
      type oc-yang:counter64;
      description
        "MAC TX underrun errors count.";
    }
    leaf counter_slice12_ifg_mac_pool84_port_mib_counter6_tx_mac_underrun_err_cnt {
      type oc-yang:counter64;
      description
        "MAC TX underrun errors count.";
    }
    leaf counter_slice12_ifg_mac_pool84_port_mib_counter7_tx_mac_underrun_err_cnt {
      type oc-yang:counter64;
      description
        "MAC TX underrun errors count.";
    }
    leaf counter_slice12_ifg_mac_pool85_port_mib_counter0_tx_mac_underrun_err_cnt {
      type oc-yang:counter64;
      description
        "MAC TX underrun errors count.";
    }
    leaf counter_slice12_ifg_mac_pool85_port_mib_counter1_tx_mac_underrun_err_cnt {
      type oc-yang:counter64;
      description
        "MAC TX underrun errors count.";
    }
    leaf counter_slice12_ifg_mac_pool85_port_mib_counter2_tx_mac_underrun_err_cnt {
      type oc-yang:counter64;
      description
        "MAC TX underrun errors count.";
    }
    leaf counter_slice12_ifg_mac_pool85_port_mib_counter3_tx_mac_underrun_err_cnt {
      type oc-yang:counter64;
      description
        "MAC TX underrun errors count.";
    }
    leaf counter_slice12_ifg_mac_pool85_port_mib_counter4_tx_mac_underrun_err_cnt {
      type oc-yang:counter64;
      description
        "MAC TX underrun errors count.";
    }
    leaf counter_slice12_ifg_mac_pool85_port_mib_counter5_tx_mac_underrun_err_cnt {
      type oc-yang:counter64;
      description
        "MAC TX underrun errors count.";
    }
    leaf counter_slice12_ifg_mac_pool85_port_mib_counter6_tx_mac_underrun_err_cnt {
      type oc-yang:counter64;
      description
        "MAC TX underrun errors count.";
    }
    leaf counter_slice12_ifg_mac_pool85_port_mib_counter7_tx_mac_underrun_err_cnt {
      type oc-yang:counter64;
      description
        "MAC TX underrun errors count.";
    }
    leaf counter_slice12_ifg_mac_pool86_port_mib_counter0_tx_mac_underrun_err_cnt {
      type oc-yang:counter64;
      description
        "MAC TX underrun errors count.";
    }
    leaf counter_slice12_ifg_mac_pool86_port_mib_counter1_tx_mac_underrun_err_cnt {
      type oc-yang:counter64;
      description
        "MAC TX underrun errors count.";
    }
    leaf counter_slice12_ifg_mac_pool86_port_mib_counter2_tx_mac_underrun_err_cnt {
      type oc-yang:counter64;
      description
        "MAC TX underrun errors count.";
    }
    leaf counter_slice12_ifg_mac_pool86_port_mib_counter3_tx_mac_underrun_err_cnt {
      type oc-yang:counter64;
      description
        "MAC TX underrun errors count.";
    }
    leaf counter_slice12_ifg_mac_pool86_port_mib_counter4_tx_mac_underrun_err_cnt {
      type oc-yang:counter64;
      description
        "MAC TX underrun errors count.";
    }
    leaf counter_slice12_ifg_mac_pool86_port_mib_counter5_tx_mac_underrun_err_cnt {
      type oc-yang:counter64;
      description
        "MAC TX underrun errors count.";
    }
    leaf counter_slice12_ifg_mac_pool86_port_mib_counter6_tx_mac_underrun_err_cnt {
      type oc-yang:counter64;
      description
        "MAC TX underrun errors count.";
    }
    leaf counter_slice12_ifg_mac_pool86_port_mib_counter7_tx_mac_underrun_err_cnt {
      type oc-yang:counter64;
      description
        "MAC TX underrun errors count.";
    }
    leaf counter_slice12_ifg_mac_pool87_port_mib_counter0_tx_mac_underrun_err_cnt {
      type oc-yang:counter64;
      description
        "MAC TX underrun errors count.";
    }
    leaf counter_slice12_ifg_mac_pool87_port_mib_counter1_tx_mac_underrun_err_cnt {
      type oc-yang:counter64;
      description
        "MAC TX underrun errors count.";
    }
    leaf counter_slice12_ifg_mac_pool87_port_mib_counter2_tx_mac_underrun_err_cnt {
      type oc-yang:counter64;
      description
        "MAC TX underrun errors count.";
    }
    leaf counter_slice12_ifg_mac_pool87_port_mib_counter3_tx_mac_underrun_err_cnt {
      type oc-yang:counter64;
      description
        "MAC TX underrun errors count.";
    }
    leaf counter_slice12_ifg_mac_pool87_port_mib_counter4_tx_mac_underrun_err_cnt {
      type oc-yang:counter64;
      description
        "MAC TX underrun errors count.";
    }
    leaf counter_slice12_ifg_mac_pool87_port_mib_counter5_tx_mac_underrun_err_cnt {
      type oc-yang:counter64;
      description
        "MAC TX underrun errors count.";
    }
    leaf counter_slice12_ifg_mac_pool87_port_mib_counter6_tx_mac_underrun_err_cnt {
      type oc-yang:counter64;
      description
        "MAC TX underrun errors count.";
    }
    leaf counter_slice12_ifg_mac_pool87_port_mib_counter7_tx_mac_underrun_err_cnt {
      type oc-yang:counter64;
      description
        "MAC TX underrun errors count.";
    }
    leaf counter_slice13_ifg_mac_pool80_port_mib_counter0_tx_mac_underrun_err_cnt {
      type oc-yang:counter64;
      description
        "MAC TX underrun errors count.";
    }
    leaf counter_slice13_ifg_mac_pool80_port_mib_counter1_tx_mac_underrun_err_cnt {
      type oc-yang:counter64;
      description
        "MAC TX underrun errors count.";
    }
    leaf counter_slice13_ifg_mac_pool80_port_mib_counter2_tx_mac_underrun_err_cnt {
      type oc-yang:counter64;
      description
        "MAC TX underrun errors count.";
    }
    leaf counter_slice13_ifg_mac_pool80_port_mib_counter3_tx_mac_underrun_err_cnt {
      type oc-yang:counter64;
      description
        "MAC TX underrun errors count.";
    }
    leaf counter_slice13_ifg_mac_pool80_port_mib_counter4_tx_mac_underrun_err_cnt {
      type oc-yang:counter64;
      description
        "MAC TX underrun errors count.";
    }
    leaf counter_slice13_ifg_mac_pool80_port_mib_counter5_tx_mac_underrun_err_cnt {
      type oc-yang:counter64;
      description
        "MAC TX underrun errors count.";
    }
    leaf counter_slice13_ifg_mac_pool80_port_mib_counter6_tx_mac_underrun_err_cnt {
      type oc-yang:counter64;
      description
        "MAC TX underrun errors count.";
    }
    leaf counter_slice13_ifg_mac_pool80_port_mib_counter7_tx_mac_underrun_err_cnt {
      type oc-yang:counter64;
      description
        "MAC TX underrun errors count.";
    }
    leaf counter_slice13_ifg_mac_pool81_port_mib_counter0_tx_mac_underrun_err_cnt {
      type oc-yang:counter64;
      description
        "MAC TX underrun errors count.";
    }
    leaf counter_slice13_ifg_mac_pool81_port_mib_counter1_tx_mac_underrun_err_cnt {
      type oc-yang:counter64;
      description
        "MAC TX underrun errors count.";
    }
    leaf counter_slice13_ifg_mac_pool81_port_mib_counter2_tx_mac_underrun_err_cnt {
      type oc-yang:counter64;
      description
        "MAC TX underrun errors count.";
    }
    leaf counter_slice13_ifg_mac_pool81_port_mib_counter3_tx_mac_underrun_err_cnt {
      type oc-yang:counter64;
      description
        "MAC TX underrun errors count.";
    }
    leaf counter_slice13_ifg_mac_pool81_port_mib_counter4_tx_mac_underrun_err_cnt {
      type oc-yang:counter64;
      description
        "MAC TX underrun errors count.";
    }
    leaf counter_slice13_ifg_mac_pool81_port_mib_counter5_tx_mac_underrun_err_cnt {
      type oc-yang:counter64;
      description
        "MAC TX underrun errors count.";
    }
    leaf counter_slice13_ifg_mac_pool81_port_mib_counter6_tx_mac_underrun_err_cnt {
      type oc-yang:counter64;
      description
        "MAC TX underrun errors count.";
    }
    leaf counter_slice13_ifg_mac_pool81_port_mib_counter7_tx_mac_underrun_err_cnt {
      type oc-yang:counter64;
      description
        "MAC TX underrun errors count.";
    }
    leaf counter_slice13_ifg_mac_pool82_port_mib_counter0_tx_mac_underrun_err_cnt {
      type oc-yang:counter64;
      description
        "MAC TX underrun errors count.";
    }
    leaf counter_slice13_ifg_mac_pool82_port_mib_counter1_tx_mac_underrun_err_cnt {
      type oc-yang:counter64;
      description
        "MAC TX underrun errors count.";
    }
    leaf counter_slice13_ifg_mac_pool82_port_mib_counter2_tx_mac_underrun_err_cnt {
      type oc-yang:counter64;
      description
        "MAC TX underrun errors count.";
    }
    leaf counter_slice13_ifg_mac_pool82_port_mib_counter3_tx_mac_underrun_err_cnt {
      type oc-yang:counter64;
      description
        "MAC TX underrun errors count.";
    }
    leaf counter_slice13_ifg_mac_pool82_port_mib_counter4_tx_mac_underrun_err_cnt {
      type oc-yang:counter64;
      description
        "MAC TX underrun errors count.";
    }
    leaf counter_slice13_ifg_mac_pool82_port_mib_counter5_tx_mac_underrun_err_cnt {
      type oc-yang:counter64;
      description
        "MAC TX underrun errors count.";
    }
    leaf counter_slice13_ifg_mac_pool82_port_mib_counter6_tx_mac_underrun_err_cnt {
      type oc-yang:counter64;
      description
        "MAC TX underrun errors count.";
    }
    leaf counter_slice13_ifg_mac_pool82_port_mib_counter7_tx_mac_underrun_err_cnt {
      type oc-yang:counter64;
      description
        "MAC TX underrun errors count.";
    }
    leaf counter_slice13_ifg_mac_pool83_port_mib_counter0_tx_mac_underrun_err_cnt {
      type oc-yang:counter64;
      description
        "MAC TX underrun errors count.";
    }
    leaf counter_slice13_ifg_mac_pool83_port_mib_counter1_tx_mac_underrun_err_cnt {
      type oc-yang:counter64;
      description
        "MAC TX underrun errors count.";
    }
    leaf counter_slice13_ifg_mac_pool83_port_mib_counter2_tx_mac_underrun_err_cnt {
      type oc-yang:counter64;
      description
        "MAC TX underrun errors count.";
    }
    leaf counter_slice13_ifg_mac_pool83_port_mib_counter3_tx_mac_underrun_err_cnt {
      type oc-yang:counter64;
      description
        "MAC TX underrun errors count.";
    }
    leaf counter_slice13_ifg_mac_pool83_port_mib_counter4_tx_mac_underrun_err_cnt {
      type oc-yang:counter64;
      description
        "MAC TX underrun errors count.";
    }
    leaf counter_slice13_ifg_mac_pool83_port_mib_counter5_tx_mac_underrun_err_cnt {
      type oc-yang:counter64;
      description
        "MAC TX underrun errors count.";
    }
    leaf counter_slice13_ifg_mac_pool83_port_mib_counter6_tx_mac_underrun_err_cnt {
      type oc-yang:counter64;
      description
        "MAC TX underrun errors count.";
    }
    leaf counter_slice13_ifg_mac_pool83_port_mib_counter7_tx_mac_underrun_err_cnt {
      type oc-yang:counter64;
      description
        "MAC TX underrun errors count.";
    }
    leaf counter_slice13_ifg_mac_pool84_port_mib_counter0_tx_mac_underrun_err_cnt {
      type oc-yang:counter64;
      description
        "MAC TX underrun errors count.";
    }
    leaf counter_slice13_ifg_mac_pool84_port_mib_counter1_tx_mac_underrun_err_cnt {
      type oc-yang:counter64;
      description
        "MAC TX underrun errors count.";
    }
    leaf counter_slice13_ifg_mac_pool84_port_mib_counter2_tx_mac_underrun_err_cnt {
      type oc-yang:counter64;
      description
        "MAC TX underrun errors count.";
    }
    leaf counter_slice13_ifg_mac_pool84_port_mib_counter3_tx_mac_underrun_err_cnt {
      type oc-yang:counter64;
      description
        "MAC TX underrun errors count.";
    }
    leaf counter_slice13_ifg_mac_pool84_port_mib_counter4_tx_mac_underrun_err_cnt {
      type oc-yang:counter64;
      description
        "MAC TX underrun errors count.";
    }
    leaf counter_slice13_ifg_mac_pool84_port_mib_counter5_tx_mac_underrun_err_cnt {
      type oc-yang:counter64;
      description
        "MAC TX underrun errors count.";
    }
    leaf counter_slice13_ifg_mac_pool84_port_mib_counter6_tx_mac_underrun_err_cnt {
      type oc-yang:counter64;
      description
        "MAC TX underrun errors count.";
    }
    leaf counter_slice13_ifg_mac_pool84_port_mib_counter7_tx_mac_underrun_err_cnt {
      type oc-yang:counter64;
      description
        "MAC TX underrun errors count.";
    }
    leaf counter_slice13_ifg_mac_pool85_port_mib_counter0_tx_mac_underrun_err_cnt {
      type oc-yang:counter64;
      description
        "MAC TX underrun errors count.";
    }
    leaf counter_slice13_ifg_mac_pool85_port_mib_counter1_tx_mac_underrun_err_cnt {
      type oc-yang:counter64;
      description
        "MAC TX underrun errors count.";
    }
    leaf counter_slice13_ifg_mac_pool85_port_mib_counter2_tx_mac_underrun_err_cnt {
      type oc-yang:counter64;
      description
        "MAC TX underrun errors count.";
    }
    leaf counter_slice13_ifg_mac_pool85_port_mib_counter3_tx_mac_underrun_err_cnt {
      type oc-yang:counter64;
      description
        "MAC TX underrun errors count.";
    }
    leaf counter_slice13_ifg_mac_pool85_port_mib_counter4_tx_mac_underrun_err_cnt {
      type oc-yang:counter64;
      description
        "MAC TX underrun errors count.";
    }
    leaf counter_slice13_ifg_mac_pool85_port_mib_counter5_tx_mac_underrun_err_cnt {
      type oc-yang:counter64;
      description
        "MAC TX underrun errors count.";
    }
    leaf counter_slice13_ifg_mac_pool85_port_mib_counter6_tx_mac_underrun_err_cnt {
      type oc-yang:counter64;
      description
        "MAC TX underrun errors count.";
    }
    leaf counter_slice13_ifg_mac_pool85_port_mib_counter7_tx_mac_underrun_err_cnt {
      type oc-yang:counter64;
      description
        "MAC TX underrun errors count.";
    }
    leaf counter_slice13_ifg_mac_pool86_port_mib_counter0_tx_mac_underrun_err_cnt {
      type oc-yang:counter64;
      description
        "MAC TX underrun errors count.";
    }
    leaf counter_slice13_ifg_mac_pool86_port_mib_counter1_tx_mac_underrun_err_cnt {
      type oc-yang:counter64;
      description
        "MAC TX underrun errors count.";
    }
    leaf counter_slice13_ifg_mac_pool86_port_mib_counter2_tx_mac_underrun_err_cnt {
      type oc-yang:counter64;
      description
        "MAC TX underrun errors count.";
    }
    leaf counter_slice13_ifg_mac_pool86_port_mib_counter3_tx_mac_underrun_err_cnt {
      type oc-yang:counter64;
      description
        "MAC TX underrun errors count.";
    }
    leaf counter_slice13_ifg_mac_pool86_port_mib_counter4_tx_mac_underrun_err_cnt {
      type oc-yang:counter64;
      description
        "MAC TX underrun errors count.";
    }
    leaf counter_slice13_ifg_mac_pool86_port_mib_counter5_tx_mac_underrun_err_cnt {
      type oc-yang:counter64;
      description
        "MAC TX underrun errors count.";
    }
    leaf counter_slice13_ifg_mac_pool86_port_mib_counter6_tx_mac_underrun_err_cnt {
      type oc-yang:counter64;
      description
        "MAC TX underrun errors count.";
    }
    leaf counter_slice13_ifg_mac_pool86_port_mib_counter7_tx_mac_underrun_err_cnt {
      type oc-yang:counter64;
      description
        "MAC TX underrun errors count.";
    }
    leaf counter_slice13_ifg_mac_pool87_port_mib_counter0_tx_mac_underrun_err_cnt {
      type oc-yang:counter64;
      description
        "MAC TX underrun errors count.";
    }
    leaf counter_slice13_ifg_mac_pool87_port_mib_counter1_tx_mac_underrun_err_cnt {
      type oc-yang:counter64;
      description
        "MAC TX underrun errors count.";
    }
    leaf counter_slice13_ifg_mac_pool87_port_mib_counter2_tx_mac_underrun_err_cnt {
      type oc-yang:counter64;
      description
        "MAC TX underrun errors count.";
    }
    leaf counter_slice13_ifg_mac_pool87_port_mib_counter3_tx_mac_underrun_err_cnt {
      type oc-yang:counter64;
      description
        "MAC TX underrun errors count.";
    }
    leaf counter_slice13_ifg_mac_pool87_port_mib_counter4_tx_mac_underrun_err_cnt {
      type oc-yang:counter64;
      description
        "MAC TX underrun errors count.";
    }
    leaf counter_slice13_ifg_mac_pool87_port_mib_counter5_tx_mac_underrun_err_cnt {
      type oc-yang:counter64;
      description
        "MAC TX underrun errors count.";
    }
    leaf counter_slice13_ifg_mac_pool87_port_mib_counter6_tx_mac_underrun_err_cnt {
      type oc-yang:counter64;
      description
        "MAC TX underrun errors count.";
    }
    leaf counter_slice13_ifg_mac_pool87_port_mib_counter7_tx_mac_underrun_err_cnt {
      type oc-yang:counter64;
      description
        "MAC TX underrun errors count.";
    }
    leaf counter_slice14_ifg_mac_pool80_port_mib_counter0_tx_mac_underrun_err_cnt {
      type oc-yang:counter64;
      description
        "MAC TX underrun errors count.";
    }
    leaf counter_slice14_ifg_mac_pool80_port_mib_counter1_tx_mac_underrun_err_cnt {
      type oc-yang:counter64;
      description
        "MAC TX underrun errors count.";
    }
    leaf counter_slice14_ifg_mac_pool80_port_mib_counter2_tx_mac_underrun_err_cnt {
      type oc-yang:counter64;
      description
        "MAC TX underrun errors count.";
    }
    leaf counter_slice14_ifg_mac_pool80_port_mib_counter3_tx_mac_underrun_err_cnt {
      type oc-yang:counter64;
      description
        "MAC TX underrun errors count.";
    }
    leaf counter_slice14_ifg_mac_pool80_port_mib_counter4_tx_mac_underrun_err_cnt {
      type oc-yang:counter64;
      description
        "MAC TX underrun errors count.";
    }
    leaf counter_slice14_ifg_mac_pool80_port_mib_counter5_tx_mac_underrun_err_cnt {
      type oc-yang:counter64;
      description
        "MAC TX underrun errors count.";
    }
    leaf counter_slice14_ifg_mac_pool80_port_mib_counter6_tx_mac_underrun_err_cnt {
      type oc-yang:counter64;
      description
        "MAC TX underrun errors count.";
    }
    leaf counter_slice14_ifg_mac_pool80_port_mib_counter7_tx_mac_underrun_err_cnt {
      type oc-yang:counter64;
      description
        "MAC TX underrun errors count.";
    }
    leaf counter_slice14_ifg_mac_pool81_port_mib_counter0_tx_mac_underrun_err_cnt {
      type oc-yang:counter64;
      description
        "MAC TX underrun errors count.";
    }
    leaf counter_slice14_ifg_mac_pool81_port_mib_counter1_tx_mac_underrun_err_cnt {
      type oc-yang:counter64;
      description
        "MAC TX underrun errors count.";
    }
    leaf counter_slice14_ifg_mac_pool81_port_mib_counter2_tx_mac_underrun_err_cnt {
      type oc-yang:counter64;
      description
        "MAC TX underrun errors count.";
    }
    leaf counter_slice14_ifg_mac_pool81_port_mib_counter3_tx_mac_underrun_err_cnt {
      type oc-yang:counter64;
      description
        "MAC TX underrun errors count.";
    }
    leaf counter_slice14_ifg_mac_pool81_port_mib_counter4_tx_mac_underrun_err_cnt {
      type oc-yang:counter64;
      description
        "MAC TX underrun errors count.";
    }
    leaf counter_slice14_ifg_mac_pool81_port_mib_counter5_tx_mac_underrun_err_cnt {
      type oc-yang:counter64;
      description
        "MAC TX underrun errors count.";
    }
    leaf counter_slice14_ifg_mac_pool81_port_mib_counter6_tx_mac_underrun_err_cnt {
      type oc-yang:counter64;
      description
        "MAC TX underrun errors count.";
    }
    leaf counter_slice14_ifg_mac_pool81_port_mib_counter7_tx_mac_underrun_err_cnt {
      type oc-yang:counter64;
      description
        "MAC TX underrun errors count.";
    }
    leaf counter_slice14_ifg_mac_pool82_port_mib_counter0_tx_mac_underrun_err_cnt {
      type oc-yang:counter64;
      description
        "MAC TX underrun errors count.";
    }
    leaf counter_slice14_ifg_mac_pool82_port_mib_counter1_tx_mac_underrun_err_cnt {
      type oc-yang:counter64;
      description
        "MAC TX underrun errors count.";
    }
    leaf counter_slice14_ifg_mac_pool82_port_mib_counter2_tx_mac_underrun_err_cnt {
      type oc-yang:counter64;
      description
        "MAC TX underrun errors count.";
    }
    leaf counter_slice14_ifg_mac_pool82_port_mib_counter3_tx_mac_underrun_err_cnt {
      type oc-yang:counter64;
      description
        "MAC TX underrun errors count.";
    }
    leaf counter_slice14_ifg_mac_pool82_port_mib_counter4_tx_mac_underrun_err_cnt {
      type oc-yang:counter64;
      description
        "MAC TX underrun errors count.";
    }
    leaf counter_slice14_ifg_mac_pool82_port_mib_counter5_tx_mac_underrun_err_cnt {
      type oc-yang:counter64;
      description
        "MAC TX underrun errors count.";
    }
    leaf counter_slice14_ifg_mac_pool82_port_mib_counter6_tx_mac_underrun_err_cnt {
      type oc-yang:counter64;
      description
        "MAC TX underrun errors count.";
    }
    leaf counter_slice14_ifg_mac_pool82_port_mib_counter7_tx_mac_underrun_err_cnt {
      type oc-yang:counter64;
      description
        "MAC TX underrun errors count.";
    }
    leaf counter_slice14_ifg_mac_pool83_port_mib_counter0_tx_mac_underrun_err_cnt {
      type oc-yang:counter64;
      description
        "MAC TX underrun errors count.";
    }
    leaf counter_slice14_ifg_mac_pool83_port_mib_counter1_tx_mac_underrun_err_cnt {
      type oc-yang:counter64;
      description
        "MAC TX underrun errors count.";
    }
    leaf counter_slice14_ifg_mac_pool83_port_mib_counter2_tx_mac_underrun_err_cnt {
      type oc-yang:counter64;
      description
        "MAC TX underrun errors count.";
    }
    leaf counter_slice14_ifg_mac_pool83_port_mib_counter3_tx_mac_underrun_err_cnt {
      type oc-yang:counter64;
      description
        "MAC TX underrun errors count.";
    }
    leaf counter_slice14_ifg_mac_pool83_port_mib_counter4_tx_mac_underrun_err_cnt {
      type oc-yang:counter64;
      description
        "MAC TX underrun errors count.";
    }
    leaf counter_slice14_ifg_mac_pool83_port_mib_counter5_tx_mac_underrun_err_cnt {
      type oc-yang:counter64;
      description
        "MAC TX underrun errors count.";
    }
    leaf counter_slice14_ifg_mac_pool83_port_mib_counter6_tx_mac_underrun_err_cnt {
      type oc-yang:counter64;
      description
        "MAC TX underrun errors count.";
    }
    leaf counter_slice14_ifg_mac_pool83_port_mib_counter7_tx_mac_underrun_err_cnt {
      type oc-yang:counter64;
      description
        "MAC TX underrun errors count.";
    }
    leaf counter_slice14_ifg_mac_pool84_port_mib_counter0_tx_mac_underrun_err_cnt {
      type oc-yang:counter64;
      description
        "MAC TX underrun errors count.";
    }
    leaf counter_slice14_ifg_mac_pool84_port_mib_counter1_tx_mac_underrun_err_cnt {
      type oc-yang:counter64;
      description
        "MAC TX underrun errors count.";
    }
    leaf counter_slice14_ifg_mac_pool84_port_mib_counter2_tx_mac_underrun_err_cnt {
      type oc-yang:counter64;
      description
        "MAC TX underrun errors count.";
    }
    leaf counter_slice14_ifg_mac_pool84_port_mib_counter3_tx_mac_underrun_err_cnt {
      type oc-yang:counter64;
      description
        "MAC TX underrun errors count.";
    }
    leaf counter_slice14_ifg_mac_pool84_port_mib_counter4_tx_mac_underrun_err_cnt {
      type oc-yang:counter64;
      description
        "MAC TX underrun errors count.";
    }
    leaf counter_slice14_ifg_mac_pool84_port_mib_counter5_tx_mac_underrun_err_cnt {
      type oc-yang:counter64;
      description
        "MAC TX underrun errors count.";
    }
    leaf counter_slice14_ifg_mac_pool84_port_mib_counter6_tx_mac_underrun_err_cnt {
      type oc-yang:counter64;
      description
        "MAC TX underrun errors count.";
    }
    leaf counter_slice14_ifg_mac_pool84_port_mib_counter7_tx_mac_underrun_err_cnt {
      type oc-yang:counter64;
      description
        "MAC TX underrun errors count.";
    }
    leaf counter_slice14_ifg_mac_pool85_port_mib_counter0_tx_mac_underrun_err_cnt {
      type oc-yang:counter64;
      description
        "MAC TX underrun errors count.";
    }
    leaf counter_slice14_ifg_mac_pool85_port_mib_counter1_tx_mac_underrun_err_cnt {
      type oc-yang:counter64;
      description
        "MAC TX underrun errors count.";
    }
    leaf counter_slice14_ifg_mac_pool85_port_mib_counter2_tx_mac_underrun_err_cnt {
      type oc-yang:counter64;
      description
        "MAC TX underrun errors count.";
    }
    leaf counter_slice14_ifg_mac_pool85_port_mib_counter3_tx_mac_underrun_err_cnt {
      type oc-yang:counter64;
      description
        "MAC TX underrun errors count.";
    }
    leaf counter_slice14_ifg_mac_pool85_port_mib_counter4_tx_mac_underrun_err_cnt {
      type oc-yang:counter64;
      description
        "MAC TX underrun errors count.";
    }
    leaf counter_slice14_ifg_mac_pool85_port_mib_counter5_tx_mac_underrun_err_cnt {
      type oc-yang:counter64;
      description
        "MAC TX underrun errors count.";
    }
    leaf counter_slice14_ifg_mac_pool85_port_mib_counter6_tx_mac_underrun_err_cnt {
      type oc-yang:counter64;
      description
        "MAC TX underrun errors count.";
    }
    leaf counter_slice14_ifg_mac_pool85_port_mib_counter7_tx_mac_underrun_err_cnt {
      type oc-yang:counter64;
      description
        "MAC TX underrun errors count.";
    }
    leaf counter_slice14_ifg_mac_pool86_port_mib_counter0_tx_mac_underrun_err_cnt {
      type oc-yang:counter64;
      description
        "MAC TX underrun errors count.";
    }
    leaf counter_slice14_ifg_mac_pool86_port_mib_counter1_tx_mac_underrun_err_cnt {
      type oc-yang:counter64;
      description
        "MAC TX underrun errors count.";
    }
    leaf counter_slice14_ifg_mac_pool86_port_mib_counter2_tx_mac_underrun_err_cnt {
      type oc-yang:counter64;
      description
        "MAC TX underrun errors count.";
    }
    leaf counter_slice14_ifg_mac_pool86_port_mib_counter3_tx_mac_underrun_err_cnt {
      type oc-yang:counter64;
      description
        "MAC TX underrun errors count.";
    }
    leaf counter_slice14_ifg_mac_pool86_port_mib_counter4_tx_mac_underrun_err_cnt {
      type oc-yang:counter64;
      description
        "MAC TX underrun errors count.";
    }
    leaf counter_slice14_ifg_mac_pool86_port_mib_counter5_tx_mac_underrun_err_cnt {
      type oc-yang:counter64;
      description
        "MAC TX underrun errors count.";
    }
    leaf counter_slice14_ifg_mac_pool86_port_mib_counter6_tx_mac_underrun_err_cnt {
      type oc-yang:counter64;
      description
        "MAC TX underrun errors count.";
    }
    leaf counter_slice14_ifg_mac_pool86_port_mib_counter7_tx_mac_underrun_err_cnt {
      type oc-yang:counter64;
      description
        "MAC TX underrun errors count.";
    }
    leaf counter_slice14_ifg_mac_pool87_port_mib_counter0_tx_mac_underrun_err_cnt {
      type oc-yang:counter64;
      description
        "MAC TX underrun errors count.";
    }
    leaf counter_slice14_ifg_mac_pool87_port_mib_counter1_tx_mac_underrun_err_cnt {
      type oc-yang:counter64;
      description
        "MAC TX underrun errors count.";
    }
    leaf counter_slice14_ifg_mac_pool87_port_mib_counter2_tx_mac_underrun_err_cnt {
      type oc-yang:counter64;
      description
        "MAC TX underrun errors count.";
    }
    leaf counter_slice14_ifg_mac_pool87_port_mib_counter3_tx_mac_underrun_err_cnt {
      type oc-yang:counter64;
      description
        "MAC TX underrun errors count.";
    }
    leaf counter_slice14_ifg_mac_pool87_port_mib_counter4_tx_mac_underrun_err_cnt {
      type oc-yang:counter64;
      description
        "MAC TX underrun errors count.";
    }
    leaf counter_slice14_ifg_mac_pool87_port_mib_counter5_tx_mac_underrun_err_cnt {
      type oc-yang:counter64;
      description
        "MAC TX underrun errors count.";
    }
    leaf counter_slice14_ifg_mac_pool87_port_mib_counter6_tx_mac_underrun_err_cnt {
      type oc-yang:counter64;
      description
        "MAC TX underrun errors count.";
    }
    leaf counter_slice14_ifg_mac_pool87_port_mib_counter7_tx_mac_underrun_err_cnt {
      type oc-yang:counter64;
      description
        "MAC TX underrun errors count.";
    }
    leaf counter_slice15_ifg_mac_pool80_port_mib_counter0_tx_mac_underrun_err_cnt {
      type oc-yang:counter64;
      description
        "MAC TX underrun errors count.";
    }
    leaf counter_slice15_ifg_mac_pool80_port_mib_counter1_tx_mac_underrun_err_cnt {
      type oc-yang:counter64;
      description
        "MAC TX underrun errors count.";
    }
    leaf counter_slice15_ifg_mac_pool80_port_mib_counter2_tx_mac_underrun_err_cnt {
      type oc-yang:counter64;
      description
        "MAC TX underrun errors count.";
    }
    leaf counter_slice15_ifg_mac_pool80_port_mib_counter3_tx_mac_underrun_err_cnt {
      type oc-yang:counter64;
      description
        "MAC TX underrun errors count.";
    }
    leaf counter_slice15_ifg_mac_pool80_port_mib_counter4_tx_mac_underrun_err_cnt {
      type oc-yang:counter64;
      description
        "MAC TX underrun errors count.";
    }
    leaf counter_slice15_ifg_mac_pool80_port_mib_counter5_tx_mac_underrun_err_cnt {
      type oc-yang:counter64;
      description
        "MAC TX underrun errors count.";
    }
    leaf counter_slice15_ifg_mac_pool80_port_mib_counter6_tx_mac_underrun_err_cnt {
      type oc-yang:counter64;
      description
        "MAC TX underrun errors count.";
    }
    leaf counter_slice15_ifg_mac_pool80_port_mib_counter7_tx_mac_underrun_err_cnt {
      type oc-yang:counter64;
      description
        "MAC TX underrun errors count.";
    }
    leaf counter_slice15_ifg_mac_pool81_port_mib_counter0_tx_mac_underrun_err_cnt {
      type oc-yang:counter64;
      description
        "MAC TX underrun errors count.";
    }
    leaf counter_slice15_ifg_mac_pool81_port_mib_counter1_tx_mac_underrun_err_cnt {
      type oc-yang:counter64;
      description
        "MAC TX underrun errors count.";
    }
    leaf counter_slice15_ifg_mac_pool81_port_mib_counter2_tx_mac_underrun_err_cnt {
      type oc-yang:counter64;
      description
        "MAC TX underrun errors count.";
    }
    leaf counter_slice15_ifg_mac_pool81_port_mib_counter3_tx_mac_underrun_err_cnt {
      type oc-yang:counter64;
      description
        "MAC TX underrun errors count.";
    }
    leaf counter_slice15_ifg_mac_pool81_port_mib_counter4_tx_mac_underrun_err_cnt {
      type oc-yang:counter64;
      description
        "MAC TX underrun errors count.";
    }
    leaf counter_slice15_ifg_mac_pool81_port_mib_counter5_tx_mac_underrun_err_cnt {
      type oc-yang:counter64;
      description
        "MAC TX underrun errors count.";
    }
    leaf counter_slice15_ifg_mac_pool81_port_mib_counter6_tx_mac_underrun_err_cnt {
      type oc-yang:counter64;
      description
        "MAC TX underrun errors count.";
    }
    leaf counter_slice15_ifg_mac_pool81_port_mib_counter7_tx_mac_underrun_err_cnt {
      type oc-yang:counter64;
      description
        "MAC TX underrun errors count.";
    }
    leaf counter_slice15_ifg_mac_pool82_port_mib_counter0_tx_mac_underrun_err_cnt {
      type oc-yang:counter64;
      description
        "MAC TX underrun errors count.";
    }
    leaf counter_slice15_ifg_mac_pool82_port_mib_counter1_tx_mac_underrun_err_cnt {
      type oc-yang:counter64;
      description
        "MAC TX underrun errors count.";
    }
    leaf counter_slice15_ifg_mac_pool82_port_mib_counter2_tx_mac_underrun_err_cnt {
      type oc-yang:counter64;
      description
        "MAC TX underrun errors count.";
    }
    leaf counter_slice15_ifg_mac_pool82_port_mib_counter3_tx_mac_underrun_err_cnt {
      type oc-yang:counter64;
      description
        "MAC TX underrun errors count.";
    }
    leaf counter_slice15_ifg_mac_pool82_port_mib_counter4_tx_mac_underrun_err_cnt {
      type oc-yang:counter64;
      description
        "MAC TX underrun errors count.";
    }
    leaf counter_slice15_ifg_mac_pool82_port_mib_counter5_tx_mac_underrun_err_cnt {
      type oc-yang:counter64;
      description
        "MAC TX underrun errors count.";
    }
    leaf counter_slice15_ifg_mac_pool82_port_mib_counter6_tx_mac_underrun_err_cnt {
      type oc-yang:counter64;
      description
        "MAC TX underrun errors count.";
    }
    leaf counter_slice15_ifg_mac_pool82_port_mib_counter7_tx_mac_underrun_err_cnt {
      type oc-yang:counter64;
      description
        "MAC TX underrun errors count.";
    }
    leaf counter_slice15_ifg_mac_pool83_port_mib_counter0_tx_mac_underrun_err_cnt {
      type oc-yang:counter64;
      description
        "MAC TX underrun errors count.";
    }
    leaf counter_slice15_ifg_mac_pool83_port_mib_counter1_tx_mac_underrun_err_cnt {
      type oc-yang:counter64;
      description
        "MAC TX underrun errors count.";
    }
    leaf counter_slice15_ifg_mac_pool83_port_mib_counter2_tx_mac_underrun_err_cnt {
      type oc-yang:counter64;
      description
        "MAC TX underrun errors count.";
    }
    leaf counter_slice15_ifg_mac_pool83_port_mib_counter3_tx_mac_underrun_err_cnt {
      type oc-yang:counter64;
      description
        "MAC TX underrun errors count.";
    }
    leaf counter_slice15_ifg_mac_pool83_port_mib_counter4_tx_mac_underrun_err_cnt {
      type oc-yang:counter64;
      description
        "MAC TX underrun errors count.";
    }
    leaf counter_slice15_ifg_mac_pool83_port_mib_counter5_tx_mac_underrun_err_cnt {
      type oc-yang:counter64;
      description
        "MAC TX underrun errors count.";
    }
    leaf counter_slice15_ifg_mac_pool83_port_mib_counter6_tx_mac_underrun_err_cnt {
      type oc-yang:counter64;
      description
        "MAC TX underrun errors count.";
    }
    leaf counter_slice15_ifg_mac_pool83_port_mib_counter7_tx_mac_underrun_err_cnt {
      type oc-yang:counter64;
      description
        "MAC TX underrun errors count.";
    }
    leaf counter_slice15_ifg_mac_pool84_port_mib_counter0_tx_mac_underrun_err_cnt {
      type oc-yang:counter64;
      description
        "MAC TX underrun errors count.";
    }
    leaf counter_slice15_ifg_mac_pool84_port_mib_counter1_tx_mac_underrun_err_cnt {
      type oc-yang:counter64;
      description
        "MAC TX underrun errors count.";
    }
    leaf counter_slice15_ifg_mac_pool84_port_mib_counter2_tx_mac_underrun_err_cnt {
      type oc-yang:counter64;
      description
        "MAC TX underrun errors count.";
    }
    leaf counter_slice15_ifg_mac_pool84_port_mib_counter3_tx_mac_underrun_err_cnt {
      type oc-yang:counter64;
      description
        "MAC TX underrun errors count.";
    }
    leaf counter_slice15_ifg_mac_pool84_port_mib_counter4_tx_mac_underrun_err_cnt {
      type oc-yang:counter64;
      description
        "MAC TX underrun errors count.";
    }
    leaf counter_slice15_ifg_mac_pool84_port_mib_counter5_tx_mac_underrun_err_cnt {
      type oc-yang:counter64;
      description
        "MAC TX underrun errors count.";
    }
    leaf counter_slice15_ifg_mac_pool84_port_mib_counter6_tx_mac_underrun_err_cnt {
      type oc-yang:counter64;
      description
        "MAC TX underrun errors count.";
    }
    leaf counter_slice15_ifg_mac_pool84_port_mib_counter7_tx_mac_underrun_err_cnt {
      type oc-yang:counter64;
      description
        "MAC TX underrun errors count.";
    }
    leaf counter_slice15_ifg_mac_pool85_port_mib_counter0_tx_mac_underrun_err_cnt {
      type oc-yang:counter64;
      description
        "MAC TX underrun errors count.";
    }
    leaf counter_slice15_ifg_mac_pool85_port_mib_counter1_tx_mac_underrun_err_cnt {
      type oc-yang:counter64;
      description
        "MAC TX underrun errors count.";
    }
    leaf counter_slice15_ifg_mac_pool85_port_mib_counter2_tx_mac_underrun_err_cnt {
      type oc-yang:counter64;
      description
        "MAC TX underrun errors count.";
    }
    leaf counter_slice15_ifg_mac_pool85_port_mib_counter3_tx_mac_underrun_err_cnt {
      type oc-yang:counter64;
      description
        "MAC TX underrun errors count.";
    }
    leaf counter_slice15_ifg_mac_pool85_port_mib_counter4_tx_mac_underrun_err_cnt {
      type oc-yang:counter64;
      description
        "MAC TX underrun errors count.";
    }
    leaf counter_slice15_ifg_mac_pool85_port_mib_counter5_tx_mac_underrun_err_cnt {
      type oc-yang:counter64;
      description
        "MAC TX underrun errors count.";
    }
    leaf counter_slice15_ifg_mac_pool85_port_mib_counter6_tx_mac_underrun_err_cnt {
      type oc-yang:counter64;
      description
        "MAC TX underrun errors count.";
    }
    leaf counter_slice15_ifg_mac_pool85_port_mib_counter7_tx_mac_underrun_err_cnt {
      type oc-yang:counter64;
      description
        "MAC TX underrun errors count.";
    }
    leaf counter_slice15_ifg_mac_pool86_port_mib_counter0_tx_mac_underrun_err_cnt {
      type oc-yang:counter64;
      description
        "MAC TX underrun errors count.";
    }
    leaf counter_slice15_ifg_mac_pool86_port_mib_counter1_tx_mac_underrun_err_cnt {
      type oc-yang:counter64;
      description
        "MAC TX underrun errors count.";
    }
    leaf counter_slice15_ifg_mac_pool86_port_mib_counter2_tx_mac_underrun_err_cnt {
      type oc-yang:counter64;
      description
        "MAC TX underrun errors count.";
    }
    leaf counter_slice15_ifg_mac_pool86_port_mib_counter3_tx_mac_underrun_err_cnt {
      type oc-yang:counter64;
      description
        "MAC TX underrun errors count.";
    }
    leaf counter_slice15_ifg_mac_pool86_port_mib_counter4_tx_mac_underrun_err_cnt {
      type oc-yang:counter64;
      description
        "MAC TX underrun errors count.";
    }
    leaf counter_slice15_ifg_mac_pool86_port_mib_counter5_tx_mac_underrun_err_cnt {
      type oc-yang:counter64;
      description
        "MAC TX underrun errors count.";
    }
    leaf counter_slice15_ifg_mac_pool86_port_mib_counter6_tx_mac_underrun_err_cnt {
      type oc-yang:counter64;
      description
        "MAC TX underrun errors count.";
    }
    leaf counter_slice15_ifg_mac_pool86_port_mib_counter7_tx_mac_underrun_err_cnt {
      type oc-yang:counter64;
      description
        "MAC TX underrun errors count.";
    }
    leaf counter_slice15_ifg_mac_pool87_port_mib_counter0_tx_mac_underrun_err_cnt {
      type oc-yang:counter64;
      description
        "MAC TX underrun errors count.";
    }
    leaf counter_slice15_ifg_mac_pool87_port_mib_counter1_tx_mac_underrun_err_cnt {
      type oc-yang:counter64;
      description
        "MAC TX underrun errors count.";
    }
    leaf counter_slice15_ifg_mac_pool87_port_mib_counter2_tx_mac_underrun_err_cnt {
      type oc-yang:counter64;
      description
        "MAC TX underrun errors count.";
    }
    leaf counter_slice15_ifg_mac_pool87_port_mib_counter3_tx_mac_underrun_err_cnt {
      type oc-yang:counter64;
      description
        "MAC TX underrun errors count.";
    }
    leaf counter_slice15_ifg_mac_pool87_port_mib_counter4_tx_mac_underrun_err_cnt {
      type oc-yang:counter64;
      description
        "MAC TX underrun errors count.";
    }
    leaf counter_slice15_ifg_mac_pool87_port_mib_counter5_tx_mac_underrun_err_cnt {
      type oc-yang:counter64;
      description
        "MAC TX underrun errors count.";
    }
    leaf counter_slice15_ifg_mac_pool87_port_mib_counter6_tx_mac_underrun_err_cnt {
      type oc-yang:counter64;
      description
        "MAC TX underrun errors count.";
    }
    leaf counter_slice15_ifg_mac_pool87_port_mib_counter7_tx_mac_underrun_err_cnt {
      type oc-yang:counter64;
      description
        "MAC TX underrun errors count.";
    }
    leaf counter_slice0_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice1_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice2_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice3_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice4_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice5_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice6_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice7_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice8_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice9_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice10_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice11_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice12_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice13_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice14_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool82_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool83_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool84_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool85_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool86_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice15_ifg_mac_pool87_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_slice0_ifg_mac_pool80_rx_mac_partial1_invert_crc_cnt_reg0_rx_mac_partial1_invert_crc_cnt {
      type oc-yang:counter64;
      description
        "Counts the number of received packets with partial CRC type 1.";
    }
    leaf counter_slice0_ifg_mac_pool80_rx_mac_partial1_invert_crc_cnt_reg1_rx_mac_partial1_invert_crc_cnt {
      type oc-yang:counter64;
      description
        "Counts the number of received packets with partial CRC type 1.";
    }
    leaf counter_slice0_ifg_mac_pool80_rx_mac_partial1_invert_crc_cnt_reg2_rx_mac_partial1_invert_crc_cnt {
      type oc-yang:counter64;
      description
        "Counts the number of received packets with partial CRC type 1.";
    }
    leaf counter_slice0_ifg_mac_pool80_rx_mac_partial1_invert_crc_cnt_reg3_rx_mac_partial1_invert_crc_cnt {
      type oc-yang:counter64;
      description
        "Counts the number of received packets with partial CRC type 1.";
    }
    leaf counter_slice0_ifg_mac_pool80_rx_mac_partial1_invert_crc_cnt_reg4_rx_mac_partial1_invert_crc_cnt {
      type oc-yang:counter64;
      description
        "Counts the number of received packets with partial CRC type 1.";
    }
    leaf counter_slice0_ifg_mac_pool80_rx_mac_partial1_invert_crc_cnt_reg5_rx_mac_partial1_invert_crc_cnt {
      type oc-yang:counter64;
      description
        "Counts the number of received packets with partial CRC type 1.";
    }
    leaf counter_slice0_ifg_mac_pool80_rx_mac_partial1_invert_crc_cnt_reg6_rx_mac_partial1_invert_crc_cnt {
      type oc-yang:counter64;
      description
        "Counts the number of received packets with partial CRC type 1.";
    }
    leaf counter_slice0_ifg_mac_pool80_rx_mac_partial1_invert_crc_cnt_reg7_rx_mac_partial1_invert_crc_cnt {
      type oc-yang:counter64;
      description
        "Counts the number of received packets with partial CRC type 1.";
    }
    leaf counter_slice0_ifg_mac_pool81_rx_mac_partial1_invert_crc_cnt_reg0_rx_mac_partial1_invert_crc_cnt {
      type oc-yang:counter64;
      description
        "Counts the number of received packets with partial CRC type 1.";
    }
    leaf counter_slice0_ifg_mac_pool81_rx_mac_partial1_invert_crc_cnt_reg1_rx_mac_partial1_invert_crc_cnt {
      type oc-yang:counter64;
      description
        "Counts the number of received packets with partial CRC type 1.";
    }
    leaf counter_slice0_ifg_mac_pool81_rx_mac_partial1_invert_crc_cnt_reg2_rx_mac_partial1_invert_crc_cnt {
      type oc-yang:counter64;
      description
        "Counts the number of received packets with partial CRC type 1.";
    }
    leaf counter_slice0_ifg_mac_pool81_rx_mac_partial1_invert_crc_cnt_reg3_rx_mac_partial1_invert_crc_cnt {
      type oc-yang:counter64;
      description
        "Counts the number of received packets with partial CRC type 1.";
    }
    leaf counter_slice0_ifg_mac_pool81_rx_mac_partial1_invert_crc_cnt_reg4_rx_mac_partial1_invert_crc_cnt {
      type oc-yang:counter64;
      description
        "Counts the number of received packets with partial CRC type 1.";
    }
    leaf counter_slice0_ifg_mac_pool81_rx_mac_partial1_invert_crc_cnt_reg5_rx_mac_partial1_invert_crc_cnt {
      type oc-yang:counter64;
      description
        "Counts the number of received packets with partial CRC type 1.";
    }
    leaf counter_slice0_ifg_mac_pool81_rx_mac_partial1_invert_crc_cnt_reg6_rx_mac_partial1_invert_crc_cnt {
      type oc-yang:counter64;
      description
        "Counts the number of received packets with partial CRC type 1.";
    }
    leaf counter_slice0_ifg_mac_pool81_rx_mac_partial1_invert_crc_cnt_reg7_rx_mac_partial1_invert_crc_cnt {
      type oc-yang:counter64;
      description
        "Counts the number of received packets with partial CRC type 1.";
    }
    leaf counter_slice0_ifg_mac_pool82_rx_mac_partial1_invert_crc_cnt_reg0_rx_mac_partial1_invert_crc_cnt {
      type oc-yang:counter64;
      description
        "Counts the number of received packets with partial CRC type 1.";
    }
    leaf counter_slice0_ifg_mac_pool82_rx_mac_partial1_invert_crc_cnt_reg1_rx_mac_partial1_invert_crc_cnt {
      type oc-yang:counter64;
      description
        "Counts the number of received packets with partial CRC type 1.";
    }
    leaf counter_slice0_ifg_mac_pool82_rx_mac_partial1_invert_crc_cnt_reg2_rx_mac_partial1_invert_crc_cnt {
      type oc-yang:counter64;
      description
        "Counts the number of received packets with partial CRC type 1.";
    }
    leaf counter_slice0_ifg_mac_pool82_rx_mac_partial1_invert_crc_cnt_reg3_rx_mac_partial1_invert_crc_cnt {
      type oc-yang:counter64;
      description
        "Counts the number of received packets with partial CRC type 1.";
    }
    leaf counter_slice0_ifg_mac_pool82_rx_mac_partial1_invert_crc_cnt_reg4_rx_mac_partial1_invert_crc_cnt {
      type oc-yang:counter64;
      description
        "Counts the number of received packets with partial CRC type 1.";
    }
    leaf counter_slice0_ifg_mac_pool82_rx_mac_partial1_invert_crc_cnt_reg5_rx_mac_partial1_invert_crc_cnt {
      type oc-yang:counter64;
      description
        "Counts the number of received packets with partial CRC type 1.";
    }
    leaf counter_slice0_ifg_mac_pool82_rx_mac_partial1_invert_crc_cnt_reg6_rx_mac_partial1_invert_crc_cnt {
      type oc-yang:counter64;
      description
        "Counts the number of received packets with partial CRC type 1.";
    }
    leaf counter_slice0_ifg_mac_pool82_rx_mac_partial1_invert_crc_cnt_reg7_rx_mac_partial1_invert_crc_cnt {
      type oc-yang:counter64;
      description
        "Counts the number of received packets with partial CRC type 1.";
    }
    leaf counter_slice0_ifg_mac_pool83_rx_mac_partial1_invert_crc_cnt_reg0_rx_mac_partial1_invert_crc_cnt {
      type oc-yang:counter64;
      description
        "Counts the number of received packets with partial CRC type 1.";
    }
    leaf counter_slice0_ifg_mac_pool83_rx_mac_partial1_invert_crc_cnt_reg1_rx_mac_partial1_invert_crc_cnt {
      type oc-yang:counter64;
      description
        "Counts the number of received packets with partial CRC type 1.";
    }
    leaf counter_slice0_ifg_mac_pool83_rx_mac_partial1_invert_crc_cnt_reg2_rx_mac_partial1_invert_crc_cnt {
      type oc-yang:counter64;
      description
        "Counts the number of received packets with partial CRC type 1.";
    }
    leaf counter_slice0_ifg_mac_pool83_rx_mac_partial1_invert_crc_cnt_reg3_rx_mac_partial1_invert_crc_cnt {
      type oc-yang:counter64;
      description
        "Counts the number of received packets with partial CRC type 1.";
    }
    leaf counter_slice0_ifg_mac_pool83_rx_mac_partial1_invert_crc_cnt_reg4_rx_mac_partial1_invert_crc_cnt {
      type oc-yang:counter64;
      description
        "Counts the number of received packets with partial CRC type 1.";
    }
    leaf counter_slice0_ifg_mac_pool83_rx_mac_partial1_invert_crc_cnt_reg5_rx_mac_partial1_invert_crc_cnt {
      type oc-yang:counter64;
      description
        "Counts the number of received packets with partial CRC type 1.";
    }
    leaf counter_slice0_ifg_mac_pool83_rx_mac_partial1_invert_crc_cnt_reg6_rx_mac_partial1_invert_crc_cnt {
      type oc-yang:counter64;
      description
        "Counts the number of received packets with partial CRC type 1.";
    }
    leaf counter_slice0_ifg_mac_pool83_rx_mac_partial1_invert_crc_cnt_reg7_rx_mac_partial1_invert_crc_cnt {
      type oc-yang:counter64;
      description
        "Counts the number of received packets with partial CRC type 1.";
    }
    leaf counter_slice0_ifg_mac_pool84_rx_mac_partial1_invert_crc_cnt_reg0_rx_mac_partial1_invert_crc_cnt {
      type oc-yang:counter64;
      description
        "Counts the number of received packets with partial CRC type 1.";
    }
    leaf counter_slice0_ifg_mac_pool84_rx_mac_partial1_invert_crc_cnt_reg1_rx_mac_partial1_invert_crc_cnt {
      type oc-yang:counter64;
      description
        "Counts the number of received packets with partial CRC type 1.";
    }
    leaf counter_slice0_ifg_mac_pool84_rx_mac_partial1_invert_crc_cnt_reg2_rx_mac_partial1_invert_crc_cnt {
      type oc-yang:counter64;
      description
        "Counts the number of received packets with partial CRC type 1.";
    }
    leaf counter_slice0_ifg_mac_pool84_rx_mac_partial1_invert_crc_cnt_reg3_rx_mac_partial1_invert_crc_cnt {
      type oc-yang:counter64;
      description
        "Counts the number of received packets with partial CRC type 1.";
    }
    leaf counter_slice0_ifg_mac_pool84_rx_mac_partial1_invert_crc_cnt_reg4_rx_mac_partial1_invert_crc_cnt {
      type oc-yang:counter64;
      description
        "Counts the number of received packets with partial CRC type 1.";
    }
    leaf counter_slice0_ifg_mac_pool84_rx_mac_partial1_invert_crc_cnt_reg5_rx_mac_partial1_invert_crc_cnt {
      type oc-yang:counter64;
      description
        "Counts the number of received packets with partial CRC type 1.";
    }
    leaf counter_slice0_ifg_mac_pool84_rx_mac_partial1_invert_crc_cnt_reg6_rx_mac_partial1_invert_crc_cnt {
      type oc-yang:counter64;
      description
        "Counts the number of received packets with partial CRC type 1.";
    }
    leaf counter_slice0_ifg_mac_pool84_rx_mac_partial1_invert_crc_cnt_reg7_rx_mac_partial1_invert_crc_cnt {
      type oc-yang:counter64;
      description
        "Counts the number of received packets with partial CRC type 1.";
    }
    leaf counter_slice0_ifg_mac_pool85_rx_mac_partial1_invert_crc_cnt_reg0_rx_mac_partial1_invert_crc_cnt {
      type oc-yang:counter64;
      description
        "Counts the number of received packets with partial CRC type 1.";
    }
    leaf counter_slice0_ifg_mac_pool85_rx_mac_partial1_invert_crc_cnt_reg1_rx_mac_partial1_invert_crc_cnt {
      type oc-yang:counter64;
      description
        "Counts the number of received packets with partial CRC type 1.";
    }
    leaf counter_slice0_ifg_mac_pool85_rx_mac_partial1_invert_crc_cnt_reg2_rx_mac_partial1_invert_crc_cnt {
      type oc-yang:counter64;
      description
        "Counts the number of received packets with partial CRC type 1.";
    }
    leaf counter_slice0_ifg_mac_pool85_rx_mac_partial1_invert_crc_cnt_reg3_rx_mac_partial1_invert_crc_cnt {
      type oc-yang:counter64;
      description
        "Counts the number of received packets with partial CRC type 1.";
    }
    leaf counter_slice0_ifg_mac_pool85_rx_mac_partial1_invert_crc_cnt_reg4_rx_mac_partial1_invert_crc_cnt {
      type oc-yang:counter64;
      description
        "Counts the number of received packets with partial CRC type 1.";
    }
    leaf counter_slice0_ifg_mac_pool85_rx_mac_partial1_invert_crc_cnt_reg5_rx_mac_partial1_invert_crc_cnt {
      type oc-yang:counter64;
      description
        "Counts the number of received packets with partial CRC type 1.";
    }
    leaf counter_slice0_ifg_mac_pool85_rx_mac_partial1_invert_crc_cnt_reg6_rx_mac_partial1_invert_crc_cnt {
      type oc-yang:counter64;
      description
        "Counts the number of received packets with partial CRC type 1.";
    }
    leaf counter_slice0_ifg_mac_pool85_rx_mac_partial1_invert_crc_cnt_reg7_rx_mac_partial1_invert_crc_cnt {
      type oc-yang:counter64;
      description
        "Counts the number of received packets with partial CRC type 1.";
    }
    leaf counter_slice0_ifg_mac_pool86_rx_mac_partial1_invert_crc_cnt_reg0_rx_mac_partial1_invert_crc_cnt {
      type oc-yang:counter64;
      description
        "Counts the number of received packets with partial CRC type 1.";
    }
    leaf counter_slice0_ifg_mac_pool86_rx_mac_partial1_invert_crc_cnt_reg1_rx_mac_partial1_invert_crc_cnt {
      type oc-yang:counter64;
      description
        "Counts the number of received packets with partial CRC type 1.";
    }
    leaf counter_slice0_ifg_mac_pool86_rx_mac_partial1_invert_crc_cnt_reg2_rx_mac_partial1_invert_crc_cnt {
      type oc-yang:counter64;
      description
        "Counts the number of received packets with partial CRC type 1.";
    }
    leaf counter_slice0_ifg_mac_pool86_rx_mac_partial1_invert_crc_cnt_reg3_rx_mac_partial1_invert_crc_cnt {
      type oc-yang:counter64;
      description
        "Counts the number of received packets with partial CRC type 1.";
    }
    leaf counter_slice0_ifg_mac_pool86_rx_mac_partial1_invert_crc_cnt_reg4_rx_mac_partial1_invert_crc_cnt {
      type oc-yang:counter64;
      description
        "Counts the number of received packets with partial CRC type 1.";
    }
    leaf counter_slice0_ifg_mac_pool86_rx_mac_partial1_invert_crc_cnt_reg5_rx_mac_partial1_invert_crc_cnt {
      type oc-yang:counter64;
      description
        "Counts the number of received packets with partial CRC type 1.";
    }
    leaf counter_slice0_ifg_mac_pool86_rx_mac_partial1_invert_crc_cnt_reg6_rx_mac_partial1_invert_crc_cnt {
      type oc-yang:counter64;
      description
        "Counts the number of received packets with partial CRC type 1.";
    }
    leaf counter_slice0_ifg_mac_pool86_rx_mac_partial1_invert_crc_cnt_reg7_rx_mac_partial1_invert_crc_cnt {
      type oc-yang:counter64;
      description
        "Counts the number of received packets with partial CRC type 1.";
    }
    leaf counter_slice0_ifg_mac_pool87_rx_mac_partial1_invert_crc_cnt_reg0_rx_mac_partial1_invert_crc_cnt {
      type oc-yang:counter64;
      description
        "Counts the number of received packets with partial CRC type 1.";
    }
    leaf counter_slice0_ifg_mac_pool87_rx_mac_partial1_invert_crc_cnt_reg1_rx_mac_partial1_invert_crc_cnt {
      type oc-yang:counter64;
      description
        "Counts the number of received packets with partial CRC type 1.";
    }
    leaf counter_slice0_ifg_mac_pool87_rx_mac_partial1_invert_crc_cnt_reg2_rx_mac_partial1_invert_crc_cnt {
      type oc-yang:counter64;
      description
        "Counts the number of received packets with partial CRC type 1.";
    }
    leaf counter_slice0_ifg_mac_pool87_rx_mac_partial1_invert_crc_cnt_reg3_rx_mac_partial1_invert_crc_cnt {
      type oc-yang:counter64;
      description
        "Counts the number of received packets with partial CRC type 1.";
    }
    leaf counter_slice0_ifg_mac_pool87_rx_mac_partial1_invert_crc_cnt_reg4_rx_mac_partial1_invert_crc_cnt {
      type oc-yang:counter64;
      description
        "Counts the number of received packets with partial CRC type 1.";
    }
    leaf counter_slice0_ifg_mac_pool87_rx_mac_partial1_invert_crc_cnt_reg5_rx_mac_partial1_invert_crc_cnt {
      type oc-yang:counter64;
      description
        "Counts the number of received packets with partial CRC type 1.";
    }
    leaf counter_slice0_ifg_mac_pool87_rx_mac_partial1_invert_crc_cnt_reg6_rx_mac_partial1_invert_crc_cnt {
      type oc-yang:counter64;
      description
        "Counts the number of received packets with partial CRC type 1.";
    }
    leaf counter_slice0_ifg_mac_pool87_rx_mac_partial1_invert_crc_cnt_reg7_rx_mac_partial1_invert_crc_cnt {
      type oc-yang:counter64;
      description
        "Counts the number of received packets with partial CRC type 1.";
    }
    leaf counter_slice1_ifg_mac_pool80_rx_mac_partial1_invert_crc_cnt_reg0_rx_mac_partial1_invert_crc_cnt {
      type oc-yang:counter64;
      description
        "Counts the number of received packets with partial CRC type 1.";
    }
    leaf counter_slice1_ifg_mac_pool80_rx_mac_partial1_invert_crc_cnt_reg1_rx_mac_partial1_invert_crc_cnt {
      type oc-yang:counter64;
      description
        "Counts the number of received packets with partial CRC type 1.";
    }
    leaf counter_slice1_ifg_mac_pool80_rx_mac_partial1_invert_crc_cnt_reg2_rx_mac_partial1_invert_crc_cnt {
      type oc-yang:counter64;
      description
        "Counts the number of received packets with partial CRC type 1.";
    }
    leaf counter_slice1_ifg_mac_pool80_rx_mac_partial1_invert_crc_cnt_reg3_rx_mac_partial1_invert_crc_cnt {
      type oc-yang:counter64;
      description
        "Counts the number of received packets with partial CRC type 1.";
    }
    leaf counter_slice1_ifg_mac_pool80_rx_mac_partial1_invert_crc_cnt_reg4_rx_mac_partial1_invert_crc_cnt {
      type oc-yang:counter64;
      description
        "Counts the number of received packets with partial CRC type 1.";
    }
    leaf counter_slice1_ifg_mac_pool80_rx_mac_partial1_invert_crc_cnt_reg5_rx_mac_partial1_invert_crc_cnt {
      type oc-yang:counter64;
      description
        "Counts the number of received packets with partial CRC type 1.";
    }
    leaf counter_slice1_ifg_mac_pool80_rx_mac_partial1_invert_crc_cnt_reg6_rx_mac_partial1_invert_crc_cnt {
      type oc-yang:counter64;
      description
        "Counts the number of received packets with partial CRC type 1.";
    }
    leaf counter_slice1_ifg_mac_pool80_rx_mac_partial1_invert_crc_cnt_reg7_rx_mac_partial1_invert_crc_cnt {
      type oc-yang:counter64;
      description
        "Counts the number of received packets with partial CRC type 1.";
    }
    leaf counter_slice1_ifg_mac_pool81_rx_mac_partial1_invert_crc_cnt_reg0_rx_mac_partial1_invert_crc_cnt {
      type oc-yang:counter64;
      description
        "Counts the number of received packets with partial CRC type 1.";
    }
    leaf counter_slice1_ifg_mac_pool81_rx_mac_partial1_invert_crc_cnt_reg1_rx_mac_partial1_invert_crc_cnt {
      type oc-yang:counter64;
      description
        "Counts the number of received packets with partial CRC type 1.";
    }
    leaf counter_slice1_ifg_mac_pool81_rx_mac_partial1_invert_crc_cnt_reg2_rx_mac_partial1_invert_crc_cnt {
      type oc-yang:counter64;
      description
        "Counts the number of received packets with partial CRC type 1.";
    }
    leaf counter_slice1_ifg_mac_pool81_rx_mac_partial1_invert_crc_cnt_reg3_rx_mac_partial1_invert_crc_cnt {
      type oc-yang:counter64;
      description
        "Counts the number of received packets with partial CRC type 1.";
    }
    leaf counter_slice1_ifg_mac_pool81_rx_mac_partial1_invert_crc_cnt_reg4_rx_mac_partial1_invert_crc_cnt {
      type oc-yang:counter64;
      description
        "Counts the number of received packets with partial CRC type 1.";
    }
    leaf counter_slice1_ifg_mac_pool81_rx_mac_partial1_invert_crc_cnt_reg5_rx_mac_partial1_invert_crc_cnt {
      type oc-yang:counter64;
      description
        "Counts the number of received packets with partial CRC type 1.";
    }
    leaf counter_slice1_ifg_mac_pool81_rx_mac_partial1_invert_crc_cnt_reg6_rx_mac_partial1_invert_crc_cnt {
      type oc-yang:counter64;
      description
        "Counts the number of received packets with partial CRC type 1.";
    }
    leaf counter_slice1_ifg_mac_pool81_rx_mac_partial1_invert_crc_cnt_reg7_rx_mac_partial1_invert_crc_cnt {
      type oc-yang:counter64;
      description
        "Counts the number of received packets with partial CRC type 1.";
    }
    leaf counter_slice1_ifg_mac_pool82_rx_mac_partial1_invert_crc_cnt_reg0_rx_mac_partial1_invert_crc_cnt {
      type oc-yang:counter64;
      description
        "Counts the number of received packets with partial CRC type 1.";
    }
    leaf counter_slice1_ifg_mac_pool82_rx_mac_partial1_invert_crc_cnt_reg1_rx_mac_partial1_invert_crc_cnt {
      type oc-yang:counter64;
      description
        "Counts the number of received packets with partial CRC type 1.";
    }
    leaf counter_slice1_ifg_mac_pool82_rx_mac_partial1_invert_crc_cnt_reg2_rx_mac_partial1_invert_crc_cnt {
      type oc-yang:counter64;
      description
        "Counts the number of received packets with partial CRC type 1.";
    }
    leaf counter_slice1_ifg_mac_pool82_rx_mac_partial1_invert_crc_cnt_reg3_rx_mac_partial1_invert_crc_cnt {
      type oc-yang:counter64;
      description
        "Counts the number of received packets with partial CRC type 1.";
    }
    leaf counter_slice1_ifg_mac_pool82_rx_mac_partial1_invert_crc_cnt_reg4_rx_mac_partial1_invert_crc_cnt {
      type oc-yang:counter64;
      description
        "Counts the number of received packets with partial CRC type 1.";
    }
    leaf counter_slice1_ifg_mac_pool82_rx_mac_partial1_invert_crc_cnt_reg5_rx_mac_partial1_invert_crc_cnt {
      type oc-yang:counter64;
      description
        "Counts the number of received packets with partial CRC type 1.";
    }
    leaf counter_slice1_ifg_mac_pool82_rx_mac_partial1_invert_crc_cnt_reg6_rx_mac_partial1_invert_crc_cnt {
      type oc-yang:counter64;
      description
        "Counts the number of received packets with partial CRC type 1.";
    }
    leaf counter_slice1_ifg_mac_pool82_rx_mac_partial1_invert_crc_cnt_reg7_rx_mac_partial1_invert_crc_cnt {
      type oc-yang:counter64;
      description
        "Counts the number of received packets with partial CRC type 1.";
    }
    leaf counter_slice1_ifg_mac_pool83_rx_mac_partial1_invert_crc_cnt_reg0_rx_mac_partial1_invert_crc_cnt {
      type oc-yang:counter64;
      description
        "Counts the number of received packets with partial CRC type 1.";
    }
    leaf counter_slice1_ifg_mac_pool83_rx_mac_partial1_invert_crc_cnt_reg1_rx_mac_partial1_invert_crc_cnt {
      type oc-yang:counter64;
      description
        "Counts the number of received packets with partial CRC type 1.";
    }
    leaf counter_slice1_ifg_mac_pool83_rx_mac_partial1_invert_crc_cnt_reg2_rx_mac_partial1_invert_crc_cnt {
      type oc-yang:counter64;
      description
        "Counts the number of received packets with partial CRC type 1.";
    }
    leaf counter_slice1_ifg_mac_pool83_rx_mac_partial1_invert_crc_cnt_reg3_rx_mac_partial1_invert_crc_cnt {
      type oc-yang:counter64;
      description
        "Counts the number of received packets with partial CRC type 1.";
    }
    leaf counter_slice1_ifg_mac_pool83_rx_mac_partial1_invert_crc_cnt_reg4_rx_mac_partial1_invert_crc_cnt {
      type oc-yang:counter64;
      description
        "Counts the number of received packets with partial CRC type 1.";
    }
    leaf counter_slice1_ifg_mac_pool83_rx_mac_partial1_invert_crc_cnt_reg5_rx_mac_partial1_invert_crc_cnt {
      type oc-yang:counter64;
      description
        "Counts the number of received packets with partial CRC type 1.";
    }
    leaf counter_slice1_ifg_mac_pool83_rx_mac_partial1_invert_crc_cnt_reg6_rx_mac_partial1_invert_crc_cnt {
      type oc-yang:counter64;
      description
        "Counts the number of received packets with partial CRC type 1.";
    }
    leaf counter_slice1_ifg_mac_pool83_rx_mac_partial1_invert_crc_cnt_reg7_rx_mac_partial1_invert_crc_cnt {
      type oc-yang:counter64;
      description
        "Counts the number of received packets with partial CRC type 1.";
    }
    leaf counter_slice1_ifg_mac_pool84_rx_mac_partial1_invert_crc_cnt_reg0_rx_mac_partial1_invert_crc_cnt {
      type oc-yang:counter64;
      description
        "Counts the number of received packets with partial CRC type 1.";
    }
    leaf counter_slice1_ifg_mac_pool84_rx_mac_partial1_invert_crc_cnt_reg1_rx_mac_partial1_invert_crc_cnt {
      type oc-yang:counter64;
      description
        "Counts the number of received packets with partial CRC type 1.";
    }
    leaf counter_slice1_ifg_mac_pool84_rx_mac_partial1_invert_crc_cnt_reg2_rx_mac_partial1_invert_crc_cnt {
      type oc-yang:counter64;
      description
        "Counts the number of received packets with partial CRC type 1.";
    }
    leaf counter_slice1_ifg_mac_pool84_rx_mac_partial1_invert_crc_cnt_reg3_rx_mac_partial1_invert_crc_cnt {
      type oc-yang:counter64;
      description
        "Counts the number of received packets with partial CRC type 1.";
    }
    leaf counter_slice1_ifg_mac_pool84_rx_mac_partial1_invert_crc_cnt_reg4_rx_mac_partial1_invert_crc_cnt {
      type oc-yang:counter64;
      description
        "Counts the number of received packets with partial CRC type 1.";
    }
    leaf counter_slice1_ifg_mac_pool84_rx_mac_partial1_invert_crc_cnt_reg5_rx_mac_partial1_invert_crc_cnt {
      type oc-yang:counter64;
      description
        "Counts the number of received packets with partial CRC type 1.";
    }
    leaf counter_slice1_ifg_mac_pool84_rx_mac_partial1_invert_crc_cnt_reg6_rx_mac_partial1_invert_crc_cnt {
      type oc-yang:counter64;
      description
        "Counts the number of received packets with partial CRC type 1.";
    }
    leaf counter_slice1_ifg_mac_pool84_rx_mac_partial1_invert_crc_cnt_reg7_rx_mac_partial1_invert_crc_cnt {
      type oc-yang:counter64;
      description
        "Counts the number of received packets with partial CRC type 1.";
    }
    leaf counter_slice1_ifg_mac_pool85_rx_mac_partial1_invert_crc_cnt_reg0_rx_mac_partial1_invert_crc_cnt {
      type oc-yang:counter64;
      description
        "Counts the number of received packets with partial CRC type 1.";
    }
    leaf counter_slice1_ifg_mac_pool85_rx_mac_partial1_invert_crc_cnt_reg1_rx_mac_partial1_invert_crc_cnt {
      type oc-yang:counter64;
      description
        "Counts the number of received packets with partial CRC type 1.";
    }
    leaf counter_slice1_ifg_mac_pool85_rx_mac_partial1_invert_crc_cnt_reg2_rx_mac_partial1_invert_crc_cnt {
      type oc-yang:counter64;
      description
        "Counts the number of received packets with partial CRC type 1.";
    }
    leaf counter_slice1_ifg_mac_pool85_rx_mac_partial1_invert_crc_cnt_reg3_rx_mac_partial1_invert_crc_cnt {
      type oc-yang:counter64;
      description
        "Counts the number of received packets with partial CRC type 1.";
    }
    leaf counter_slice1_ifg_mac_pool85_rx_mac_partial1_invert_crc_cnt_reg4_rx_mac_partial1_invert_crc_cnt {
      type oc-yang:counter64;
      description
        "Counts the number of received packets with partial CRC type 1.";
    }
    leaf counter_slice1_ifg_mac_pool85_rx_mac_partial1_invert_crc_cnt_reg5_rx_mac_partial1_invert_crc_cnt {
      type oc-yang:counter64;
      description
        "Counts the number of received packets with partial CRC type 1.";
    }
    leaf counter_slice1_ifg_mac_pool85_rx_mac_partial1_invert_crc_cnt_reg6_rx_mac_partial1_invert_crc_cnt {
      type oc-yang:counter64;
      description
        "Counts the number of received packets with partial CRC type 1.";
    }
    leaf counter_slice1_ifg_mac_pool85_rx_mac_partial1_invert_crc_cnt_reg7_rx_mac_partial1_invert_crc_cnt {
      type oc-yang:counter64;
      description
        "Counts the number of received packets with partial CRC type 1.";
    }
    leaf counter_slice1_ifg_mac_pool86_rx_mac_partial1_invert_crc_cnt_reg0_rx_mac_partial1_invert_crc_cnt {
      type oc-yang:counter64;
      description
        "Counts the number of received packets with partial CRC type 1.";
    }
    leaf counter_slice1_ifg_mac_pool86_rx_mac_partial1_invert_crc_cnt_reg1_rx_mac_partial1_invert_crc_cnt {
      type oc-yang:counter64;
      description
        "Counts the number of received packets with partial CRC type 1.";
    }
    leaf counter_slice1_ifg_mac_pool86_rx_mac_partial1_invert_crc_cnt_reg2_rx_mac_partial1_invert_crc_cnt {
      type oc-yang:counter64;
      description
        "Counts the number of received packets with partial CRC type 1.";
    }
    leaf counter_slice1_ifg_mac_pool86_rx_mac_partial1_invert_crc_cnt_reg3_rx_mac_partial1_invert_crc_cnt {
      type oc-yang:counter64;
      description
        "Counts the number of received packets with partial CRC type 1.";
    }
    leaf counter_slice1_ifg_mac_pool86_rx_mac_partial1_invert_crc_cnt_reg4_rx_mac_partial1_invert_crc_cnt {
      type oc-yang:counter64;
      description
        "Counts the number of received packets with partial CRC type 1.";
    }
    leaf counter_slice1_ifg_mac_pool86_rx_mac_partial1_invert_crc_cnt_reg5_rx_mac_partial1_invert_crc_cnt {
      type oc-yang:counter64;
      description
        "Counts the number of received packets with partial CRC type 1.";
    }
    leaf counter_slice1_ifg_mac_pool86_rx_mac_partial1_invert_crc_cnt_reg6_rx_mac_partial1_invert_crc_cnt {
      type oc-yang:counter64;
      description
        "Counts the number of received packets with partial CRC type 1.";
    }
    leaf counter_slice1_ifg_mac_pool86_rx_mac_partial1_invert_crc_cnt_reg7_rx_mac_partial1_invert_crc_cnt {
      type oc-yang:counter64;
      description
        "Counts the number of received packets with partial CRC type 1.";
    }
    leaf counter_slice1_ifg_mac_pool87_rx_mac_partial1_invert_crc_cnt_reg0_rx_mac_partial1_invert_crc_cnt {
      type oc-yang:counter64;
      description
        "Counts the number of received packets with partial CRC type 1.";
    }
    leaf counter_slice1_ifg_mac_pool87_rx_mac_partial1_invert_crc_cnt_reg1_rx_mac_partial1_invert_crc_cnt {
      type oc-yang:counter64;
      description
        "Counts the number of received packets with partial CRC type 1.";
    }
    leaf counter_slice1_ifg_mac_pool87_rx_mac_partial1_invert_crc_cnt_reg2_rx_mac_partial1_invert_crc_cnt {
      type oc-yang:counter64;
      description
        "Counts the number of received packets with partial CRC type 1.";
    }
    leaf counter_slice1_ifg_mac_pool87_rx_mac_partial1_invert_crc_cnt_reg3_rx_mac_partial1_invert_crc_cnt {
      type oc-yang:counter64;
      description
        "Counts the number of received packets with partial CRC type 1.";
    }
    leaf counter_slice1_ifg_mac_pool87_rx_mac_partial1_invert_crc_cnt_reg4_rx_mac_partial1_invert_crc_cnt {
      type oc-yang:counter64;
      description
        "Counts the number of received packets with partial CRC type 1.";
    }
    leaf counter_slice1_ifg_mac_pool87_rx_mac_partial1_invert_crc_cnt_reg5_rx_mac_partial1_invert_crc_cnt {
      type oc-yang:counter64;
      description
        "Counts the number of received packets with partial CRC type 1.";
    }
    leaf counter_slice1_ifg_mac_pool87_rx_mac_partial1_invert_crc_cnt_reg6_rx_mac_partial1_invert_crc_cnt {
      type oc-yang:counter64;
      description
        "Counts the number of received packets with partial CRC type 1.";
    }
    leaf counter_slice1_ifg_mac_pool87_rx_mac_partial1_invert_crc_cnt_reg7_rx_mac_partial1_invert_crc_cnt {
      type oc-yang:counter64;
      description
        "Counts the number of received packets with partial CRC type 1.";
    }
    leaf counter_slice2_ifg_mac_pool80_rx_mac_partial1_invert_crc_cnt_reg0_rx_mac_partial1_invert_crc_cnt {
      type oc-yang:counter64;
      description
        "Counts the number of received packets with partial CRC type 1.";
    }
    leaf counter_slice2_ifg_mac_pool80_rx_mac_partial1_invert_crc_cnt_reg1_rx_mac_partial1_invert_crc_cnt {
      type oc-yang:counter64;
      description
        "Counts the number of received packets with partial CRC type 1.";
    }
    leaf counter_slice2_ifg_mac_pool80_rx_mac_partial1_invert_crc_cnt_reg2_rx_mac_partial1_invert_crc_cnt {
      type oc-yang:counter64;
      description
        "Counts the number of received packets with partial CRC type 1.";
    }
    leaf counter_slice2_ifg_mac_pool80_rx_mac_partial1_invert_crc_cnt_reg3_rx_mac_partial1_invert_crc_cnt {
      type oc-yang:counter64;
      description
        "Counts the number of received packets with partial CRC type 1.";
    }
    leaf counter_slice2_ifg_mac_pool80_rx_mac_partial1_invert_crc_cnt_reg4_rx_mac_partial1_invert_crc_cnt {
      type oc-yang:counter64;
      description
        "Counts the number of received packets with partial CRC type 1.";
    }
    leaf counter_slice2_ifg_mac_pool80_rx_mac_partial1_invert_crc_cnt_reg5_rx_mac_partial1_invert_crc_cnt {
      type oc-yang:counter64;
      description
        "Counts the number of received packets with partial CRC type 1.";
    }
    leaf counter_slice2_ifg_mac_pool80_rx_mac_partial1_invert_crc_cnt_reg6_rx_mac_partial1_invert_crc_cnt {
      type oc-yang:counter64;
      description
        "Counts the number of received packets with partial CRC type 1.";
    }
    leaf counter_slice2_ifg_mac_pool80_rx_mac_partial1_invert_crc_cnt_reg7_rx_mac_partial1_invert_crc_cnt {
      type oc-yang:counter64;
      description
        "Counts the number of received packets with partial CRC type 1.";
    }
    leaf counter_slice2_ifg_mac_pool81_rx_mac_partial1_invert_crc_cnt_reg0_rx_mac_partial1_invert_crc_cnt {
      type oc-yang:counter64;
      description
        "Counts the number of received packets with partial CRC type 1.";
    }
    leaf counter_slice2_ifg_mac_pool81_rx_mac_partial1_invert_crc_cnt_reg1_rx_mac_partial1_invert_crc_cnt {
      type oc-yang:counter64;
      description
        "Counts the number of received packets with partial CRC type 1.";
    }
    leaf counter_slice2_ifg_mac_pool81_rx_mac_partial1_invert_crc_cnt_reg2_rx_mac_partial1_invert_crc_cnt {
      type oc-yang:counter64;
      description
        "Counts the number of received packets with partial CRC type 1.";
    }
    leaf counter_slice2_ifg_mac_pool81_rx_mac_partial1_invert_crc_cnt_reg3_rx_mac_partial1_invert_crc_cnt {
      type oc-yang:counter64;
      description
        "Counts the number of received packets with partial CRC type 1.";
    }
    leaf counter_slice2_ifg_mac_pool81_rx_mac_partial1_invert_crc_cnt_reg4_rx_mac_partial1_invert_crc_cnt {
      type oc-yang:counter64;
      description
        "Counts the number of received packets with partial CRC type 1.";
    }
    leaf counter_slice2_ifg_mac_pool81_rx_mac_partial1_invert_crc_cnt_reg5_rx_mac_partial1_invert_crc_cnt {
      type oc-yang:counter64;
      description
        "Counts the number of received packets with partial CRC type 1.";
    }
    leaf counter_slice2_ifg_mac_pool81_rx_mac_partial1_invert_crc_cnt_reg6_rx_mac_partial1_invert_crc_cnt {
      type oc-yang:counter64;
      description
        "Counts the number of received packets with partial CRC type 1.";
    }
    leaf counter_slice2_ifg_mac_pool81_rx_mac_partial1_invert_crc_cnt_reg7_rx_mac_partial1_invert_crc_cnt {
      type oc-yang:counter64;
      description
        "Counts the number of received packets with partial CRC type 1.";
    }
    leaf counter_slice2_ifg_mac_pool82_rx_mac_partial1_invert_crc_cnt_reg0_rx_mac_partial1_invert_crc_cnt {
      type oc-yang:counter64;
      description
        "Counts the number of received packets with partial CRC type 1.";
    }
    leaf counter_slice2_ifg_mac_pool82_rx_mac_partial1_invert_crc_cnt_reg1_rx_mac_partial1_invert_crc_cnt {
      type oc-yang:counter64;
      description
        "Counts the number of received packets with partial CRC type 1.";
    }
    leaf counter_slice2_ifg_mac_pool82_rx_mac_partial1_invert_crc_cnt_reg2_rx_mac_partial1_invert_crc_cnt {
      type oc-yang:counter64;
      description
        "Counts the number of received packets with partial CRC type 1.";
    }
    leaf counter_slice2_ifg_mac_pool82_rx_mac_partial1_invert_crc_cnt_reg3_rx_mac_partial1_invert_crc_cnt {
      type oc-yang:counter64;
      description
        "Counts the number of received packets with partial CRC type 1.";
    }
    leaf counter_slice2_ifg_mac_pool82_rx_mac_partial1_invert_crc_cnt_reg4_rx_mac_partial1_invert_crc_cnt {
      type oc-yang:counter64;
      description
        "Counts the number of received packets with partial CRC type 1.";
    }
    leaf counter_slice2_ifg_mac_pool82_rx_mac_partial1_invert_crc_cnt_reg5_rx_mac_partial1_invert_crc_cnt {
      type oc-yang:counter64;
      description
        "Counts the number of received packets with partial CRC type 1.";
    }
    leaf counter_slice2_ifg_mac_pool82_rx_mac_partial1_invert_crc_cnt_reg6_rx_mac_partial1_invert_crc_cnt {
      type oc-yang:counter64;
      description
        "Counts the number of received packets with partial CRC type 1.";
    }
    leaf counter_slice2_ifg_mac_pool82_rx_mac_partial1_invert_crc_cnt_reg7_rx_mac_partial1_invert_crc_cnt {
      type oc-yang:counter64;
      description
        "Counts the number of received packets with partial CRC type 1.";
    }
    leaf counter_slice2_ifg_mac_pool83_rx_mac_partial1_invert_crc_cnt_reg0_rx_mac_partial1_invert_crc_cnt {
      type oc-yang:counter64;
      description
        "Counts the number of received packets with partial CRC type 1.";
    }
    leaf counter_slice2_ifg_mac_pool83_rx_mac_partial1_invert_crc_cnt_reg1_rx_mac_partial1_invert_crc_cnt {
      type oc-yang:counter64;
      description
        "Counts the number of received packets with partial CRC type 1.";
    }
    leaf counter_slice2_ifg_mac_pool83_rx_mac_partial1_invert_crc_cnt_reg2_rx_mac_partial1_invert_crc_cnt {
      type oc-yang:counter64;
      description
        "Counts the number of received packets with partial CRC type 1.";
    }
    leaf counter_slice2_ifg_mac_pool83_rx_mac_partial1_invert_crc_cnt_reg3_rx_mac_partial1_invert_crc_cnt {
      type oc-yang:counter64;
      description
        "Counts the number of received packets with partial CRC type 1.";
    }
    leaf counter_slice2_ifg_mac_pool83_rx_mac_partial1_invert_crc_cnt_reg4_rx_mac_partial1_invert_crc_cnt {
      type oc-yang:counter64;
      description
        "Counts the number of received packets with partial CRC type 1.";
    }
    leaf counter_slice2_ifg_mac_pool83_rx_mac_partial1_invert_crc_cnt_reg5_rx_mac_partial1_invert_crc_cnt {
      type oc-yang:counter64;
      description
        "Counts the number of received packets with partial CRC type 1.";
    }
    leaf counter_slice2_ifg_mac_pool83_rx_mac_partial1_invert_crc_cnt_reg6_rx_mac_partial1_invert_crc_cnt {
      type oc-yang:counter64;
      description
        "Counts the number of received packets with partial CRC type 1.";
    }
    leaf counter_slice2_ifg_mac_pool83_rx_mac_partial1_invert_crc_cnt_reg7_rx_mac_partial1_invert_crc_cnt {
      type oc-yang:counter64;
      description
        "Counts the number of received packets with partial CRC type 1.";
    }
    leaf counter_slice2_ifg_mac_pool84_rx_mac_partial1_invert_crc_cnt_reg0_rx_mac_partial1_invert_crc_cnt {
      type oc-yang:counter64;
      description
        "Counts the number of received packets with partial CRC type 1.";
    }
    leaf counter_slice2_ifg_mac_pool84_rx_mac_partial1_invert_crc_cnt_reg1_rx_mac_partial1_invert_crc_cnt {
      type oc-yang:counter64;
      description
        "Counts the number of received packets with partial CRC type 1.";
    }
    leaf counter_slice2_ifg_mac_pool84_rx_mac_partial1_invert_crc_cnt_reg2_rx_mac_partial1_invert_crc_cnt {
      type oc-yang:counter64;
      description
        "Counts the number of received packets with partial CRC type 1.";
    }
    leaf counter_slice2_ifg_mac_pool84_rx_mac_partial1_invert_crc_cnt_reg3_rx_mac_partial1_invert_crc_cnt {
      type oc-yang:counter64;
      description
        "Counts the number of received packets with partial CRC type 1.";
    }
    leaf counter_slice2_ifg_mac_pool84_rx_mac_partial1_invert_crc_cnt_reg4_rx_mac_partial1_invert_crc_cnt {
      type oc-yang:counter64;
      description
        "Counts the number of received packets with partial CRC type 1.";
    }
    leaf counter_slice2_ifg_mac_pool84_rx_mac_partial1_invert_crc_cnt_reg5_rx_mac_partial1_invert_crc_cnt {
      type oc-yang:counter64;
      description
        "Counts the number of received packets with partial CRC type 1.";
    }
    leaf counter_slice2_ifg_mac_pool84_rx_mac_partial1_invert_crc_cnt_reg6_rx_mac_partial1_invert_crc_cnt {
      type oc-yang:counter64;
      description
        "Counts the number of received packets with partial CRC type 1.";
    }
    leaf counter_slice2_ifg_mac_pool84_rx_mac_partial1_invert_crc_cnt_reg7_rx_mac_partial1_invert_crc_cnt {
      type oc-yang:counter64;
      description
        "Counts the number of received packets with partial CRC type 1.";
    }
    leaf counter_slice2_ifg_mac_pool85_rx_mac_partial1_invert_crc_cnt_reg0_rx_mac_partial1_invert_crc_cnt {
      type oc-yang:counter64;
      description
        "Counts the number of received packets with partial CRC type 1.";
    }
    leaf counter_slice2_ifg_mac_pool85_rx_mac_partial1_invert_crc_cnt_reg1_rx_mac_partial1_invert_crc_cnt {
      type oc-yang:counter64;
      description
        "Counts the number of received packets with partial CRC type 1.";
    }
    leaf counter_slice2_ifg_mac_pool85_rx_mac_partial1_invert_crc_cnt_reg2_rx_mac_partial1_invert_crc_cnt {
      type oc-yang:counter64;
      description
        "Counts the number of received packets with partial CRC type 1.";
    }
    leaf counter_slice2_ifg_mac_pool85_rx_mac_partial1_invert_crc_cnt_reg3_rx_mac_partial1_invert_crc_cnt {
      type oc-yang:counter64;
      description
        "Counts the number of received packets with partial CRC type 1.";
    }
    leaf counter_slice2_ifg_mac_pool85_rx_mac_partial1_invert_crc_cnt_reg4_rx_mac_partial1_invert_crc_cnt {
      type oc-yang:counter64;
      description
        "Counts the number of received packets with partial CRC type 1.";
    }
    leaf counter_slice2_ifg_mac_pool85_rx_mac_partial1_invert_crc_cnt_reg5_rx_mac_partial1_invert_crc_cnt {
      type oc-yang:counter64;
      description
        "Counts the number of received packets with partial CRC type 1.";
    }
    leaf counter_slice2_ifg_mac_pool85_rx_mac_partial1_invert_crc_cnt_reg6_rx_mac_partial1_invert_crc_cnt {
      type oc-yang:counter64;
      description
        "Counts the number of received packets with partial CRC type 1.";
    }
    leaf counter_slice2_ifg_mac_pool85_rx_mac_partial1_invert_crc_cnt_reg7_rx_mac_partial1_invert_crc_cnt {
      type oc-yang:counter64;
      description
        "Counts the number of received packets with partial CRC type 1.";
    }
    leaf counter_slice2_ifg_mac_pool86_rx_mac_partial1_invert_crc_cnt_reg0_rx_mac_partial1_invert_crc_cnt {
      type oc-yang:counter64;
      description
        "Counts the number of received packets with partial CRC type 1.";
    }
    leaf counter_slice2_ifg_mac_pool86_rx_mac_partial1_invert_crc_cnt_reg1_rx_mac_partial1_invert_crc_cnt {
      type oc-yang:counter64;
      description
        "Counts the number of received packets with partial CRC type 1.";
    }
    leaf counter_slice2_ifg_mac_pool86_rx_mac_partial1_invert_crc_cnt_reg2_rx_mac_partial1_invert_crc_cnt {
      type oc-yang:counter64;
      description
        "Counts the number of received packets with partial CRC type 1.";
    }
    leaf counter_slice2_ifg_mac_pool86_rx_mac_partial1_invert_crc_cnt_reg3_rx_mac_partial1_invert_crc_cnt {
      type oc-yang:counter64;
      description
        "Counts the number of received packets with partial CRC type 1.";
    }
    leaf counter_slice2_ifg_mac_pool86_rx_mac_partial1_invert_crc_cnt_reg4_rx_mac_partial1_invert_crc_cnt {
      type oc-yang:counter64;
      description
        "Counts the number of received packets with partial CRC type 1.";
    }
    leaf counter_slice2_ifg_mac_pool86_rx_mac_partial1_invert_crc_cnt_reg5_rx_mac_partial1_invert_crc_cnt {
      type oc-yang:counter64;
      description
        "Counts the number of received packets with partial CRC type 1.";
    }
    leaf counter_slice2_ifg_mac_pool86_rx_mac_partial1_invert_crc_cnt_reg6_rx_mac_partial1_invert_crc_cnt {
      type oc-yang:counter64;
      description
        "Counts the number of received packets with partial CRC type 1.";
    }
    leaf counter_slice2_ifg_mac_pool86_rx_mac_partial1_invert_crc_cnt_reg7_rx_mac_partial1_invert_crc_cnt {
      type oc-yang:counter64;
      description
        "Counts the number of received packets with partial CRC type 1.";
    }
    leaf counter_slice2_ifg_mac_pool87_rx_mac_partial1_invert_crc_cnt_reg0_rx_mac_partial1_invert_crc_cnt {
      type oc-yang:counter64;
      description
        "Counts the number of received packets with partial CRC type 1.";
    }
    leaf counter_slice2_ifg_mac_pool87_rx_mac_partial1_invert_crc_cnt_reg1_rx_mac_partial1_invert_crc_cnt {
      type oc-yang:counter64;
      description
        "Counts the number of received packets with partial CRC type 1.";
    }
    leaf counter_slice2_ifg_mac_pool87_rx_mac_partial1_invert_crc_cnt_reg2_rx_mac_partial1_invert_crc_cnt {
      type oc-yang:counter64;
      description
        "Counts the number of received packets with partial CRC type 1.";
    }
    leaf counter_slice2_ifg_mac_pool87_rx_mac_partial1_invert_crc_cnt_reg3_rx_mac_partial1_invert_crc_cnt {
      type oc-yang:counter64;
      description
        "Counts the number of received packets with partial CRC type 1.";
    }
    leaf counter_slice2_ifg_mac_pool87_rx_mac_partial1_invert_crc_cnt_reg4_rx_mac_partial1_invert_crc_cnt {
      type oc-yang:counter64;
      description
        "Counts the number of received packets with partial CRC type 1.";
    }
    leaf counter_slice2_ifg_mac_pool87_rx_mac_partial1_invert_crc_cnt_reg5_rx_mac_partial1_invert_crc_cnt {
      type oc-yang:counter64;
      description
        "Counts the number of received packets with partial CRC type 1.";
    }
    leaf counter_slice2_ifg_mac_pool87_rx_mac_partial1_invert_crc_cnt_reg6_rx_mac_partial1_invert_crc_cnt {
      type oc-yang:counter64;
      description
        "Counts the number of received packets with partial CRC type 1.";
    }
    leaf counter_slice2_ifg_mac_pool87_rx_mac_partial1_invert_crc_cnt_reg7_rx_mac_partial1_invert_crc_cnt {
      type oc-yang:counter64;
      description
        "Counts the number of received packets with partial CRC type 1.";
    }
    leaf counter_slice3_ifg_mac_pool80_rx_mac_partial1_invert_crc_cnt_reg0_rx_mac_partial1_invert_crc_cnt {
      type oc-yang:counter64;
      description
        "Counts the number of received packets with partial CRC type 1.";
    }
    leaf counter_slice3_ifg_mac_pool80_rx_mac_partial1_invert_crc_cnt_reg1_rx_mac_partial1_invert_crc_cnt {
      type oc-yang:counter64;
      description
        "Counts the number of received packets with partial CRC type 1.";
    }
    leaf counter_slice3_ifg_mac_pool80_rx_mac_partial1_invert_crc_cnt_reg2_rx_mac_partial1_invert_crc_cnt {
      type oc-yang:counter64;
      description
        "Counts the number of received packets with partial CRC type 1.";
    }
    leaf counter_slice3_ifg_mac_pool80_rx_mac_partial1_invert_crc_cnt_reg3_rx_mac_partial1_invert_crc_cnt {
      type oc-yang:counter64;
      description
        "Counts the number of received packets with partial CRC type 1.";
    }
    leaf counter_slice3_ifg_mac_pool80_rx_mac_partial1_invert_crc_cnt_reg4_rx_mac_partial1_invert_crc_cnt {
      type oc-yang:counter64;
      description
        "Counts the number of received packets with partial CRC type 1.";
    }
    leaf counter_slice3_ifg_mac_pool80_rx_mac_partial1_invert_crc_cnt_reg5_rx_mac_partial1_invert_crc_cnt {
      type oc-yang:counter64;
      description
        "Counts the number of received packets with partial CRC type 1.";
    }
    leaf counter_slice3_ifg_mac_pool80_rx_mac_partial1_invert_crc_cnt_reg6_rx_mac_partial1_invert_crc_cnt {
      type oc-yang:counter64;
      description
        "Counts the number of received packets with partial CRC type 1.";
    }
    leaf counter_slice3_ifg_mac_pool80_rx_mac_partial1_invert_crc_cnt_reg7_rx_mac_partial1_invert_crc_cnt {
      type oc-yang:counter64;
      description
        "Counts the number of received packets with partial CRC type 1.";
    }
    leaf counter_slice3_ifg_mac_pool81_rx_mac_partial1_invert_crc_cnt_reg0_rx_mac_partial1_invert_crc_cnt {
      type oc-yang:counter64;
      description
        "Counts the number of received packets with partial CRC type 1.";
    }
    leaf counter_slice3_ifg_mac_pool81_rx_mac_partial1_invert_crc_cnt_reg1_rx_mac_partial1_invert_crc_cnt {
      type oc-yang:counter64;
      description
        "Counts the number of received packets with partial CRC type 1.";
    }
    leaf counter_slice3_ifg_mac_pool81_rx_mac_partial1_invert_crc_cnt_reg2_rx_mac_partial1_invert_crc_cnt {
      type oc-yang:counter64;
      description
        "Counts the number of received packets with partial CRC type 1.";
    }
    leaf counter_slice3_ifg_mac_pool81_rx_mac_partial1_invert_crc_cnt_reg3_rx_mac_partial1_invert_crc_cnt {
      type oc-yang:counter64;
      description
        "Counts the number of received packets with partial CRC type 1.";
    }
    leaf counter_slice3_ifg_mac_pool81_rx_mac_partial1_invert_crc_cnt_reg4_rx_mac_partial1_invert_crc_cnt {
      type oc-yang:counter64;
      description
        "Counts the number of received packets with partial CRC type 1.";
    }
    leaf counter_slice3_ifg_mac_pool81_rx_mac_partial1_invert_crc_cnt_reg5_rx_mac_partial1_invert_crc_cnt {
      type oc-yang:counter64;
      description
        "Counts the number of received packets with partial CRC type 1.";
    }
    leaf counter_slice3_ifg_mac_pool81_rx_mac_partial1_invert_crc_cnt_reg6_rx_mac_partial1_invert_crc_cnt {
      type oc-yang:counter64;
      description
        "Counts the number of received packets with partial CRC type 1.";
    }
    leaf counter_slice3_ifg_mac_pool81_rx_mac_partial1_invert_crc_cnt_reg7_rx_mac_partial1_invert_crc_cnt {
      type oc-yang:counter64;
      description
        "Counts the number of received packets with partial CRC type 1.";
    }
    leaf counter_slice3_ifg_mac_pool82_rx_mac_partial1_invert_crc_cnt_reg0_rx_mac_partial1_invert_crc_cnt {
      type oc-yang:counter64;
      description
        "Counts the number of received packets with partial CRC type 1.";
    }
    leaf counter_slice3_ifg_mac_pool82_rx_mac_partial1_invert_crc_cnt_reg1_rx_mac_partial1_invert_crc_cnt {
      type oc-yang:counter64;
      description
        "Counts the number of received packets with partial CRC type 1.";
    }
    leaf counter_slice3_ifg_mac_pool82_rx_mac_partial1_invert_crc_cnt_reg2_rx_mac_partial1_invert_crc_cnt {
      type oc-yang:counter64;
      description
        "Counts the number of received packets with partial CRC type 1.";
    }
    leaf counter_slice3_ifg_mac_pool82_rx_mac_partial1_invert_crc_cnt_reg3_rx_mac_partial1_invert_crc_cnt {
      type oc-yang:counter64;
      description
        "Counts the number of received packets with partial CRC type 1.";
    }
    leaf counter_slice3_ifg_mac_pool82_rx_mac_partial1_invert_crc_cnt_reg4_rx_mac_partial1_invert_crc_cnt {
      type oc-yang:counter64;
      description
        "Counts the number of received packets with partial CRC type 1.";
    }
    leaf counter_slice3_ifg_mac_pool82_rx_mac_partial1_invert_crc_cnt_reg5_rx_mac_partial1_invert_crc_cnt {
      type oc-yang:counter64;
      description
        "Counts the number of received packets with partial CRC type 1.";
    }
    leaf counter_slice3_ifg_mac_pool82_rx_mac_partial1_invert_crc_cnt_reg6_rx_mac_partial1_invert_crc_cnt {
      type oc-yang:counter64;
      description
        "Counts the number of received packets with partial CRC type 1.";
    }
    leaf counter_slice3_ifg_mac_pool82_rx_mac_partial1_invert_crc_cnt_reg7_rx_mac_partial1_invert_crc_cnt {
      type oc-yang:counter64;
      description
        "Counts the number of received packets with partial CRC type 1.";
    }
    leaf counter_slice3_ifg_mac_pool83_rx_mac_partial1_invert_crc_cnt_reg0_rx_mac_partial1_invert_crc_cnt {
      type oc-yang:counter64;
      description
        "Counts the number of received packets with partial CRC type 1.";
    }
    leaf counter_slice3_ifg_mac_pool83_rx_mac_partial1_invert_crc_cnt_reg1_rx_mac_partial1_invert_crc_cnt {
      type oc-yang:counter64;
      description
        "Counts the number of received packets with partial CRC type 1.";
    }
    leaf counter_slice3_ifg_mac_pool83_rx_mac_partial1_invert_crc_cnt_reg2_rx_mac_partial1_invert_crc_cnt {
      type oc-yang:counter64;
      description
        "Counts the number of received packets with partial CRC type 1.";
    }
    leaf counter_slice3_ifg_mac_pool83_rx_mac_partial1_invert_crc_cnt_reg3_rx_mac_partial1_invert_crc_cnt {
      type oc-yang:counter64;
      description
        "Counts the number of received packets with partial CRC type 1.";
    }
    leaf counter_slice3_ifg_mac_pool83_rx_mac_partial1_invert_crc_cnt_reg4_rx_mac_partial1_invert_crc_cnt {
      type oc-yang:counter64;
      description
        "Counts the number of received packets with partial CRC type 1.";
    }
    leaf counter_slice3_ifg_mac_pool83_rx_mac_partial1_invert_crc_cnt_reg5_rx_mac_partial1_invert_crc_cnt {
      type oc-yang:counter64;
      description
        "Counts the number of received packets with partial CRC type 1.";
    }
    leaf counter_slice3_ifg_mac_pool83_rx_mac_partial1_invert_crc_cnt_reg6_rx_mac_partial1_invert_crc_cnt {
      type oc-yang:counter64;
      description
        "Counts the number of received packets with partial CRC type 1.";
    }
    leaf counter_slice3_ifg_mac_pool83_rx_mac_partial1_invert_crc_cnt_reg7_rx_mac_partial1_invert_crc_cnt {
      type oc-yang:counter64;
      description
        "Counts the number of received packets with partial CRC type 1.";
    }
    leaf counter_slice3_ifg_mac_pool84_rx_mac_partial1_invert_crc_cnt_reg0_rx_mac_partial1_invert_crc_cnt {
      type oc-yang:counter64;
      description
        "Counts the number of received packets with partial CRC type 1.";
    }
    leaf counter_slice3_ifg_mac_pool84_rx_mac_partial1_invert_crc_cnt_reg1_rx_mac_partial1_invert_crc_cnt {
      type oc-yang:counter64;
      description
        "Counts the number of received packets with partial CRC type 1.";
    }
    leaf counter_slice3_ifg_mac_pool84_rx_mac_partial1_invert_crc_cnt_reg2_rx_mac_partial1_invert_crc_cnt {
      type oc-yang:counter64;
      description
        "Counts the number of received packets with partial CRC type 1.";
    }
    leaf counter_slice3_ifg_mac_pool84_rx_mac_partial1_invert_crc_cnt_reg3_rx_mac_partial1_invert_crc_cnt {
      type oc-yang:counter64;
      description
        "Counts the number of received packets with partial CRC type 1.";
    }
    leaf counter_slice3_ifg_mac_pool84_rx_mac_partial1_invert_crc_cnt_reg4_rx_mac_partial1_invert_crc_cnt {
      type oc-yang:counter64;
      description
        "Counts the number of received packets with partial CRC type 1.";
    }
    leaf counter_slice3_ifg_mac_pool84_rx_mac_partial1_invert_crc_cnt_reg5_rx_mac_partial1_invert_crc_cnt {
      type oc-yang:counter64;
      description
        "Counts the number of received packets with partial CRC type 1.";
    }
    leaf counter_slice3_ifg_mac_pool84_rx_mac_partial1_invert_crc_cnt_reg6_rx_mac_partial1_invert_crc_cnt {
      type oc-yang:counter64;
      description
        "Counts the number of received packets with partial CRC type 1.";
    }
    leaf counter_slice3_ifg_mac_pool84_rx_mac_partial1_invert_crc_cnt_reg7_rx_mac_partial1_invert_crc_cnt {
      type oc-yang:counter64;
      description
        "Counts the number of received packets with partial CRC type 1.";
    }
    leaf counter_slice3_ifg_mac_pool85_rx_mac_partial1_invert_crc_cnt_reg0_rx_mac_partial1_invert_crc_cnt {
      type oc-yang:counter64;
      description
        "Counts the number of received packets with partial CRC type 1.";
    }
    leaf counter_slice3_ifg_mac_pool85_rx_mac_partial1_invert_crc_cnt_reg1_rx_mac_partial1_invert_crc_cnt {
      type oc-yang:counter64;
      description
        "Counts the number of received packets with partial CRC type 1.";
    }
    leaf counter_slice3_ifg_mac_pool85_rx_mac_partial1_invert_crc_cnt_reg2_rx_mac_partial1_invert_crc_cnt {
      type oc-yang:counter64;
      description
        "Counts the number of received packets with partial CRC type 1.";
    }
    leaf counter_slice3_ifg_mac_pool85_rx_mac_partial1_invert_crc_cnt_reg3_rx_mac_partial1_invert_crc_cnt {
      type oc-yang:counter64;
      description
        "Counts the number of received packets with partial CRC type 1.";
    }
    leaf counter_slice3_ifg_mac_pool85_rx_mac_partial1_invert_crc_cnt_reg4_rx_mac_partial1_invert_crc_cnt {
      type oc-yang:counter64;
      description
        "Counts the number of received packets with partial CRC type 1.";
    }
    leaf counter_slice3_ifg_mac_pool85_rx_mac_partial1_invert_crc_cnt_reg5_rx_mac_partial1_invert_crc_cnt {
      type oc-yang:counter64;
      description
        "Counts the number of received packets with partial CRC type 1.";
    }
    leaf counter_slice3_ifg_mac_pool85_rx_mac_partial1_invert_crc_cnt_reg6_rx_mac_partial1_invert_crc_cnt {
      type oc-yang:counter64;
      description
        "Counts the number of received packets with partial CRC type 1.";
    }
    leaf counter_slice3_ifg_mac_pool85_rx_mac_partial1_invert_crc_cnt_reg7_rx_mac_partial1_invert_crc_cnt {
      type oc-yang:counter64;
      description
        "Counts the number of received packets with partial CRC type 1.";
    }
    leaf counter_slice3_ifg_mac_pool86_rx_mac_partial1_invert_crc_cnt_reg0_rx_mac_partial1_invert_crc_cnt {
      type oc-yang:counter64;
      description
        "Counts the number of received packets with partial CRC type 1.";
    }
    leaf counter_slice3_ifg_mac_pool86_rx_mac_partial1_invert_crc_cnt_reg1_rx_mac_partial1_invert_crc_cnt {
      type oc-yang:counter64;
      description
        "Counts the number of received packets with partial CRC type 1.";
    }
    leaf counter_slice3_ifg_mac_pool86_rx_mac_partial1_invert_crc_cnt_reg2_rx_mac_partial1_invert_crc_cnt {
      type oc-yang:counter64;
      description
        "Counts the number of received packets with partial CRC type 1.";
    }
    leaf counter_slice3_ifg_mac_pool86_rx_mac_partial1_invert_crc_cnt_reg3_rx_mac_partial1_invert_crc_cnt {
      type oc-yang:counter64;
      description
        "Counts the number of received packets with partial CRC type 1.";
    }
    leaf counter_slice3_ifg_mac_pool86_rx_mac_partial1_invert_crc_cnt_reg4_rx_mac_partial1_invert_crc_cnt {
      type oc-yang:counter64;
      description
        "Counts the number of received packets with partial CRC type 1.";
    }
    leaf counter_slice3_ifg_mac_pool86_rx_mac_partial1_invert_crc_cnt_reg5_rx_mac_partial1_invert_crc_cnt {
      type oc-yang:counter64;
      description
        "Counts the number of received packets with partial CRC type 1.";
    }
    leaf counter_slice3_ifg_mac_pool86_rx_mac_partial1_invert_crc_cnt_reg6_rx_mac_partial1_invert_crc_cnt {
      type oc-yang:counter64;
      description
        "Counts the number of received packets with partial CRC type 1.";
    }
    leaf counter_slice3_ifg_mac_pool86_rx_mac_partial1_invert_crc_cnt_reg7_rx_mac_partial1_invert_crc_cnt {
      type oc-yang:counter64;
      description
        "Counts the number of received packets with partial CRC type 1.";
    }
    leaf counter_slice3_ifg_mac_pool87_rx_mac_partial1_invert_crc_cnt_reg0_rx_mac_partial1_invert_crc_cnt {
      type oc-yang:counter64;
      description
        "Counts the number of received packets with partial CRC type 1.";
    }
    leaf counter_slice3_ifg_mac_pool87_rx_mac_partial1_invert_crc_cnt_reg1_rx_mac_partial1_invert_crc_cnt {
      type oc-yang:counter64;
      description
        "Counts the number of received packets with partial CRC type 1.";
    }
    leaf counter_slice3_ifg_mac_pool87_rx_mac_partial1_invert_crc_cnt_reg2_rx_mac_partial1_invert_crc_cnt {
      type oc-yang:counter64;
      description
        "Counts the number of received packets with partial CRC type 1.";
    }
    leaf counter_slice3_ifg_mac_pool87_rx_mac_partial1_invert_crc_cnt_reg3_rx_mac_partial1_invert_crc_cnt {
      type oc-yang:counter64;
      description
        "Counts the number of received packets with partial CRC type 1.";
    }
    leaf counter_slice3_ifg_mac_pool87_rx_mac_partial1_invert_crc_cnt_reg4_rx_mac_partial1_invert_crc_cnt {
      type oc-yang:counter64;
      description
        "Counts the number of received packets with partial CRC type 1.";
    }
    leaf counter_slice3_ifg_mac_pool87_rx_mac_partial1_invert_crc_cnt_reg5_rx_mac_partial1_invert_crc_cnt {
      type oc-yang:counter64;
      description
        "Counts the number of received packets with partial CRC type 1.";
    }
    leaf counter_slice3_ifg_mac_pool87_rx_mac_partial1_invert_crc_cnt_reg6_rx_mac_partial1_invert_crc_cnt {
      type oc-yang:counter64;
      description
        "Counts the number of received packets with partial CRC type 1.";
    }
    leaf counter_slice3_ifg_mac_pool87_rx_mac_partial1_invert_crc_cnt_reg7_rx_mac_partial1_invert_crc_cnt {
      type oc-yang:counter64;
      description
        "Counts the number of received packets with partial CRC type 1.";
    }
    leaf counter_slice4_ifg_mac_pool80_rx_mac_partial1_invert_crc_cnt_reg0_rx_mac_partial1_invert_crc_cnt {
      type oc-yang:counter64;
      description
        "Counts the number of received packets with partial CRC type 1.";
    }
    leaf counter_slice4_ifg_mac_pool80_rx_mac_partial1_invert_crc_cnt_reg1_rx_mac_partial1_invert_crc_cnt {
      type oc-yang:counter64;
      description
        "Counts the number of received packets with partial CRC type 1.";
    }
    leaf counter_slice4_ifg_mac_pool80_rx_mac_partial1_invert_crc_cnt_reg2_rx_mac_partial1_invert_crc_cnt {
      type oc-yang:counter64;
      description
        "Counts the number of received packets with partial CRC type 1.";
    }
    leaf counter_slice4_ifg_mac_pool80_rx_mac_partial1_invert_crc_cnt_reg3_rx_mac_partial1_invert_crc_cnt {
      type oc-yang:counter64;
      description
        "Counts the number of received packets with partial CRC type 1.";
    }
    leaf counter_slice4_ifg_mac_pool80_rx_mac_partial1_invert_crc_cnt_reg4_rx_mac_partial1_invert_crc_cnt {
      type oc-yang:counter64;
      description
        "Counts the number of received packets with partial CRC type 1.";
    }
    leaf counter_slice4_ifg_mac_pool80_rx_mac_partial1_invert_crc_cnt_reg5_rx_mac_partial1_invert_crc_cnt {
      type oc-yang:counter64;
      description
        "Counts the number of received packets with partial CRC type 1.";
    }
    leaf counter_slice4_ifg_mac_pool80_rx_mac_partial1_invert_crc_cnt_reg6_rx_mac_partial1_invert_crc_cnt {
      type oc-yang:counter64;
      description
        "Counts the number of received packets with partial CRC type 1.";
    }
    leaf counter_slice4_ifg_mac_pool80_rx_mac_partial1_invert_crc_cnt_reg7_rx_mac_partial1_invert_crc_cnt {
      type oc-yang:counter64;
      description
        "Counts the number of received packets with partial CRC type 1.";
    }
    leaf counter_slice4_ifg_mac_pool81_rx_mac_partial1_invert_crc_cnt_reg0_rx_mac_partial1_invert_crc_cnt {
      type oc-yang:counter64;
      description
        "Counts the number of received packets with partial CRC type 1.";
    }
    leaf counter_slice4_ifg_mac_pool81_rx_mac_partial1_invert_crc_cnt_reg1_rx_mac_partial1_invert_crc_cnt {
      type oc-yang:counter64;
      description
        "Counts the number of received packets with partial CRC type 1.";
    }
    leaf counter_slice4_ifg_mac_pool81_rx_mac_partial1_invert_crc_cnt_reg2_rx_mac_partial1_invert_crc_cnt {
      type oc-yang:counter64;
      description
        "Counts the number of received packets with partial CRC type 1.";
    }
    leaf counter_slice4_ifg_mac_pool81_rx_mac_partial1_invert_crc_cnt_reg3_rx_mac_partial1_invert_crc_cnt {
      type oc-yang:counter64;
      description
        "Counts the number of received packets with partial CRC type 1.";
    }
    leaf counter_slice4_ifg_mac_pool81_rx_mac_partial1_invert_crc_cnt_reg4_rx_mac_partial1_invert_crc_cnt {
      type oc-yang:counter64;
      description
        "Counts the number of received packets with partial CRC type 1.";
    }
    leaf counter_slice4_ifg_mac_pool81_rx_mac_partial1_invert_crc_cnt_reg5_rx_mac_partial1_invert_crc_cnt {
      type oc-yang:counter64;
      description
        "Counts the number of received packets with partial CRC type 1.";
    }
    leaf counter_slice4_ifg_mac_pool81_rx_mac_partial1_invert_crc_cnt_reg6_rx_mac_partial1_invert_crc_cnt {
      type oc-yang:counter64;
      description
        "Counts the number of received packets with partial CRC type 1.";
    }
    leaf counter_slice4_ifg_mac_pool81_rx_mac_partial1_invert_crc_cnt_reg7_rx_mac_partial1_invert_crc_cnt {
      type oc-yang:counter64;
      description
        "Counts the number of received packets with partial CRC type 1.";
    }
    leaf counter_slice4_ifg_mac_pool82_rx_mac_partial1_invert_crc_cnt_reg0_rx_mac_partial1_invert_crc_cnt {
      type oc-yang:counter64;
      description
        "Counts the number of received packets with partial CRC type 1.";
    }
    leaf counter_slice4_ifg_mac_pool82_rx_mac_partial1_invert_crc_cnt_reg1_rx_mac_partial1_invert_crc_cnt {
      type oc-yang:counter64;
      description
        "Counts the number of received packets with partial CRC type 1.";
    }
    leaf counter_slice4_ifg_mac_pool82_rx_mac_partial1_invert_crc_cnt_reg2_rx_mac_partial1_invert_crc_cnt {
      type oc-yang:counter64;
      description
        "Counts the number of received packets with partial CRC type 1.";
    }
    leaf counter_slice4_ifg_mac_pool82_rx_mac_partial1_invert_crc_cnt_reg3_rx_mac_partial1_invert_crc_cnt {
      type oc-yang:counter64;
      description
        "Counts the number of received packets with partial CRC type 1.";
    }
    leaf counter_slice4_ifg_mac_pool82_rx_mac_partial1_invert_crc_cnt_reg4_rx_mac_partial1_invert_crc_cnt {
      type oc-yang:counter64;
      description
        "Counts the number of received packets with partial CRC type 1.";
    }
    leaf counter_slice4_ifg_mac_pool82_rx_mac_partial1_invert_crc_cnt_reg5_rx_mac_partial1_invert_crc_cnt {
      type oc-yang:counter64;
      description
        "Counts the number of received packets with partial CRC type 1.";
    }
    leaf counter_slice4_ifg_mac_pool82_rx_mac_partial1_invert_crc_cnt_reg6_rx_mac_partial1_invert_crc_cnt {
      type oc-yang:counter64;
      description
        "Counts the number of received packets with partial CRC type 1.";
    }
    leaf counter_slice4_ifg_mac_pool82_rx_mac_partial1_invert_crc_cnt_reg7_rx_mac_partial1_invert_crc_cnt {
      type oc-yang:counter64;
      description
        "Counts the number of received packets with partial CRC type 1.";
    }
    leaf counter_slice4_ifg_mac_pool83_rx_mac_partial1_invert_crc_cnt_reg0_rx_mac_partial1_invert_crc_cnt {
      type oc-yang:counter64;
      description
        "Counts the number of received packets with partial CRC type 1.";
    }
    leaf counter_slice4_ifg_mac_pool83_rx_mac_partial1_invert_crc_cnt_reg1_rx_mac_partial1_invert_crc_cnt {
      type oc-yang:counter64;
      description
        "Counts the number of received packets with partial CRC type 1.";
    }
    leaf counter_slice4_ifg_mac_pool83_rx_mac_partial1_invert_crc_cnt_reg2_rx_mac_partial1_invert_crc_cnt {
      type oc-yang:counter64;
      description
        "Counts the number of received packets with partial CRC type 1.";
    }
    leaf counter_slice4_ifg_mac_pool83_rx_mac_partial1_invert_crc_cnt_reg3_rx_mac_partial1_invert_crc_cnt {
      type oc-yang:counter64;
      description
        "Counts the number of received packets with partial CRC type 1.";
    }
    leaf counter_slice4_ifg_mac_pool83_rx_mac_partial1_invert_crc_cnt_reg4_rx_mac_partial1_invert_crc_cnt {
      type oc-yang:counter64;
      description
        "Counts the number of received packets with partial CRC type 1.";
    }
    leaf counter_slice4_ifg_mac_pool83_rx_mac_partial1_invert_crc_cnt_reg5_rx_mac_partial1_invert_crc_cnt {
      type oc-yang:counter64;
      description
        "Counts the number of received packets with partial CRC type 1.";
    }
    leaf counter_slice4_ifg_mac_pool83_rx_mac_partial1_invert_crc_cnt_reg6_rx_mac_partial1_invert_crc_cnt {
      type oc-yang:counter64;
      description
        "Counts the number of received packets with partial CRC type 1.";
    }
    leaf counter_slice4_ifg_mac_pool83_rx_mac_partial1_invert_crc_cnt_reg7_rx_mac_partial1_invert_crc_cnt {
      type oc-yang:counter64;
      description
        "Counts the number of received packets with partial CRC type 1.";
    }
    leaf counter_slice4_ifg_mac_pool84_rx_mac_partial1_invert_crc_cnt_reg0_rx_mac_partial1_invert_crc_cnt {
      type oc-yang:counter64;
      description
        "Counts the number of received packets with partial CRC type 1.";
    }
    leaf counter_slice4_ifg_mac_pool84_rx_mac_partial1_invert_crc_cnt_reg1_rx_mac_partial1_invert_crc_cnt {
      type oc-yang:counter64;
      description
        "Counts the number of received packets with partial CRC type 1.";
    }
    leaf counter_slice4_ifg_mac_pool84_rx_mac_partial1_invert_crc_cnt_reg2_rx_mac_partial1_invert_crc_cnt {
      type oc-yang:counter64;
      description
        "Counts the number of received packets with partial CRC type 1.";
    }
    leaf counter_slice4_ifg_mac_pool84_rx_mac_partial1_invert_crc_cnt_reg3_rx_mac_partial1_invert_crc_cnt {
      type oc-yang:counter64;
      description
        "Counts the number of received packets with partial CRC type 1.";
    }
    leaf counter_slice4_ifg_mac_pool84_rx_mac_partial1_invert_crc_cnt_reg4_rx_mac_partial1_invert_crc_cnt {
      type oc-yang:counter64;
      description
        "Counts the number of received packets with partial CRC type 1.";
    }
    leaf counter_slice4_ifg_mac_pool84_rx_mac_partial1_invert_crc_cnt_reg5_rx_mac_partial1_invert_crc_cnt {
      type oc-yang:counter64;
      description
        "Counts the number of received packets with partial CRC type 1.";
    }
    leaf counter_slice4_ifg_mac_pool84_rx_mac_partial1_invert_crc_cnt_reg6_rx_mac_partial1_invert_crc_cnt {
      type oc-yang:counter64;
      description
        "Counts the number of received packets with partial CRC type 1.";
    }
    leaf counter_slice4_ifg_mac_pool84_rx_mac_partial1_invert_crc_cnt_reg7_rx_mac_partial1_invert_crc_cnt {
      type oc-yang:counter64;
      description
        "Counts the number of received packets with partial CRC type 1.";
    }
    leaf counter_slice4_ifg_mac_pool85_rx_mac_partial1_invert_crc_cnt_reg0_rx_mac_partial1_invert_crc_cnt {
      type oc-yang:counter64;
      description
        "Counts the number of received packets with partial CRC type 1.";
    }
    leaf counter_slice4_ifg_mac_pool85_rx_mac_partial1_invert_crc_cnt_reg1_rx_mac_partial1_invert_crc_cnt {
      type oc-yang:counter64;
      description
        "Counts the number of received packets with partial CRC type 1.";
    }
    leaf counter_slice4_ifg_mac_pool85_rx_mac_partial1_invert_crc_cnt_reg2_rx_mac_partial1_invert_crc_cnt {
      type oc-yang:counter64;
      description
        "Counts the number of received packets with partial CRC type 1.";
    }
    leaf counter_slice4_ifg_mac_pool85_rx_mac_partial1_invert_crc_cnt_reg3_rx_mac_partial1_invert_crc_cnt {
      type oc-yang:counter64;
      description
        "Counts the number of received packets with partial CRC type 1.";
    }
    leaf counter_slice4_ifg_mac_pool85_rx_mac_partial1_invert_crc_cnt_reg4_rx_mac_partial1_invert_crc_cnt {
      type oc-yang:counter64;
      description
        "Counts the number of received packets with partial CRC type 1.";
    }
    leaf counter_slice4_ifg_mac_pool85_rx_mac_partial1_invert_crc_cnt_reg5_rx_mac_partial1_invert_crc_cnt {
      type oc-yang:counter64;
      description
        "Counts the number of received packets with partial CRC type 1.";
    }
    leaf counter_slice4_ifg_mac_pool85_rx_mac_partial1_invert_crc_cnt_reg6_rx_mac_partial1_invert_crc_cnt {
      type oc-yang:counter64;
      description
        "Counts the number of received packets with partial CRC type 1.";
    }
    leaf counter_slice4_ifg_mac_pool85_rx_mac_partial1_invert_crc_cnt_reg7_rx_mac_partial1_invert_crc_cnt {
      type oc-yang:counter64;
      description
        "Counts the number of received packets with partial CRC type 1.";
    }
    leaf counter_slice4_ifg_mac_pool86_rx_mac_partial1_invert_crc_cnt_reg0_rx_mac_partial1_invert_crc_cnt {
      type oc-yang:counter64;
      description
        "Counts the number of received packets with partial CRC type 1.";
    }
    leaf counter_slice4_ifg_mac_pool86_rx_mac_partial1_invert_crc_cnt_reg1_rx_mac_partial1_invert_crc_cnt {
      type oc-yang:counter64;
      description
        "Counts the number of received packets with partial CRC type 1.";
    }
    leaf counter_slice4_ifg_mac_pool86_rx_mac_partial1_invert_crc_cnt_reg2_rx_mac_partial1_invert_crc_cnt {
      type oc-yang:counter64;
      description
        "Counts the number of received packets with partial CRC type 1.";
    }
    leaf counter_slice4_ifg_mac_pool86_rx_mac_partial1_invert_crc_cnt_reg3_rx_mac_partial1_invert_crc_cnt {
      type oc-yang:counter64;
      description
        "Counts the number of received packets with partial CRC type 1.";
    }
    leaf counter_slice4_ifg_mac_pool86_rx_mac_partial1_invert_crc_cnt_reg4_rx_mac_partial1_invert_crc_cnt {
      type oc-yang:counter64;
      description
        "Counts the number of received packets with partial CRC type 1.";
    }
    leaf counter_slice4_ifg_mac_pool86_rx_mac_partial1_invert_crc_cnt_reg5_rx_mac_partial1_invert_crc_cnt {
      type oc-yang:counter64;
      description
        "Counts the number of received packets with partial CRC type 1.";
    }
    leaf counter_slice4_ifg_mac_pool86_rx_mac_partial1_invert_crc_cnt_reg6_rx_mac_partial1_invert_crc_cnt {
      type oc-yang:counter64;
      description
        "Counts the number of received packets with partial CRC type 1.";
    }
    leaf counter_slice4_ifg_mac_pool86_rx_mac_partial1_invert_crc_cnt_reg7_rx_mac_partial1_invert_crc_cnt {
      type oc-yang:counter64;
      description
        "Counts the number of received packets with partial CRC type 1.";
    }
    leaf counter_slice4_ifg_mac_pool87_rx_mac_partial1_invert_crc_cnt_reg0_rx_mac_partial1_invert_crc_cnt {
      type oc-yang:counter64;
      description
        "Counts the number of received packets with partial CRC type 1.";
    }
    leaf counter_slice4_ifg_mac_pool87_rx_mac_partial1_invert_crc_cnt_reg1_rx_mac_partial1_invert_crc_cnt {
      type oc-yang:counter64;
      description
        "Counts the number of received packets with partial CRC type 1.";
    }
    leaf counter_slice4_ifg_mac_pool87_rx_mac_partial1_invert_crc_cnt_reg2_rx_mac_partial1_invert_crc_cnt {
      type oc-yang:counter64;
      description
        "Counts the number of received packets with partial CRC type 1.";
    }
    leaf counter_slice4_ifg_mac_pool87_rx_mac_partial1_invert_crc_cnt_reg3_rx_mac_partial1_invert_crc_cnt {
      type oc-yang:counter64;
      description
        "Counts the number of received packets with partial CRC type 1.";
    }
    leaf counter_slice4_ifg_mac_pool87_rx_mac_partial1_invert_crc_cnt_reg4_rx_mac_partial1_invert_crc_cnt {
      type oc-yang:counter64;
      description
        "Counts the number of received packets with partial CRC type 1.";
    }
    leaf counter_slice4_ifg_mac_pool87_rx_mac_partial1_invert_crc_cnt_reg5_rx_mac_partial1_invert_crc_cnt {
      type oc-yang:counter64;
      description
        "Counts the number of received packets with partial CRC type 1.";
    }
    leaf counter_slice4_ifg_mac_pool87_rx_mac_partial1_invert_crc_cnt_reg6_rx_mac_partial1_invert_crc_cnt {
      type oc-yang:counter64;
      description
        "Counts the number of received packets with partial CRC type 1.";
    }
    leaf counter_slice4_ifg_mac_pool87_rx_mac_partial1_invert_crc_cnt_reg7_rx_mac_partial1_invert_crc_cnt {
      type oc-yang:counter64;
      description
        "Counts the number of received packets with partial CRC type 1.";
    }
    leaf counter_slice5_ifg_mac_pool80_rx_mac_partial1_invert_crc_cnt_reg0_rx_mac_partial1_invert_crc_cnt {
      type oc-yang:counter64;
      description
        "Counts the number of received packets with partial CRC type 1.";
    }
    leaf counter_slice5_ifg_mac_pool80_rx_mac_partial1_invert_crc_cnt_reg1_rx_mac_partial1_invert_crc_cnt {
      type oc-yang:counter64;
      description
        "Counts the number of received packets with partial CRC type 1.";
    }
    leaf counter_slice5_ifg_mac_pool80_rx_mac_partial1_invert_crc_cnt_reg2_rx_mac_partial1_invert_crc_cnt {
      type oc-yang:counter64;
      description
        "Counts the number of received packets with partial CRC type 1.";
    }
    leaf counter_slice5_ifg_mac_pool80_rx_mac_partial1_invert_crc_cnt_reg3_rx_mac_partial1_invert_crc_cnt {
      type oc-yang:counter64;
      description
        "Counts the number of received packets with partial CRC type 1.";
    }
    leaf counter_slice5_ifg_mac_pool80_rx_mac_partial1_invert_crc_cnt_reg4_rx_mac_partial1_invert_crc_cnt {
      type oc-yang:counter64;
      description
        "Counts the number of received packets with partial CRC type 1.";
    }
    leaf counter_slice5_ifg_mac_pool80_rx_mac_partial1_invert_crc_cnt_reg5_rx_mac_partial1_invert_crc_cnt {
      type oc-yang:counter64;
      description
        "Counts the number of received packets with partial CRC type 1.";
    }
    leaf counter_slice5_ifg_mac_pool80_rx_mac_partial1_invert_crc_cnt_reg6_rx_mac_partial1_invert_crc_cnt {
      type oc-yang:counter64;
      description
        "Counts the number of received packets with partial CRC type 1.";
    }
    leaf counter_slice5_ifg_mac_pool80_rx_mac_partial1_invert_crc_cnt_reg7_rx_mac_partial1_invert_crc_cnt {
      type oc-yang:counter64;
      description
        "Counts the number of received packets with partial CRC type 1.";
    }
    leaf counter_slice5_ifg_mac_pool81_rx_mac_partial1_invert_crc_cnt_reg0_rx_mac_partial1_invert_crc_cnt {
      type oc-yang:counter64;
      description
        "Counts the number of received packets with partial CRC type 1.";
    }
    leaf counter_slice5_ifg_mac_pool81_rx_mac_partial1_invert_crc_cnt_reg1_rx_mac_partial1_invert_crc_cnt {
      type oc-yang:counter64;
      description
        "Counts the number of received packets with partial CRC type 1.";
    }
    leaf counter_slice5_ifg_mac_pool81_rx_mac_partial1_invert_crc_cnt_reg2_rx_mac_partial1_invert_crc_cnt {
      type oc-yang:counter64;
      description
        "Counts the number of received packets with partial CRC type 1.";
    }
    leaf counter_slice5_ifg_mac_pool81_rx_mac_partial1_invert_crc_cnt_reg3_rx_mac_partial1_invert_crc_cnt {
      type oc-yang:counter64;
      description
        "Counts the number of received packets with partial CRC type 1.";
    }
    leaf counter_slice5_ifg_mac_pool81_rx_mac_partial1_invert_crc_cnt_reg4_rx_mac_partial1_invert_crc_cnt {
      type oc-yang:counter64;
      description
        "Counts the number of received packets with partial CRC type 1.";
    }
    leaf counter_slice5_ifg_mac_pool81_rx_mac_partial1_invert_crc_cnt_reg5_rx_mac_partial1_invert_crc_cnt {
      type oc-yang:counter64;
      description
        "Counts the number of received packets with partial CRC type 1.";
    }
    leaf counter_slice5_ifg_mac_pool81_rx_mac_partial1_invert_crc_cnt_reg6_rx_mac_partial1_invert_crc_cnt {
      type oc-yang:counter64;
      description
        "Counts the number of received packets with partial CRC type 1.";
    }
    leaf counter_slice5_ifg_mac_pool81_rx_mac_partial1_invert_crc_cnt_reg7_rx_mac_partial1_invert_crc_cnt {
      type oc-yang:counter64;
      description
        "Counts the number of received packets with partial CRC type 1.";
    }
    leaf counter_slice5_ifg_mac_pool82_rx_mac_partial1_invert_crc_cnt_reg0_rx_mac_partial1_invert_crc_cnt {
      type oc-yang:counter64;
      description
        "Counts the number of received packets with partial CRC type 1.";
    }
    leaf counter_slice5_ifg_mac_pool82_rx_mac_partial1_invert_crc_cnt_reg1_rx_mac_partial1_invert_crc_cnt {
      type oc-yang:counter64;
      description
        "Counts the number of received packets with partial CRC type 1.";
    }
    leaf counter_slice5_ifg_mac_pool82_rx_mac_partial1_invert_crc_cnt_reg2_rx_mac_partial1_invert_crc_cnt {
      type oc-yang:counter64;
      description
        "Counts the number of received packets with partial CRC type 1.";
    }
    leaf counter_slice5_ifg_mac_pool82_rx_mac_partial1_invert_crc_cnt_reg3_rx_mac_partial1_invert_crc_cnt {
      type oc-yang:counter64;
      description
        "Counts the number of received packets with partial CRC type 1.";
    }
    leaf counter_slice5_ifg_mac_pool82_rx_mac_partial1_invert_crc_cnt_reg4_rx_mac_partial1_invert_crc_cnt {
      type oc-yang:counter64;
      description
        "Counts the number of received packets with partial CRC type 1.";
    }
    leaf counter_slice5_ifg_mac_pool82_rx_mac_partial1_invert_crc_cnt_reg5_rx_mac_partial1_invert_crc_cnt {
      type oc-yang:counter64;
      description
        "Counts the number of received packets with partial CRC type 1.";
    }
    leaf counter_slice5_ifg_mac_pool82_rx_mac_partial1_invert_crc_cnt_reg6_rx_mac_partial1_invert_crc_cnt {
      type oc-yang:counter64;
      description
        "Counts the number of received packets with partial CRC type 1.";
    }
    leaf counter_slice5_ifg_mac_pool82_rx_mac_partial1_invert_crc_cnt_reg7_rx_mac_partial1_invert_crc_cnt {
      type oc-yang:counter64;
      description
        "Counts the number of received packets with partial CRC type 1.";
    }
    leaf counter_slice5_ifg_mac_pool83_rx_mac_partial1_invert_crc_cnt_reg0_rx_mac_partial1_invert_crc_cnt {
      type oc-yang:counter64;
      description
        "Counts the number of received packets with partial CRC type 1.";
    }
    leaf counter_slice5_ifg_mac_pool83_rx_mac_partial1_invert_crc_cnt_reg1_rx_mac_partial1_invert_crc_cnt {
      type oc-yang:counter64;
      description
        "Counts the number of received packets with partial CRC type 1.";
    }
    leaf counter_slice5_ifg_mac_pool83_rx_mac_partial1_invert_crc_cnt_reg2_rx_mac_partial1_invert_crc_cnt {
      type oc-yang:counter64;
      description
        "Counts the number of received packets with partial CRC type 1.";
    }
    leaf counter_slice5_ifg_mac_pool83_rx_mac_partial1_invert_crc_cnt_reg3_rx_mac_partial1_invert_crc_cnt {
      type oc-yang:counter64;
      description
        "Counts the number of received packets with partial CRC type 1.";
    }
    leaf counter_slice5_ifg_mac_pool83_rx_mac_partial1_invert_crc_cnt_reg4_rx_mac_partial1_invert_crc_cnt {
      type oc-yang:counter64;
      description
        "Counts the number of received packets with partial CRC type 1.";
    }
    leaf counter_slice5_ifg_mac_pool83_rx_mac_partial1_invert_crc_cnt_reg5_rx_mac_partial1_invert_crc_cnt {
      type oc-yang:counter64;
      description
        "Counts the number of received packets with partial CRC type 1.";
    }
    leaf counter_slice5_ifg_mac_pool83_rx_mac_partial1_invert_crc_cnt_reg6_rx_mac_partial1_invert_crc_cnt {
      type oc-yang:counter64;
      description
        "Counts the number of received packets with partial CRC type 1.";
    }
    leaf counter_slice5_ifg_mac_pool83_rx_mac_partial1_invert_crc_cnt_reg7_rx_mac_partial1_invert_crc_cnt {
      type oc-yang:counter64;
      description
        "Counts the number of received packets with partial CRC type 1.";
    }
    leaf counter_slice5_ifg_mac_pool84_rx_mac_partial1_invert_crc_cnt_reg0_rx_mac_partial1_invert_crc_cnt {
      type oc-yang:counter64;
      description
        "Counts the number of received packets with partial CRC type 1.";
    }
    leaf counter_slice5_ifg_mac_pool84_rx_mac_partial1_invert_crc_cnt_reg1_rx_mac_partial1_invert_crc_cnt {
      type oc-yang:counter64;
      description
        "Counts the number of received packets with partial CRC type 1.";
    }
    leaf counter_slice5_ifg_mac_pool84_rx_mac_partial1_invert_crc_cnt_reg2_rx_mac_partial1_invert_crc_cnt {
      type oc-yang:counter64;
      description
        "Counts the number of received packets with partial CRC type 1.";
    }
    leaf counter_slice5_ifg_mac_pool84_rx_mac_partial1_invert_crc_cnt_reg3_rx_mac_partial1_invert_crc_cnt {
      type oc-yang:counter64;
      description
        "Counts the number of received packets with partial CRC type 1.";
    }
    leaf counter_slice5_ifg_mac_pool84_rx_mac_partial1_invert_crc_cnt_reg4_rx_mac_partial1_invert_crc_cnt {
      type oc-yang:counter64;
      description
        "Counts the number of received packets with partial CRC type 1.";
    }
    leaf counter_slice5_ifg_mac_pool84_rx_mac_partial1_invert_crc_cnt_reg5_rx_mac_partial1_invert_crc_cnt {
      type oc-yang:counter64;
      description
        "Counts the number of received packets with partial CRC type 1.";
    }
    leaf counter_slice5_ifg_mac_pool84_rx_mac_partial1_invert_crc_cnt_reg6_rx_mac_partial1_invert_crc_cnt {
      type oc-yang:counter64;
      description
        "Counts the number of received packets with partial CRC type 1.";
    }
    leaf counter_slice5_ifg_mac_pool84_rx_mac_partial1_invert_crc_cnt_reg7_rx_mac_partial1_invert_crc_cnt {
      type oc-yang:counter64;
      description
        "Counts the number of received packets with partial CRC type 1.";
    }
    leaf counter_slice5_ifg_mac_pool85_rx_mac_partial1_invert_crc_cnt_reg0_rx_mac_partial1_invert_crc_cnt {
      type oc-yang:counter64;
      description
        "Counts the number of received packets with partial CRC type 1.";
    }
    leaf counter_slice5_ifg_mac_pool85_rx_mac_partial1_invert_crc_cnt_reg1_rx_mac_partial1_invert_crc_cnt {
      type oc-yang:counter64;
      description
        "Counts the number of received packets with partial CRC type 1.";
    }
    leaf counter_slice5_ifg_mac_pool85_rx_mac_partial1_invert_crc_cnt_reg2_rx_mac_partial1_invert_crc_cnt {
      type oc-yang:counter64;
      description
        "Counts the number of received packets with partial CRC type 1.";
    }
    leaf counter_slice5_ifg_mac_pool85_rx_mac_partial1_invert_crc_cnt_reg3_rx_mac_partial1_invert_crc_cnt {
      type oc-yang:counter64;
      description
        "Counts the number of received packets with partial CRC type 1.";
    }
    leaf counter_slice5_ifg_mac_pool85_rx_mac_partial1_invert_crc_cnt_reg4_rx_mac_partial1_invert_crc_cnt {
      type oc-yang:counter64;
      description
        "Counts the number of received packets with partial CRC type 1.";
    }
    leaf counter_slice5_ifg_mac_pool85_rx_mac_partial1_invert_crc_cnt_reg5_rx_mac_partial1_invert_crc_cnt {
      type oc-yang:counter64;
      description
        "Counts the number of received packets with partial CRC type 1.";
    }
    leaf counter_slice5_ifg_mac_pool85_rx_mac_partial1_invert_crc_cnt_reg6_rx_mac_partial1_invert_crc_cnt {
      type oc-yang:counter64;
      description
        "Counts the number of received packets with partial CRC type 1.";
    }
    leaf counter_slice5_ifg_mac_pool85_rx_mac_partial1_invert_crc_cnt_reg7_rx_mac_partial1_invert_crc_cnt {
      type oc-yang:counter64;
      description
        "Counts the number of received packets with partial CRC type 1.";
    }
    leaf counter_slice5_ifg_mac_pool86_rx_mac_partial1_invert_crc_cnt_reg0_rx_mac_partial1_invert_crc_cnt {
      type oc-yang:counter64;
      description
        "Counts the number of received packets with partial CRC type 1.";
    }
    leaf counter_slice5_ifg_mac_pool86_rx_mac_partial1_invert_crc_cnt_reg1_rx_mac_partial1_invert_crc_cnt {
      type oc-yang:counter64;
      description
        "Counts the number of received packets with partial CRC type 1.";
    }
    leaf counter_slice5_ifg_mac_pool86_rx_mac_partial1_invert_crc_cnt_reg2_rx_mac_partial1_invert_crc_cnt {
      type oc-yang:counter64;
      description
        "Counts the number of received packets with partial CRC type 1.";
    }
    leaf counter_slice5_ifg_mac_pool86_rx_mac_partial1_invert_crc_cnt_reg3_rx_mac_partial1_invert_crc_cnt {
      type oc-yang:counter64;
      description
        "Counts the number of received packets with partial CRC type 1.";
    }
    leaf counter_slice5_ifg_mac_pool86_rx_mac_partial1_invert_crc_cnt_reg4_rx_mac_partial1_invert_crc_cnt {
      type oc-yang:counter64;
      description
        "Counts the number of received packets with partial CRC type 1.";
    }
    leaf counter_slice5_ifg_mac_pool86_rx_mac_partial1_invert_crc_cnt_reg5_rx_mac_partial1_invert_crc_cnt {
      type oc-yang:counter64;
      description
        "Counts the number of received packets with partial CRC type 1.";
    }
    leaf counter_slice5_ifg_mac_pool86_rx_mac_partial1_invert_crc_cnt_reg6_rx_mac_partial1_invert_crc_cnt {
      type oc-yang:counter64;
      description
        "Counts the number of received packets with partial CRC type 1.";
    }
    leaf counter_slice5_ifg_mac_pool86_rx_mac_partial1_invert_crc_cnt_reg7_rx_mac_partial1_invert_crc_cnt {
      type oc-yang:counter64;
      description
        "Counts the number of received packets with partial CRC type 1.";
    }
    leaf counter_slice5_ifg_mac_pool87_rx_mac_partial1_invert_crc_cnt_reg0_rx_mac_partial1_invert_crc_cnt {
      type oc-yang:counter64;
      description
        "Counts the number of received packets with partial CRC type 1.";
    }
    leaf counter_slice5_ifg_mac_pool87_rx_mac_partial1_invert_crc_cnt_reg1_rx_mac_partial1_invert_crc_cnt {
      type oc-yang:counter64;
      description
        "Counts the number of received packets with partial CRC type 1.";
    }
    leaf counter_slice5_ifg_mac_pool87_rx_mac_partial1_invert_crc_cnt_reg2_rx_mac_partial1_invert_crc_cnt {
      type oc-yang:counter64;
      description
        "Counts the number of received packets with partial CRC type 1.";
    }
    leaf counter_slice5_ifg_mac_pool87_rx_mac_partial1_invert_crc_cnt_reg3_rx_mac_partial1_invert_crc_cnt {
      type oc-yang:counter64;
      description
        "Counts the number of received packets with partial CRC type 1.";
    }
    leaf counter_slice5_ifg_mac_pool87_rx_mac_partial1_invert_crc_cnt_reg4_rx_mac_partial1_invert_crc_cnt {
      type oc-yang:counter64;
      description
        "Counts the number of received packets with partial CRC type 1.";
    }
    leaf counter_slice5_ifg_mac_pool87_rx_mac_partial1_invert_crc_cnt_reg5_rx_mac_partial1_invert_crc_cnt {
      type oc-yang:counter64;
      description
        "Counts the number of received packets with partial CRC type 1.";
    }
    leaf counter_slice5_ifg_mac_pool87_rx_mac_partial1_invert_crc_cnt_reg6_rx_mac_partial1_invert_crc_cnt {
      type oc-yang:counter64;
      description
        "Counts the number of received packets with partial CRC type 1.";
    }
    leaf counter_slice5_ifg_mac_pool87_rx_mac_partial1_invert_crc_cnt_reg7_rx_mac_partial1_invert_crc_cnt {
      type oc-yang:counter64;
      description
        "Counts the number of received packets with partial CRC type 1.";
    }
    leaf counter_slice6_ifg_mac_pool80_rx_mac_partial1_invert_crc_cnt_reg0_rx_mac_partial1_invert_crc_cnt {
      type oc-yang:counter64;
      description
        "Counts the number of received packets with partial CRC type 1.";
    }
    leaf counter_slice6_ifg_mac_pool80_rx_mac_partial1_invert_crc_cnt_reg1_rx_mac_partial1_invert_crc_cnt {
      type oc-yang:counter64;
      description
        "Counts the number of received packets with partial CRC type 1.";
    }
    leaf counter_slice6_ifg_mac_pool80_rx_mac_partial1_invert_crc_cnt_reg2_rx_mac_partial1_invert_crc_cnt {
      type oc-yang:counter64;
      description
        "Counts the number of received packets with partial CRC type 1.";
    }
    leaf counter_slice6_ifg_mac_pool80_rx_mac_partial1_invert_crc_cnt_reg3_rx_mac_partial1_invert_crc_cnt {
      type oc-yang:counter64;
      description
        "Counts the number of received packets with partial CRC type 1.";
    }
    leaf counter_slice6_ifg_mac_pool80_rx_mac_partial1_invert_crc_cnt_reg4_rx_mac_partial1_invert_crc_cnt {
      type oc-yang:counter64;
      description
        "Counts the number of received packets with partial CRC type 1.";
    }
    leaf counter_slice6_ifg_mac_pool80_rx_mac_partial1_invert_crc_cnt_reg5_rx_mac_partial1_invert_crc_cnt {
      type oc-yang:counter64;
      description
        "Counts the number of received packets with partial CRC type 1.";
    }
    leaf counter_slice6_ifg_mac_pool80_rx_mac_partial1_invert_crc_cnt_reg6_rx_mac_partial1_invert_crc_cnt {
      type oc-yang:counter64;
      description
        "Counts the number of received packets with partial CRC type 1.";
    }
    leaf counter_slice6_ifg_mac_pool80_rx_mac_partial1_invert_crc_cnt_reg7_rx_mac_partial1_invert_crc_cnt {
      type oc-yang:counter64;
      description
        "Counts the number of received packets with partial CRC type 1.";
    }
    leaf counter_slice6_ifg_mac_pool81_rx_mac_partial1_invert_crc_cnt_reg0_rx_mac_partial1_invert_crc_cnt {
      type oc-yang:counter64;
      description
        "Counts the number of received packets with partial CRC type 1.";
    }
    leaf counter_slice6_ifg_mac_pool81_rx_mac_partial1_invert_crc_cnt_reg1_rx_mac_partial1_invert_crc_cnt {
      type oc-yang:counter64;
      description
        "Counts the number of received packets with partial CRC type 1.";
    }
    leaf counter_slice6_ifg_mac_pool81_rx_mac_partial1_invert_crc_cnt_reg2_rx_mac_partial1_invert_crc_cnt {
      type oc-yang:counter64;
      description
        "Counts the number of received packets with partial CRC type 1.";
    }
    leaf counter_slice6_ifg_mac_pool81_rx_mac_partial1_invert_crc_cnt_reg3_rx_mac_partial1_invert_crc_cnt {
      type oc-yang:counter64;
      description
        "Counts the number of received packets with partial CRC type 1.";
    }
    leaf counter_slice6_ifg_mac_pool81_rx_mac_partial1_invert_crc_cnt_reg4_rx_mac_partial1_invert_crc_cnt {
      type oc-yang:counter64;
      description
        "Counts the number of received packets with partial CRC type 1.";
    }
    leaf counter_slice6_ifg_mac_pool81_rx_mac_partial1_invert_crc_cnt_reg5_rx_mac_partial1_invert_crc_cnt {
      type oc-yang:counter64;
      description
        "Counts the number of received packets with partial CRC type 1.";
    }
    leaf counter_slice6_ifg_mac_pool81_rx_mac_partial1_invert_crc_cnt_reg6_rx_mac_partial1_invert_crc_cnt {
      type oc-yang:counter64;
      description
        "Counts the number of received packets with partial CRC type 1.";
    }
    leaf counter_slice6_ifg_mac_pool81_rx_mac_partial1_invert_crc_cnt_reg7_rx_mac_partial1_invert_crc_cnt {
      type oc-yang:counter64;
      description
        "Counts the number of received packets with partial CRC type 1.";
    }
    leaf counter_slice6_ifg_mac_pool82_rx_mac_partial1_invert_crc_cnt_reg0_rx_mac_partial1_invert_crc_cnt {
      type oc-yang:counter64;
      description
        "Counts the number of received packets with partial CRC type 1.";
    }
    leaf counter_slice6_ifg_mac_pool82_rx_mac_partial1_invert_crc_cnt_reg1_rx_mac_partial1_invert_crc_cnt {
      type oc-yang:counter64;
      description
        "Counts the number of received packets with partial CRC type 1.";
    }
    leaf counter_slice6_ifg_mac_pool82_rx_mac_partial1_invert_crc_cnt_reg2_rx_mac_partial1_invert_crc_cnt {
      type oc-yang:counter64;
      description
        "Counts the number of received packets with partial CRC type 1.";
    }
    leaf counter_slice6_ifg_mac_pool82_rx_mac_partial1_invert_crc_cnt_reg3_rx_mac_partial1_invert_crc_cnt {
      type oc-yang:counter64;
      description
        "Counts the number of received packets with partial CRC type 1.";
    }
    leaf counter_slice6_ifg_mac_pool82_rx_mac_partial1_invert_crc_cnt_reg4_rx_mac_partial1_invert_crc_cnt {
      type oc-yang:counter64;
      description
        "Counts the number of received packets with partial CRC type 1.";
    }
    leaf counter_slice6_ifg_mac_pool82_rx_mac_partial1_invert_crc_cnt_reg5_rx_mac_partial1_invert_crc_cnt {
      type oc-yang:counter64;
      description
        "Counts the number of received packets with partial CRC type 1.";
    }
    leaf counter_slice6_ifg_mac_pool82_rx_mac_partial1_invert_crc_cnt_reg6_rx_mac_partial1_invert_crc_cnt {
      type oc-yang:counter64;
      description
        "Counts the number of received packets with partial CRC type 1.";
    }
    leaf counter_slice6_ifg_mac_pool82_rx_mac_partial1_invert_crc_cnt_reg7_rx_mac_partial1_invert_crc_cnt {
      type oc-yang:counter64;
      description
        "Counts the number of received packets with partial CRC type 1.";
    }
    leaf counter_slice6_ifg_mac_pool83_rx_mac_partial1_invert_crc_cnt_reg0_rx_mac_partial1_invert_crc_cnt {
      type oc-yang:counter64;
      description
        "Counts the number of received packets with partial CRC type 1.";
    }
    leaf counter_slice6_ifg_mac_pool83_rx_mac_partial1_invert_crc_cnt_reg1_rx_mac_partial1_invert_crc_cnt {
      type oc-yang:counter64;
      description
        "Counts the number of received packets with partial CRC type 1.";
    }
    leaf counter_slice6_ifg_mac_pool83_rx_mac_partial1_invert_crc_cnt_reg2_rx_mac_partial1_invert_crc_cnt {
      type oc-yang:counter64;
      description
        "Counts the number of received packets with partial CRC type 1.";
    }
    leaf counter_slice6_ifg_mac_pool83_rx_mac_partial1_invert_crc_cnt_reg3_rx_mac_partial1_invert_crc_cnt {
      type oc-yang:counter64;
      description
        "Counts the number of received packets with partial CRC type 1.";
    }
    leaf counter_slice6_ifg_mac_pool83_rx_mac_partial1_invert_crc_cnt_reg4_rx_mac_partial1_invert_crc_cnt {
      type oc-yang:counter64;
      description
        "Counts the number of received packets with partial CRC type 1.";
    }
    leaf counter_slice6_ifg_mac_pool83_rx_mac_partial1_invert_crc_cnt_reg5_rx_mac_partial1_invert_crc_cnt {
      type oc-yang:counter64;
      description
        "Counts the number of received packets with partial CRC type 1.";
    }
    leaf counter_slice6_ifg_mac_pool83_rx_mac_partial1_invert_crc_cnt_reg6_rx_mac_partial1_invert_crc_cnt {
      type oc-yang:counter64;
      description
        "Counts the number of received packets with partial CRC type 1.";
    }
    leaf counter_slice6_ifg_mac_pool83_rx_mac_partial1_invert_crc_cnt_reg7_rx_mac_partial1_invert_crc_cnt {
      type oc-yang:counter64;
      description
        "Counts the number of received packets with partial CRC type 1.";
    }
    leaf counter_slice6_ifg_mac_pool84_rx_mac_partial1_invert_crc_cnt_reg0_rx_mac_partial1_invert_crc_cnt {
      type oc-yang:counter64;
      description
        "Counts the number of received packets with partial CRC type 1.";
    }
    leaf counter_slice6_ifg_mac_pool84_rx_mac_partial1_invert_crc_cnt_reg1_rx_mac_partial1_invert_crc_cnt {
      type oc-yang:counter64;
      description
        "Counts the number of received packets with partial CRC type 1.";
    }
    leaf counter_slice6_ifg_mac_pool84_rx_mac_partial1_invert_crc_cnt_reg2_rx_mac_partial1_invert_crc_cnt {
      type oc-yang:counter64;
      description
        "Counts the number of received packets with partial CRC type 1.";
    }
    leaf counter_slice6_ifg_mac_pool84_rx_mac_partial1_invert_crc_cnt_reg3_rx_mac_partial1_invert_crc_cnt {
      type oc-yang:counter64;
      description
        "Counts the number of received packets with partial CRC type 1.";
    }
    leaf counter_slice6_ifg_mac_pool84_rx_mac_partial1_invert_crc_cnt_reg4_rx_mac_partial1_invert_crc_cnt {
      type oc-yang:counter64;
      description
        "Counts the number of received packets with partial CRC type 1.";
    }
    leaf counter_slice6_ifg_mac_pool84_rx_mac_partial1_invert_crc_cnt_reg5_rx_mac_partial1_invert_crc_cnt {
      type oc-yang:counter64;
      description
        "Counts the number of received packets with partial CRC type 1.";
    }
    leaf counter_slice6_ifg_mac_pool84_rx_mac_partial1_invert_crc_cnt_reg6_rx_mac_partial1_invert_crc_cnt {
      type oc-yang:counter64;
      description
        "Counts the number of received packets with partial CRC type 1.";
    }
    leaf counter_slice6_ifg_mac_pool84_rx_mac_partial1_invert_crc_cnt_reg7_rx_mac_partial1_invert_crc_cnt {
      type oc-yang:counter64;
      description
        "Counts the number of received packets with partial CRC type 1.";
    }
    leaf counter_slice6_ifg_mac_pool85_rx_mac_partial1_invert_crc_cnt_reg0_rx_mac_partial1_invert_crc_cnt {
      type oc-yang:counter64;
      description
        "Counts the number of received packets with partial CRC type 1.";
    }
    leaf counter_slice6_ifg_mac_pool85_rx_mac_partial1_invert_crc_cnt_reg1_rx_mac_partial1_invert_crc_cnt {
      type oc-yang:counter64;
      description
        "Counts the number of received packets with partial CRC type 1.";
    }
    leaf counter_slice6_ifg_mac_pool85_rx_mac_partial1_invert_crc_cnt_reg2_rx_mac_partial1_invert_crc_cnt {
      type oc-yang:counter64;
      description
        "Counts the number of received packets with partial CRC type 1.";
    }
    leaf counter_slice6_ifg_mac_pool85_rx_mac_partial1_invert_crc_cnt_reg3_rx_mac_partial1_invert_crc_cnt {
      type oc-yang:counter64;
      description
        "Counts the number of received packets with partial CRC type 1.";
    }
    leaf counter_slice6_ifg_mac_pool85_rx_mac_partial1_invert_crc_cnt_reg4_rx_mac_partial1_invert_crc_cnt {
      type oc-yang:counter64;
      description
        "Counts the number of received packets with partial CRC type 1.";
    }
    leaf counter_slice6_ifg_mac_pool85_rx_mac_partial1_invert_crc_cnt_reg5_rx_mac_partial1_invert_crc_cnt {
      type oc-yang:counter64;
      description
        "Counts the number of received packets with partial CRC type 1.";
    }
    leaf counter_slice6_ifg_mac_pool85_rx_mac_partial1_invert_crc_cnt_reg6_rx_mac_partial1_invert_crc_cnt {
      type oc-yang:counter64;
      description
        "Counts the number of received packets with partial CRC type 1.";
    }
    leaf counter_slice6_ifg_mac_pool85_rx_mac_partial1_invert_crc_cnt_reg7_rx_mac_partial1_invert_crc_cnt {
      type oc-yang:counter64;
      description
        "Counts the number of received packets with partial CRC type 1.";
    }
    leaf counter_slice6_ifg_mac_pool86_rx_mac_partial1_invert_crc_cnt_reg0_rx_mac_partial1_invert_crc_cnt {
      type oc-yang:counter64;
      description
        "Counts the number of received packets with partial CRC type 1.";
    }
    leaf counter_slice6_ifg_mac_pool86_rx_mac_partial1_invert_crc_cnt_reg1_rx_mac_partial1_invert_crc_cnt {
      type oc-yang:counter64;
      description
        "Counts the number of received packets with partial CRC type 1.";
    }
    leaf counter_slice6_ifg_mac_pool86_rx_mac_partial1_invert_crc_cnt_reg2_rx_mac_partial1_invert_crc_cnt {
      type oc-yang:counter64;
      description
        "Counts the number of received packets with partial CRC type 1.";
    }
    leaf counter_slice6_ifg_mac_pool86_rx_mac_partial1_invert_crc_cnt_reg3_rx_mac_partial1_invert_crc_cnt {
      type oc-yang:counter64;
      description
        "Counts the number of received packets with partial CRC type 1.";
    }
    leaf counter_slice6_ifg_mac_pool86_rx_mac_partial1_invert_crc_cnt_reg4_rx_mac_partial1_invert_crc_cnt {
      type oc-yang:counter64;
      description
        "Counts the number of received packets with partial CRC type 1.";
    }
    leaf counter_slice6_ifg_mac_pool86_rx_mac_partial1_invert_crc_cnt_reg5_rx_mac_partial1_invert_crc_cnt {
      type oc-yang:counter64;
      description
        "Counts the number of received packets with partial CRC type 1.";
    }
    leaf counter_slice6_ifg_mac_pool86_rx_mac_partial1_invert_crc_cnt_reg6_rx_mac_partial1_invert_crc_cnt {
      type oc-yang:counter64;
      description
        "Counts the number of received packets with partial CRC type 1.";
    }
    leaf counter_slice6_ifg_mac_pool86_rx_mac_partial1_invert_crc_cnt_reg7_rx_mac_partial1_invert_crc_cnt {
      type oc-yang:counter64;
      description
        "Counts the number of received packets with partial CRC type 1.";
    }
    leaf counter_slice6_ifg_mac_pool87_rx_mac_partial1_invert_crc_cnt_reg0_rx_mac_partial1_invert_crc_cnt {
      type oc-yang:counter64;
      description
        "Counts the number of received packets with partial CRC type 1.";
    }
    leaf counter_slice6_ifg_mac_pool87_rx_mac_partial1_invert_crc_cnt_reg1_rx_mac_partial1_invert_crc_cnt {
      type oc-yang:counter64;
      description
        "Counts the number of received packets with partial CRC type 1.";
    }
    leaf counter_slice6_ifg_mac_pool87_rx_mac_partial1_invert_crc_cnt_reg2_rx_mac_partial1_invert_crc_cnt {
      type oc-yang:counter64;
      description
        "Counts the number of received packets with partial CRC type 1.";
    }
    leaf counter_slice6_ifg_mac_pool87_rx_mac_partial1_invert_crc_cnt_reg3_rx_mac_partial1_invert_crc_cnt {
      type oc-yang:counter64;
      description
        "Counts the number of received packets with partial CRC type 1.";
    }
    leaf counter_slice6_ifg_mac_pool87_rx_mac_partial1_invert_crc_cnt_reg4_rx_mac_partial1_invert_crc_cnt {
      type oc-yang:counter64;
      description
        "Counts the number of received packets with partial CRC type 1.";
    }
    leaf counter_slice6_ifg_mac_pool87_rx_mac_partial1_invert_crc_cnt_reg5_rx_mac_partial1_invert_crc_cnt {
      type oc-yang:counter64;
      description
        "Counts the number of received packets with partial CRC type 1.";
    }
    leaf counter_slice6_ifg_mac_pool87_rx_mac_partial1_invert_crc_cnt_reg6_rx_mac_partial1_invert_crc_cnt {
      type oc-yang:counter64;
      description
        "Counts the number of received packets with partial CRC type 1.";
    }
    leaf counter_slice6_ifg_mac_pool87_rx_mac_partial1_invert_crc_cnt_reg7_rx_mac_partial1_invert_crc_cnt {
      type oc-yang:counter64;
      description
        "Counts the number of received packets with partial CRC type 1.";
    }
    leaf counter_slice7_ifg_mac_pool80_rx_mac_partial1_invert_crc_cnt_reg0_rx_mac_partial1_invert_crc_cnt {
      type oc-yang:counter64;
      description
        "Counts the number of received packets with partial CRC type 1.";
    }
    leaf counter_slice7_ifg_mac_pool80_rx_mac_partial1_invert_crc_cnt_reg1_rx_mac_partial1_invert_crc_cnt {
      type oc-yang:counter64;
      description
        "Counts the number of received packets with partial CRC type 1.";
    }
    leaf counter_slice7_ifg_mac_pool80_rx_mac_partial1_invert_crc_cnt_reg2_rx_mac_partial1_invert_crc_cnt {
      type oc-yang:counter64;
      description
        "Counts the number of received packets with partial CRC type 1.";
    }
    leaf counter_slice7_ifg_mac_pool80_rx_mac_partial1_invert_crc_cnt_reg3_rx_mac_partial1_invert_crc_cnt {
      type oc-yang:counter64;
      description
        "Counts the number of received packets with partial CRC type 1.";
    }
    leaf counter_slice7_ifg_mac_pool80_rx_mac_partial1_invert_crc_cnt_reg4_rx_mac_partial1_invert_crc_cnt {
      type oc-yang:counter64;
      description
        "Counts the number of received packets with partial CRC type 1.";
    }
    leaf counter_slice7_ifg_mac_pool80_rx_mac_partial1_invert_crc_cnt_reg5_rx_mac_partial1_invert_crc_cnt {
      type oc-yang:counter64;
      description
        "Counts the number of received packets with partial CRC type 1.";
    }
    leaf counter_slice7_ifg_mac_pool80_rx_mac_partial1_invert_crc_cnt_reg6_rx_mac_partial1_invert_crc_cnt {
      type oc-yang:counter64;
      description
        "Counts the number of received packets with partial CRC type 1.";
    }
    leaf counter_slice7_ifg_mac_pool80_rx_mac_partial1_invert_crc_cnt_reg7_rx_mac_partial1_invert_crc_cnt {
      type oc-yang:counter64;
      description
        "Counts the number of received packets with partial CRC type 1.";
    }
    leaf counter_slice7_ifg_mac_pool81_rx_mac_partial1_invert_crc_cnt_reg0_rx_mac_partial1_invert_crc_cnt {
      type oc-yang:counter64;
      description
        "Counts the number of received packets with partial CRC type 1.";
    }
    leaf counter_slice7_ifg_mac_pool81_rx_mac_partial1_invert_crc_cnt_reg1_rx_mac_partial1_invert_crc_cnt {
      type oc-yang:counter64;
      description
        "Counts the number of received packets with partial CRC type 1.";
    }
    leaf counter_slice7_ifg_mac_pool81_rx_mac_partial1_invert_crc_cnt_reg2_rx_mac_partial1_invert_crc_cnt {
      type oc-yang:counter64;
      description
        "Counts the number of received packets with partial CRC type 1.";
    }
    leaf counter_slice7_ifg_mac_pool81_rx_mac_partial1_invert_crc_cnt_reg3_rx_mac_partial1_invert_crc_cnt {
      type oc-yang:counter64;
      description
        "Counts the number of received packets with partial CRC type 1.";
    }
    leaf counter_slice7_ifg_mac_pool81_rx_mac_partial1_invert_crc_cnt_reg4_rx_mac_partial1_invert_crc_cnt {
      type oc-yang:counter64;
      description
        "Counts the number of received packets with partial CRC type 1.";
    }
    leaf counter_slice7_ifg_mac_pool81_rx_mac_partial1_invert_crc_cnt_reg5_rx_mac_partial1_invert_crc_cnt {
      type oc-yang:counter64;
      description
        "Counts the number of received packets with partial CRC type 1.";
    }
    leaf counter_slice7_ifg_mac_pool81_rx_mac_partial1_invert_crc_cnt_reg6_rx_mac_partial1_invert_crc_cnt {
      type oc-yang:counter64;
      description
        "Counts the number of received packets with partial CRC type 1.";
    }
    leaf counter_slice7_ifg_mac_pool81_rx_mac_partial1_invert_crc_cnt_reg7_rx_mac_partial1_invert_crc_cnt {
      type oc-yang:counter64;
      description
        "Counts the number of received packets with partial CRC type 1.";
    }
    leaf counter_slice7_ifg_mac_pool82_rx_mac_partial1_invert_crc_cnt_reg0_rx_mac_partial1_invert_crc_cnt {
      type oc-yang:counter64;
      description
        "Counts the number of received packets with partial CRC type 1.";
    }
    leaf counter_slice7_ifg_mac_pool82_rx_mac_partial1_invert_crc_cnt_reg1_rx_mac_partial1_invert_crc_cnt {
      type oc-yang:counter64;
      description
        "Counts the number of received packets with partial CRC type 1.";
    }
    leaf counter_slice7_ifg_mac_pool82_rx_mac_partial1_invert_crc_cnt_reg2_rx_mac_partial1_invert_crc_cnt {
      type oc-yang:counter64;
      description
        "Counts the number of received packets with partial CRC type 1.";
    }
    leaf counter_slice7_ifg_mac_pool82_rx_mac_partial1_invert_crc_cnt_reg3_rx_mac_partial1_invert_crc_cnt {
      type oc-yang:counter64;
      description
        "Counts the number of received packets with partial CRC type 1.";
    }
    leaf counter_slice7_ifg_mac_pool82_rx_mac_partial1_invert_crc_cnt_reg4_rx_mac_partial1_invert_crc_cnt {
      type oc-yang:counter64;
      description
        "Counts the number of received packets with partial CRC type 1.";
    }
    leaf counter_slice7_ifg_mac_pool82_rx_mac_partial1_invert_crc_cnt_reg5_rx_mac_partial1_invert_crc_cnt {
      type oc-yang:counter64;
      description
        "Counts the number of received packets with partial CRC type 1.";
    }
    leaf counter_slice7_ifg_mac_pool82_rx_mac_partial1_invert_crc_cnt_reg6_rx_mac_partial1_invert_crc_cnt {
      type oc-yang:counter64;
      description
        "Counts the number of received packets with partial CRC type 1.";
    }
    leaf counter_slice7_ifg_mac_pool82_rx_mac_partial1_invert_crc_cnt_reg7_rx_mac_partial1_invert_crc_cnt {
      type oc-yang:counter64;
      description
        "Counts the number of received packets with partial CRC type 1.";
    }
    leaf counter_slice7_ifg_mac_pool83_rx_mac_partial1_invert_crc_cnt_reg0_rx_mac_partial1_invert_crc_cnt {
      type oc-yang:counter64;
      description
        "Counts the number of received packets with partial CRC type 1.";
    }
    leaf counter_slice7_ifg_mac_pool83_rx_mac_partial1_invert_crc_cnt_reg1_rx_mac_partial1_invert_crc_cnt {
      type oc-yang:counter64;
      description
        "Counts the number of received packets with partial CRC type 1.";
    }
    leaf counter_slice7_ifg_mac_pool83_rx_mac_partial1_invert_crc_cnt_reg2_rx_mac_partial1_invert_crc_cnt {
      type oc-yang:counter64;
      description
        "Counts the number of received packets with partial CRC type 1.";
    }
    leaf counter_slice7_ifg_mac_pool83_rx_mac_partial1_invert_crc_cnt_reg3_rx_mac_partial1_invert_crc_cnt {
      type oc-yang:counter64;
      description
        "Counts the number of received packets with partial CRC type 1.";
    }
    leaf counter_slice7_ifg_mac_pool83_rx_mac_partial1_invert_crc_cnt_reg4_rx_mac_partial1_invert_crc_cnt {
      type oc-yang:counter64;
      description
        "Counts the number of received packets with partial CRC type 1.";
    }
    leaf counter_slice7_ifg_mac_pool83_rx_mac_partial1_invert_crc_cnt_reg5_rx_mac_partial1_invert_crc_cnt {
      type oc-yang:counter64;
      description
        "Counts the number of received packets with partial CRC type 1.";
    }
    leaf counter_slice7_ifg_mac_pool83_rx_mac_partial1_invert_crc_cnt_reg6_rx_mac_partial1_invert_crc_cnt {
      type oc-yang:counter64;
      description
        "Counts the number of received packets with partial CRC type 1.";
    }
    leaf counter_slice7_ifg_mac_pool83_rx_mac_partial1_invert_crc_cnt_reg7_rx_mac_partial1_invert_crc_cnt {
      type oc-yang:counter64;
      description
        "Counts the number of received packets with partial CRC type 1.";
    }
    leaf counter_slice7_ifg_mac_pool84_rx_mac_partial1_invert_crc_cnt_reg0_rx_mac_partial1_invert_crc_cnt {
      type oc-yang:counter64;
      description
        "Counts the number of received packets with partial CRC type 1.";
    }
    leaf counter_slice7_ifg_mac_pool84_rx_mac_partial1_invert_crc_cnt_reg1_rx_mac_partial1_invert_crc_cnt {
      type oc-yang:counter64;
      description
        "Counts the number of received packets with partial CRC type 1.";
    }
    leaf counter_slice7_ifg_mac_pool84_rx_mac_partial1_invert_crc_cnt_reg2_rx_mac_partial1_invert_crc_cnt {
      type oc-yang:counter64;
      description
        "Counts the number of received packets with partial CRC type 1.";
    }
    leaf counter_slice7_ifg_mac_pool84_rx_mac_partial1_invert_crc_cnt_reg3_rx_mac_partial1_invert_crc_cnt {
      type oc-yang:counter64;
      description
        "Counts the number of received packets with partial CRC type 1.";
    }
    leaf counter_slice7_ifg_mac_pool84_rx_mac_partial1_invert_crc_cnt_reg4_rx_mac_partial1_invert_crc_cnt {
      type oc-yang:counter64;
      description
        "Counts the number of received packets with partial CRC type 1.";
    }
    leaf counter_slice7_ifg_mac_pool84_rx_mac_partial1_invert_crc_cnt_reg5_rx_mac_partial1_invert_crc_cnt {
      type oc-yang:counter64;
      description
        "Counts the number of received packets with partial CRC type 1.";
    }
    leaf counter_slice7_ifg_mac_pool84_rx_mac_partial1_invert_crc_cnt_reg6_rx_mac_partial1_invert_crc_cnt {
      type oc-yang:counter64;
      description
        "Counts the number of received packets with partial CRC type 1.";
    }
    leaf counter_slice7_ifg_mac_pool84_rx_mac_partial1_invert_crc_cnt_reg7_rx_mac_partial1_invert_crc_cnt {
      type oc-yang:counter64;
      description
        "Counts the number of received packets with partial CRC type 1.";
    }
    leaf counter_slice7_ifg_mac_pool85_rx_mac_partial1_invert_crc_cnt_reg0_rx_mac_partial1_invert_crc_cnt {
      type oc-yang:counter64;
      description
        "Counts the number of received packets with partial CRC type 1.";
    }
    leaf counter_slice7_ifg_mac_pool85_rx_mac_partial1_invert_crc_cnt_reg1_rx_mac_partial1_invert_crc_cnt {
      type oc-yang:counter64;
      description
        "Counts the number of received packets with partial CRC type 1.";
    }
    leaf counter_slice7_ifg_mac_pool85_rx_mac_partial1_invert_crc_cnt_reg2_rx_mac_partial1_invert_crc_cnt {
      type oc-yang:counter64;
      description
        "Counts the number of received packets with partial CRC type 1.";
    }
    leaf counter_slice7_ifg_mac_pool85_rx_mac_partial1_invert_crc_cnt_reg3_rx_mac_partial1_invert_crc_cnt {
      type oc-yang:counter64;
      description
        "Counts the number of received packets with partial CRC type 1.";
    }
    leaf counter_slice7_ifg_mac_pool85_rx_mac_partial1_invert_crc_cnt_reg4_rx_mac_partial1_invert_crc_cnt {
      type oc-yang:counter64;
      description
        "Counts the number of received packets with partial CRC type 1.";
    }
    leaf counter_slice7_ifg_mac_pool85_rx_mac_partial1_invert_crc_cnt_reg5_rx_mac_partial1_invert_crc_cnt {
      type oc-yang:counter64;
      description
        "Counts the number of received packets with partial CRC type 1.";
    }
    leaf counter_slice7_ifg_mac_pool85_rx_mac_partial1_invert_crc_cnt_reg6_rx_mac_partial1_invert_crc_cnt {
      type oc-yang:counter64;
      description
        "Counts the number of received packets with partial CRC type 1.";
    }
    leaf counter_slice7_ifg_mac_pool85_rx_mac_partial1_invert_crc_cnt_reg7_rx_mac_partial1_invert_crc_cnt {
      type oc-yang:counter64;
      description
        "Counts the number of received packets with partial CRC type 1.";
    }
    leaf counter_slice7_ifg_mac_pool86_rx_mac_partial1_invert_crc_cnt_reg0_rx_mac_partial1_invert_crc_cnt {
      type oc-yang:counter64;
      description
        "Counts the number of received packets with partial CRC type 1.";
    }
    leaf counter_slice7_ifg_mac_pool86_rx_mac_partial1_invert_crc_cnt_reg1_rx_mac_partial1_invert_crc_cnt {
      type oc-yang:counter64;
      description
        "Counts the number of received packets with partial CRC type 1.";
    }
    leaf counter_slice7_ifg_mac_pool86_rx_mac_partial1_invert_crc_cnt_reg2_rx_mac_partial1_invert_crc_cnt {
      type oc-yang:counter64;
      description
        "Counts the number of received packets with partial CRC type 1.";
    }
    leaf counter_slice7_ifg_mac_pool86_rx_mac_partial1_invert_crc_cnt_reg3_rx_mac_partial1_invert_crc_cnt {
      type oc-yang:counter64;
      description
        "Counts the number of received packets with partial CRC type 1.";
    }
    leaf counter_slice7_ifg_mac_pool86_rx_mac_partial1_invert_crc_cnt_reg4_rx_mac_partial1_invert_crc_cnt {
      type oc-yang:counter64;
      description
        "Counts the number of received packets with partial CRC type 1.";
    }
    leaf counter_slice7_ifg_mac_pool86_rx_mac_partial1_invert_crc_cnt_reg5_rx_mac_partial1_invert_crc_cnt {
      type oc-yang:counter64;
      description
        "Counts the number of received packets with partial CRC type 1.";
    }
    leaf counter_slice7_ifg_mac_pool86_rx_mac_partial1_invert_crc_cnt_reg6_rx_mac_partial1_invert_crc_cnt {
      type oc-yang:counter64;
      description
        "Counts the number of received packets with partial CRC type 1.";
    }
    leaf counter_slice7_ifg_mac_pool86_rx_mac_partial1_invert_crc_cnt_reg7_rx_mac_partial1_invert_crc_cnt {
      type oc-yang:counter64;
      description
        "Counts the number of received packets with partial CRC type 1.";
    }
    leaf counter_slice7_ifg_mac_pool87_rx_mac_partial1_invert_crc_cnt_reg0_rx_mac_partial1_invert_crc_cnt {
      type oc-yang:counter64;
      description
        "Counts the number of received packets with partial CRC type 1.";
    }
    leaf counter_slice7_ifg_mac_pool87_rx_mac_partial1_invert_crc_cnt_reg1_rx_mac_partial1_invert_crc_cnt {
      type oc-yang:counter64;
      description
        "Counts the number of received packets with partial CRC type 1.";
    }
    leaf counter_slice7_ifg_mac_pool87_rx_mac_partial1_invert_crc_cnt_reg2_rx_mac_partial1_invert_crc_cnt {
      type oc-yang:counter64;
      description
        "Counts the number of received packets with partial CRC type 1.";
    }
    leaf counter_slice7_ifg_mac_pool87_rx_mac_partial1_invert_crc_cnt_reg3_rx_mac_partial1_invert_crc_cnt {
      type oc-yang:counter64;
      description
        "Counts the number of received packets with partial CRC type 1.";
    }
    leaf counter_slice7_ifg_mac_pool87_rx_mac_partial1_invert_crc_cnt_reg4_rx_mac_partial1_invert_crc_cnt {
      type oc-yang:counter64;
      description
        "Counts the number of received packets with partial CRC type 1.";
    }
    leaf counter_slice7_ifg_mac_pool87_rx_mac_partial1_invert_crc_cnt_reg5_rx_mac_partial1_invert_crc_cnt {
      type oc-yang:counter64;
      description
        "Counts the number of received packets with partial CRC type 1.";
    }
    leaf counter_slice7_ifg_mac_pool87_rx_mac_partial1_invert_crc_cnt_reg6_rx_mac_partial1_invert_crc_cnt {
      type oc-yang:counter64;
      description
        "Counts the number of received packets with partial CRC type 1.";
    }
    leaf counter_slice7_ifg_mac_pool87_rx_mac_partial1_invert_crc_cnt_reg7_rx_mac_partial1_invert_crc_cnt {
      type oc-yang:counter64;
      description
        "Counts the number of received packets with partial CRC type 1.";
    }
    leaf counter_slice8_ifg_mac_pool80_rx_mac_partial1_invert_crc_cnt_reg0_rx_mac_partial1_invert_crc_cnt {
      type oc-yang:counter64;
      description
        "Counts the number of received packets with partial CRC type 1.";
    }
    leaf counter_slice8_ifg_mac_pool80_rx_mac_partial1_invert_crc_cnt_reg1_rx_mac_partial1_invert_crc_cnt {
      type oc-yang:counter64;
      description
        "Counts the number of received packets with partial CRC type 1.";
    }
    leaf counter_slice8_ifg_mac_pool80_rx_mac_partial1_invert_crc_cnt_reg2_rx_mac_partial1_invert_crc_cnt {
      type oc-yang:counter64;
      description
        "Counts the number of received packets with partial CRC type 1.";
    }
    leaf counter_slice8_ifg_mac_pool80_rx_mac_partial1_invert_crc_cnt_reg3_rx_mac_partial1_invert_crc_cnt {
      type oc-yang:counter64;
      description
        "Counts the number of received packets with partial CRC type 1.";
    }
    leaf counter_slice8_ifg_mac_pool80_rx_mac_partial1_invert_crc_cnt_reg4_rx_mac_partial1_invert_crc_cnt {
      type oc-yang:counter64;
      description
        "Counts the number of received packets with partial CRC type 1.";
    }
    leaf counter_slice8_ifg_mac_pool80_rx_mac_partial1_invert_crc_cnt_reg5_rx_mac_partial1_invert_crc_cnt {
      type oc-yang:counter64;
      description
        "Counts the number of received packets with partial CRC type 1.";
    }
    leaf counter_slice8_ifg_mac_pool80_rx_mac_partial1_invert_crc_cnt_reg6_rx_mac_partial1_invert_crc_cnt {
      type oc-yang:counter64;
      description
        "Counts the number of received packets with partial CRC type 1.";
    }
    leaf counter_slice8_ifg_mac_pool80_rx_mac_partial1_invert_crc_cnt_reg7_rx_mac_partial1_invert_crc_cnt {
      type oc-yang:counter64;
      description
        "Counts the number of received packets with partial CRC type 1.";
    }
    leaf counter_slice8_ifg_mac_pool81_rx_mac_partial1_invert_crc_cnt_reg0_rx_mac_partial1_invert_crc_cnt {
      type oc-yang:counter64;
      description
        "Counts the number of received packets with partial CRC type 1.";
    }
    leaf counter_slice8_ifg_mac_pool81_rx_mac_partial1_invert_crc_cnt_reg1_rx_mac_partial1_invert_crc_cnt {
      type oc-yang:counter64;
      description
        "Counts the number of received packets with partial CRC type 1.";
    }
    leaf counter_slice8_ifg_mac_pool81_rx_mac_partial1_invert_crc_cnt_reg2_rx_mac_partial1_invert_crc_cnt {
      type oc-yang:counter64;
      description
        "Counts the number of received packets with partial CRC type 1.";
    }
    leaf counter_slice8_ifg_mac_pool81_rx_mac_partial1_invert_crc_cnt_reg3_rx_mac_partial1_invert_crc_cnt {
      type oc-yang:counter64;
      description
        "Counts the number of received packets with partial CRC type 1.";
    }
    leaf counter_slice8_ifg_mac_pool81_rx_mac_partial1_invert_crc_cnt_reg4_rx_mac_partial1_invert_crc_cnt {
      type oc-yang:counter64;
      description
        "Counts the number of received packets with partial CRC type 1.";
    }
    leaf counter_slice8_ifg_mac_pool81_rx_mac_partial1_invert_crc_cnt_reg5_rx_mac_partial1_invert_crc_cnt {
      type oc-yang:counter64;
      description
        "Counts the number of received packets with partial CRC type 1.";
    }
    leaf counter_slice8_ifg_mac_pool81_rx_mac_partial1_invert_crc_cnt_reg6_rx_mac_partial1_invert_crc_cnt {
      type oc-yang:counter64;
      description
        "Counts the number of received packets with partial CRC type 1.";
    }
    leaf counter_slice8_ifg_mac_pool81_rx_mac_partial1_invert_crc_cnt_reg7_rx_mac_partial1_invert_crc_cnt {
      type oc-yang:counter64;
      description
        "Counts the number of received packets with partial CRC type 1.";
    }
    leaf counter_slice8_ifg_mac_pool82_rx_mac_partial1_invert_crc_cnt_reg0_rx_mac_partial1_invert_crc_cnt {
      type oc-yang:counter64;
      description
        "Counts the number of received packets with partial CRC type 1.";
    }
    leaf counter_slice8_ifg_mac_pool82_rx_mac_partial1_invert_crc_cnt_reg1_rx_mac_partial1_invert_crc_cnt {
      type oc-yang:counter64;
      description
        "Counts the number of received packets with partial CRC type 1.";
    }
    leaf counter_slice8_ifg_mac_pool82_rx_mac_partial1_invert_crc_cnt_reg2_rx_mac_partial1_invert_crc_cnt {
      type oc-yang:counter64;
      description
        "Counts the number of received packets with partial CRC type 1.";
    }
    leaf counter_slice8_ifg_mac_pool82_rx_mac_partial1_invert_crc_cnt_reg3_rx_mac_partial1_invert_crc_cnt {
      type oc-yang:counter64;
      description
        "Counts the number of received packets with partial CRC type 1.";
    }
    leaf counter_slice8_ifg_mac_pool82_rx_mac_partial1_invert_crc_cnt_reg4_rx_mac_partial1_invert_crc_cnt {
      type oc-yang:counter64;
      description
        "Counts the number of received packets with partial CRC type 1.";
    }
    leaf counter_slice8_ifg_mac_pool82_rx_mac_partial1_invert_crc_cnt_reg5_rx_mac_partial1_invert_crc_cnt {
      type oc-yang:counter64;
      description
        "Counts the number of received packets with partial CRC type 1.";
    }
    leaf counter_slice8_ifg_mac_pool82_rx_mac_partial1_invert_crc_cnt_reg6_rx_mac_partial1_invert_crc_cnt {
      type oc-yang:counter64;
      description
        "Counts the number of received packets with partial CRC type 1.";
    }
    leaf counter_slice8_ifg_mac_pool82_rx_mac_partial1_invert_crc_cnt_reg7_rx_mac_partial1_invert_crc_cnt {
      type oc-yang:counter64;
      description
        "Counts the number of received packets with partial CRC type 1.";
    }
    leaf counter_slice8_ifg_mac_pool83_rx_mac_partial1_invert_crc_cnt_reg0_rx_mac_partial1_invert_crc_cnt {
      type oc-yang:counter64;
      description
        "Counts the number of received packets with partial CRC type 1.";
    }
    leaf counter_slice8_ifg_mac_pool83_rx_mac_partial1_invert_crc_cnt_reg1_rx_mac_partial1_invert_crc_cnt {
      type oc-yang:counter64;
      description
        "Counts the number of received packets with partial CRC type 1.";
    }
    leaf counter_slice8_ifg_mac_pool83_rx_mac_partial1_invert_crc_cnt_reg2_rx_mac_partial1_invert_crc_cnt {
      type oc-yang:counter64;
      description
        "Counts the number of received packets with partial CRC type 1.";
    }
    leaf counter_slice8_ifg_mac_pool83_rx_mac_partial1_invert_crc_cnt_reg3_rx_mac_partial1_invert_crc_cnt {
      type oc-yang:counter64;
      description
        "Counts the number of received packets with partial CRC type 1.";
    }
    leaf counter_slice8_ifg_mac_pool83_rx_mac_partial1_invert_crc_cnt_reg4_rx_mac_partial1_invert_crc_cnt {
      type oc-yang:counter64;
      description
        "Counts the number of received packets with partial CRC type 1.";
    }
    leaf counter_slice8_ifg_mac_pool83_rx_mac_partial1_invert_crc_cnt_reg5_rx_mac_partial1_invert_crc_cnt {
      type oc-yang:counter64;
      description
        "Counts the number of received packets with partial CRC type 1.";
    }
    leaf counter_slice8_ifg_mac_pool83_rx_mac_partial1_invert_crc_cnt_reg6_rx_mac_partial1_invert_crc_cnt {
      type oc-yang:counter64;
      description
        "Counts the number of received packets with partial CRC type 1.";
    }
    leaf counter_slice8_ifg_mac_pool83_rx_mac_partial1_invert_crc_cnt_reg7_rx_mac_partial1_invert_crc_cnt {
      type oc-yang:counter64;
      description
        "Counts the number of received packets with partial CRC type 1.";
    }
    leaf counter_slice8_ifg_mac_pool84_rx_mac_partial1_invert_crc_cnt_reg0_rx_mac_partial1_invert_crc_cnt {
      type oc-yang:counter64;
      description
        "Counts the number of received packets with partial CRC type 1.";
    }
    leaf counter_slice8_ifg_mac_pool84_rx_mac_partial1_invert_crc_cnt_reg1_rx_mac_partial1_invert_crc_cnt {
      type oc-yang:counter64;
      description
        "Counts the number of received packets with partial CRC type 1.";
    }
    leaf counter_slice8_ifg_mac_pool84_rx_mac_partial1_invert_crc_cnt_reg2_rx_mac_partial1_invert_crc_cnt {
      type oc-yang:counter64;
      description
        "Counts the number of received packets with partial CRC type 1.";
    }
    leaf counter_slice8_ifg_mac_pool84_rx_mac_partial1_invert_crc_cnt_reg3_rx_mac_partial1_invert_crc_cnt {
      type oc-yang:counter64;
      description
        "Counts the number of received packets with partial CRC type 1.";
    }
    leaf counter_slice8_ifg_mac_pool84_rx_mac_partial1_invert_crc_cnt_reg4_rx_mac_partial1_invert_crc_cnt {
      type oc-yang:counter64;
      description
        "Counts the number of received packets with partial CRC type 1.";
    }
    leaf counter_slice8_ifg_mac_pool84_rx_mac_partial1_invert_crc_cnt_reg5_rx_mac_partial1_invert_crc_cnt {
      type oc-yang:counter64;
      description
        "Counts the number of received packets with partial CRC type 1.";
    }
    leaf counter_slice8_ifg_mac_pool84_rx_mac_partial1_invert_crc_cnt_reg6_rx_mac_partial1_invert_crc_cnt {
      type oc-yang:counter64;
      description
        "Counts the number of received packets with partial CRC type 1.";
    }
    leaf counter_slice8_ifg_mac_pool84_rx_mac_partial1_invert_crc_cnt_reg7_rx_mac_partial1_invert_crc_cnt {
      type oc-yang:counter64;
      description
        "Counts the number of received packets with partial CRC type 1.";
    }
    leaf counter_slice8_ifg_mac_pool85_rx_mac_partial1_invert_crc_cnt_reg0_rx_mac_partial1_invert_crc_cnt {
      type oc-yang:counter64;
      description
        "Counts the number of received packets with partial CRC type 1.";
    }
    leaf counter_slice8_ifg_mac_pool85_rx_mac_partial1_invert_crc_cnt_reg1_rx_mac_partial1_invert_crc_cnt {
      type oc-yang:counter64;
      description
        "Counts the number of received packets with partial CRC type 1.";
    }
    leaf counter_slice8_ifg_mac_pool85_rx_mac_partial1_invert_crc_cnt_reg2_rx_mac_partial1_invert_crc_cnt {
      type oc-yang:counter64;
      description
        "Counts the number of received packets with partial CRC type 1.";
    }
    leaf counter_slice8_ifg_mac_pool85_rx_mac_partial1_invert_crc_cnt_reg3_rx_mac_partial1_invert_crc_cnt {
      type oc-yang:counter64;
      description
        "Counts the number of received packets with partial CRC type 1.";
    }
    leaf counter_slice8_ifg_mac_pool85_rx_mac_partial1_invert_crc_cnt_reg4_rx_mac_partial1_invert_crc_cnt {
      type oc-yang:counter64;
      description
        "Counts the number of received packets with partial CRC type 1.";
    }
    leaf counter_slice8_ifg_mac_pool85_rx_mac_partial1_invert_crc_cnt_reg5_rx_mac_partial1_invert_crc_cnt {
      type oc-yang:counter64;
      description
        "Counts the number of received packets with partial CRC type 1.";
    }
    leaf counter_slice8_ifg_mac_pool85_rx_mac_partial1_invert_crc_cnt_reg6_rx_mac_partial1_invert_crc_cnt {
      type oc-yang:counter64;
      description
        "Counts the number of received packets with partial CRC type 1.";
    }
    leaf counter_slice8_ifg_mac_pool85_rx_mac_partial1_invert_crc_cnt_reg7_rx_mac_partial1_invert_crc_cnt {
      type oc-yang:counter64;
      description
        "Counts the number of received packets with partial CRC type 1.";
    }
    leaf counter_slice8_ifg_mac_pool86_rx_mac_partial1_invert_crc_cnt_reg0_rx_mac_partial1_invert_crc_cnt {
      type oc-yang:counter64;
      description
        "Counts the number of received packets with partial CRC type 1.";
    }
    leaf counter_slice8_ifg_mac_pool86_rx_mac_partial1_invert_crc_cnt_reg1_rx_mac_partial1_invert_crc_cnt {
      type oc-yang:counter64;
      description
        "Counts the number of received packets with partial CRC type 1.";
    }
    leaf counter_slice8_ifg_mac_pool86_rx_mac_partial1_invert_crc_cnt_reg2_rx_mac_partial1_invert_crc_cnt {
      type oc-yang:counter64;
      description
        "Counts the number of received packets with partial CRC type 1.";
    }
    leaf counter_slice8_ifg_mac_pool86_rx_mac_partial1_invert_crc_cnt_reg3_rx_mac_partial1_invert_crc_cnt {
      type oc-yang:counter64;
      description
        "Counts the number of received packets with partial CRC type 1.";
    }
    leaf counter_slice8_ifg_mac_pool86_rx_mac_partial1_invert_crc_cnt_reg4_rx_mac_partial1_invert_crc_cnt {
      type oc-yang:counter64;
      description
        "Counts the number of received packets with partial CRC type 1.";
    }
    leaf counter_slice8_ifg_mac_pool86_rx_mac_partial1_invert_crc_cnt_reg5_rx_mac_partial1_invert_crc_cnt {
      type oc-yang:counter64;
      description
        "Counts the number of received packets with partial CRC type 1.";
    }
    leaf counter_slice8_ifg_mac_pool86_rx_mac_partial1_invert_crc_cnt_reg6_rx_mac_partial1_invert_crc_cnt {
      type oc-yang:counter64;
      description
        "Counts the number of received packets with partial CRC type 1.";
    }
    leaf counter_slice8_ifg_mac_pool86_rx_mac_partial1_invert_crc_cnt_reg7_rx_mac_partial1_invert_crc_cnt {
      type oc-yang:counter64;
      description
        "Counts the number of received packets with partial CRC type 1.";
    }
    leaf counter_slice8_ifg_mac_pool87_rx_mac_partial1_invert_crc_cnt_reg0_rx_mac_partial1_invert_crc_cnt {
      type oc-yang:counter64;
      description
        "Counts the number of received packets with partial CRC type 1.";
    }
    leaf counter_slice8_ifg_mac_pool87_rx_mac_partial1_invert_crc_cnt_reg1_rx_mac_partial1_invert_crc_cnt {
      type oc-yang:counter64;
      description
        "Counts the number of received packets with partial CRC type 1.";
    }
    leaf counter_slice8_ifg_mac_pool87_rx_mac_partial1_invert_crc_cnt_reg2_rx_mac_partial1_invert_crc_cnt {
      type oc-yang:counter64;
      description
        "Counts the number of received packets with partial CRC type 1.";
    }
    leaf counter_slice8_ifg_mac_pool87_rx_mac_partial1_invert_crc_cnt_reg3_rx_mac_partial1_invert_crc_cnt {
      type oc-yang:counter64;
      description
        "Counts the number of received packets with partial CRC type 1.";
    }
    leaf counter_slice8_ifg_mac_pool87_rx_mac_partial1_invert_crc_cnt_reg4_rx_mac_partial1_invert_crc_cnt {
      type oc-yang:counter64;
      description
        "Counts the number of received packets with partial CRC type 1.";
    }
    leaf counter_slice8_ifg_mac_pool87_rx_mac_partial1_invert_crc_cnt_reg5_rx_mac_partial1_invert_crc_cnt {
      type oc-yang:counter64;
      description
        "Counts the number of received packets with partial CRC type 1.";
    }
    leaf counter_slice8_ifg_mac_pool87_rx_mac_partial1_invert_crc_cnt_reg6_rx_mac_partial1_invert_crc_cnt {
      type oc-yang:counter64;
      description
        "Counts the number of received packets with partial CRC type 1.";
    }
    leaf counter_slice8_ifg_mac_pool87_rx_mac_partial1_invert_crc_cnt_reg7_rx_mac_partial1_invert_crc_cnt {
      type oc-yang:counter64;
      description
        "Counts the number of received packets with partial CRC type 1.";
    }
    leaf counter_slice9_ifg_mac_pool80_rx_mac_partial1_invert_crc_cnt_reg0_rx_mac_partial1_invert_crc_cnt {
      type oc-yang:counter64;
      description
        "Counts the number of received packets with partial CRC type 1.";
    }
    leaf counter_slice9_ifg_mac_pool80_rx_mac_partial1_invert_crc_cnt_reg1_rx_mac_partial1_invert_crc_cnt {
      type oc-yang:counter64;
      description
        "Counts the number of received packets with partial CRC type 1.";
    }
    leaf counter_slice9_ifg_mac_pool80_rx_mac_partial1_invert_crc_cnt_reg2_rx_mac_partial1_invert_crc_cnt {
      type oc-yang:counter64;
      description
        "Counts the number of received packets with partial CRC type 1.";
    }
    leaf counter_slice9_ifg_mac_pool80_rx_mac_partial1_invert_crc_cnt_reg3_rx_mac_partial1_invert_crc_cnt {
      type oc-yang:counter64;
      description
        "Counts the number of received packets with partial CRC type 1.";
    }
    leaf counter_slice9_ifg_mac_pool80_rx_mac_partial1_invert_crc_cnt_reg4_rx_mac_partial1_invert_crc_cnt {
      type oc-yang:counter64;
      description
        "Counts the number of received packets with partial CRC type 1.";
    }
    leaf counter_slice9_ifg_mac_pool80_rx_mac_partial1_invert_crc_cnt_reg5_rx_mac_partial1_invert_crc_cnt {
      type oc-yang:counter64;
      description
        "Counts the number of received packets with partial CRC type 1.";
    }
    leaf counter_slice9_ifg_mac_pool80_rx_mac_partial1_invert_crc_cnt_reg6_rx_mac_partial1_invert_crc_cnt {
      type oc-yang:counter64;
      description
        "Counts the number of received packets with partial CRC type 1.";
    }
    leaf counter_slice9_ifg_mac_pool80_rx_mac_partial1_invert_crc_cnt_reg7_rx_mac_partial1_invert_crc_cnt {
      type oc-yang:counter64;
      description
        "Counts the number of received packets with partial CRC type 1.";
    }
    leaf counter_slice9_ifg_mac_pool81_rx_mac_partial1_invert_crc_cnt_reg0_rx_mac_partial1_invert_crc_cnt {
      type oc-yang:counter64;
      description
        "Counts the number of received packets with partial CRC type 1.";
    }
    leaf counter_slice9_ifg_mac_pool81_rx_mac_partial1_invert_crc_cnt_reg1_rx_mac_partial1_invert_crc_cnt {
      type oc-yang:counter64;
      description
        "Counts the number of received packets with partial CRC type 1.";
    }
    leaf counter_slice9_ifg_mac_pool81_rx_mac_partial1_invert_crc_cnt_reg2_rx_mac_partial1_invert_crc_cnt {
      type oc-yang:counter64;
      description
        "Counts the number of received packets with partial CRC type 1.";
    }
    leaf counter_slice9_ifg_mac_pool81_rx_mac_partial1_invert_crc_cnt_reg3_rx_mac_partial1_invert_crc_cnt {
      type oc-yang:counter64;
      description
        "Counts the number of received packets with partial CRC type 1.";
    }
    leaf counter_slice9_ifg_mac_pool81_rx_mac_partial1_invert_crc_cnt_reg4_rx_mac_partial1_invert_crc_cnt {
      type oc-yang:counter64;
      description
        "Counts the number of received packets with partial CRC type 1.";
    }
    leaf counter_slice9_ifg_mac_pool81_rx_mac_partial1_invert_crc_cnt_reg5_rx_mac_partial1_invert_crc_cnt {
      type oc-yang:counter64;
      description
        "Counts the number of received packets with partial CRC type 1.";
    }
    leaf counter_slice9_ifg_mac_pool81_rx_mac_partial1_invert_crc_cnt_reg6_rx_mac_partial1_invert_crc_cnt {
      type oc-yang:counter64;
      description
        "Counts the number of received packets with partial CRC type 1.";
    }
    leaf counter_slice9_ifg_mac_pool81_rx_mac_partial1_invert_crc_cnt_reg7_rx_mac_partial1_invert_crc_cnt {
      type oc-yang:counter64;
      description
        "Counts the number of received packets with partial CRC type 1.";
    }
    leaf counter_slice9_ifg_mac_pool82_rx_mac_partial1_invert_crc_cnt_reg0_rx_mac_partial1_invert_crc_cnt {
      type oc-yang:counter64;
      description
        "Counts the number of received packets with partial CRC type 1.";
    }
    leaf counter_slice9_ifg_mac_pool82_rx_mac_partial1_invert_crc_cnt_reg1_rx_mac_partial1_invert_crc_cnt {
      type oc-yang:counter64;
      description
        "Counts the number of received packets with partial CRC type 1.";
    }
    leaf counter_slice9_ifg_mac_pool82_rx_mac_partial1_invert_crc_cnt_reg2_rx_mac_partial1_invert_crc_cnt {
      type oc-yang:counter64;
      description
        "Counts the number of received packets with partial CRC type 1.";
    }
    leaf counter_slice9_ifg_mac_pool82_rx_mac_partial1_invert_crc_cnt_reg3_rx_mac_partial1_invert_crc_cnt {
      type oc-yang:counter64;
      description
        "Counts the number of received packets with partial CRC type 1.";
    }
    leaf counter_slice9_ifg_mac_pool82_rx_mac_partial1_invert_crc_cnt_reg4_rx_mac_partial1_invert_crc_cnt {
      type oc-yang:counter64;
      description
        "Counts the number of received packets with partial CRC type 1.";
    }
    leaf counter_slice9_ifg_mac_pool82_rx_mac_partial1_invert_crc_cnt_reg5_rx_mac_partial1_invert_crc_cnt {
      type oc-yang:counter64;
      description
        "Counts the number of received packets with partial CRC type 1.";
    }
    leaf counter_slice9_ifg_mac_pool82_rx_mac_partial1_invert_crc_cnt_reg6_rx_mac_partial1_invert_crc_cnt {
      type oc-yang:counter64;
      description
        "Counts the number of received packets with partial CRC type 1.";
    }
    leaf counter_slice9_ifg_mac_pool82_rx_mac_partial1_invert_crc_cnt_reg7_rx_mac_partial1_invert_crc_cnt {
      type oc-yang:counter64;
      description
        "Counts the number of received packets with partial CRC type 1.";
    }
    leaf counter_slice9_ifg_mac_pool83_rx_mac_partial1_invert_crc_cnt_reg0_rx_mac_partial1_invert_crc_cnt {
      type oc-yang:counter64;
      description
        "Counts the number of received packets with partial CRC type 1.";
    }
    leaf counter_slice9_ifg_mac_pool83_rx_mac_partial1_invert_crc_cnt_reg1_rx_mac_partial1_invert_crc_cnt {
      type oc-yang:counter64;
      description
        "Counts the number of received packets with partial CRC type 1.";
    }
    leaf counter_slice9_ifg_mac_pool83_rx_mac_partial1_invert_crc_cnt_reg2_rx_mac_partial1_invert_crc_cnt {
      type oc-yang:counter64;
      description
        "Counts the number of received packets with partial CRC type 1.";
    }
    leaf counter_slice9_ifg_mac_pool83_rx_mac_partial1_invert_crc_cnt_reg3_rx_mac_partial1_invert_crc_cnt {
      type oc-yang:counter64;
      description
        "Counts the number of received packets with partial CRC type 1.";
    }
    leaf counter_slice9_ifg_mac_pool83_rx_mac_partial1_invert_crc_cnt_reg4_rx_mac_partial1_invert_crc_cnt {
      type oc-yang:counter64;
      description
        "Counts the number of received packets with partial CRC type 1.";
    }
    leaf counter_slice9_ifg_mac_pool83_rx_mac_partial1_invert_crc_cnt_reg5_rx_mac_partial1_invert_crc_cnt {
      type oc-yang:counter64;
      description
        "Counts the number of received packets with partial CRC type 1.";
    }
    leaf counter_slice9_ifg_mac_pool83_rx_mac_partial1_invert_crc_cnt_reg6_rx_mac_partial1_invert_crc_cnt {
      type oc-yang:counter64;
      description
        "Counts the number of received packets with partial CRC type 1.";
    }
    leaf counter_slice9_ifg_mac_pool83_rx_mac_partial1_invert_crc_cnt_reg7_rx_mac_partial1_invert_crc_cnt {
      type oc-yang:counter64;
      description
        "Counts the number of received packets with partial CRC type 1.";
    }
    leaf counter_slice9_ifg_mac_pool84_rx_mac_partial1_invert_crc_cnt_reg0_rx_mac_partial1_invert_crc_cnt {
      type oc-yang:counter64;
      description
        "Counts the number of received packets with partial CRC type 1.";
    }
    leaf counter_slice9_ifg_mac_pool84_rx_mac_partial1_invert_crc_cnt_reg1_rx_mac_partial1_invert_crc_cnt {
      type oc-yang:counter64;
      description
        "Counts the number of received packets with partial CRC type 1.";
    }
    leaf counter_slice9_ifg_mac_pool84_rx_mac_partial1_invert_crc_cnt_reg2_rx_mac_partial1_invert_crc_cnt {
      type oc-yang:counter64;
      description
        "Counts the number of received packets with partial CRC type 1.";
    }
    leaf counter_slice9_ifg_mac_pool84_rx_mac_partial1_invert_crc_cnt_reg3_rx_mac_partial1_invert_crc_cnt {
      type oc-yang:counter64;
      description
        "Counts the number of received packets with partial CRC type 1.";
    }
    leaf counter_slice9_ifg_mac_pool84_rx_mac_partial1_invert_crc_cnt_reg4_rx_mac_partial1_invert_crc_cnt {
      type oc-yang:counter64;
      description
        "Counts the number of received packets with partial CRC type 1.";
    }
    leaf counter_slice9_ifg_mac_pool84_rx_mac_partial1_invert_crc_cnt_reg5_rx_mac_partial1_invert_crc_cnt {
      type oc-yang:counter64;
      description
        "Counts the number of received packets with partial CRC type 1.";
    }
    leaf counter_slice9_ifg_mac_pool84_rx_mac_partial1_invert_crc_cnt_reg6_rx_mac_partial1_invert_crc_cnt {
      type oc-yang:counter64;
      description
        "Counts the number of received packets with partial CRC type 1.";
    }
    leaf counter_slice9_ifg_mac_pool84_rx_mac_partial1_invert_crc_cnt_reg7_rx_mac_partial1_invert_crc_cnt {
      type oc-yang:counter64;
      description
        "Counts the number of received packets with partial CRC type 1.";
    }
    leaf counter_slice9_ifg_mac_pool85_rx_mac_partial1_invert_crc_cnt_reg0_rx_mac_partial1_invert_crc_cnt {
      type oc-yang:counter64;
      description
        "Counts the number of received packets with partial CRC type 1.";
    }
    leaf counter_slice9_ifg_mac_pool85_rx_mac_partial1_invert_crc_cnt_reg1_rx_mac_partial1_invert_crc_cnt {
      type oc-yang:counter64;
      description
        "Counts the number of received packets with partial CRC type 1.";
    }
    leaf counter_slice9_ifg_mac_pool85_rx_mac_partial1_invert_crc_cnt_reg2_rx_mac_partial1_invert_crc_cnt {
      type oc-yang:counter64;
      description
        "Counts the number of received packets with partial CRC type 1.";
    }
    leaf counter_slice9_ifg_mac_pool85_rx_mac_partial1_invert_crc_cnt_reg3_rx_mac_partial1_invert_crc_cnt {
      type oc-yang:counter64;
      description
        "Counts the number of received packets with partial CRC type 1.";
    }
    leaf counter_slice9_ifg_mac_pool85_rx_mac_partial1_invert_crc_cnt_reg4_rx_mac_partial1_invert_crc_cnt {
      type oc-yang:counter64;
      description
        "Counts the number of received packets with partial CRC type 1.";
    }
    leaf counter_slice9_ifg_mac_pool85_rx_mac_partial1_invert_crc_cnt_reg5_rx_mac_partial1_invert_crc_cnt {
      type oc-yang:counter64;
      description
        "Counts the number of received packets with partial CRC type 1.";
    }
    leaf counter_slice9_ifg_mac_pool85_rx_mac_partial1_invert_crc_cnt_reg6_rx_mac_partial1_invert_crc_cnt {
      type oc-yang:counter64;
      description
        "Counts the number of received packets with partial CRC type 1.";
    }
    leaf counter_slice9_ifg_mac_pool85_rx_mac_partial1_invert_crc_cnt_reg7_rx_mac_partial1_invert_crc_cnt {
      type oc-yang:counter64;
      description
        "Counts the number of received packets with partial CRC type 1.";
    }
    leaf counter_slice9_ifg_mac_pool86_rx_mac_partial1_invert_crc_cnt_reg0_rx_mac_partial1_invert_crc_cnt {
      type oc-yang:counter64;
      description
        "Counts the number of received packets with partial CRC type 1.";
    }
    leaf counter_slice9_ifg_mac_pool86_rx_mac_partial1_invert_crc_cnt_reg1_rx_mac_partial1_invert_crc_cnt {
      type oc-yang:counter64;
      description
        "Counts the number of received packets with partial CRC type 1.";
    }
    leaf counter_slice9_ifg_mac_pool86_rx_mac_partial1_invert_crc_cnt_reg2_rx_mac_partial1_invert_crc_cnt {
      type oc-yang:counter64;
      description
        "Counts the number of received packets with partial CRC type 1.";
    }
    leaf counter_slice9_ifg_mac_pool86_rx_mac_partial1_invert_crc_cnt_reg3_rx_mac_partial1_invert_crc_cnt {
      type oc-yang:counter64;
      description
        "Counts the number of received packets with partial CRC type 1.";
    }
    leaf counter_slice9_ifg_mac_pool86_rx_mac_partial1_invert_crc_cnt_reg4_rx_mac_partial1_invert_crc_cnt {
      type oc-yang:counter64;
      description
        "Counts the number of received packets with partial CRC type 1.";
    }
    leaf counter_slice9_ifg_mac_pool86_rx_mac_partial1_invert_crc_cnt_reg5_rx_mac_partial1_invert_crc_cnt {
      type oc-yang:counter64;
      description
        "Counts the number of received packets with partial CRC type 1.";
    }
    leaf counter_slice9_ifg_mac_pool86_rx_mac_partial1_invert_crc_cnt_reg6_rx_mac_partial1_invert_crc_cnt {
      type oc-yang:counter64;
      description
        "Counts the number of received packets with partial CRC type 1.";
    }
    leaf counter_slice9_ifg_mac_pool86_rx_mac_partial1_invert_crc_cnt_reg7_rx_mac_partial1_invert_crc_cnt {
      type oc-yang:counter64;
      description
        "Counts the number of received packets with partial CRC type 1.";
    }
    leaf counter_slice9_ifg_mac_pool87_rx_mac_partial1_invert_crc_cnt_reg0_rx_mac_partial1_invert_crc_cnt {
      type oc-yang:counter64;
      description
        "Counts the number of received packets with partial CRC type 1.";
    }
    leaf counter_slice9_ifg_mac_pool87_rx_mac_partial1_invert_crc_cnt_reg1_rx_mac_partial1_invert_crc_cnt {
      type oc-yang:counter64;
      description
        "Counts the number of received packets with partial CRC type 1.";
    }
    leaf counter_slice9_ifg_mac_pool87_rx_mac_partial1_invert_crc_cnt_reg2_rx_mac_partial1_invert_crc_cnt {
      type oc-yang:counter64;
      description
        "Counts the number of received packets with partial CRC type 1.";
    }
    leaf counter_slice9_ifg_mac_pool87_rx_mac_partial1_invert_crc_cnt_reg3_rx_mac_partial1_invert_crc_cnt {
      type oc-yang:counter64;
      description
        "Counts the number of received packets with partial CRC type 1.";
    }
    leaf counter_slice9_ifg_mac_pool87_rx_mac_partial1_invert_crc_cnt_reg4_rx_mac_partial1_invert_crc_cnt {
      type oc-yang:counter64;
      description
        "Counts the number of received packets with partial CRC type 1.";
    }
    leaf counter_slice9_ifg_mac_pool87_rx_mac_partial1_invert_crc_cnt_reg5_rx_mac_partial1_invert_crc_cnt {
      type oc-yang:counter64;
      description
        "Counts the number of received packets with partial CRC type 1.";
    }
    leaf counter_slice9_ifg_mac_pool87_rx_mac_partial1_invert_crc_cnt_reg6_rx_mac_partial1_invert_crc_cnt {
      type oc-yang:counter64;
      description
        "Counts the number of received packets with partial CRC type 1.";
    }
    leaf counter_slice9_ifg_mac_pool87_rx_mac_partial1_invert_crc_cnt_reg7_rx_mac_partial1_invert_crc_cnt {
      type oc-yang:counter64;
      description
        "Counts the number of received packets with partial CRC type 1.";
    }
    leaf counter_slice10_ifg_mac_pool80_rx_mac_partial1_invert_crc_cnt_reg0_rx_mac_partial1_invert_crc_cnt {
      type oc-yang:counter64;
      description
        "Counts the number of received packets with partial CRC type 1.";
    }
    leaf counter_slice10_ifg_mac_pool80_rx_mac_partial1_invert_crc_cnt_reg1_rx_mac_partial1_invert_crc_cnt {
      type oc-yang:counter64;
      description
        "Counts the number of received packets with partial CRC type 1.";
    }
    leaf counter_slice10_ifg_mac_pool80_rx_mac_partial1_invert_crc_cnt_reg2_rx_mac_partial1_invert_crc_cnt {
      type oc-yang:counter64;
      description
        "Counts the number of received packets with partial CRC type 1.";
    }
    leaf counter_slice10_ifg_mac_pool80_rx_mac_partial1_invert_crc_cnt_reg3_rx_mac_partial1_invert_crc_cnt {
      type oc-yang:counter64;
      description
        "Counts the number of received packets with partial CRC type 1.";
    }
    leaf counter_slice10_ifg_mac_pool80_rx_mac_partial1_invert_crc_cnt_reg4_rx_mac_partial1_invert_crc_cnt {
      type oc-yang:counter64;
      description
        "Counts the number of received packets with partial CRC type 1.";
    }
    leaf counter_slice10_ifg_mac_pool80_rx_mac_partial1_invert_crc_cnt_reg5_rx_mac_partial1_invert_crc_cnt {
      type oc-yang:counter64;
      description
        "Counts the number of received packets with partial CRC type 1.";
    }
    leaf counter_slice10_ifg_mac_pool80_rx_mac_partial1_invert_crc_cnt_reg6_rx_mac_partial1_invert_crc_cnt {
      type oc-yang:counter64;
      description
        "Counts the number of received packets with partial CRC type 1.";
    }
    leaf counter_slice10_ifg_mac_pool80_rx_mac_partial1_invert_crc_cnt_reg7_rx_mac_partial1_invert_crc_cnt {
      type oc-yang:counter64;
      description
        "Counts the number of received packets with partial CRC type 1.";
    }
    leaf counter_slice10_ifg_mac_pool81_rx_mac_partial1_invert_crc_cnt_reg0_rx_mac_partial1_invert_crc_cnt {
      type oc-yang:counter64;
      description
        "Counts the number of received packets with partial CRC type 1.";
    }
    leaf counter_slice10_ifg_mac_pool81_rx_mac_partial1_invert_crc_cnt_reg1_rx_mac_partial1_invert_crc_cnt {
      type oc-yang:counter64;
      description
        "Counts the number of received packets with partial CRC type 1.";
    }
    leaf counter_slice10_ifg_mac_pool81_rx_mac_partial1_invert_crc_cnt_reg2_rx_mac_partial1_invert_crc_cnt {
      type oc-yang:counter64;
      description
        "Counts the number of received packets with partial CRC type 1.";
    }
    leaf counter_slice10_ifg_mac_pool81_rx_mac_partial1_invert_crc_cnt_reg3_rx_mac_partial1_invert_crc_cnt {
      type oc-yang:counter64;
      description
        "Counts the number of received packets with partial CRC type 1.";
    }
    leaf counter_slice10_ifg_mac_pool81_rx_mac_partial1_invert_crc_cnt_reg4_rx_mac_partial1_invert_crc_cnt {
      type oc-yang:counter64;
      description
        "Counts the number of received packets with partial CRC type 1.";
    }
    leaf counter_slice10_ifg_mac_pool81_rx_mac_partial1_invert_crc_cnt_reg5_rx_mac_partial1_invert_crc_cnt {
      type oc-yang:counter64;
      description
        "Counts the number of received packets with partial CRC type 1.";
    }
    leaf counter_slice10_ifg_mac_pool81_rx_mac_partial1_invert_crc_cnt_reg6_rx_mac_partial1_invert_crc_cnt {
      type oc-yang:counter64;
      description
        "Counts the number of received packets with partial CRC type 1.";
    }
    leaf counter_slice10_ifg_mac_pool81_rx_mac_partial1_invert_crc_cnt_reg7_rx_mac_partial1_invert_crc_cnt {
      type oc-yang:counter64;
      description
        "Counts the number of received packets with partial CRC type 1.";
    }
    leaf counter_slice10_ifg_mac_pool82_rx_mac_partial1_invert_crc_cnt_reg0_rx_mac_partial1_invert_crc_cnt {
      type oc-yang:counter64;
      description
        "Counts the number of received packets with partial CRC type 1.";
    }
    leaf counter_slice10_ifg_mac_pool82_rx_mac_partial1_invert_crc_cnt_reg1_rx_mac_partial1_invert_crc_cnt {
      type oc-yang:counter64;
      description
        "Counts the number of received packets with partial CRC type 1.";
    }
    leaf counter_slice10_ifg_mac_pool82_rx_mac_partial1_invert_crc_cnt_reg2_rx_mac_partial1_invert_crc_cnt {
      type oc-yang:counter64;
      description
        "Counts the number of received packets with partial CRC type 1.";
    }
    leaf counter_slice10_ifg_mac_pool82_rx_mac_partial1_invert_crc_cnt_reg3_rx_mac_partial1_invert_crc_cnt {
      type oc-yang:counter64;
      description
        "Counts the number of received packets with partial CRC type 1.";
    }
    leaf counter_slice10_ifg_mac_pool82_rx_mac_partial1_invert_crc_cnt_reg4_rx_mac_partial1_invert_crc_cnt {
      type oc-yang:counter64;
      description
        "Counts the number of received packets with partial CRC type 1.";
    }
    leaf counter_slice10_ifg_mac_pool82_rx_mac_partial1_invert_crc_cnt_reg5_rx_mac_partial1_invert_crc_cnt {
      type oc-yang:counter64;
      description
        "Counts the number of received packets with partial CRC type 1.";
    }
    leaf counter_slice10_ifg_mac_pool82_rx_mac_partial1_invert_crc_cnt_reg6_rx_mac_partial1_invert_crc_cnt {
      type oc-yang:counter64;
      description
        "Counts the number of received packets with partial CRC type 1.";
    }
    leaf counter_slice10_ifg_mac_pool82_rx_mac_partial1_invert_crc_cnt_reg7_rx_mac_partial1_invert_crc_cnt {
      type oc-yang:counter64;
      description
        "Counts the number of received packets with partial CRC type 1.";
    }
    leaf counter_slice10_ifg_mac_pool83_rx_mac_partial1_invert_crc_cnt_reg0_rx_mac_partial1_invert_crc_cnt {
      type oc-yang:counter64;
      description
        "Counts the number of received packets with partial CRC type 1.";
    }
    leaf counter_slice10_ifg_mac_pool83_rx_mac_partial1_invert_crc_cnt_reg1_rx_mac_partial1_invert_crc_cnt {
      type oc-yang:counter64;
      description
        "Counts the number of received packets with partial CRC type 1.";
    }
    leaf counter_slice10_ifg_mac_pool83_rx_mac_partial1_invert_crc_cnt_reg2_rx_mac_partial1_invert_crc_cnt {
      type oc-yang:counter64;
      description
        "Counts the number of received packets with partial CRC type 1.";
    }
    leaf counter_slice10_ifg_mac_pool83_rx_mac_partial1_invert_crc_cnt_reg3_rx_mac_partial1_invert_crc_cnt {
      type oc-yang:counter64;
      description
        "Counts the number of received packets with partial CRC type 1.";
    }
    leaf counter_slice10_ifg_mac_pool83_rx_mac_partial1_invert_crc_cnt_reg4_rx_mac_partial1_invert_crc_cnt {
      type oc-yang:counter64;
      description
        "Counts the number of received packets with partial CRC type 1.";
    }
    leaf counter_slice10_ifg_mac_pool83_rx_mac_partial1_invert_crc_cnt_reg5_rx_mac_partial1_invert_crc_cnt {
      type oc-yang:counter64;
      description
        "Counts the number of received packets with partial CRC type 1.";
    }
    leaf counter_slice10_ifg_mac_pool83_rx_mac_partial1_invert_crc_cnt_reg6_rx_mac_partial1_invert_crc_cnt {
      type oc-yang:counter64;
      description
        "Counts the number of received packets with partial CRC type 1.";
    }
    leaf counter_slice10_ifg_mac_pool83_rx_mac_partial1_invert_crc_cnt_reg7_rx_mac_partial1_invert_crc_cnt {
      type oc-yang:counter64;
      description
        "Counts the number of received packets with partial CRC type 1.";
    }
    leaf counter_slice10_ifg_mac_pool84_rx_mac_partial1_invert_crc_cnt_reg0_rx_mac_partial1_invert_crc_cnt {
      type oc-yang:counter64;
      description
        "Counts the number of received packets with partial CRC type 1.";
    }
    leaf counter_slice10_ifg_mac_pool84_rx_mac_partial1_invert_crc_cnt_reg1_rx_mac_partial1_invert_crc_cnt {
      type oc-yang:counter64;
      description
        "Counts the number of received packets with partial CRC type 1.";
    }
    leaf counter_slice10_ifg_mac_pool84_rx_mac_partial1_invert_crc_cnt_reg2_rx_mac_partial1_invert_crc_cnt {
      type oc-yang:counter64;
      description
        "Counts the number of received packets with partial CRC type 1.";
    }
    leaf counter_slice10_ifg_mac_pool84_rx_mac_partial1_invert_crc_cnt_reg3_rx_mac_partial1_invert_crc_cnt {
      type oc-yang:counter64;
      description
        "Counts the number of received packets with partial CRC type 1.";
    }
    leaf counter_slice10_ifg_mac_pool84_rx_mac_partial1_invert_crc_cnt_reg4_rx_mac_partial1_invert_crc_cnt {
      type oc-yang:counter64;
      description
        "Counts the number of received packets with partial CRC type 1.";
    }
    leaf counter_slice10_ifg_mac_pool84_rx_mac_partial1_invert_crc_cnt_reg5_rx_mac_partial1_invert_crc_cnt {
      type oc-yang:counter64;
      description
        "Counts the number of received packets with partial CRC type 1.";
    }
    leaf counter_slice10_ifg_mac_pool84_rx_mac_partial1_invert_crc_cnt_reg6_rx_mac_partial1_invert_crc_cnt {
      type oc-yang:counter64;
      description
        "Counts the number of received packets with partial CRC type 1.";
    }
    leaf counter_slice10_ifg_mac_pool84_rx_mac_partial1_invert_crc_cnt_reg7_rx_mac_partial1_invert_crc_cnt {
      type oc-yang:counter64;
      description
        "Counts the number of received packets with partial CRC type 1.";
    }
    leaf counter_slice10_ifg_mac_pool85_rx_mac_partial1_invert_crc_cnt_reg0_rx_mac_partial1_invert_crc_cnt {
      type oc-yang:counter64;
      description
        "Counts the number of received packets with partial CRC type 1.";
    }
    leaf counter_slice10_ifg_mac_pool85_rx_mac_partial1_invert_crc_cnt_reg1_rx_mac_partial1_invert_crc_cnt {
      type oc-yang:counter64;
      description
        "Counts the number of received packets with partial CRC type 1.";
    }
    leaf counter_slice10_ifg_mac_pool85_rx_mac_partial1_invert_crc_cnt_reg2_rx_mac_partial1_invert_crc_cnt {
      type oc-yang:counter64;
      description
        "Counts the number of received packets with partial CRC type 1.";
    }
    leaf counter_slice10_ifg_mac_pool85_rx_mac_partial1_invert_crc_cnt_reg3_rx_mac_partial1_invert_crc_cnt {
      type oc-yang:counter64;
      description
        "Counts the number of received packets with partial CRC type 1.";
    }
    leaf counter_slice10_ifg_mac_pool85_rx_mac_partial1_invert_crc_cnt_reg4_rx_mac_partial1_invert_crc_cnt {
      type oc-yang:counter64;
      description
        "Counts the number of received packets with partial CRC type 1.";
    }
    leaf counter_slice10_ifg_mac_pool85_rx_mac_partial1_invert_crc_cnt_reg5_rx_mac_partial1_invert_crc_cnt {
      type oc-yang:counter64;
      description
        "Counts the number of received packets with partial CRC type 1.";
    }
    leaf counter_slice10_ifg_mac_pool85_rx_mac_partial1_invert_crc_cnt_reg6_rx_mac_partial1_invert_crc_cnt {
      type oc-yang:counter64;
      description
        "Counts the number of received packets with partial CRC type 1.";
    }
    leaf counter_slice10_ifg_mac_pool85_rx_mac_partial1_invert_crc_cnt_reg7_rx_mac_partial1_invert_crc_cnt {
      type oc-yang:counter64;
      description
        "Counts the number of received packets with partial CRC type 1.";
    }
    leaf counter_slice10_ifg_mac_pool86_rx_mac_partial1_invert_crc_cnt_reg0_rx_mac_partial1_invert_crc_cnt {
      type oc-yang:counter64;
      description
        "Counts the number of received packets with partial CRC type 1.";
    }
    leaf counter_slice10_ifg_mac_pool86_rx_mac_partial1_invert_crc_cnt_reg1_rx_mac_partial1_invert_crc_cnt {
      type oc-yang:counter64;
      description
        "Counts the number of received packets with partial CRC type 1.";
    }
    leaf counter_slice10_ifg_mac_pool86_rx_mac_partial1_invert_crc_cnt_reg2_rx_mac_partial1_invert_crc_cnt {
      type oc-yang:counter64;
      description
        "Counts the number of received packets with partial CRC type 1.";
    }
    leaf counter_slice10_ifg_mac_pool86_rx_mac_partial1_invert_crc_cnt_reg3_rx_mac_partial1_invert_crc_cnt {
      type oc-yang:counter64;
      description
        "Counts the number of received packets with partial CRC type 1.";
    }
    leaf counter_slice10_ifg_mac_pool86_rx_mac_partial1_invert_crc_cnt_reg4_rx_mac_partial1_invert_crc_cnt {
      type oc-yang:counter64;
      description
        "Counts the number of received packets with partial CRC type 1.";
    }
    leaf counter_slice10_ifg_mac_pool86_rx_mac_partial1_invert_crc_cnt_reg5_rx_mac_partial1_invert_crc_cnt {
      type oc-yang:counter64;
      description
        "Counts the number of received packets with partial CRC type 1.";
    }
    leaf counter_slice10_ifg_mac_pool86_rx_mac_partial1_invert_crc_cnt_reg6_rx_mac_partial1_invert_crc_cnt {
      type oc-yang:counter64;
      description
        "Counts the number of received packets with partial CRC type 1.";
    }
    leaf counter_slice10_ifg_mac_pool86_rx_mac_partial1_invert_crc_cnt_reg7_rx_mac_partial1_invert_crc_cnt {
      type oc-yang:counter64;
      description
        "Counts the number of received packets with partial CRC type 1.";
    }
    leaf counter_slice10_ifg_mac_pool87_rx_mac_partial1_invert_crc_cnt_reg0_rx_mac_partial1_invert_crc_cnt {
      type oc-yang:counter64;
      description
        "Counts the number of received packets with partial CRC type 1.";
    }
    leaf counter_slice10_ifg_mac_pool87_rx_mac_partial1_invert_crc_cnt_reg1_rx_mac_partial1_invert_crc_cnt {
      type oc-yang:counter64;
      description
        "Counts the number of received packets with partial CRC type 1.";
    }
    leaf counter_slice10_ifg_mac_pool87_rx_mac_partial1_invert_crc_cnt_reg2_rx_mac_partial1_invert_crc_cnt {
      type oc-yang:counter64;
      description
        "Counts the number of received packets with partial CRC type 1.";
    }
    leaf counter_slice10_ifg_mac_pool87_rx_mac_partial1_invert_crc_cnt_reg3_rx_mac_partial1_invert_crc_cnt {
      type oc-yang:counter64;
      description
        "Counts the number of received packets with partial CRC type 1.";
    }
    leaf counter_slice10_ifg_mac_pool87_rx_mac_partial1_invert_crc_cnt_reg4_rx_mac_partial1_invert_crc_cnt {
      type oc-yang:counter64;
      description
        "Counts the number of received packets with partial CRC type 1.";
    }
    leaf counter_slice10_ifg_mac_pool87_rx_mac_partial1_invert_crc_cnt_reg5_rx_mac_partial1_invert_crc_cnt {
      type oc-yang:counter64;
      description
        "Counts the number of received packets with partial CRC type 1.";
    }
    leaf counter_slice10_ifg_mac_pool87_rx_mac_partial1_invert_crc_cnt_reg6_rx_mac_partial1_invert_crc_cnt {
      type oc-yang:counter64;
      description
        "Counts the number of received packets with partial CRC type 1.";
    }
    leaf counter_slice10_ifg_mac_pool87_rx_mac_partial1_invert_crc_cnt_reg7_rx_mac_partial1_invert_crc_cnt {
      type oc-yang:counter64;
      description
        "Counts the number of received packets with partial CRC type 1.";
    }
    leaf counter_slice11_ifg_mac_pool80_rx_mac_partial1_invert_crc_cnt_reg0_rx_mac_partial1_invert_crc_cnt {
      type oc-yang:counter64;
      description
        "Counts the number of received packets with partial CRC type 1.";
    }
    leaf counter_slice11_ifg_mac_pool80_rx_mac_partial1_invert_crc_cnt_reg1_rx_mac_partial1_invert_crc_cnt {
      type oc-yang:counter64;
      description
        "Counts the number of received packets with partial CRC type 1.";
    }
    leaf counter_slice11_ifg_mac_pool80_rx_mac_partial1_invert_crc_cnt_reg2_rx_mac_partial1_invert_crc_cnt {
      type oc-yang:counter64;
      description
        "Counts the number of received packets with partial CRC type 1.";
    }
    leaf counter_slice11_ifg_mac_pool80_rx_mac_partial1_invert_crc_cnt_reg3_rx_mac_partial1_invert_crc_cnt {
      type oc-yang:counter64;
      description
        "Counts the number of received packets with partial CRC type 1.";
    }
    leaf counter_slice11_ifg_mac_pool80_rx_mac_partial1_invert_crc_cnt_reg4_rx_mac_partial1_invert_crc_cnt {
      type oc-yang:counter64;
      description
        "Counts the number of received packets with partial CRC type 1.";
    }
    leaf counter_slice11_ifg_mac_pool80_rx_mac_partial1_invert_crc_cnt_reg5_rx_mac_partial1_invert_crc_cnt {
      type oc-yang:counter64;
      description
        "Counts the number of received packets with partial CRC type 1.";
    }
    leaf counter_slice11_ifg_mac_pool80_rx_mac_partial1_invert_crc_cnt_reg6_rx_mac_partial1_invert_crc_cnt {
      type oc-yang:counter64;
      description
        "Counts the number of received packets with partial CRC type 1.";
    }
    leaf counter_slice11_ifg_mac_pool80_rx_mac_partial1_invert_crc_cnt_reg7_rx_mac_partial1_invert_crc_cnt {
      type oc-yang:counter64;
      description
        "Counts the number of received packets with partial CRC type 1.";
    }
    leaf counter_slice11_ifg_mac_pool81_rx_mac_partial1_invert_crc_cnt_reg0_rx_mac_partial1_invert_crc_cnt {
      type oc-yang:counter64;
      description
        "Counts the number of received packets with partial CRC type 1.";
    }
    leaf counter_slice11_ifg_mac_pool81_rx_mac_partial1_invert_crc_cnt_reg1_rx_mac_partial1_invert_crc_cnt {
      type oc-yang:counter64;
      description
        "Counts the number of received packets with partial CRC type 1.";
    }
    leaf counter_slice11_ifg_mac_pool81_rx_mac_partial1_invert_crc_cnt_reg2_rx_mac_partial1_invert_crc_cnt {
      type oc-yang:counter64;
      description
        "Counts the number of received packets with partial CRC type 1.";
    }
    leaf counter_slice11_ifg_mac_pool81_rx_mac_partial1_invert_crc_cnt_reg3_rx_mac_partial1_invert_crc_cnt {
      type oc-yang:counter64;
      description
        "Counts the number of received packets with partial CRC type 1.";
    }
    leaf counter_slice11_ifg_mac_pool81_rx_mac_partial1_invert_crc_cnt_reg4_rx_mac_partial1_invert_crc_cnt {
      type oc-yang:counter64;
      description
        "Counts the number of received packets with partial CRC type 1.";
    }
    leaf counter_slice11_ifg_mac_pool81_rx_mac_partial1_invert_crc_cnt_reg5_rx_mac_partial1_invert_crc_cnt {
      type oc-yang:counter64;
      description
        "Counts the number of received packets with partial CRC type 1.";
    }
    leaf counter_slice11_ifg_mac_pool81_rx_mac_partial1_invert_crc_cnt_reg6_rx_mac_partial1_invert_crc_cnt {
      type oc-yang:counter64;
      description
        "Counts the number of received packets with partial CRC type 1.";
    }
    leaf counter_slice11_ifg_mac_pool81_rx_mac_partial1_invert_crc_cnt_reg7_rx_mac_partial1_invert_crc_cnt {
      type oc-yang:counter64;
      description
        "Counts the number of received packets with partial CRC type 1.";
    }
    leaf counter_slice11_ifg_mac_pool82_rx_mac_partial1_invert_crc_cnt_reg0_rx_mac_partial1_invert_crc_cnt {
      type oc-yang:counter64;
      description
        "Counts the number of received packets with partial CRC type 1.";
    }
    leaf counter_slice11_ifg_mac_pool82_rx_mac_partial1_invert_crc_cnt_reg1_rx_mac_partial1_invert_crc_cnt {
      type oc-yang:counter64;
      description
        "Counts the number of received packets with partial CRC type 1.";
    }
    leaf counter_slice11_ifg_mac_pool82_rx_mac_partial1_invert_crc_cnt_reg2_rx_mac_partial1_invert_crc_cnt {
      type oc-yang:counter64;
      description
        "Counts the number of received packets with partial CRC type 1.";
    }
    leaf counter_slice11_ifg_mac_pool82_rx_mac_partial1_invert_crc_cnt_reg3_rx_mac_partial1_invert_crc_cnt {
      type oc-yang:counter64;
      description
        "Counts the number of received packets with partial CRC type 1.";
    }
    leaf counter_slice11_ifg_mac_pool82_rx_mac_partial1_invert_crc_cnt_reg4_rx_mac_partial1_invert_crc_cnt {
      type oc-yang:counter64;
      description
        "Counts the number of received packets with partial CRC type 1.";
    }
    leaf counter_slice11_ifg_mac_pool82_rx_mac_partial1_invert_crc_cnt_reg5_rx_mac_partial1_invert_crc_cnt {
      type oc-yang:counter64;
      description
        "Counts the number of received packets with partial CRC type 1.";
    }
    leaf counter_slice11_ifg_mac_pool82_rx_mac_partial1_invert_crc_cnt_reg6_rx_mac_partial1_invert_crc_cnt {
      type oc-yang:counter64;
      description
        "Counts the number of received packets with partial CRC type 1.";
    }
    leaf counter_slice11_ifg_mac_pool82_rx_mac_partial1_invert_crc_cnt_reg7_rx_mac_partial1_invert_crc_cnt {
      type oc-yang:counter64;
      description
        "Counts the number of received packets with partial CRC type 1.";
    }
    leaf counter_slice11_ifg_mac_pool83_rx_mac_partial1_invert_crc_cnt_reg0_rx_mac_partial1_invert_crc_cnt {
      type oc-yang:counter64;
      description
        "Counts the number of received packets with partial CRC type 1.";
    }
    leaf counter_slice11_ifg_mac_pool83_rx_mac_partial1_invert_crc_cnt_reg1_rx_mac_partial1_invert_crc_cnt {
      type oc-yang:counter64;
      description
        "Counts the number of received packets with partial CRC type 1.";
    }
    leaf counter_slice11_ifg_mac_pool83_rx_mac_partial1_invert_crc_cnt_reg2_rx_mac_partial1_invert_crc_cnt {
      type oc-yang:counter64;
      description
        "Counts the number of received packets with partial CRC type 1.";
    }
    leaf counter_slice11_ifg_mac_pool83_rx_mac_partial1_invert_crc_cnt_reg3_rx_mac_partial1_invert_crc_cnt {
      type oc-yang:counter64;
      description
        "Counts the number of received packets with partial CRC type 1.";
    }
    leaf counter_slice11_ifg_mac_pool83_rx_mac_partial1_invert_crc_cnt_reg4_rx_mac_partial1_invert_crc_cnt {
      type oc-yang:counter64;
      description
        "Counts the number of received packets with partial CRC type 1.";
    }
    leaf counter_slice11_ifg_mac_pool83_rx_mac_partial1_invert_crc_cnt_reg5_rx_mac_partial1_invert_crc_cnt {
      type oc-yang:counter64;
      description
        "Counts the number of received packets with partial CRC type 1.";
    }
    leaf counter_slice11_ifg_mac_pool83_rx_mac_partial1_invert_crc_cnt_reg6_rx_mac_partial1_invert_crc_cnt {
      type oc-yang:counter64;
      description
        "Counts the number of received packets with partial CRC type 1.";
    }
    leaf counter_slice11_ifg_mac_pool83_rx_mac_partial1_invert_crc_cnt_reg7_rx_mac_partial1_invert_crc_cnt {
      type oc-yang:counter64;
      description
        "Counts the number of received packets with partial CRC type 1.";
    }
    leaf counter_slice11_ifg_mac_pool84_rx_mac_partial1_invert_crc_cnt_reg0_rx_mac_partial1_invert_crc_cnt {
      type oc-yang:counter64;
      description
        "Counts the number of received packets with partial CRC type 1.";
    }
    leaf counter_slice11_ifg_mac_pool84_rx_mac_partial1_invert_crc_cnt_reg1_rx_mac_partial1_invert_crc_cnt {
      type oc-yang:counter64;
      description
        "Counts the number of received packets with partial CRC type 1.";
    }
    leaf counter_slice11_ifg_mac_pool84_rx_mac_partial1_invert_crc_cnt_reg2_rx_mac_partial1_invert_crc_cnt {
      type oc-yang:counter64;
      description
        "Counts the number of received packets with partial CRC type 1.";
    }
    leaf counter_slice11_ifg_mac_pool84_rx_mac_partial1_invert_crc_cnt_reg3_rx_mac_partial1_invert_crc_cnt {
      type oc-yang:counter64;
      description
        "Counts the number of received packets with partial CRC type 1.";
    }
    leaf counter_slice11_ifg_mac_pool84_rx_mac_partial1_invert_crc_cnt_reg4_rx_mac_partial1_invert_crc_cnt {
      type oc-yang:counter64;
      description
        "Counts the number of received packets with partial CRC type 1.";
    }
    leaf counter_slice11_ifg_mac_pool84_rx_mac_partial1_invert_crc_cnt_reg5_rx_mac_partial1_invert_crc_cnt {
      type oc-yang:counter64;
      description
        "Counts the number of received packets with partial CRC type 1.";
    }
    leaf counter_slice11_ifg_mac_pool84_rx_mac_partial1_invert_crc_cnt_reg6_rx_mac_partial1_invert_crc_cnt {
      type oc-yang:counter64;
      description
        "Counts the number of received packets with partial CRC type 1.";
    }
    leaf counter_slice11_ifg_mac_pool84_rx_mac_partial1_invert_crc_cnt_reg7_rx_mac_partial1_invert_crc_cnt {
      type oc-yang:counter64;
      description
        "Counts the number of received packets with partial CRC type 1.";
    }
    leaf counter_slice11_ifg_mac_pool85_rx_mac_partial1_invert_crc_cnt_reg0_rx_mac_partial1_invert_crc_cnt {
      type oc-yang:counter64;
      description
        "Counts the number of received packets with partial CRC type 1.";
    }
    leaf counter_slice11_ifg_mac_pool85_rx_mac_partial1_invert_crc_cnt_reg1_rx_mac_partial1_invert_crc_cnt {
      type oc-yang:counter64;
      description
        "Counts the number of received packets with partial CRC type 1.";
    }
    leaf counter_slice11_ifg_mac_pool85_rx_mac_partial1_invert_crc_cnt_reg2_rx_mac_partial1_invert_crc_cnt {
      type oc-yang:counter64;
      description
        "Counts the number of received packets with partial CRC type 1.";
    }
    leaf counter_slice11_ifg_mac_pool85_rx_mac_partial1_invert_crc_cnt_reg3_rx_mac_partial1_invert_crc_cnt {
      type oc-yang:counter64;
      description
        "Counts the number of received packets with partial CRC type 1.";
    }
    leaf counter_slice11_ifg_mac_pool85_rx_mac_partial1_invert_crc_cnt_reg4_rx_mac_partial1_invert_crc_cnt {
      type oc-yang:counter64;
      description
        "Counts the number of received packets with partial CRC type 1.";
    }
    leaf counter_slice11_ifg_mac_pool85_rx_mac_partial1_invert_crc_cnt_reg5_rx_mac_partial1_invert_crc_cnt {
      type oc-yang:counter64;
      description
        "Counts the number of received packets with partial CRC type 1.";
    }
    leaf counter_slice11_ifg_mac_pool85_rx_mac_partial1_invert_crc_cnt_reg6_rx_mac_partial1_invert_crc_cnt {
      type oc-yang:counter64;
      description
        "Counts the number of received packets with partial CRC type 1.";
    }
    leaf counter_slice11_ifg_mac_pool85_rx_mac_partial1_invert_crc_cnt_reg7_rx_mac_partial1_invert_crc_cnt {
      type oc-yang:counter64;
      description
        "Counts the number of received packets with partial CRC type 1.";
    }
    leaf counter_slice11_ifg_mac_pool86_rx_mac_partial1_invert_crc_cnt_reg0_rx_mac_partial1_invert_crc_cnt {
      type oc-yang:counter64;
      description
        "Counts the number of received packets with partial CRC type 1.";
    }
    leaf counter_slice11_ifg_mac_pool86_rx_mac_partial1_invert_crc_cnt_reg1_rx_mac_partial1_invert_crc_cnt {
      type oc-yang:counter64;
      description
        "Counts the number of received packets with partial CRC type 1.";
    }
    leaf counter_slice11_ifg_mac_pool86_rx_mac_partial1_invert_crc_cnt_reg2_rx_mac_partial1_invert_crc_cnt {
      type oc-yang:counter64;
      description
        "Counts the number of received packets with partial CRC type 1.";
    }
    leaf counter_slice11_ifg_mac_pool86_rx_mac_partial1_invert_crc_cnt_reg3_rx_mac_partial1_invert_crc_cnt {
      type oc-yang:counter64;
      description
        "Counts the number of received packets with partial CRC type 1.";
    }
    leaf counter_slice11_ifg_mac_pool86_rx_mac_partial1_invert_crc_cnt_reg4_rx_mac_partial1_invert_crc_cnt {
      type oc-yang:counter64;
      description
        "Counts the number of received packets with partial CRC type 1.";
    }
    leaf counter_slice11_ifg_mac_pool86_rx_mac_partial1_invert_crc_cnt_reg5_rx_mac_partial1_invert_crc_cnt {
      type oc-yang:counter64;
      description
        "Counts the number of received packets with partial CRC type 1.";
    }
    leaf counter_slice11_ifg_mac_pool86_rx_mac_partial1_invert_crc_cnt_reg6_rx_mac_partial1_invert_crc_cnt {
      type oc-yang:counter64;
      description
        "Counts the number of received packets with partial CRC type 1.";
    }
    leaf counter_slice11_ifg_mac_pool86_rx_mac_partial1_invert_crc_cnt_reg7_rx_mac_partial1_invert_crc_cnt {
      type oc-yang:counter64;
      description
        "Counts the number of received packets with partial CRC type 1.";
    }
    leaf counter_slice11_ifg_mac_pool87_rx_mac_partial1_invert_crc_cnt_reg0_rx_mac_partial1_invert_crc_cnt {
      type oc-yang:counter64;
      description
        "Counts the number of received packets with partial CRC type 1.";
    }
    leaf counter_slice11_ifg_mac_pool87_rx_mac_partial1_invert_crc_cnt_reg1_rx_mac_partial1_invert_crc_cnt {
      type oc-yang:counter64;
      description
        "Counts the number of received packets with partial CRC type 1.";
    }
    leaf counter_slice11_ifg_mac_pool87_rx_mac_partial1_invert_crc_cnt_reg2_rx_mac_partial1_invert_crc_cnt {
      type oc-yang:counter64;
      description
        "Counts the number of received packets with partial CRC type 1.";
    }
    leaf counter_slice11_ifg_mac_pool87_rx_mac_partial1_invert_crc_cnt_reg3_rx_mac_partial1_invert_crc_cnt {
      type oc-yang:counter64;
      description
        "Counts the number of received packets with partial CRC type 1.";
    }
    leaf counter_slice11_ifg_mac_pool87_rx_mac_partial1_invert_crc_cnt_reg4_rx_mac_partial1_invert_crc_cnt {
      type oc-yang:counter64;
      description
        "Counts the number of received packets with partial CRC type 1.";
    }
    leaf counter_slice11_ifg_mac_pool87_rx_mac_partial1_invert_crc_cnt_reg5_rx_mac_partial1_invert_crc_cnt {
      type oc-yang:counter64;
      description
        "Counts the number of received packets with partial CRC type 1.";
    }
    leaf counter_slice11_ifg_mac_pool87_rx_mac_partial1_invert_crc_cnt_reg6_rx_mac_partial1_invert_crc_cnt {
      type oc-yang:counter64;
      description
        "Counts the number of received packets with partial CRC type 1.";
    }
    leaf counter_slice11_ifg_mac_pool87_rx_mac_partial1_invert_crc_cnt_reg7_rx_mac_partial1_invert_crc_cnt {
      type oc-yang:counter64;
      description
        "Counts the number of received packets with partial CRC type 1.";
    }
    leaf counter_slice12_ifg_mac_pool80_rx_mac_partial1_invert_crc_cnt_reg0_rx_mac_partial1_invert_crc_cnt {
      type oc-yang:counter64;
      description
        "Counts the number of received packets with partial CRC type 1.";
    }
    leaf counter_slice12_ifg_mac_pool80_rx_mac_partial1_invert_crc_cnt_reg1_rx_mac_partial1_invert_crc_cnt {
      type oc-yang:counter64;
      description
        "Counts the number of received packets with partial CRC type 1.";
    }
    leaf counter_slice12_ifg_mac_pool80_rx_mac_partial1_invert_crc_cnt_reg2_rx_mac_partial1_invert_crc_cnt {
      type oc-yang:counter64;
      description
        "Counts the number of received packets with partial CRC type 1.";
    }
    leaf counter_slice12_ifg_mac_pool80_rx_mac_partial1_invert_crc_cnt_reg3_rx_mac_partial1_invert_crc_cnt {
      type oc-yang:counter64;
      description
        "Counts the number of received packets with partial CRC type 1.";
    }
    leaf counter_slice12_ifg_mac_pool80_rx_mac_partial1_invert_crc_cnt_reg4_rx_mac_partial1_invert_crc_cnt {
      type oc-yang:counter64;
      description
        "Counts the number of received packets with partial CRC type 1.";
    }
    leaf counter_slice12_ifg_mac_pool80_rx_mac_partial1_invert_crc_cnt_reg5_rx_mac_partial1_invert_crc_cnt {
      type oc-yang:counter64;
      description
        "Counts the number of received packets with partial CRC type 1.";
    }
    leaf counter_slice12_ifg_mac_pool80_rx_mac_partial1_invert_crc_cnt_reg6_rx_mac_partial1_invert_crc_cnt {
      type oc-yang:counter64;
      description
        "Counts the number of received packets with partial CRC type 1.";
    }
    leaf counter_slice12_ifg_mac_pool80_rx_mac_partial1_invert_crc_cnt_reg7_rx_mac_partial1_invert_crc_cnt {
      type oc-yang:counter64;
      description
        "Counts the number of received packets with partial CRC type 1.";
    }
    leaf counter_slice12_ifg_mac_pool81_rx_mac_partial1_invert_crc_cnt_reg0_rx_mac_partial1_invert_crc_cnt {
      type oc-yang:counter64;
      description
        "Counts the number of received packets with partial CRC type 1.";
    }
    leaf counter_slice12_ifg_mac_pool81_rx_mac_partial1_invert_crc_cnt_reg1_rx_mac_partial1_invert_crc_cnt {
      type oc-yang:counter64;
      description
        "Counts the number of received packets with partial CRC type 1.";
    }
    leaf counter_slice12_ifg_mac_pool81_rx_mac_partial1_invert_crc_cnt_reg2_rx_mac_partial1_invert_crc_cnt {
      type oc-yang:counter64;
      description
        "Counts the number of received packets with partial CRC type 1.";
    }
    leaf counter_slice12_ifg_mac_pool81_rx_mac_partial1_invert_crc_cnt_reg3_rx_mac_partial1_invert_crc_cnt {
      type oc-yang:counter64;
      description
        "Counts the number of received packets with partial CRC type 1.";
    }
    leaf counter_slice12_ifg_mac_pool81_rx_mac_partial1_invert_crc_cnt_reg4_rx_mac_partial1_invert_crc_cnt {
      type oc-yang:counter64;
      description
        "Counts the number of received packets with partial CRC type 1.";
    }
    leaf counter_slice12_ifg_mac_pool81_rx_mac_partial1_invert_crc_cnt_reg5_rx_mac_partial1_invert_crc_cnt {
      type oc-yang:counter64;
      description
        "Counts the number of received packets with partial CRC type 1.";
    }
    leaf counter_slice12_ifg_mac_pool81_rx_mac_partial1_invert_crc_cnt_reg6_rx_mac_partial1_invert_crc_cnt {
      type oc-yang:counter64;
      description
        "Counts the number of received packets with partial CRC type 1.";
    }
    leaf counter_slice12_ifg_mac_pool81_rx_mac_partial1_invert_crc_cnt_reg7_rx_mac_partial1_invert_crc_cnt {
      type oc-yang:counter64;
      description
        "Counts the number of received packets with partial CRC type 1.";
    }
    leaf counter_slice12_ifg_mac_pool82_rx_mac_partial1_invert_crc_cnt_reg0_rx_mac_partial1_invert_crc_cnt {
      type oc-yang:counter64;
      description
        "Counts the number of received packets with partial CRC type 1.";
    }
    leaf counter_slice12_ifg_mac_pool82_rx_mac_partial1_invert_crc_cnt_reg1_rx_mac_partial1_invert_crc_cnt {
      type oc-yang:counter64;
      description
        "Counts the number of received packets with partial CRC type 1.";
    }
    leaf counter_slice12_ifg_mac_pool82_rx_mac_partial1_invert_crc_cnt_reg2_rx_mac_partial1_invert_crc_cnt {
      type oc-yang:counter64;
      description
        "Counts the number of received packets with partial CRC type 1.";
    }
    leaf counter_slice12_ifg_mac_pool82_rx_mac_partial1_invert_crc_cnt_reg3_rx_mac_partial1_invert_crc_cnt {
      type oc-yang:counter64;
      description
        "Counts the number of received packets with partial CRC type 1.";
    }
    leaf counter_slice12_ifg_mac_pool82_rx_mac_partial1_invert_crc_cnt_reg4_rx_mac_partial1_invert_crc_cnt {
      type oc-yang:counter64;
      description
        "Counts the number of received packets with partial CRC type 1.";
    }
    leaf counter_slice12_ifg_mac_pool82_rx_mac_partial1_invert_crc_cnt_reg5_rx_mac_partial1_invert_crc_cnt {
      type oc-yang:counter64;
      description
        "Counts the number of received packets with partial CRC type 1.";
    }
    leaf counter_slice12_ifg_mac_pool82_rx_mac_partial1_invert_crc_cnt_reg6_rx_mac_partial1_invert_crc_cnt {
      type oc-yang:counter64;
      description
        "Counts the number of received packets with partial CRC type 1.";
    }
    leaf counter_slice12_ifg_mac_pool82_rx_mac_partial1_invert_crc_cnt_reg7_rx_mac_partial1_invert_crc_cnt {
      type oc-yang:counter64;
      description
        "Counts the number of received packets with partial CRC type 1.";
    }
    leaf counter_slice12_ifg_mac_pool83_rx_mac_partial1_invert_crc_cnt_reg0_rx_mac_partial1_invert_crc_cnt {
      type oc-yang:counter64;
      description
        "Counts the number of received packets with partial CRC type 1.";
    }
    leaf counter_slice12_ifg_mac_pool83_rx_mac_partial1_invert_crc_cnt_reg1_rx_mac_partial1_invert_crc_cnt {
      type oc-yang:counter64;
      description
        "Counts the number of received packets with partial CRC type 1.";
    }
    leaf counter_slice12_ifg_mac_pool83_rx_mac_partial1_invert_crc_cnt_reg2_rx_mac_partial1_invert_crc_cnt {
      type oc-yang:counter64;
      description
        "Counts the number of received packets with partial CRC type 1.";
    }
    leaf counter_slice12_ifg_mac_pool83_rx_mac_partial1_invert_crc_cnt_reg3_rx_mac_partial1_invert_crc_cnt {
      type oc-yang:counter64;
      description
        "Counts the number of received packets with partial CRC type 1.";
    }
    leaf counter_slice12_ifg_mac_pool83_rx_mac_partial1_invert_crc_cnt_reg4_rx_mac_partial1_invert_crc_cnt {
      type oc-yang:counter64;
      description
        "Counts the number of received packets with partial CRC type 1.";
    }
    leaf counter_slice12_ifg_mac_pool83_rx_mac_partial1_invert_crc_cnt_reg5_rx_mac_partial1_invert_crc_cnt {
      type oc-yang:counter64;
      description
        "Counts the number of received packets with partial CRC type 1.";
    }
    leaf counter_slice12_ifg_mac_pool83_rx_mac_partial1_invert_crc_cnt_reg6_rx_mac_partial1_invert_crc_cnt {
      type oc-yang:counter64;
      description
        "Counts the number of received packets with partial CRC type 1.";
    }
    leaf counter_slice12_ifg_mac_pool83_rx_mac_partial1_invert_crc_cnt_reg7_rx_mac_partial1_invert_crc_cnt {
      type oc-yang:counter64;
      description
        "Counts the number of received packets with partial CRC type 1.";
    }
    leaf counter_slice12_ifg_mac_pool84_rx_mac_partial1_invert_crc_cnt_reg0_rx_mac_partial1_invert_crc_cnt {
      type oc-yang:counter64;
      description
        "Counts the number of received packets with partial CRC type 1.";
    }
    leaf counter_slice12_ifg_mac_pool84_rx_mac_partial1_invert_crc_cnt_reg1_rx_mac_partial1_invert_crc_cnt {
      type oc-yang:counter64;
      description
        "Counts the number of received packets with partial CRC type 1.";
    }
    leaf counter_slice12_ifg_mac_pool84_rx_mac_partial1_invert_crc_cnt_reg2_rx_mac_partial1_invert_crc_cnt {
      type oc-yang:counter64;
      description
        "Counts the number of received packets with partial CRC type 1.";
    }
    leaf counter_slice12_ifg_mac_pool84_rx_mac_partial1_invert_crc_cnt_reg3_rx_mac_partial1_invert_crc_cnt {
      type oc-yang:counter64;
      description
        "Counts the number of received packets with partial CRC type 1.";
    }
    leaf counter_slice12_ifg_mac_pool84_rx_mac_partial1_invert_crc_cnt_reg4_rx_mac_partial1_invert_crc_cnt {
      type oc-yang:counter64;
      description
        "Counts the number of received packets with partial CRC type 1.";
    }
    leaf counter_slice12_ifg_mac_pool84_rx_mac_partial1_invert_crc_cnt_reg5_rx_mac_partial1_invert_crc_cnt {
      type oc-yang:counter64;
      description
        "Counts the number of received packets with partial CRC type 1.";
    }
    leaf counter_slice12_ifg_mac_pool84_rx_mac_partial1_invert_crc_cnt_reg6_rx_mac_partial1_invert_crc_cnt {
      type oc-yang:counter64;
      description
        "Counts the number of received packets with partial CRC type 1.";
    }
    leaf counter_slice12_ifg_mac_pool84_rx_mac_partial1_invert_crc_cnt_reg7_rx_mac_partial1_invert_crc_cnt {
      type oc-yang:counter64;
      description
        "Counts the number of received packets with partial CRC type 1.";
    }
    leaf counter_slice12_ifg_mac_pool85_rx_mac_partial1_invert_crc_cnt_reg0_rx_mac_partial1_invert_crc_cnt {
      type oc-yang:counter64;
      description
        "Counts the number of received packets with partial CRC type 1.";
    }
    leaf counter_slice12_ifg_mac_pool85_rx_mac_partial1_invert_crc_cnt_reg1_rx_mac_partial1_invert_crc_cnt {
      type oc-yang:counter64;
      description
        "Counts the number of received packets with partial CRC type 1.";
    }
    leaf counter_slice12_ifg_mac_pool85_rx_mac_partial1_invert_crc_cnt_reg2_rx_mac_partial1_invert_crc_cnt {
      type oc-yang:counter64;
      description
        "Counts the number of received packets with partial CRC type 1.";
    }
    leaf counter_slice12_ifg_mac_pool85_rx_mac_partial1_invert_crc_cnt_reg3_rx_mac_partial1_invert_crc_cnt {
      type oc-yang:counter64;
      description
        "Counts the number of received packets with partial CRC type 1.";
    }
    leaf counter_slice12_ifg_mac_pool85_rx_mac_partial1_invert_crc_cnt_reg4_rx_mac_partial1_invert_crc_cnt {
      type oc-yang:counter64;
      description
        "Counts the number of received packets with partial CRC type 1.";
    }
    leaf counter_slice12_ifg_mac_pool85_rx_mac_partial1_invert_crc_cnt_reg5_rx_mac_partial1_invert_crc_cnt {
      type oc-yang:counter64;
      description
        "Counts the number of received packets with partial CRC type 1.";
    }
    leaf counter_slice12_ifg_mac_pool85_rx_mac_partial1_invert_crc_cnt_reg6_rx_mac_partial1_invert_crc_cnt {
      type oc-yang:counter64;
      description
        "Counts the number of received packets with partial CRC type 1.";
    }
    leaf counter_slice12_ifg_mac_pool85_rx_mac_partial1_invert_crc_cnt_reg7_rx_mac_partial1_invert_crc_cnt {
      type oc-yang:counter64;
      description
        "Counts the number of received packets with partial CRC type 1.";
    }
    leaf counter_slice12_ifg_mac_pool86_rx_mac_partial1_invert_crc_cnt_reg0_rx_mac_partial1_invert_crc_cnt {
      type oc-yang:counter64;
      description
        "Counts the number of received packets with partial CRC type 1.";
    }
    leaf counter_slice12_ifg_mac_pool86_rx_mac_partial1_invert_crc_cnt_reg1_rx_mac_partial1_invert_crc_cnt {
      type oc-yang:counter64;
      description
        "Counts the number of received packets with partial CRC type 1.";
    }
    leaf counter_slice12_ifg_mac_pool86_rx_mac_partial1_invert_crc_cnt_reg2_rx_mac_partial1_invert_crc_cnt {
      type oc-yang:counter64;
      description
        "Counts the number of received packets with partial CRC type 1.";
    }
    leaf counter_slice12_ifg_mac_pool86_rx_mac_partial1_invert_crc_cnt_reg3_rx_mac_partial1_invert_crc_cnt {
      type oc-yang:counter64;
      description
        "Counts the number of received packets with partial CRC type 1.";
    }
    leaf counter_slice12_ifg_mac_pool86_rx_mac_partial1_invert_crc_cnt_reg4_rx_mac_partial1_invert_crc_cnt {
      type oc-yang:counter64;
      description
        "Counts the number of received packets with partial CRC type 1.";
    }
    leaf counter_slice12_ifg_mac_pool86_rx_mac_partial1_invert_crc_cnt_reg5_rx_mac_partial1_invert_crc_cnt {
      type oc-yang:counter64;
      description
        "Counts the number of received packets with partial CRC type 1.";
    }
    leaf counter_slice12_ifg_mac_pool86_rx_mac_partial1_invert_crc_cnt_reg6_rx_mac_partial1_invert_crc_cnt {
      type oc-yang:counter64;
      description
        "Counts the number of received packets with partial CRC type 1.";
    }
    leaf counter_slice12_ifg_mac_pool86_rx_mac_partial1_invert_crc_cnt_reg7_rx_mac_partial1_invert_crc_cnt {
      type oc-yang:counter64;
      description
        "Counts the number of received packets with partial CRC type 1.";
    }
    leaf counter_slice12_ifg_mac_pool87_rx_mac_partial1_invert_crc_cnt_reg0_rx_mac_partial1_invert_crc_cnt {
      type oc-yang:counter64;
      description
        "Counts the number of received packets with partial CRC type 1.";
    }
    leaf counter_slice12_ifg_mac_pool87_rx_mac_partial1_invert_crc_cnt_reg1_rx_mac_partial1_invert_crc_cnt {
      type oc-yang:counter64;
      description
        "Counts the number of received packets with partial CRC type 1.";
    }
    leaf counter_slice12_ifg_mac_pool87_rx_mac_partial1_invert_crc_cnt_reg2_rx_mac_partial1_invert_crc_cnt {
      type oc-yang:counter64;
      description
        "Counts the number of received packets with partial CRC type 1.";
    }
    leaf counter_slice12_ifg_mac_pool87_rx_mac_partial1_invert_crc_cnt_reg3_rx_mac_partial1_invert_crc_cnt {
      type oc-yang:counter64;
      description
        "Counts the number of received packets with partial CRC type 1.";
    }
    leaf counter_slice12_ifg_mac_pool87_rx_mac_partial1_invert_crc_cnt_reg4_rx_mac_partial1_invert_crc_cnt {
      type oc-yang:counter64;
      description
        "Counts the number of received packets with partial CRC type 1.";
    }
    leaf counter_slice12_ifg_mac_pool87_rx_mac_partial1_invert_crc_cnt_reg5_rx_mac_partial1_invert_crc_cnt {
      type oc-yang:counter64;
      description
        "Counts the number of received packets with partial CRC type 1.";
    }
    leaf counter_slice12_ifg_mac_pool87_rx_mac_partial1_invert_crc_cnt_reg6_rx_mac_partial1_invert_crc_cnt {
      type oc-yang:counter64;
      description
        "Counts the number of received packets with partial CRC type 1.";
    }
    leaf counter_slice12_ifg_mac_pool87_rx_mac_partial1_invert_crc_cnt_reg7_rx_mac_partial1_invert_crc_cnt {
      type oc-yang:counter64;
      description
        "Counts the number of received packets with partial CRC type 1.";
    }
    leaf counter_slice13_ifg_mac_pool80_rx_mac_partial1_invert_crc_cnt_reg0_rx_mac_partial1_invert_crc_cnt {
      type oc-yang:counter64;
      description
        "Counts the number of received packets with partial CRC type 1.";
    }
    leaf counter_slice13_ifg_mac_pool80_rx_mac_partial1_invert_crc_cnt_reg1_rx_mac_partial1_invert_crc_cnt {
      type oc-yang:counter64;
      description
        "Counts the number of received packets with partial CRC type 1.";
    }
    leaf counter_slice13_ifg_mac_pool80_rx_mac_partial1_invert_crc_cnt_reg2_rx_mac_partial1_invert_crc_cnt {
      type oc-yang:counter64;
      description
        "Counts the number of received packets with partial CRC type 1.";
    }
    leaf counter_slice13_ifg_mac_pool80_rx_mac_partial1_invert_crc_cnt_reg3_rx_mac_partial1_invert_crc_cnt {
      type oc-yang:counter64;
      description
        "Counts the number of received packets with partial CRC type 1.";
    }
    leaf counter_slice13_ifg_mac_pool80_rx_mac_partial1_invert_crc_cnt_reg4_rx_mac_partial1_invert_crc_cnt {
      type oc-yang:counter64;
      description
        "Counts the number of received packets with partial CRC type 1.";
    }
    leaf counter_slice13_ifg_mac_pool80_rx_mac_partial1_invert_crc_cnt_reg5_rx_mac_partial1_invert_crc_cnt {
      type oc-yang:counter64;
      description
        "Counts the number of received packets with partial CRC type 1.";
    }
    leaf counter_slice13_ifg_mac_pool80_rx_mac_partial1_invert_crc_cnt_reg6_rx_mac_partial1_invert_crc_cnt {
      type oc-yang:counter64;
      description
        "Counts the number of received packets with partial CRC type 1.";
    }
    leaf counter_slice13_ifg_mac_pool80_rx_mac_partial1_invert_crc_cnt_reg7_rx_mac_partial1_invert_crc_cnt {
      type oc-yang:counter64;
      description
        "Counts the number of received packets with partial CRC type 1.";
    }
    leaf counter_slice13_ifg_mac_pool81_rx_mac_partial1_invert_crc_cnt_reg0_rx_mac_partial1_invert_crc_cnt {
      type oc-yang:counter64;
      description
        "Counts the number of received packets with partial CRC type 1.";
    }
    leaf counter_slice13_ifg_mac_pool81_rx_mac_partial1_invert_crc_cnt_reg1_rx_mac_partial1_invert_crc_cnt {
      type oc-yang:counter64;
      description
        "Counts the number of received packets with partial CRC type 1.";
    }
    leaf counter_slice13_ifg_mac_pool81_rx_mac_partial1_invert_crc_cnt_reg2_rx_mac_partial1_invert_crc_cnt {
      type oc-yang:counter64;
      description
        "Counts the number of received packets with partial CRC type 1.";
    }
    leaf counter_slice13_ifg_mac_pool81_rx_mac_partial1_invert_crc_cnt_reg3_rx_mac_partial1_invert_crc_cnt {
      type oc-yang:counter64;
      description
        "Counts the number of received packets with partial CRC type 1.";
    }
    leaf counter_slice13_ifg_mac_pool81_rx_mac_partial1_invert_crc_cnt_reg4_rx_mac_partial1_invert_crc_cnt {
      type oc-yang:counter64;
      description
        "Counts the number of received packets with partial CRC type 1.";
    }
    leaf counter_slice13_ifg_mac_pool81_rx_mac_partial1_invert_crc_cnt_reg5_rx_mac_partial1_invert_crc_cnt {
      type oc-yang:counter64;
      description
        "Counts the number of received packets with partial CRC type 1.";
    }
    leaf counter_slice13_ifg_mac_pool81_rx_mac_partial1_invert_crc_cnt_reg6_rx_mac_partial1_invert_crc_cnt {
      type oc-yang:counter64;
      description
        "Counts the number of received packets with partial CRC type 1.";
    }
    leaf counter_slice13_ifg_mac_pool81_rx_mac_partial1_invert_crc_cnt_reg7_rx_mac_partial1_invert_crc_cnt {
      type oc-yang:counter64;
      description
        "Counts the number of received packets with partial CRC type 1.";
    }
    leaf counter_slice13_ifg_mac_pool82_rx_mac_partial1_invert_crc_cnt_reg0_rx_mac_partial1_invert_crc_cnt {
      type oc-yang:counter64;
      description
        "Counts the number of received packets with partial CRC type 1.";
    }
    leaf counter_slice13_ifg_mac_pool82_rx_mac_partial1_invert_crc_cnt_reg1_rx_mac_partial1_invert_crc_cnt {
      type oc-yang:counter64;
      description
        "Counts the number of received packets with partial CRC type 1.";
    }
    leaf counter_slice13_ifg_mac_pool82_rx_mac_partial1_invert_crc_cnt_reg2_rx_mac_partial1_invert_crc_cnt {
      type oc-yang:counter64;
      description
        "Counts the number of received packets with partial CRC type 1.";
    }
    leaf counter_slice13_ifg_mac_pool82_rx_mac_partial1_invert_crc_cnt_reg3_rx_mac_partial1_invert_crc_cnt {
      type oc-yang:counter64;
      description
        "Counts the number of received packets with partial CRC type 1.";
    }
    leaf counter_slice13_ifg_mac_pool82_rx_mac_partial1_invert_crc_cnt_reg4_rx_mac_partial1_invert_crc_cnt {
      type oc-yang:counter64;
      description
        "Counts the number of received packets with partial CRC type 1.";
    }
    leaf counter_slice13_ifg_mac_pool82_rx_mac_partial1_invert_crc_cnt_reg5_rx_mac_partial1_invert_crc_cnt {
      type oc-yang:counter64;
      description
        "Counts the number of received packets with partial CRC type 1.";
    }
    leaf counter_slice13_ifg_mac_pool82_rx_mac_partial1_invert_crc_cnt_reg6_rx_mac_partial1_invert_crc_cnt {
      type oc-yang:counter64;
      description
        "Counts the number of received packets with partial CRC type 1.";
    }
    leaf counter_slice13_ifg_mac_pool82_rx_mac_partial1_invert_crc_cnt_reg7_rx_mac_partial1_invert_crc_cnt {
      type oc-yang:counter64;
      description
        "Counts the number of received packets with partial CRC type 1.";
    }
    leaf counter_slice13_ifg_mac_pool83_rx_mac_partial1_invert_crc_cnt_reg0_rx_mac_partial1_invert_crc_cnt {
      type oc-yang:counter64;
      description
        "Counts the number of received packets with partial CRC type 1.";
    }
    leaf counter_slice13_ifg_mac_pool83_rx_mac_partial1_invert_crc_cnt_reg1_rx_mac_partial1_invert_crc_cnt {
      type oc-yang:counter64;
      description
        "Counts the number of received packets with partial CRC type 1.";
    }
    leaf counter_slice13_ifg_mac_pool83_rx_mac_partial1_invert_crc_cnt_reg2_rx_mac_partial1_invert_crc_cnt {
      type oc-yang:counter64;
      description
        "Counts the number of received packets with partial CRC type 1.";
    }
    leaf counter_slice13_ifg_mac_pool83_rx_mac_partial1_invert_crc_cnt_reg3_rx_mac_partial1_invert_crc_cnt {
      type oc-yang:counter64;
      description
        "Counts the number of received packets with partial CRC type 1.";
    }
    leaf counter_slice13_ifg_mac_pool83_rx_mac_partial1_invert_crc_cnt_reg4_rx_mac_partial1_invert_crc_cnt {
      type oc-yang:counter64;
      description
        "Counts the number of received packets with partial CRC type 1.";
    }
    leaf counter_slice13_ifg_mac_pool83_rx_mac_partial1_invert_crc_cnt_reg5_rx_mac_partial1_invert_crc_cnt {
      type oc-yang:counter64;
      description
        "Counts the number of received packets with partial CRC type 1.";
    }
    leaf counter_slice13_ifg_mac_pool83_rx_mac_partial1_invert_crc_cnt_reg6_rx_mac_partial1_invert_crc_cnt {
      type oc-yang:counter64;
      description
        "Counts the number of received packets with partial CRC type 1.";
    }
    leaf counter_slice13_ifg_mac_pool83_rx_mac_partial1_invert_crc_cnt_reg7_rx_mac_partial1_invert_crc_cnt {
      type oc-yang:counter64;
      description
        "Counts the number of received packets with partial CRC type 1.";
    }
    leaf counter_slice13_ifg_mac_pool84_rx_mac_partial1_invert_crc_cnt_reg0_rx_mac_partial1_invert_crc_cnt {
      type oc-yang:counter64;
      description
        "Counts the number of received packets with partial CRC type 1.";
    }
    leaf counter_slice13_ifg_mac_pool84_rx_mac_partial1_invert_crc_cnt_reg1_rx_mac_partial1_invert_crc_cnt {
      type oc-yang:counter64;
      description
        "Counts the number of received packets with partial CRC type 1.";
    }
    leaf counter_slice13_ifg_mac_pool84_rx_mac_partial1_invert_crc_cnt_reg2_rx_mac_partial1_invert_crc_cnt {
      type oc-yang:counter64;
      description
        "Counts the number of received packets with partial CRC type 1.";
    }
    leaf counter_slice13_ifg_mac_pool84_rx_mac_partial1_invert_crc_cnt_reg3_rx_mac_partial1_invert_crc_cnt {
      type oc-yang:counter64;
      description
        "Counts the number of received packets with partial CRC type 1.";
    }
    leaf counter_slice13_ifg_mac_pool84_rx_mac_partial1_invert_crc_cnt_reg4_rx_mac_partial1_invert_crc_cnt {
      type oc-yang:counter64;
      description
        "Counts the number of received packets with partial CRC type 1.";
    }
    leaf counter_slice13_ifg_mac_pool84_rx_mac_partial1_invert_crc_cnt_reg5_rx_mac_partial1_invert_crc_cnt {
      type oc-yang:counter64;
      description
        "Counts the number of received packets with partial CRC type 1.";
    }
    leaf counter_slice13_ifg_mac_pool84_rx_mac_partial1_invert_crc_cnt_reg6_rx_mac_partial1_invert_crc_cnt {
      type oc-yang:counter64;
      description
        "Counts the number of received packets with partial CRC type 1.";
    }
    leaf counter_slice13_ifg_mac_pool84_rx_mac_partial1_invert_crc_cnt_reg7_rx_mac_partial1_invert_crc_cnt {
      type oc-yang:counter64;
      description
        "Counts the number of received packets with partial CRC type 1.";
    }
    leaf counter_slice13_ifg_mac_pool85_rx_mac_partial1_invert_crc_cnt_reg0_rx_mac_partial1_invert_crc_cnt {
      type oc-yang:counter64;
      description
        "Counts the number of received packets with partial CRC type 1.";
    }
    leaf counter_slice13_ifg_mac_pool85_rx_mac_partial1_invert_crc_cnt_reg1_rx_mac_partial1_invert_crc_cnt {
      type oc-yang:counter64;
      description
        "Counts the number of received packets with partial CRC type 1.";
    }
    leaf counter_slice13_ifg_mac_pool85_rx_mac_partial1_invert_crc_cnt_reg2_rx_mac_partial1_invert_crc_cnt {
      type oc-yang:counter64;
      description
        "Counts the number of received packets with partial CRC type 1.";
    }
    leaf counter_slice13_ifg_mac_pool85_rx_mac_partial1_invert_crc_cnt_reg3_rx_mac_partial1_invert_crc_cnt {
      type oc-yang:counter64;
      description
        "Counts the number of received packets with partial CRC type 1.";
    }
    leaf counter_slice13_ifg_mac_pool85_rx_mac_partial1_invert_crc_cnt_reg4_rx_mac_partial1_invert_crc_cnt {
      type oc-yang:counter64;
      description
        "Counts the number of received packets with partial CRC type 1.";
    }
    leaf counter_slice13_ifg_mac_pool85_rx_mac_partial1_invert_crc_cnt_reg5_rx_mac_partial1_invert_crc_cnt {
      type oc-yang:counter64;
      description
        "Counts the number of received packets with partial CRC type 1.";
    }
    leaf counter_slice13_ifg_mac_pool85_rx_mac_partial1_invert_crc_cnt_reg6_rx_mac_partial1_invert_crc_cnt {
      type oc-yang:counter64;
      description
        "Counts the number of received packets with partial CRC type 1.";
    }
    leaf counter_slice13_ifg_mac_pool85_rx_mac_partial1_invert_crc_cnt_reg7_rx_mac_partial1_invert_crc_cnt {
      type oc-yang:counter64;
      description
        "Counts the number of received packets with partial CRC type 1.";
    }
    leaf counter_slice13_ifg_mac_pool86_rx_mac_partial1_invert_crc_cnt_reg0_rx_mac_partial1_invert_crc_cnt {
      type oc-yang:counter64;
      description
        "Counts the number of received packets with partial CRC type 1.";
    }
    leaf counter_slice13_ifg_mac_pool86_rx_mac_partial1_invert_crc_cnt_reg1_rx_mac_partial1_invert_crc_cnt {
      type oc-yang:counter64;
      description
        "Counts the number of received packets with partial CRC type 1.";
    }
    leaf counter_slice13_ifg_mac_pool86_rx_mac_partial1_invert_crc_cnt_reg2_rx_mac_partial1_invert_crc_cnt {
      type oc-yang:counter64;
      description
        "Counts the number of received packets with partial CRC type 1.";
    }
    leaf counter_slice13_ifg_mac_pool86_rx_mac_partial1_invert_crc_cnt_reg3_rx_mac_partial1_invert_crc_cnt {
      type oc-yang:counter64;
      description
        "Counts the number of received packets with partial CRC type 1.";
    }
    leaf counter_slice13_ifg_mac_pool86_rx_mac_partial1_invert_crc_cnt_reg4_rx_mac_partial1_invert_crc_cnt {
      type oc-yang:counter64;
      description
        "Counts the number of received packets with partial CRC type 1.";
    }
    leaf counter_slice13_ifg_mac_pool86_rx_mac_partial1_invert_crc_cnt_reg5_rx_mac_partial1_invert_crc_cnt {
      type oc-yang:counter64;
      description
        "Counts the number of received packets with partial CRC type 1.";
    }
    leaf counter_slice13_ifg_mac_pool86_rx_mac_partial1_invert_crc_cnt_reg6_rx_mac_partial1_invert_crc_cnt {
      type oc-yang:counter64;
      description
        "Counts the number of received packets with partial CRC type 1.";
    }
    leaf counter_slice13_ifg_mac_pool86_rx_mac_partial1_invert_crc_cnt_reg7_rx_mac_partial1_invert_crc_cnt {
      type oc-yang:counter64;
      description
        "Counts the number of received packets with partial CRC type 1.";
    }
    leaf counter_slice13_ifg_mac_pool87_rx_mac_partial1_invert_crc_cnt_reg0_rx_mac_partial1_invert_crc_cnt {
      type oc-yang:counter64;
      description
        "Counts the number of received packets with partial CRC type 1.";
    }
    leaf counter_slice13_ifg_mac_pool87_rx_mac_partial1_invert_crc_cnt_reg1_rx_mac_partial1_invert_crc_cnt {
      type oc-yang:counter64;
      description
        "Counts the number of received packets with partial CRC type 1.";
    }
    leaf counter_slice13_ifg_mac_pool87_rx_mac_partial1_invert_crc_cnt_reg2_rx_mac_partial1_invert_crc_cnt {
      type oc-yang:counter64;
      description
        "Counts the number of received packets with partial CRC type 1.";
    }
    leaf counter_slice13_ifg_mac_pool87_rx_mac_partial1_invert_crc_cnt_reg3_rx_mac_partial1_invert_crc_cnt {
      type oc-yang:counter64;
      description
        "Counts the number of received packets with partial CRC type 1.";
    }
    leaf counter_slice13_ifg_mac_pool87_rx_mac_partial1_invert_crc_cnt_reg4_rx_mac_partial1_invert_crc_cnt {
      type oc-yang:counter64;
      description
        "Counts the number of received packets with partial CRC type 1.";
    }
    leaf counter_slice13_ifg_mac_pool87_rx_mac_partial1_invert_crc_cnt_reg5_rx_mac_partial1_invert_crc_cnt {
      type oc-yang:counter64;
      description
        "Counts the number of received packets with partial CRC type 1.";
    }
    leaf counter_slice13_ifg_mac_pool87_rx_mac_partial1_invert_crc_cnt_reg6_rx_mac_partial1_invert_crc_cnt {
      type oc-yang:counter64;
      description
        "Counts the number of received packets with partial CRC type 1.";
    }
    leaf counter_slice13_ifg_mac_pool87_rx_mac_partial1_invert_crc_cnt_reg7_rx_mac_partial1_invert_crc_cnt {
      type oc-yang:counter64;
      description
        "Counts the number of received packets with partial CRC type 1.";
    }
    leaf counter_slice14_ifg_mac_pool80_rx_mac_partial1_invert_crc_cnt_reg0_rx_mac_partial1_invert_crc_cnt {
      type oc-yang:counter64;
      description
        "Counts the number of received packets with partial CRC type 1.";
    }
    leaf counter_slice14_ifg_mac_pool80_rx_mac_partial1_invert_crc_cnt_reg1_rx_mac_partial1_invert_crc_cnt {
      type oc-yang:counter64;
      description
        "Counts the number of received packets with partial CRC type 1.";
    }
    leaf counter_slice14_ifg_mac_pool80_rx_mac_partial1_invert_crc_cnt_reg2_rx_mac_partial1_invert_crc_cnt {
      type oc-yang:counter64;
      description
        "Counts the number of received packets with partial CRC type 1.";
    }
    leaf counter_slice14_ifg_mac_pool80_rx_mac_partial1_invert_crc_cnt_reg3_rx_mac_partial1_invert_crc_cnt {
      type oc-yang:counter64;
      description
        "Counts the number of received packets with partial CRC type 1.";
    }
    leaf counter_slice14_ifg_mac_pool80_rx_mac_partial1_invert_crc_cnt_reg4_rx_mac_partial1_invert_crc_cnt {
      type oc-yang:counter64;
      description
        "Counts the number of received packets with partial CRC type 1.";
    }
    leaf counter_slice14_ifg_mac_pool80_rx_mac_partial1_invert_crc_cnt_reg5_rx_mac_partial1_invert_crc_cnt {
      type oc-yang:counter64;
      description
        "Counts the number of received packets with partial CRC type 1.";
    }
    leaf counter_slice14_ifg_mac_pool80_rx_mac_partial1_invert_crc_cnt_reg6_rx_mac_partial1_invert_crc_cnt {
      type oc-yang:counter64;
      description
        "Counts the number of received packets with partial CRC type 1.";
    }
    leaf counter_slice14_ifg_mac_pool80_rx_mac_partial1_invert_crc_cnt_reg7_rx_mac_partial1_invert_crc_cnt {
      type oc-yang:counter64;
      description
        "Counts the number of received packets with partial CRC type 1.";
    }
    leaf counter_slice14_ifg_mac_pool81_rx_mac_partial1_invert_crc_cnt_reg0_rx_mac_partial1_invert_crc_cnt {
      type oc-yang:counter64;
      description
        "Counts the number of received packets with partial CRC type 1.";
    }
    leaf counter_slice14_ifg_mac_pool81_rx_mac_partial1_invert_crc_cnt_reg1_rx_mac_partial1_invert_crc_cnt {
      type oc-yang:counter64;
      description
        "Counts the number of received packets with partial CRC type 1.";
    }
    leaf counter_slice14_ifg_mac_pool81_rx_mac_partial1_invert_crc_cnt_reg2_rx_mac_partial1_invert_crc_cnt {
      type oc-yang:counter64;
      description
        "Counts the number of received packets with partial CRC type 1.";
    }
    leaf counter_slice14_ifg_mac_pool81_rx_mac_partial1_invert_crc_cnt_reg3_rx_mac_partial1_invert_crc_cnt {
      type oc-yang:counter64;
      description
        "Counts the number of received packets with partial CRC type 1.";
    }
    leaf counter_slice14_ifg_mac_pool81_rx_mac_partial1_invert_crc_cnt_reg4_rx_mac_partial1_invert_crc_cnt {
      type oc-yang:counter64;
      description
        "Counts the number of received packets with partial CRC type 1.";
    }
    leaf counter_slice14_ifg_mac_pool81_rx_mac_partial1_invert_crc_cnt_reg5_rx_mac_partial1_invert_crc_cnt {
      type oc-yang:counter64;
      description
        "Counts the number of received packets with partial CRC type 1.";
    }
    leaf counter_slice14_ifg_mac_pool81_rx_mac_partial1_invert_crc_cnt_reg6_rx_mac_partial1_invert_crc_cnt {
      type oc-yang:counter64;
      description
        "Counts the number of received packets with partial CRC type 1.";
    }
    leaf counter_slice14_ifg_mac_pool81_rx_mac_partial1_invert_crc_cnt_reg7_rx_mac_partial1_invert_crc_cnt {
      type oc-yang:counter64;
      description
        "Counts the number of received packets with partial CRC type 1.";
    }
    leaf counter_slice14_ifg_mac_pool82_rx_mac_partial1_invert_crc_cnt_reg0_rx_mac_partial1_invert_crc_cnt {
      type oc-yang:counter64;
      description
        "Counts the number of received packets with partial CRC type 1.";
    }
    leaf counter_slice14_ifg_mac_pool82_rx_mac_partial1_invert_crc_cnt_reg1_rx_mac_partial1_invert_crc_cnt {
      type oc-yang:counter64;
      description
        "Counts the number of received packets with partial CRC type 1.";
    }
    leaf counter_slice14_ifg_mac_pool82_rx_mac_partial1_invert_crc_cnt_reg2_rx_mac_partial1_invert_crc_cnt {
      type oc-yang:counter64;
      description
        "Counts the number of received packets with partial CRC type 1.";
    }
    leaf counter_slice14_ifg_mac_pool82_rx_mac_partial1_invert_crc_cnt_reg3_rx_mac_partial1_invert_crc_cnt {
      type oc-yang:counter64;
      description
        "Counts the number of received packets with partial CRC type 1.";
    }
    leaf counter_slice14_ifg_mac_pool82_rx_mac_partial1_invert_crc_cnt_reg4_rx_mac_partial1_invert_crc_cnt {
      type oc-yang:counter64;
      description
        "Counts the number of received packets with partial CRC type 1.";
    }
    leaf counter_slice14_ifg_mac_pool82_rx_mac_partial1_invert_crc_cnt_reg5_rx_mac_partial1_invert_crc_cnt {
      type oc-yang:counter64;
      description
        "Counts the number of received packets with partial CRC type 1.";
    }
    leaf counter_slice14_ifg_mac_pool82_rx_mac_partial1_invert_crc_cnt_reg6_rx_mac_partial1_invert_crc_cnt {
      type oc-yang:counter64;
      description
        "Counts the number of received packets with partial CRC type 1.";
    }
    leaf counter_slice14_ifg_mac_pool82_rx_mac_partial1_invert_crc_cnt_reg7_rx_mac_partial1_invert_crc_cnt {
      type oc-yang:counter64;
      description
        "Counts the number of received packets with partial CRC type 1.";
    }
    leaf counter_slice14_ifg_mac_pool83_rx_mac_partial1_invert_crc_cnt_reg0_rx_mac_partial1_invert_crc_cnt {
      type oc-yang:counter64;
      description
        "Counts the number of received packets with partial CRC type 1.";
    }
    leaf counter_slice14_ifg_mac_pool83_rx_mac_partial1_invert_crc_cnt_reg1_rx_mac_partial1_invert_crc_cnt {
      type oc-yang:counter64;
      description
        "Counts the number of received packets with partial CRC type 1.";
    }
    leaf counter_slice14_ifg_mac_pool83_rx_mac_partial1_invert_crc_cnt_reg2_rx_mac_partial1_invert_crc_cnt {
      type oc-yang:counter64;
      description
        "Counts the number of received packets with partial CRC type 1.";
    }
    leaf counter_slice14_ifg_mac_pool83_rx_mac_partial1_invert_crc_cnt_reg3_rx_mac_partial1_invert_crc_cnt {
      type oc-yang:counter64;
      description
        "Counts the number of received packets with partial CRC type 1.";
    }
    leaf counter_slice14_ifg_mac_pool83_rx_mac_partial1_invert_crc_cnt_reg4_rx_mac_partial1_invert_crc_cnt {
      type oc-yang:counter64;
      description
        "Counts the number of received packets with partial CRC type 1.";
    }
    leaf counter_slice14_ifg_mac_pool83_rx_mac_partial1_invert_crc_cnt_reg5_rx_mac_partial1_invert_crc_cnt {
      type oc-yang:counter64;
      description
        "Counts the number of received packets with partial CRC type 1.";
    }
    leaf counter_slice14_ifg_mac_pool83_rx_mac_partial1_invert_crc_cnt_reg6_rx_mac_partial1_invert_crc_cnt {
      type oc-yang:counter64;
      description
        "Counts the number of received packets with partial CRC type 1.";
    }
    leaf counter_slice14_ifg_mac_pool83_rx_mac_partial1_invert_crc_cnt_reg7_rx_mac_partial1_invert_crc_cnt {
      type oc-yang:counter64;
      description
        "Counts the number of received packets with partial CRC type 1.";
    }
    leaf counter_slice14_ifg_mac_pool84_rx_mac_partial1_invert_crc_cnt_reg0_rx_mac_partial1_invert_crc_cnt {
      type oc-yang:counter64;
      description
        "Counts the number of received packets with partial CRC type 1.";
    }
    leaf counter_slice14_ifg_mac_pool84_rx_mac_partial1_invert_crc_cnt_reg1_rx_mac_partial1_invert_crc_cnt {
      type oc-yang:counter64;
      description
        "Counts the number of received packets with partial CRC type 1.";
    }
    leaf counter_slice14_ifg_mac_pool84_rx_mac_partial1_invert_crc_cnt_reg2_rx_mac_partial1_invert_crc_cnt {
      type oc-yang:counter64;
      description
        "Counts the number of received packets with partial CRC type 1.";
    }
    leaf counter_slice14_ifg_mac_pool84_rx_mac_partial1_invert_crc_cnt_reg3_rx_mac_partial1_invert_crc_cnt {
      type oc-yang:counter64;
      description
        "Counts the number of received packets with partial CRC type 1.";
    }
    leaf counter_slice14_ifg_mac_pool84_rx_mac_partial1_invert_crc_cnt_reg4_rx_mac_partial1_invert_crc_cnt {
      type oc-yang:counter64;
      description
        "Counts the number of received packets with partial CRC type 1.";
    }
    leaf counter_slice14_ifg_mac_pool84_rx_mac_partial1_invert_crc_cnt_reg5_rx_mac_partial1_invert_crc_cnt {
      type oc-yang:counter64;
      description
        "Counts the number of received packets with partial CRC type 1.";
    }
    leaf counter_slice14_ifg_mac_pool84_rx_mac_partial1_invert_crc_cnt_reg6_rx_mac_partial1_invert_crc_cnt {
      type oc-yang:counter64;
      description
        "Counts the number of received packets with partial CRC type 1.";
    }
    leaf counter_slice14_ifg_mac_pool84_rx_mac_partial1_invert_crc_cnt_reg7_rx_mac_partial1_invert_crc_cnt {
      type oc-yang:counter64;
      description
        "Counts the number of received packets with partial CRC type 1.";
    }
    leaf counter_slice14_ifg_mac_pool85_rx_mac_partial1_invert_crc_cnt_reg0_rx_mac_partial1_invert_crc_cnt {
      type oc-yang:counter64;
      description
        "Counts the number of received packets with partial CRC type 1.";
    }
    leaf counter_slice14_ifg_mac_pool85_rx_mac_partial1_invert_crc_cnt_reg1_rx_mac_partial1_invert_crc_cnt {
      type oc-yang:counter64;
      description
        "Counts the number of received packets with partial CRC type 1.";
    }
    leaf counter_slice14_ifg_mac_pool85_rx_mac_partial1_invert_crc_cnt_reg2_rx_mac_partial1_invert_crc_cnt {
      type oc-yang:counter64;
      description
        "Counts the number of received packets with partial CRC type 1.";
    }
    leaf counter_slice14_ifg_mac_pool85_rx_mac_partial1_invert_crc_cnt_reg3_rx_mac_partial1_invert_crc_cnt {
      type oc-yang:counter64;
      description
        "Counts the number of received packets with partial CRC type 1.";
    }
    leaf counter_slice14_ifg_mac_pool85_rx_mac_partial1_invert_crc_cnt_reg4_rx_mac_partial1_invert_crc_cnt {
      type oc-yang:counter64;
      description
        "Counts the number of received packets with partial CRC type 1.";
    }
    leaf counter_slice14_ifg_mac_pool85_rx_mac_partial1_invert_crc_cnt_reg5_rx_mac_partial1_invert_crc_cnt {
      type oc-yang:counter64;
      description
        "Counts the number of received packets with partial CRC type 1.";
    }
    leaf counter_slice14_ifg_mac_pool85_rx_mac_partial1_invert_crc_cnt_reg6_rx_mac_partial1_invert_crc_cnt {
      type oc-yang:counter64;
      description
        "Counts the number of received packets with partial CRC type 1.";
    }
    leaf counter_slice14_ifg_mac_pool85_rx_mac_partial1_invert_crc_cnt_reg7_rx_mac_partial1_invert_crc_cnt {
      type oc-yang:counter64;
      description
        "Counts the number of received packets with partial CRC type 1.";
    }
    leaf counter_slice14_ifg_mac_pool86_rx_mac_partial1_invert_crc_cnt_reg0_rx_mac_partial1_invert_crc_cnt {
      type oc-yang:counter64;
      description
        "Counts the number of received packets with partial CRC type 1.";
    }
    leaf counter_slice14_ifg_mac_pool86_rx_mac_partial1_invert_crc_cnt_reg1_rx_mac_partial1_invert_crc_cnt {
      type oc-yang:counter64;
      description
        "Counts the number of received packets with partial CRC type 1.";
    }
    leaf counter_slice14_ifg_mac_pool86_rx_mac_partial1_invert_crc_cnt_reg2_rx_mac_partial1_invert_crc_cnt {
      type oc-yang:counter64;
      description
        "Counts the number of received packets with partial CRC type 1.";
    }
    leaf counter_slice14_ifg_mac_pool86_rx_mac_partial1_invert_crc_cnt_reg3_rx_mac_partial1_invert_crc_cnt {
      type oc-yang:counter64;
      description
        "Counts the number of received packets with partial CRC type 1.";
    }
    leaf counter_slice14_ifg_mac_pool86_rx_mac_partial1_invert_crc_cnt_reg4_rx_mac_partial1_invert_crc_cnt {
      type oc-yang:counter64;
      description
        "Counts the number of received packets with partial CRC type 1.";
    }
    leaf counter_slice14_ifg_mac_pool86_rx_mac_partial1_invert_crc_cnt_reg5_rx_mac_partial1_invert_crc_cnt {
      type oc-yang:counter64;
      description
        "Counts the number of received packets with partial CRC type 1.";
    }
    leaf counter_slice14_ifg_mac_pool86_rx_mac_partial1_invert_crc_cnt_reg6_rx_mac_partial1_invert_crc_cnt {
      type oc-yang:counter64;
      description
        "Counts the number of received packets with partial CRC type 1.";
    }
    leaf counter_slice14_ifg_mac_pool86_rx_mac_partial1_invert_crc_cnt_reg7_rx_mac_partial1_invert_crc_cnt {
      type oc-yang:counter64;
      description
        "Counts the number of received packets with partial CRC type 1.";
    }
    leaf counter_slice14_ifg_mac_pool87_rx_mac_partial1_invert_crc_cnt_reg0_rx_mac_partial1_invert_crc_cnt {
      type oc-yang:counter64;
      description
        "Counts the number of received packets with partial CRC type 1.";
    }
    leaf counter_slice14_ifg_mac_pool87_rx_mac_partial1_invert_crc_cnt_reg1_rx_mac_partial1_invert_crc_cnt {
      type oc-yang:counter64;
      description
        "Counts the number of received packets with partial CRC type 1.";
    }
    leaf counter_slice14_ifg_mac_pool87_rx_mac_partial1_invert_crc_cnt_reg2_rx_mac_partial1_invert_crc_cnt {
      type oc-yang:counter64;
      description
        "Counts the number of received packets with partial CRC type 1.";
    }
    leaf counter_slice14_ifg_mac_pool87_rx_mac_partial1_invert_crc_cnt_reg3_rx_mac_partial1_invert_crc_cnt {
      type oc-yang:counter64;
      description
        "Counts the number of received packets with partial CRC type 1.";
    }
    leaf counter_slice14_ifg_mac_pool87_rx_mac_partial1_invert_crc_cnt_reg4_rx_mac_partial1_invert_crc_cnt {
      type oc-yang:counter64;
      description
        "Counts the number of received packets with partial CRC type 1.";
    }
    leaf counter_slice14_ifg_mac_pool87_rx_mac_partial1_invert_crc_cnt_reg5_rx_mac_partial1_invert_crc_cnt {
      type oc-yang:counter64;
      description
        "Counts the number of received packets with partial CRC type 1.";
    }
    leaf counter_slice14_ifg_mac_pool87_rx_mac_partial1_invert_crc_cnt_reg6_rx_mac_partial1_invert_crc_cnt {
      type oc-yang:counter64;
      description
        "Counts the number of received packets with partial CRC type 1.";
    }
    leaf counter_slice14_ifg_mac_pool87_rx_mac_partial1_invert_crc_cnt_reg7_rx_mac_partial1_invert_crc_cnt {
      type oc-yang:counter64;
      description
        "Counts the number of received packets with partial CRC type 1.";
    }
    leaf counter_slice15_ifg_mac_pool80_rx_mac_partial1_invert_crc_cnt_reg0_rx_mac_partial1_invert_crc_cnt {
      type oc-yang:counter64;
      description
        "Counts the number of received packets with partial CRC type 1.";
    }
    leaf counter_slice15_ifg_mac_pool80_rx_mac_partial1_invert_crc_cnt_reg1_rx_mac_partial1_invert_crc_cnt {
      type oc-yang:counter64;
      description
        "Counts the number of received packets with partial CRC type 1.";
    }
    leaf counter_slice15_ifg_mac_pool80_rx_mac_partial1_invert_crc_cnt_reg2_rx_mac_partial1_invert_crc_cnt {
      type oc-yang:counter64;
      description
        "Counts the number of received packets with partial CRC type 1.";
    }
    leaf counter_slice15_ifg_mac_pool80_rx_mac_partial1_invert_crc_cnt_reg3_rx_mac_partial1_invert_crc_cnt {
      type oc-yang:counter64;
      description
        "Counts the number of received packets with partial CRC type 1.";
    }
    leaf counter_slice15_ifg_mac_pool80_rx_mac_partial1_invert_crc_cnt_reg4_rx_mac_partial1_invert_crc_cnt {
      type oc-yang:counter64;
      description
        "Counts the number of received packets with partial CRC type 1.";
    }
    leaf counter_slice15_ifg_mac_pool80_rx_mac_partial1_invert_crc_cnt_reg5_rx_mac_partial1_invert_crc_cnt {
      type oc-yang:counter64;
      description
        "Counts the number of received packets with partial CRC type 1.";
    }
    leaf counter_slice15_ifg_mac_pool80_rx_mac_partial1_invert_crc_cnt_reg6_rx_mac_partial1_invert_crc_cnt {
      type oc-yang:counter64;
      description
        "Counts the number of received packets with partial CRC type 1.";
    }
    leaf counter_slice15_ifg_mac_pool80_rx_mac_partial1_invert_crc_cnt_reg7_rx_mac_partial1_invert_crc_cnt {
      type oc-yang:counter64;
      description
        "Counts the number of received packets with partial CRC type 1.";
    }
    leaf counter_slice15_ifg_mac_pool81_rx_mac_partial1_invert_crc_cnt_reg0_rx_mac_partial1_invert_crc_cnt {
      type oc-yang:counter64;
      description
        "Counts the number of received packets with partial CRC type 1.";
    }
    leaf counter_slice15_ifg_mac_pool81_rx_mac_partial1_invert_crc_cnt_reg1_rx_mac_partial1_invert_crc_cnt {
      type oc-yang:counter64;
      description
        "Counts the number of received packets with partial CRC type 1.";
    }
    leaf counter_slice15_ifg_mac_pool81_rx_mac_partial1_invert_crc_cnt_reg2_rx_mac_partial1_invert_crc_cnt {
      type oc-yang:counter64;
      description
        "Counts the number of received packets with partial CRC type 1.";
    }
    leaf counter_slice15_ifg_mac_pool81_rx_mac_partial1_invert_crc_cnt_reg3_rx_mac_partial1_invert_crc_cnt {
      type oc-yang:counter64;
      description
        "Counts the number of received packets with partial CRC type 1.";
    }
    leaf counter_slice15_ifg_mac_pool81_rx_mac_partial1_invert_crc_cnt_reg4_rx_mac_partial1_invert_crc_cnt {
      type oc-yang:counter64;
      description
        "Counts the number of received packets with partial CRC type 1.";
    }
    leaf counter_slice15_ifg_mac_pool81_rx_mac_partial1_invert_crc_cnt_reg5_rx_mac_partial1_invert_crc_cnt {
      type oc-yang:counter64;
      description
        "Counts the number of received packets with partial CRC type 1.";
    }
    leaf counter_slice15_ifg_mac_pool81_rx_mac_partial1_invert_crc_cnt_reg6_rx_mac_partial1_invert_crc_cnt {
      type oc-yang:counter64;
      description
        "Counts the number of received packets with partial CRC type 1.";
    }
    leaf counter_slice15_ifg_mac_pool81_rx_mac_partial1_invert_crc_cnt_reg7_rx_mac_partial1_invert_crc_cnt {
      type oc-yang:counter64;
      description
        "Counts the number of received packets with partial CRC type 1.";
    }
    leaf counter_slice15_ifg_mac_pool82_rx_mac_partial1_invert_crc_cnt_reg0_rx_mac_partial1_invert_crc_cnt {
      type oc-yang:counter64;
      description
        "Counts the number of received packets with partial CRC type 1.";
    }
    leaf counter_slice15_ifg_mac_pool82_rx_mac_partial1_invert_crc_cnt_reg1_rx_mac_partial1_invert_crc_cnt {
      type oc-yang:counter64;
      description
        "Counts the number of received packets with partial CRC type 1.";
    }
    leaf counter_slice15_ifg_mac_pool82_rx_mac_partial1_invert_crc_cnt_reg2_rx_mac_partial1_invert_crc_cnt {
      type oc-yang:counter64;
      description
        "Counts the number of received packets with partial CRC type 1.";
    }
    leaf counter_slice15_ifg_mac_pool82_rx_mac_partial1_invert_crc_cnt_reg3_rx_mac_partial1_invert_crc_cnt {
      type oc-yang:counter64;
      description
        "Counts the number of received packets with partial CRC type 1.";
    }
    leaf counter_slice15_ifg_mac_pool82_rx_mac_partial1_invert_crc_cnt_reg4_rx_mac_partial1_invert_crc_cnt {
      type oc-yang:counter64;
      description
        "Counts the number of received packets with partial CRC type 1.";
    }
    leaf counter_slice15_ifg_mac_pool82_rx_mac_partial1_invert_crc_cnt_reg5_rx_mac_partial1_invert_crc_cnt {
      type oc-yang:counter64;
      description
        "Counts the number of received packets with partial CRC type 1.";
    }
    leaf counter_slice15_ifg_mac_pool82_rx_mac_partial1_invert_crc_cnt_reg6_rx_mac_partial1_invert_crc_cnt {
      type oc-yang:counter64;
      description
        "Counts the number of received packets with partial CRC type 1.";
    }
    leaf counter_slice15_ifg_mac_pool82_rx_mac_partial1_invert_crc_cnt_reg7_rx_mac_partial1_invert_crc_cnt {
      type oc-yang:counter64;
      description
        "Counts the number of received packets with partial CRC type 1.";
    }
    leaf counter_slice15_ifg_mac_pool83_rx_mac_partial1_invert_crc_cnt_reg0_rx_mac_partial1_invert_crc_cnt {
      type oc-yang:counter64;
      description
        "Counts the number of received packets with partial CRC type 1.";
    }
    leaf counter_slice15_ifg_mac_pool83_rx_mac_partial1_invert_crc_cnt_reg1_rx_mac_partial1_invert_crc_cnt {
      type oc-yang:counter64;
      description
        "Counts the number of received packets with partial CRC type 1.";
    }
    leaf counter_slice15_ifg_mac_pool83_rx_mac_partial1_invert_crc_cnt_reg2_rx_mac_partial1_invert_crc_cnt {
      type oc-yang:counter64;
      description
        "Counts the number of received packets with partial CRC type 1.";
    }
    leaf counter_slice15_ifg_mac_pool83_rx_mac_partial1_invert_crc_cnt_reg3_rx_mac_partial1_invert_crc_cnt {
      type oc-yang:counter64;
      description
        "Counts the number of received packets with partial CRC type 1.";
    }
    leaf counter_slice15_ifg_mac_pool83_rx_mac_partial1_invert_crc_cnt_reg4_rx_mac_partial1_invert_crc_cnt {
      type oc-yang:counter64;
      description
        "Counts the number of received packets with partial CRC type 1.";
    }
    leaf counter_slice15_ifg_mac_pool83_rx_mac_partial1_invert_crc_cnt_reg5_rx_mac_partial1_invert_crc_cnt {
      type oc-yang:counter64;
      description
        "Counts the number of received packets with partial CRC type 1.";
    }
    leaf counter_slice15_ifg_mac_pool83_rx_mac_partial1_invert_crc_cnt_reg6_rx_mac_partial1_invert_crc_cnt {
      type oc-yang:counter64;
      description
        "Counts the number of received packets with partial CRC type 1.";
    }
    leaf counter_slice15_ifg_mac_pool83_rx_mac_partial1_invert_crc_cnt_reg7_rx_mac_partial1_invert_crc_cnt {
      type oc-yang:counter64;
      description
        "Counts the number of received packets with partial CRC type 1.";
    }
    leaf counter_slice15_ifg_mac_pool84_rx_mac_partial1_invert_crc_cnt_reg0_rx_mac_partial1_invert_crc_cnt {
      type oc-yang:counter64;
      description
        "Counts the number of received packets with partial CRC type 1.";
    }
    leaf counter_slice15_ifg_mac_pool84_rx_mac_partial1_invert_crc_cnt_reg1_rx_mac_partial1_invert_crc_cnt {
      type oc-yang:counter64;
      description
        "Counts the number of received packets with partial CRC type 1.";
    }
    leaf counter_slice15_ifg_mac_pool84_rx_mac_partial1_invert_crc_cnt_reg2_rx_mac_partial1_invert_crc_cnt {
      type oc-yang:counter64;
      description
        "Counts the number of received packets with partial CRC type 1.";
    }
    leaf counter_slice15_ifg_mac_pool84_rx_mac_partial1_invert_crc_cnt_reg3_rx_mac_partial1_invert_crc_cnt {
      type oc-yang:counter64;
      description
        "Counts the number of received packets with partial CRC type 1.";
    }
    leaf counter_slice15_ifg_mac_pool84_rx_mac_partial1_invert_crc_cnt_reg4_rx_mac_partial1_invert_crc_cnt {
      type oc-yang:counter64;
      description
        "Counts the number of received packets with partial CRC type 1.";
    }
    leaf counter_slice15_ifg_mac_pool84_rx_mac_partial1_invert_crc_cnt_reg5_rx_mac_partial1_invert_crc_cnt {
      type oc-yang:counter64;
      description
        "Counts the number of received packets with partial CRC type 1.";
    }
    leaf counter_slice15_ifg_mac_pool84_rx_mac_partial1_invert_crc_cnt_reg6_rx_mac_partial1_invert_crc_cnt {
      type oc-yang:counter64;
      description
        "Counts the number of received packets with partial CRC type 1.";
    }
    leaf counter_slice15_ifg_mac_pool84_rx_mac_partial1_invert_crc_cnt_reg7_rx_mac_partial1_invert_crc_cnt {
      type oc-yang:counter64;
      description
        "Counts the number of received packets with partial CRC type 1.";
    }
    leaf counter_slice15_ifg_mac_pool85_rx_mac_partial1_invert_crc_cnt_reg0_rx_mac_partial1_invert_crc_cnt {
      type oc-yang:counter64;
      description
        "Counts the number of received packets with partial CRC type 1.";
    }
    leaf counter_slice15_ifg_mac_pool85_rx_mac_partial1_invert_crc_cnt_reg1_rx_mac_partial1_invert_crc_cnt {
      type oc-yang:counter64;
      description
        "Counts the number of received packets with partial CRC type 1.";
    }
    leaf counter_slice15_ifg_mac_pool85_rx_mac_partial1_invert_crc_cnt_reg2_rx_mac_partial1_invert_crc_cnt {
      type oc-yang:counter64;
      description
        "Counts the number of received packets with partial CRC type 1.";
    }
    leaf counter_slice15_ifg_mac_pool85_rx_mac_partial1_invert_crc_cnt_reg3_rx_mac_partial1_invert_crc_cnt {
      type oc-yang:counter64;
      description
        "Counts the number of received packets with partial CRC type 1.";
    }
    leaf counter_slice15_ifg_mac_pool85_rx_mac_partial1_invert_crc_cnt_reg4_rx_mac_partial1_invert_crc_cnt {
      type oc-yang:counter64;
      description
        "Counts the number of received packets with partial CRC type 1.";
    }
    leaf counter_slice15_ifg_mac_pool85_rx_mac_partial1_invert_crc_cnt_reg5_rx_mac_partial1_invert_crc_cnt {
      type oc-yang:counter64;
      description
        "Counts the number of received packets with partial CRC type 1.";
    }
    leaf counter_slice15_ifg_mac_pool85_rx_mac_partial1_invert_crc_cnt_reg6_rx_mac_partial1_invert_crc_cnt {
      type oc-yang:counter64;
      description
        "Counts the number of received packets with partial CRC type 1.";
    }
    leaf counter_slice15_ifg_mac_pool85_rx_mac_partial1_invert_crc_cnt_reg7_rx_mac_partial1_invert_crc_cnt {
      type oc-yang:counter64;
      description
        "Counts the number of received packets with partial CRC type 1.";
    }
    leaf counter_slice15_ifg_mac_pool86_rx_mac_partial1_invert_crc_cnt_reg0_rx_mac_partial1_invert_crc_cnt {
      type oc-yang:counter64;
      description
        "Counts the number of received packets with partial CRC type 1.";
    }
    leaf counter_slice15_ifg_mac_pool86_rx_mac_partial1_invert_crc_cnt_reg1_rx_mac_partial1_invert_crc_cnt {
      type oc-yang:counter64;
      description
        "Counts the number of received packets with partial CRC type 1.";
    }
    leaf counter_slice15_ifg_mac_pool86_rx_mac_partial1_invert_crc_cnt_reg2_rx_mac_partial1_invert_crc_cnt {
      type oc-yang:counter64;
      description
        "Counts the number of received packets with partial CRC type 1.";
    }
    leaf counter_slice15_ifg_mac_pool86_rx_mac_partial1_invert_crc_cnt_reg3_rx_mac_partial1_invert_crc_cnt {
      type oc-yang:counter64;
      description
        "Counts the number of received packets with partial CRC type 1.";
    }
    leaf counter_slice15_ifg_mac_pool86_rx_mac_partial1_invert_crc_cnt_reg4_rx_mac_partial1_invert_crc_cnt {
      type oc-yang:counter64;
      description
        "Counts the number of received packets with partial CRC type 1.";
    }
    leaf counter_slice15_ifg_mac_pool86_rx_mac_partial1_invert_crc_cnt_reg5_rx_mac_partial1_invert_crc_cnt {
      type oc-yang:counter64;
      description
        "Counts the number of received packets with partial CRC type 1.";
    }
    leaf counter_slice15_ifg_mac_pool86_rx_mac_partial1_invert_crc_cnt_reg6_rx_mac_partial1_invert_crc_cnt {
      type oc-yang:counter64;
      description
        "Counts the number of received packets with partial CRC type 1.";
    }
    leaf counter_slice15_ifg_mac_pool86_rx_mac_partial1_invert_crc_cnt_reg7_rx_mac_partial1_invert_crc_cnt {
      type oc-yang:counter64;
      description
        "Counts the number of received packets with partial CRC type 1.";
    }
    leaf counter_slice15_ifg_mac_pool87_rx_mac_partial1_invert_crc_cnt_reg0_rx_mac_partial1_invert_crc_cnt {
      type oc-yang:counter64;
      description
        "Counts the number of received packets with partial CRC type 1.";
    }
    leaf counter_slice15_ifg_mac_pool87_rx_mac_partial1_invert_crc_cnt_reg1_rx_mac_partial1_invert_crc_cnt {
      type oc-yang:counter64;
      description
        "Counts the number of received packets with partial CRC type 1.";
    }
    leaf counter_slice15_ifg_mac_pool87_rx_mac_partial1_invert_crc_cnt_reg2_rx_mac_partial1_invert_crc_cnt {
      type oc-yang:counter64;
      description
        "Counts the number of received packets with partial CRC type 1.";
    }
    leaf counter_slice15_ifg_mac_pool87_rx_mac_partial1_invert_crc_cnt_reg3_rx_mac_partial1_invert_crc_cnt {
      type oc-yang:counter64;
      description
        "Counts the number of received packets with partial CRC type 1.";
    }
    leaf counter_slice15_ifg_mac_pool87_rx_mac_partial1_invert_crc_cnt_reg4_rx_mac_partial1_invert_crc_cnt {
      type oc-yang:counter64;
      description
        "Counts the number of received packets with partial CRC type 1.";
    }
    leaf counter_slice15_ifg_mac_pool87_rx_mac_partial1_invert_crc_cnt_reg5_rx_mac_partial1_invert_crc_cnt {
      type oc-yang:counter64;
      description
        "Counts the number of received packets with partial CRC type 1.";
    }
    leaf counter_slice15_ifg_mac_pool87_rx_mac_partial1_invert_crc_cnt_reg6_rx_mac_partial1_invert_crc_cnt {
      type oc-yang:counter64;
      description
        "Counts the number of received packets with partial CRC type 1.";
    }
    leaf counter_slice15_ifg_mac_pool87_rx_mac_partial1_invert_crc_cnt_reg7_rx_mac_partial1_invert_crc_cnt {
      type oc-yang:counter64;
      description
        "Counts the number of received packets with partial CRC type 1.";
    }
    leaf counter_slice0_ifg_mac_pool80_rx_mac_partial2_invert_crc_cnt_reg0_rx_mac_partial2_invert_crc_cnt {
      type oc-yang:counter64;
      description
        "Counts the number of received packets with partial CRC type 2.";
    }
    leaf counter_slice0_ifg_mac_pool80_rx_mac_partial2_invert_crc_cnt_reg1_rx_mac_partial2_invert_crc_cnt {
      type oc-yang:counter64;
      description
        "Counts the number of received packets with partial CRC type 2.";
    }
    leaf counter_slice0_ifg_mac_pool80_rx_mac_partial2_invert_crc_cnt_reg2_rx_mac_partial2_invert_crc_cnt {
      type oc-yang:counter64;
      description
        "Counts the number of received packets with partial CRC type 2.";
    }
    leaf counter_slice0_ifg_mac_pool80_rx_mac_partial2_invert_crc_cnt_reg3_rx_mac_partial2_invert_crc_cnt {
      type oc-yang:counter64;
      description
        "Counts the number of received packets with partial CRC type 2.";
    }
    leaf counter_slice0_ifg_mac_pool80_rx_mac_partial2_invert_crc_cnt_reg4_rx_mac_partial2_invert_crc_cnt {
      type oc-yang:counter64;
      description
        "Counts the number of received packets with partial CRC type 2.";
    }
    leaf counter_slice0_ifg_mac_pool80_rx_mac_partial2_invert_crc_cnt_reg5_rx_mac_partial2_invert_crc_cnt {
      type oc-yang:counter64;
      description
        "Counts the number of received packets with partial CRC type 2.";
    }
    leaf counter_slice0_ifg_mac_pool80_rx_mac_partial2_invert_crc_cnt_reg6_rx_mac_partial2_invert_crc_cnt {
      type oc-yang:counter64;
      description
        "Counts the number of received packets with partial CRC type 2.";
    }
    leaf counter_slice0_ifg_mac_pool80_rx_mac_partial2_invert_crc_cnt_reg7_rx_mac_partial2_invert_crc_cnt {
      type oc-yang:counter64;
      description
        "Counts the number of received packets with partial CRC type 2.";
    }
    leaf counter_slice0_ifg_mac_pool81_rx_mac_partial2_invert_crc_cnt_reg0_rx_mac_partial2_invert_crc_cnt {
      type oc-yang:counter64;
      description
        "Counts the number of received packets with partial CRC type 2.";
    }
    leaf counter_slice0_ifg_mac_pool81_rx_mac_partial2_invert_crc_cnt_reg1_rx_mac_partial2_invert_crc_cnt {
      type oc-yang:counter64;
      description
        "Counts the number of received packets with partial CRC type 2.";
    }
    leaf counter_slice0_ifg_mac_pool81_rx_mac_partial2_invert_crc_cnt_reg2_rx_mac_partial2_invert_crc_cnt {
      type oc-yang:counter64;
      description
        "Counts the number of received packets with partial CRC type 2.";
    }
    leaf counter_slice0_ifg_mac_pool81_rx_mac_partial2_invert_crc_cnt_reg3_rx_mac_partial2_invert_crc_cnt {
      type oc-yang:counter64;
      description
        "Counts the number of received packets with partial CRC type 2.";
    }
    leaf counter_slice0_ifg_mac_pool81_rx_mac_partial2_invert_crc_cnt_reg4_rx_mac_partial2_invert_crc_cnt {
      type oc-yang:counter64;
      description
        "Counts the number of received packets with partial CRC type 2.";
    }
    leaf counter_slice0_ifg_mac_pool81_rx_mac_partial2_invert_crc_cnt_reg5_rx_mac_partial2_invert_crc_cnt {
      type oc-yang:counter64;
      description
        "Counts the number of received packets with partial CRC type 2.";
    }
    leaf counter_slice0_ifg_mac_pool81_rx_mac_partial2_invert_crc_cnt_reg6_rx_mac_partial2_invert_crc_cnt {
      type oc-yang:counter64;
      description
        "Counts the number of received packets with partial CRC type 2.";
    }
    leaf counter_slice0_ifg_mac_pool81_rx_mac_partial2_invert_crc_cnt_reg7_rx_mac_partial2_invert_crc_cnt {
      type oc-yang:counter64;
      description
        "Counts the number of received packets with partial CRC type 2.";
    }
    leaf counter_slice0_ifg_mac_pool82_rx_mac_partial2_invert_crc_cnt_reg0_rx_mac_partial2_invert_crc_cnt {
      type oc-yang:counter64;
      description
        "Counts the number of received packets with partial CRC type 2.";
    }
    leaf counter_slice0_ifg_mac_pool82_rx_mac_partial2_invert_crc_cnt_reg1_rx_mac_partial2_invert_crc_cnt {
      type oc-yang:counter64;
      description
        "Counts the number of received packets with partial CRC type 2.";
    }
    leaf counter_slice0_ifg_mac_pool82_rx_mac_partial2_invert_crc_cnt_reg2_rx_mac_partial2_invert_crc_cnt {
      type oc-yang:counter64;
      description
        "Counts the number of received packets with partial CRC type 2.";
    }
    leaf counter_slice0_ifg_mac_pool82_rx_mac_partial2_invert_crc_cnt_reg3_rx_mac_partial2_invert_crc_cnt {
      type oc-yang:counter64;
      description
        "Counts the number of received packets with partial CRC type 2.";
    }
    leaf counter_slice0_ifg_mac_pool82_rx_mac_partial2_invert_crc_cnt_reg4_rx_mac_partial2_invert_crc_cnt {
      type oc-yang:counter64;
      description
        "Counts the number of received packets with partial CRC type 2.";
    }
    leaf counter_slice0_ifg_mac_pool82_rx_mac_partial2_invert_crc_cnt_reg5_rx_mac_partial2_invert_crc_cnt {
      type oc-yang:counter64;
      description
        "Counts the number of received packets with partial CRC type 2.";
    }
    leaf counter_slice0_ifg_mac_pool82_rx_mac_partial2_invert_crc_cnt_reg6_rx_mac_partial2_invert_crc_cnt {
      type oc-yang:counter64;
      description
        "Counts the number of received packets with partial CRC type 2.";
    }
    leaf counter_slice0_ifg_mac_pool82_rx_mac_partial2_invert_crc_cnt_reg7_rx_mac_partial2_invert_crc_cnt {
      type oc-yang:counter64;
      description
        "Counts the number of received packets with partial CRC type 2.";
    }
    leaf counter_slice0_ifg_mac_pool83_rx_mac_partial2_invert_crc_cnt_reg0_rx_mac_partial2_invert_crc_cnt {
      type oc-yang:counter64;
      description
        "Counts the number of received packets with partial CRC type 2.";
    }
    leaf counter_slice0_ifg_mac_pool83_rx_mac_partial2_invert_crc_cnt_reg1_rx_mac_partial2_invert_crc_cnt {
      type oc-yang:counter64;
      description
        "Counts the number of received packets with partial CRC type 2.";
    }
    leaf counter_slice0_ifg_mac_pool83_rx_mac_partial2_invert_crc_cnt_reg2_rx_mac_partial2_invert_crc_cnt {
      type oc-yang:counter64;
      description
        "Counts the number of received packets with partial CRC type 2.";
    }
    leaf counter_slice0_ifg_mac_pool83_rx_mac_partial2_invert_crc_cnt_reg3_rx_mac_partial2_invert_crc_cnt {
      type oc-yang:counter64;
      description
        "Counts the number of received packets with partial CRC type 2.";
    }
    leaf counter_slice0_ifg_mac_pool83_rx_mac_partial2_invert_crc_cnt_reg4_rx_mac_partial2_invert_crc_cnt {
      type oc-yang:counter64;
      description
        "Counts the number of received packets with partial CRC type 2.";
    }
    leaf counter_slice0_ifg_mac_pool83_rx_mac_partial2_invert_crc_cnt_reg5_rx_mac_partial2_invert_crc_cnt {
      type oc-yang:counter64;
      description
        "Counts the number of received packets with partial CRC type 2.";
    }
    leaf counter_slice0_ifg_mac_pool83_rx_mac_partial2_invert_crc_cnt_reg6_rx_mac_partial2_invert_crc_cnt {
      type oc-yang:counter64;
      description
        "Counts the number of received packets with partial CRC type 2.";
    }
    leaf counter_slice0_ifg_mac_pool83_rx_mac_partial2_invert_crc_cnt_reg7_rx_mac_partial2_invert_crc_cnt {
      type oc-yang:counter64;
      description
        "Counts the number of received packets with partial CRC type 2.";
    }
    leaf counter_slice0_ifg_mac_pool84_rx_mac_partial2_invert_crc_cnt_reg0_rx_mac_partial2_invert_crc_cnt {
      type oc-yang:counter64;
      description
        "Counts the number of received packets with partial CRC type 2.";
    }
    leaf counter_slice0_ifg_mac_pool84_rx_mac_partial2_invert_crc_cnt_reg1_rx_mac_partial2_invert_crc_cnt {
      type oc-yang:counter64;
      description
        "Counts the number of received packets with partial CRC type 2.";
    }
    leaf counter_slice0_ifg_mac_pool84_rx_mac_partial2_invert_crc_cnt_reg2_rx_mac_partial2_invert_crc_cnt {
      type oc-yang:counter64;
      description
        "Counts the number of received packets with partial CRC type 2.";
    }
    leaf counter_slice0_ifg_mac_pool84_rx_mac_partial2_invert_crc_cnt_reg3_rx_mac_partial2_invert_crc_cnt {
      type oc-yang:counter64;
      description
        "Counts the number of received packets with partial CRC type 2.";
    }
    leaf counter_slice0_ifg_mac_pool84_rx_mac_partial2_invert_crc_cnt_reg4_rx_mac_partial2_invert_crc_cnt {
      type oc-yang:counter64;
      description
        "Counts the number of received packets with partial CRC type 2.";
    }
    leaf counter_slice0_ifg_mac_pool84_rx_mac_partial2_invert_crc_cnt_reg5_rx_mac_partial2_invert_crc_cnt {
      type oc-yang:counter64;
      description
        "Counts the number of received packets with partial CRC type 2.";
    }
    leaf counter_slice0_ifg_mac_pool84_rx_mac_partial2_invert_crc_cnt_reg6_rx_mac_partial2_invert_crc_cnt {
      type oc-yang:counter64;
      description
        "Counts the number of received packets with partial CRC type 2.";
    }
    leaf counter_slice0_ifg_mac_pool84_rx_mac_partial2_invert_crc_cnt_reg7_rx_mac_partial2_invert_crc_cnt {
      type oc-yang:counter64;
      description
        "Counts the number of received packets with partial CRC type 2.";
    }
    leaf counter_slice0_ifg_mac_pool85_rx_mac_partial2_invert_crc_cnt_reg0_rx_mac_partial2_invert_crc_cnt {
      type oc-yang:counter64;
      description
        "Counts the number of received packets with partial CRC type 2.";
    }
    leaf counter_slice0_ifg_mac_pool85_rx_mac_partial2_invert_crc_cnt_reg1_rx_mac_partial2_invert_crc_cnt {
      type oc-yang:counter64;
      description
        "Counts the number of received packets with partial CRC type 2.";
    }
    leaf counter_slice0_ifg_mac_pool85_rx_mac_partial2_invert_crc_cnt_reg2_rx_mac_partial2_invert_crc_cnt {
      type oc-yang:counter64;
      description
        "Counts the number of received packets with partial CRC type 2.";
    }
    leaf counter_slice0_ifg_mac_pool85_rx_mac_partial2_invert_crc_cnt_reg3_rx_mac_partial2_invert_crc_cnt {
      type oc-yang:counter64;
      description
        "Counts the number of received packets with partial CRC type 2.";
    }
    leaf counter_slice0_ifg_mac_pool85_rx_mac_partial2_invert_crc_cnt_reg4_rx_mac_partial2_invert_crc_cnt {
      type oc-yang:counter64;
      description
        "Counts the number of received packets with partial CRC type 2.";
    }
    leaf counter_slice0_ifg_mac_pool85_rx_mac_partial2_invert_crc_cnt_reg5_rx_mac_partial2_invert_crc_cnt {
      type oc-yang:counter64;
      description
        "Counts the number of received packets with partial CRC type 2.";
    }
    leaf counter_slice0_ifg_mac_pool85_rx_mac_partial2_invert_crc_cnt_reg6_rx_mac_partial2_invert_crc_cnt {
      type oc-yang:counter64;
      description
        "Counts the number of received packets with partial CRC type 2.";
    }
    leaf counter_slice0_ifg_mac_pool85_rx_mac_partial2_invert_crc_cnt_reg7_rx_mac_partial2_invert_crc_cnt {
      type oc-yang:counter64;
      description
        "Counts the number of received packets with partial CRC type 2.";
    }
    leaf counter_slice0_ifg_mac_pool86_rx_mac_partial2_invert_crc_cnt_reg0_rx_mac_partial2_invert_crc_cnt {
      type oc-yang:counter64;
      description
        "Counts the number of received packets with partial CRC type 2.";
    }
    leaf counter_slice0_ifg_mac_pool86_rx_mac_partial2_invert_crc_cnt_reg1_rx_mac_partial2_invert_crc_cnt {
      type oc-yang:counter64;
      description
        "Counts the number of received packets with partial CRC type 2.";
    }
    leaf counter_slice0_ifg_mac_pool86_rx_mac_partial2_invert_crc_cnt_reg2_rx_mac_partial2_invert_crc_cnt {
      type oc-yang:counter64;
      description
        "Counts the number of received packets with partial CRC type 2.";
    }
    leaf counter_slice0_ifg_mac_pool86_rx_mac_partial2_invert_crc_cnt_reg3_rx_mac_partial2_invert_crc_cnt {
      type oc-yang:counter64;
      description
        "Counts the number of received packets with partial CRC type 2.";
    }
    leaf counter_slice0_ifg_mac_pool86_rx_mac_partial2_invert_crc_cnt_reg4_rx_mac_partial2_invert_crc_cnt {
      type oc-yang:counter64;
      description
        "Counts the number of received packets with partial CRC type 2.";
    }
    leaf counter_slice0_ifg_mac_pool86_rx_mac_partial2_invert_crc_cnt_reg5_rx_mac_partial2_invert_crc_cnt {
      type oc-yang:counter64;
      description
        "Counts the number of received packets with partial CRC type 2.";
    }
    leaf counter_slice0_ifg_mac_pool86_rx_mac_partial2_invert_crc_cnt_reg6_rx_mac_partial2_invert_crc_cnt {
      type oc-yang:counter64;
      description
        "Counts the number of received packets with partial CRC type 2.";
    }
    leaf counter_slice0_ifg_mac_pool86_rx_mac_partial2_invert_crc_cnt_reg7_rx_mac_partial2_invert_crc_cnt {
      type oc-yang:counter64;
      description
        "Counts the number of received packets with partial CRC type 2.";
    }
    leaf counter_slice0_ifg_mac_pool87_rx_mac_partial2_invert_crc_cnt_reg0_rx_mac_partial2_invert_crc_cnt {
      type oc-yang:counter64;
      description
        "Counts the number of received packets with partial CRC type 2.";
    }
    leaf counter_slice0_ifg_mac_pool87_rx_mac_partial2_invert_crc_cnt_reg1_rx_mac_partial2_invert_crc_cnt {
      type oc-yang:counter64;
      description
        "Counts the number of received packets with partial CRC type 2.";
    }
    leaf counter_slice0_ifg_mac_pool87_rx_mac_partial2_invert_crc_cnt_reg2_rx_mac_partial2_invert_crc_cnt {
      type oc-yang:counter64;
      description
        "Counts the number of received packets with partial CRC type 2.";
    }
    leaf counter_slice0_ifg_mac_pool87_rx_mac_partial2_invert_crc_cnt_reg3_rx_mac_partial2_invert_crc_cnt {
      type oc-yang:counter64;
      description
        "Counts the number of received packets with partial CRC type 2.";
    }
    leaf counter_slice0_ifg_mac_pool87_rx_mac_partial2_invert_crc_cnt_reg4_rx_mac_partial2_invert_crc_cnt {
      type oc-yang:counter64;
      description
        "Counts the number of received packets with partial CRC type 2.";
    }
    leaf counter_slice0_ifg_mac_pool87_rx_mac_partial2_invert_crc_cnt_reg5_rx_mac_partial2_invert_crc_cnt {
      type oc-yang:counter64;
      description
        "Counts the number of received packets with partial CRC type 2.";
    }
    leaf counter_slice0_ifg_mac_pool87_rx_mac_partial2_invert_crc_cnt_reg6_rx_mac_partial2_invert_crc_cnt {
      type oc-yang:counter64;
      description
        "Counts the number of received packets with partial CRC type 2.";
    }
    leaf counter_slice0_ifg_mac_pool87_rx_mac_partial2_invert_crc_cnt_reg7_rx_mac_partial2_invert_crc_cnt {
      type oc-yang:counter64;
      description
        "Counts the number of received packets with partial CRC type 2.";
    }
    leaf counter_slice1_ifg_mac_pool80_rx_mac_partial2_invert_crc_cnt_reg0_rx_mac_partial2_invert_crc_cnt {
      type oc-yang:counter64;
      description
        "Counts the number of received packets with partial CRC type 2.";
    }
    leaf counter_slice1_ifg_mac_pool80_rx_mac_partial2_invert_crc_cnt_reg1_rx_mac_partial2_invert_crc_cnt {
      type oc-yang:counter64;
      description
        "Counts the number of received packets with partial CRC type 2.";
    }
    leaf counter_slice1_ifg_mac_pool80_rx_mac_partial2_invert_crc_cnt_reg2_rx_mac_partial2_invert_crc_cnt {
      type oc-yang:counter64;
      description
        "Counts the number of received packets with partial CRC type 2.";
    }
    leaf counter_slice1_ifg_mac_pool80_rx_mac_partial2_invert_crc_cnt_reg3_rx_mac_partial2_invert_crc_cnt {
      type oc-yang:counter64;
      description
        "Counts the number of received packets with partial CRC type 2.";
    }
    leaf counter_slice1_ifg_mac_pool80_rx_mac_partial2_invert_crc_cnt_reg4_rx_mac_partial2_invert_crc_cnt {
      type oc-yang:counter64;
      description
        "Counts the number of received packets with partial CRC type 2.";
    }
    leaf counter_slice1_ifg_mac_pool80_rx_mac_partial2_invert_crc_cnt_reg5_rx_mac_partial2_invert_crc_cnt {
      type oc-yang:counter64;
      description
        "Counts the number of received packets with partial CRC type 2.";
    }
    leaf counter_slice1_ifg_mac_pool80_rx_mac_partial2_invert_crc_cnt_reg6_rx_mac_partial2_invert_crc_cnt {
      type oc-yang:counter64;
      description
        "Counts the number of received packets with partial CRC type 2.";
    }
    leaf counter_slice1_ifg_mac_pool80_rx_mac_partial2_invert_crc_cnt_reg7_rx_mac_partial2_invert_crc_cnt {
      type oc-yang:counter64;
      description
        "Counts the number of received packets with partial CRC type 2.";
    }
    leaf counter_slice1_ifg_mac_pool81_rx_mac_partial2_invert_crc_cnt_reg0_rx_mac_partial2_invert_crc_cnt {
      type oc-yang:counter64;
      description
        "Counts the number of received packets with partial CRC type 2.";
    }
    leaf counter_slice1_ifg_mac_pool81_rx_mac_partial2_invert_crc_cnt_reg1_rx_mac_partial2_invert_crc_cnt {
      type oc-yang:counter64;
      description
        "Counts the number of received packets with partial CRC type 2.";
    }
    leaf counter_slice1_ifg_mac_pool81_rx_mac_partial2_invert_crc_cnt_reg2_rx_mac_partial2_invert_crc_cnt {
      type oc-yang:counter64;
      description
        "Counts the number of received packets with partial CRC type 2.";
    }
    leaf counter_slice1_ifg_mac_pool81_rx_mac_partial2_invert_crc_cnt_reg3_rx_mac_partial2_invert_crc_cnt {
      type oc-yang:counter64;
      description
        "Counts the number of received packets with partial CRC type 2.";
    }
    leaf counter_slice1_ifg_mac_pool81_rx_mac_partial2_invert_crc_cnt_reg4_rx_mac_partial2_invert_crc_cnt {
      type oc-yang:counter64;
      description
        "Counts the number of received packets with partial CRC type 2.";
    }
    leaf counter_slice1_ifg_mac_pool81_rx_mac_partial2_invert_crc_cnt_reg5_rx_mac_partial2_invert_crc_cnt {
      type oc-yang:counter64;
      description
        "Counts the number of received packets with partial CRC type 2.";
    }
    leaf counter_slice1_ifg_mac_pool81_rx_mac_partial2_invert_crc_cnt_reg6_rx_mac_partial2_invert_crc_cnt {
      type oc-yang:counter64;
      description
        "Counts the number of received packets with partial CRC type 2.";
    }
    leaf counter_slice1_ifg_mac_pool81_rx_mac_partial2_invert_crc_cnt_reg7_rx_mac_partial2_invert_crc_cnt {
      type oc-yang:counter64;
      description
        "Counts the number of received packets with partial CRC type 2.";
    }
    leaf counter_slice1_ifg_mac_pool82_rx_mac_partial2_invert_crc_cnt_reg0_rx_mac_partial2_invert_crc_cnt {
      type oc-yang:counter64;
      description
        "Counts the number of received packets with partial CRC type 2.";
    }
    leaf counter_slice1_ifg_mac_pool82_rx_mac_partial2_invert_crc_cnt_reg1_rx_mac_partial2_invert_crc_cnt {
      type oc-yang:counter64;
      description
        "Counts the number of received packets with partial CRC type 2.";
    }
    leaf counter_slice1_ifg_mac_pool82_rx_mac_partial2_invert_crc_cnt_reg2_rx_mac_partial2_invert_crc_cnt {
      type oc-yang:counter64;
      description
        "Counts the number of received packets with partial CRC type 2.";
    }
    leaf counter_slice1_ifg_mac_pool82_rx_mac_partial2_invert_crc_cnt_reg3_rx_mac_partial2_invert_crc_cnt {
      type oc-yang:counter64;
      description
        "Counts the number of received packets with partial CRC type 2.";
    }
    leaf counter_slice1_ifg_mac_pool82_rx_mac_partial2_invert_crc_cnt_reg4_rx_mac_partial2_invert_crc_cnt {
      type oc-yang:counter64;
      description
        "Counts the number of received packets with partial CRC type 2.";
    }
    leaf counter_slice1_ifg_mac_pool82_rx_mac_partial2_invert_crc_cnt_reg5_rx_mac_partial2_invert_crc_cnt {
      type oc-yang:counter64;
      description
        "Counts the number of received packets with partial CRC type 2.";
    }
    leaf counter_slice1_ifg_mac_pool82_rx_mac_partial2_invert_crc_cnt_reg6_rx_mac_partial2_invert_crc_cnt {
      type oc-yang:counter64;
      description
        "Counts the number of received packets with partial CRC type 2.";
    }
    leaf counter_slice1_ifg_mac_pool82_rx_mac_partial2_invert_crc_cnt_reg7_rx_mac_partial2_invert_crc_cnt {
      type oc-yang:counter64;
      description
        "Counts the number of received packets with partial CRC type 2.";
    }
    leaf counter_slice1_ifg_mac_pool83_rx_mac_partial2_invert_crc_cnt_reg0_rx_mac_partial2_invert_crc_cnt {
      type oc-yang:counter64;
      description
        "Counts the number of received packets with partial CRC type 2.";
    }
    leaf counter_slice1_ifg_mac_pool83_rx_mac_partial2_invert_crc_cnt_reg1_rx_mac_partial2_invert_crc_cnt {
      type oc-yang:counter64;
      description
        "Counts the number of received packets with partial CRC type 2.";
    }
    leaf counter_slice1_ifg_mac_pool83_rx_mac_partial2_invert_crc_cnt_reg2_rx_mac_partial2_invert_crc_cnt {
      type oc-yang:counter64;
      description
        "Counts the number of received packets with partial CRC type 2.";
    }
    leaf counter_slice1_ifg_mac_pool83_rx_mac_partial2_invert_crc_cnt_reg3_rx_mac_partial2_invert_crc_cnt {
      type oc-yang:counter64;
      description
        "Counts the number of received packets with partial CRC type 2.";
    }
    leaf counter_slice1_ifg_mac_pool83_rx_mac_partial2_invert_crc_cnt_reg4_rx_mac_partial2_invert_crc_cnt {
      type oc-yang:counter64;
      description
        "Counts the number of received packets with partial CRC type 2.";
    }
    leaf counter_slice1_ifg_mac_pool83_rx_mac_partial2_invert_crc_cnt_reg5_rx_mac_partial2_invert_crc_cnt {
      type oc-yang:counter64;
      description
        "Counts the number of received packets with partial CRC type 2.";
    }
    leaf counter_slice1_ifg_mac_pool83_rx_mac_partial2_invert_crc_cnt_reg6_rx_mac_partial2_invert_crc_cnt {
      type oc-yang:counter64;
      description
        "Counts the number of received packets with partial CRC type 2.";
    }
    leaf counter_slice1_ifg_mac_pool83_rx_mac_partial2_invert_crc_cnt_reg7_rx_mac_partial2_invert_crc_cnt {
      type oc-yang:counter64;
      description
        "Counts the number of received packets with partial CRC type 2.";
    }
    leaf counter_slice1_ifg_mac_pool84_rx_mac_partial2_invert_crc_cnt_reg0_rx_mac_partial2_invert_crc_cnt {
      type oc-yang:counter64;
      description
        "Counts the number of received packets with partial CRC type 2.";
    }
    leaf counter_slice1_ifg_mac_pool84_rx_mac_partial2_invert_crc_cnt_reg1_rx_mac_partial2_invert_crc_cnt {
      type oc-yang:counter64;
      description
        "Counts the number of received packets with partial CRC type 2.";
    }
    leaf counter_slice1_ifg_mac_pool84_rx_mac_partial2_invert_crc_cnt_reg2_rx_mac_partial2_invert_crc_cnt {
      type oc-yang:counter64;
      description
        "Counts the number of received packets with partial CRC type 2.";
    }
    leaf counter_slice1_ifg_mac_pool84_rx_mac_partial2_invert_crc_cnt_reg3_rx_mac_partial2_invert_crc_cnt {
      type oc-yang:counter64;
      description
        "Counts the number of received packets with partial CRC type 2.";
    }
    leaf counter_slice1_ifg_mac_pool84_rx_mac_partial2_invert_crc_cnt_reg4_rx_mac_partial2_invert_crc_cnt {
      type oc-yang:counter64;
      description
        "Counts the number of received packets with partial CRC type 2.";
    }
    leaf counter_slice1_ifg_mac_pool84_rx_mac_partial2_invert_crc_cnt_reg5_rx_mac_partial2_invert_crc_cnt {
      type oc-yang:counter64;
      description
        "Counts the number of received packets with partial CRC type 2.";
    }
    leaf counter_slice1_ifg_mac_pool84_rx_mac_partial2_invert_crc_cnt_reg6_rx_mac_partial2_invert_crc_cnt {
      type oc-yang:counter64;
      description
        "Counts the number of received packets with partial CRC type 2.";
    }
    leaf counter_slice1_ifg_mac_pool84_rx_mac_partial2_invert_crc_cnt_reg7_rx_mac_partial2_invert_crc_cnt {
      type oc-yang:counter64;
      description
        "Counts the number of received packets with partial CRC type 2.";
    }
    leaf counter_slice1_ifg_mac_pool85_rx_mac_partial2_invert_crc_cnt_reg0_rx_mac_partial2_invert_crc_cnt {
      type oc-yang:counter64;
      description
        "Counts the number of received packets with partial CRC type 2.";
    }
    leaf counter_slice1_ifg_mac_pool85_rx_mac_partial2_invert_crc_cnt_reg1_rx_mac_partial2_invert_crc_cnt {
      type oc-yang:counter64;
      description
        "Counts the number of received packets with partial CRC type 2.";
    }
    leaf counter_slice1_ifg_mac_pool85_rx_mac_partial2_invert_crc_cnt_reg2_rx_mac_partial2_invert_crc_cnt {
      type oc-yang:counter64;
      description
        "Counts the number of received packets with partial CRC type 2.";
    }
    leaf counter_slice1_ifg_mac_pool85_rx_mac_partial2_invert_crc_cnt_reg3_rx_mac_partial2_invert_crc_cnt {
      type oc-yang:counter64;
      description
        "Counts the number of received packets with partial CRC type 2.";
    }
    leaf counter_slice1_ifg_mac_pool85_rx_mac_partial2_invert_crc_cnt_reg4_rx_mac_partial2_invert_crc_cnt {
      type oc-yang:counter64;
      description
        "Counts the number of received packets with partial CRC type 2.";
    }
    leaf counter_slice1_ifg_mac_pool85_rx_mac_partial2_invert_crc_cnt_reg5_rx_mac_partial2_invert_crc_cnt {
      type oc-yang:counter64;
      description
        "Counts the number of received packets with partial CRC type 2.";
    }
    leaf counter_slice1_ifg_mac_pool85_rx_mac_partial2_invert_crc_cnt_reg6_rx_mac_partial2_invert_crc_cnt {
      type oc-yang:counter64;
      description
        "Counts the number of received packets with partial CRC type 2.";
    }
    leaf counter_slice1_ifg_mac_pool85_rx_mac_partial2_invert_crc_cnt_reg7_rx_mac_partial2_invert_crc_cnt {
      type oc-yang:counter64;
      description
        "Counts the number of received packets with partial CRC type 2.";
    }
    leaf counter_slice1_ifg_mac_pool86_rx_mac_partial2_invert_crc_cnt_reg0_rx_mac_partial2_invert_crc_cnt {
      type oc-yang:counter64;
      description
        "Counts the number of received packets with partial CRC type 2.";
    }
    leaf counter_slice1_ifg_mac_pool86_rx_mac_partial2_invert_crc_cnt_reg1_rx_mac_partial2_invert_crc_cnt {
      type oc-yang:counter64;
      description
        "Counts the number of received packets with partial CRC type 2.";
    }
    leaf counter_slice1_ifg_mac_pool86_rx_mac_partial2_invert_crc_cnt_reg2_rx_mac_partial2_invert_crc_cnt {
      type oc-yang:counter64;
      description
        "Counts the number of received packets with partial CRC type 2.";
    }
    leaf counter_slice1_ifg_mac_pool86_rx_mac_partial2_invert_crc_cnt_reg3_rx_mac_partial2_invert_crc_cnt {
      type oc-yang:counter64;
      description
        "Counts the number of received packets with partial CRC type 2.";
    }
    leaf counter_slice1_ifg_mac_pool86_rx_mac_partial2_invert_crc_cnt_reg4_rx_mac_partial2_invert_crc_cnt {
      type oc-yang:counter64;
      description
        "Counts the number of received packets with partial CRC type 2.";
    }
    leaf counter_slice1_ifg_mac_pool86_rx_mac_partial2_invert_crc_cnt_reg5_rx_mac_partial2_invert_crc_cnt {
      type oc-yang:counter64;
      description
        "Counts the number of received packets with partial CRC type 2.";
    }
    leaf counter_slice1_ifg_mac_pool86_rx_mac_partial2_invert_crc_cnt_reg6_rx_mac_partial2_invert_crc_cnt {
      type oc-yang:counter64;
      description
        "Counts the number of received packets with partial CRC type 2.";
    }
    leaf counter_slice1_ifg_mac_pool86_rx_mac_partial2_invert_crc_cnt_reg7_rx_mac_partial2_invert_crc_cnt {
      type oc-yang:counter64;
      description
        "Counts the number of received packets with partial CRC type 2.";
    }
    leaf counter_slice1_ifg_mac_pool87_rx_mac_partial2_invert_crc_cnt_reg0_rx_mac_partial2_invert_crc_cnt {
      type oc-yang:counter64;
      description
        "Counts the number of received packets with partial CRC type 2.";
    }
    leaf counter_slice1_ifg_mac_pool87_rx_mac_partial2_invert_crc_cnt_reg1_rx_mac_partial2_invert_crc_cnt {
      type oc-yang:counter64;
      description
        "Counts the number of received packets with partial CRC type 2.";
    }
    leaf counter_slice1_ifg_mac_pool87_rx_mac_partial2_invert_crc_cnt_reg2_rx_mac_partial2_invert_crc_cnt {
      type oc-yang:counter64;
      description
        "Counts the number of received packets with partial CRC type 2.";
    }
    leaf counter_slice1_ifg_mac_pool87_rx_mac_partial2_invert_crc_cnt_reg3_rx_mac_partial2_invert_crc_cnt {
      type oc-yang:counter64;
      description
        "Counts the number of received packets with partial CRC type 2.";
    }
    leaf counter_slice1_ifg_mac_pool87_rx_mac_partial2_invert_crc_cnt_reg4_rx_mac_partial2_invert_crc_cnt {
      type oc-yang:counter64;
      description
        "Counts the number of received packets with partial CRC type 2.";
    }
    leaf counter_slice1_ifg_mac_pool87_rx_mac_partial2_invert_crc_cnt_reg5_rx_mac_partial2_invert_crc_cnt {
      type oc-yang:counter64;
      description
        "Counts the number of received packets with partial CRC type 2.";
    }
    leaf counter_slice1_ifg_mac_pool87_rx_mac_partial2_invert_crc_cnt_reg6_rx_mac_partial2_invert_crc_cnt {
      type oc-yang:counter64;
      description
        "Counts the number of received packets with partial CRC type 2.";
    }
    leaf counter_slice1_ifg_mac_pool87_rx_mac_partial2_invert_crc_cnt_reg7_rx_mac_partial2_invert_crc_cnt {
      type oc-yang:counter64;
      description
        "Counts the number of received packets with partial CRC type 2.";
    }
    leaf counter_slice2_ifg_mac_pool80_rx_mac_partial2_invert_crc_cnt_reg0_rx_mac_partial2_invert_crc_cnt {
      type oc-yang:counter64;
      description
        "Counts the number of received packets with partial CRC type 2.";
    }
    leaf counter_slice2_ifg_mac_pool80_rx_mac_partial2_invert_crc_cnt_reg1_rx_mac_partial2_invert_crc_cnt {
      type oc-yang:counter64;
      description
        "Counts the number of received packets with partial CRC type 2.";
    }
    leaf counter_slice2_ifg_mac_pool80_rx_mac_partial2_invert_crc_cnt_reg2_rx_mac_partial2_invert_crc_cnt {
      type oc-yang:counter64;
      description
        "Counts the number of received packets with partial CRC type 2.";
    }
    leaf counter_slice2_ifg_mac_pool80_rx_mac_partial2_invert_crc_cnt_reg3_rx_mac_partial2_invert_crc_cnt {
      type oc-yang:counter64;
      description
        "Counts the number of received packets with partial CRC type 2.";
    }
    leaf counter_slice2_ifg_mac_pool80_rx_mac_partial2_invert_crc_cnt_reg4_rx_mac_partial2_invert_crc_cnt {
      type oc-yang:counter64;
      description
        "Counts the number of received packets with partial CRC type 2.";
    }
    leaf counter_slice2_ifg_mac_pool80_rx_mac_partial2_invert_crc_cnt_reg5_rx_mac_partial2_invert_crc_cnt {
      type oc-yang:counter64;
      description
        "Counts the number of received packets with partial CRC type 2.";
    }
    leaf counter_slice2_ifg_mac_pool80_rx_mac_partial2_invert_crc_cnt_reg6_rx_mac_partial2_invert_crc_cnt {
      type oc-yang:counter64;
      description
        "Counts the number of received packets with partial CRC type 2.";
    }
    leaf counter_slice2_ifg_mac_pool80_rx_mac_partial2_invert_crc_cnt_reg7_rx_mac_partial2_invert_crc_cnt {
      type oc-yang:counter64;
      description
        "Counts the number of received packets with partial CRC type 2.";
    }
    leaf counter_slice2_ifg_mac_pool81_rx_mac_partial2_invert_crc_cnt_reg0_rx_mac_partial2_invert_crc_cnt {
      type oc-yang:counter64;
      description
        "Counts the number of received packets with partial CRC type 2.";
    }
    leaf counter_slice2_ifg_mac_pool81_rx_mac_partial2_invert_crc_cnt_reg1_rx_mac_partial2_invert_crc_cnt {
      type oc-yang:counter64;
      description
        "Counts the number of received packets with partial CRC type 2.";
    }
    leaf counter_slice2_ifg_mac_pool81_rx_mac_partial2_invert_crc_cnt_reg2_rx_mac_partial2_invert_crc_cnt {
      type oc-yang:counter64;
      description
        "Counts the number of received packets with partial CRC type 2.";
    }
    leaf counter_slice2_ifg_mac_pool81_rx_mac_partial2_invert_crc_cnt_reg3_rx_mac_partial2_invert_crc_cnt {
      type oc-yang:counter64;
      description
        "Counts the number of received packets with partial CRC type 2.";
    }
    leaf counter_slice2_ifg_mac_pool81_rx_mac_partial2_invert_crc_cnt_reg4_rx_mac_partial2_invert_crc_cnt {
      type oc-yang:counter64;
      description
        "Counts the number of received packets with partial CRC type 2.";
    }
    leaf counter_slice2_ifg_mac_pool81_rx_mac_partial2_invert_crc_cnt_reg5_rx_mac_partial2_invert_crc_cnt {
      type oc-yang:counter64;
      description
        "Counts the number of received packets with partial CRC type 2.";
    }
    leaf counter_slice2_ifg_mac_pool81_rx_mac_partial2_invert_crc_cnt_reg6_rx_mac_partial2_invert_crc_cnt {
      type oc-yang:counter64;
      description
        "Counts the number of received packets with partial CRC type 2.";
    }
    leaf counter_slice2_ifg_mac_pool81_rx_mac_partial2_invert_crc_cnt_reg7_rx_mac_partial2_invert_crc_cnt {
      type oc-yang:counter64;
      description
        "Counts the number of received packets with partial CRC type 2.";
    }
    leaf counter_slice2_ifg_mac_pool82_rx_mac_partial2_invert_crc_cnt_reg0_rx_mac_partial2_invert_crc_cnt {
      type oc-yang:counter64;
      description
        "Counts the number of received packets with partial CRC type 2.";
    }
    leaf counter_slice2_ifg_mac_pool82_rx_mac_partial2_invert_crc_cnt_reg1_rx_mac_partial2_invert_crc_cnt {
      type oc-yang:counter64;
      description
        "Counts the number of received packets with partial CRC type 2.";
    }
    leaf counter_slice2_ifg_mac_pool82_rx_mac_partial2_invert_crc_cnt_reg2_rx_mac_partial2_invert_crc_cnt {
      type oc-yang:counter64;
      description
        "Counts the number of received packets with partial CRC type 2.";
    }
    leaf counter_slice2_ifg_mac_pool82_rx_mac_partial2_invert_crc_cnt_reg3_rx_mac_partial2_invert_crc_cnt {
      type oc-yang:counter64;
      description
        "Counts the number of received packets with partial CRC type 2.";
    }
    leaf counter_slice2_ifg_mac_pool82_rx_mac_partial2_invert_crc_cnt_reg4_rx_mac_partial2_invert_crc_cnt {
      type oc-yang:counter64;
      description
        "Counts the number of received packets with partial CRC type 2.";
    }
    leaf counter_slice2_ifg_mac_pool82_rx_mac_partial2_invert_crc_cnt_reg5_rx_mac_partial2_invert_crc_cnt {
      type oc-yang:counter64;
      description
        "Counts the number of received packets with partial CRC type 2.";
    }
    leaf counter_slice2_ifg_mac_pool82_rx_mac_partial2_invert_crc_cnt_reg6_rx_mac_partial2_invert_crc_cnt {
      type oc-yang:counter64;
      description
        "Counts the number of received packets with partial CRC type 2.";
    }
    leaf counter_slice2_ifg_mac_pool82_rx_mac_partial2_invert_crc_cnt_reg7_rx_mac_partial2_invert_crc_cnt {
      type oc-yang:counter64;
      description
        "Counts the number of received packets with partial CRC type 2.";
    }
    leaf counter_slice2_ifg_mac_pool83_rx_mac_partial2_invert_crc_cnt_reg0_rx_mac_partial2_invert_crc_cnt {
      type oc-yang:counter64;
      description
        "Counts the number of received packets with partial CRC type 2.";
    }
    leaf counter_slice2_ifg_mac_pool83_rx_mac_partial2_invert_crc_cnt_reg1_rx_mac_partial2_invert_crc_cnt {
      type oc-yang:counter64;
      description
        "Counts the number of received packets with partial CRC type 2.";
    }
    leaf counter_slice2_ifg_mac_pool83_rx_mac_partial2_invert_crc_cnt_reg2_rx_mac_partial2_invert_crc_cnt {
      type oc-yang:counter64;
      description
        "Counts the number of received packets with partial CRC type 2.";
    }
    leaf counter_slice2_ifg_mac_pool83_rx_mac_partial2_invert_crc_cnt_reg3_rx_mac_partial2_invert_crc_cnt {
      type oc-yang:counter64;
      description
        "Counts the number of received packets with partial CRC type 2.";
    }
    leaf counter_slice2_ifg_mac_pool83_rx_mac_partial2_invert_crc_cnt_reg4_rx_mac_partial2_invert_crc_cnt {
      type oc-yang:counter64;
      description
        "Counts the number of received packets with partial CRC type 2.";
    }
    leaf counter_slice2_ifg_mac_pool83_rx_mac_partial2_invert_crc_cnt_reg5_rx_mac_partial2_invert_crc_cnt {
      type oc-yang:counter64;
      description
        "Counts the number of received packets with partial CRC type 2.";
    }
    leaf counter_slice2_ifg_mac_pool83_rx_mac_partial2_invert_crc_cnt_reg6_rx_mac_partial2_invert_crc_cnt {
      type oc-yang:counter64;
      description
        "Counts the number of received packets with partial CRC type 2.";
    }
    leaf counter_slice2_ifg_mac_pool83_rx_mac_partial2_invert_crc_cnt_reg7_rx_mac_partial2_invert_crc_cnt {
      type oc-yang:counter64;
      description
        "Counts the number of received packets with partial CRC type 2.";
    }
    leaf counter_slice2_ifg_mac_pool84_rx_mac_partial2_invert_crc_cnt_reg0_rx_mac_partial2_invert_crc_cnt {
      type oc-yang:counter64;
      description
        "Counts the number of received packets with partial CRC type 2.";
    }
    leaf counter_slice2_ifg_mac_pool84_rx_mac_partial2_invert_crc_cnt_reg1_rx_mac_partial2_invert_crc_cnt {
      type oc-yang:counter64;
      description
        "Counts the number of received packets with partial CRC type 2.";
    }
    leaf counter_slice2_ifg_mac_pool84_rx_mac_partial2_invert_crc_cnt_reg2_rx_mac_partial2_invert_crc_cnt {
      type oc-yang:counter64;
      description
        "Counts the number of received packets with partial CRC type 2.";
    }
    leaf counter_slice2_ifg_mac_pool84_rx_mac_partial2_invert_crc_cnt_reg3_rx_mac_partial2_invert_crc_cnt {
      type oc-yang:counter64;
      description
        "Counts the number of received packets with partial CRC type 2.";
    }
    leaf counter_slice2_ifg_mac_pool84_rx_mac_partial2_invert_crc_cnt_reg4_rx_mac_partial2_invert_crc_cnt {
      type oc-yang:counter64;
      description
        "Counts the number of received packets with partial CRC type 2.";
    }
    leaf counter_slice2_ifg_mac_pool84_rx_mac_partial2_invert_crc_cnt_reg5_rx_mac_partial2_invert_crc_cnt {
      type oc-yang:counter64;
      description
        "Counts the number of received packets with partial CRC type 2.";
    }
    leaf counter_slice2_ifg_mac_pool84_rx_mac_partial2_invert_crc_cnt_reg6_rx_mac_partial2_invert_crc_cnt {
      type oc-yang:counter64;
      description
        "Counts the number of received packets with partial CRC type 2.";
    }
    leaf counter_slice2_ifg_mac_pool84_rx_mac_partial2_invert_crc_cnt_reg7_rx_mac_partial2_invert_crc_cnt {
      type oc-yang:counter64;
      description
        "Counts the number of received packets with partial CRC type 2.";
    }
    leaf counter_slice2_ifg_mac_pool85_rx_mac_partial2_invert_crc_cnt_reg0_rx_mac_partial2_invert_crc_cnt {
      type oc-yang:counter64;
      description
        "Counts the number of received packets with partial CRC type 2.";
    }
    leaf counter_slice2_ifg_mac_pool85_rx_mac_partial2_invert_crc_cnt_reg1_rx_mac_partial2_invert_crc_cnt {
      type oc-yang:counter64;
      description
        "Counts the number of received packets with partial CRC type 2.";
    }
    leaf counter_slice2_ifg_mac_pool85_rx_mac_partial2_invert_crc_cnt_reg2_rx_mac_partial2_invert_crc_cnt {
      type oc-yang:counter64;
      description
        "Counts the number of received packets with partial CRC type 2.";
    }
    leaf counter_slice2_ifg_mac_pool85_rx_mac_partial2_invert_crc_cnt_reg3_rx_mac_partial2_invert_crc_cnt {
      type oc-yang:counter64;
      description
        "Counts the number of received packets with partial CRC type 2.";
    }
    leaf counter_slice2_ifg_mac_pool85_rx_mac_partial2_invert_crc_cnt_reg4_rx_mac_partial2_invert_crc_cnt {
      type oc-yang:counter64;
      description
        "Counts the number of received packets with partial CRC type 2.";
    }
    leaf counter_slice2_ifg_mac_pool85_rx_mac_partial2_invert_crc_cnt_reg5_rx_mac_partial2_invert_crc_cnt {
      type oc-yang:counter64;
      description
        "Counts the number of received packets with partial CRC type 2.";
    }
    leaf counter_slice2_ifg_mac_pool85_rx_mac_partial2_invert_crc_cnt_reg6_rx_mac_partial2_invert_crc_cnt {
      type oc-yang:counter64;
      description
        "Counts the number of received packets with partial CRC type 2.";
    }
    leaf counter_slice2_ifg_mac_pool85_rx_mac_partial2_invert_crc_cnt_reg7_rx_mac_partial2_invert_crc_cnt {
      type oc-yang:counter64;
      description
        "Counts the number of received packets with partial CRC type 2.";
    }
    leaf counter_slice2_ifg_mac_pool86_rx_mac_partial2_invert_crc_cnt_reg0_rx_mac_partial2_invert_crc_cnt {
      type oc-yang:counter64;
      description
        "Counts the number of received packets with partial CRC type 2.";
    }
    leaf counter_slice2_ifg_mac_pool86_rx_mac_partial2_invert_crc_cnt_reg1_rx_mac_partial2_invert_crc_cnt {
      type oc-yang:counter64;
      description
        "Counts the number of received packets with partial CRC type 2.";
    }
    leaf counter_slice2_ifg_mac_pool86_rx_mac_partial2_invert_crc_cnt_reg2_rx_mac_partial2_invert_crc_cnt {
      type oc-yang:counter64;
      description
        "Counts the number of received packets with partial CRC type 2.";
    }
    leaf counter_slice2_ifg_mac_pool86_rx_mac_partial2_invert_crc_cnt_reg3_rx_mac_partial2_invert_crc_cnt {
      type oc-yang:counter64;
      description
        "Counts the number of received packets with partial CRC type 2.";
    }
    leaf counter_slice2_ifg_mac_pool86_rx_mac_partial2_invert_crc_cnt_reg4_rx_mac_partial2_invert_crc_cnt {
      type oc-yang:counter64;
      description
        "Counts the number of received packets with partial CRC type 2.";
    }
    leaf counter_slice2_ifg_mac_pool86_rx_mac_partial2_invert_crc_cnt_reg5_rx_mac_partial2_invert_crc_cnt {
      type oc-yang:counter64;
      description
        "Counts the number of received packets with partial CRC type 2.";
    }
    leaf counter_slice2_ifg_mac_pool86_rx_mac_partial2_invert_crc_cnt_reg6_rx_mac_partial2_invert_crc_cnt {
      type oc-yang:counter64;
      description
        "Counts the number of received packets with partial CRC type 2.";
    }
    leaf counter_slice2_ifg_mac_pool86_rx_mac_partial2_invert_crc_cnt_reg7_rx_mac_partial2_invert_crc_cnt {
      type oc-yang:counter64;
      description
        "Counts the number of received packets with partial CRC type 2.";
    }
    leaf counter_slice2_ifg_mac_pool87_rx_mac_partial2_invert_crc_cnt_reg0_rx_mac_partial2_invert_crc_cnt {
      type oc-yang:counter64;
      description
        "Counts the number of received packets with partial CRC type 2.";
    }
    leaf counter_slice2_ifg_mac_pool87_rx_mac_partial2_invert_crc_cnt_reg1_rx_mac_partial2_invert_crc_cnt {
      type oc-yang:counter64;
      description
        "Counts the number of received packets with partial CRC type 2.";
    }
    leaf counter_slice2_ifg_mac_pool87_rx_mac_partial2_invert_crc_cnt_reg2_rx_mac_partial2_invert_crc_cnt {
      type oc-yang:counter64;
      description
        "Counts the number of received packets with partial CRC type 2.";
    }
    leaf counter_slice2_ifg_mac_pool87_rx_mac_partial2_invert_crc_cnt_reg3_rx_mac_partial2_invert_crc_cnt {
      type oc-yang:counter64;
      description
        "Counts the number of received packets with partial CRC type 2.";
    }
    leaf counter_slice2_ifg_mac_pool87_rx_mac_partial2_invert_crc_cnt_reg4_rx_mac_partial2_invert_crc_cnt {
      type oc-yang:counter64;
      description
        "Counts the number of received packets with partial CRC type 2.";
    }
    leaf counter_slice2_ifg_mac_pool87_rx_mac_partial2_invert_crc_cnt_reg5_rx_mac_partial2_invert_crc_cnt {
      type oc-yang:counter64;
      description
        "Counts the number of received packets with partial CRC type 2.";
    }
    leaf counter_slice2_ifg_mac_pool87_rx_mac_partial2_invert_crc_cnt_reg6_rx_mac_partial2_invert_crc_cnt {
      type oc-yang:counter64;
      description
        "Counts the number of received packets with partial CRC type 2.";
    }
    leaf counter_slice2_ifg_mac_pool87_rx_mac_partial2_invert_crc_cnt_reg7_rx_mac_partial2_invert_crc_cnt {
      type oc-yang:counter64;
      description
        "Counts the number of received packets with partial CRC type 2.";
    }
    leaf counter_slice3_ifg_mac_pool80_rx_mac_partial2_invert_crc_cnt_reg0_rx_mac_partial2_invert_crc_cnt {
      type oc-yang:counter64;
      description
        "Counts the number of received packets with partial CRC type 2.";
    }
    leaf counter_slice3_ifg_mac_pool80_rx_mac_partial2_invert_crc_cnt_reg1_rx_mac_partial2_invert_crc_cnt {
      type oc-yang:counter64;
      description
        "Counts the number of received packets with partial CRC type 2.";
    }
    leaf counter_slice3_ifg_mac_pool80_rx_mac_partial2_invert_crc_cnt_reg2_rx_mac_partial2_invert_crc_cnt {
      type oc-yang:counter64;
      description
        "Counts the number of received packets with partial CRC type 2.";
    }
    leaf counter_slice3_ifg_mac_pool80_rx_mac_partial2_invert_crc_cnt_reg3_rx_mac_partial2_invert_crc_cnt {
      type oc-yang:counter64;
      description
        "Counts the number of received packets with partial CRC type 2.";
    }
    leaf counter_slice3_ifg_mac_pool80_rx_mac_partial2_invert_crc_cnt_reg4_rx_mac_partial2_invert_crc_cnt {
      type oc-yang:counter64;
      description
        "Counts the number of received packets with partial CRC type 2.";
    }
    leaf counter_slice3_ifg_mac_pool80_rx_mac_partial2_invert_crc_cnt_reg5_rx_mac_partial2_invert_crc_cnt {
      type oc-yang:counter64;
      description
        "Counts the number of received packets with partial CRC type 2.";
    }
    leaf counter_slice3_ifg_mac_pool80_rx_mac_partial2_invert_crc_cnt_reg6_rx_mac_partial2_invert_crc_cnt {
      type oc-yang:counter64;
      description
        "Counts the number of received packets with partial CRC type 2.";
    }
    leaf counter_slice3_ifg_mac_pool80_rx_mac_partial2_invert_crc_cnt_reg7_rx_mac_partial2_invert_crc_cnt {
      type oc-yang:counter64;
      description
        "Counts the number of received packets with partial CRC type 2.";
    }
    leaf counter_slice3_ifg_mac_pool81_rx_mac_partial2_invert_crc_cnt_reg0_rx_mac_partial2_invert_crc_cnt {
      type oc-yang:counter64;
      description
        "Counts the number of received packets with partial CRC type 2.";
    }
    leaf counter_slice3_ifg_mac_pool81_rx_mac_partial2_invert_crc_cnt_reg1_rx_mac_partial2_invert_crc_cnt {
      type oc-yang:counter64;
      description
        "Counts the number of received packets with partial CRC type 2.";
    }
    leaf counter_slice3_ifg_mac_pool81_rx_mac_partial2_invert_crc_cnt_reg2_rx_mac_partial2_invert_crc_cnt {
      type oc-yang:counter64;
      description
        "Counts the number of received packets with partial CRC type 2.";
    }
    leaf counter_slice3_ifg_mac_pool81_rx_mac_partial2_invert_crc_cnt_reg3_rx_mac_partial2_invert_crc_cnt {
      type oc-yang:counter64;
      description
        "Counts the number of received packets with partial CRC type 2.";
    }
    leaf counter_slice3_ifg_mac_pool81_rx_mac_partial2_invert_crc_cnt_reg4_rx_mac_partial2_invert_crc_cnt {
      type oc-yang:counter64;
      description
        "Counts the number of received packets with partial CRC type 2.";
    }
    leaf counter_slice3_ifg_mac_pool81_rx_mac_partial2_invert_crc_cnt_reg5_rx_mac_partial2_invert_crc_cnt {
      type oc-yang:counter64;
      description
        "Counts the number of received packets with partial CRC type 2.";
    }
    leaf counter_slice3_ifg_mac_pool81_rx_mac_partial2_invert_crc_cnt_reg6_rx_mac_partial2_invert_crc_cnt {
      type oc-yang:counter64;
      description
        "Counts the number of received packets with partial CRC type 2.";
    }
    leaf counter_slice3_ifg_mac_pool81_rx_mac_partial2_invert_crc_cnt_reg7_rx_mac_partial2_invert_crc_cnt {
      type oc-yang:counter64;
      description
        "Counts the number of received packets with partial CRC type 2.";
    }
    leaf counter_slice3_ifg_mac_pool82_rx_mac_partial2_invert_crc_cnt_reg0_rx_mac_partial2_invert_crc_cnt {
      type oc-yang:counter64;
      description
        "Counts the number of received packets with partial CRC type 2.";
    }
    leaf counter_slice3_ifg_mac_pool82_rx_mac_partial2_invert_crc_cnt_reg1_rx_mac_partial2_invert_crc_cnt {
      type oc-yang:counter64;
      description
        "Counts the number of received packets with partial CRC type 2.";
    }
    leaf counter_slice3_ifg_mac_pool82_rx_mac_partial2_invert_crc_cnt_reg2_rx_mac_partial2_invert_crc_cnt {
      type oc-yang:counter64;
      description
        "Counts the number of received packets with partial CRC type 2.";
    }
    leaf counter_slice3_ifg_mac_pool82_rx_mac_partial2_invert_crc_cnt_reg3_rx_mac_partial2_invert_crc_cnt {
      type oc-yang:counter64;
      description
        "Counts the number of received packets with partial CRC type 2.";
    }
    leaf counter_slice3_ifg_mac_pool82_rx_mac_partial2_invert_crc_cnt_reg4_rx_mac_partial2_invert_crc_cnt {
      type oc-yang:counter64;
      description
        "Counts the number of received packets with partial CRC type 2.";
    }
    leaf counter_slice3_ifg_mac_pool82_rx_mac_partial2_invert_crc_cnt_reg5_rx_mac_partial2_invert_crc_cnt {
      type oc-yang:counter64;
      description
        "Counts the number of received packets with partial CRC type 2.";
    }
    leaf counter_slice3_ifg_mac_pool82_rx_mac_partial2_invert_crc_cnt_reg6_rx_mac_partial2_invert_crc_cnt {
      type oc-yang:counter64;
      description
        "Counts the number of received packets with partial CRC type 2.";
    }
    leaf counter_slice3_ifg_mac_pool82_rx_mac_partial2_invert_crc_cnt_reg7_rx_mac_partial2_invert_crc_cnt {
      type oc-yang:counter64;
      description
        "Counts the number of received packets with partial CRC type 2.";
    }
    leaf counter_slice3_ifg_mac_pool83_rx_mac_partial2_invert_crc_cnt_reg0_rx_mac_partial2_invert_crc_cnt {
      type oc-yang:counter64;
      description
        "Counts the number of received packets with partial CRC type 2.";
    }
    leaf counter_slice3_ifg_mac_pool83_rx_mac_partial2_invert_crc_cnt_reg1_rx_mac_partial2_invert_crc_cnt {
      type oc-yang:counter64;
      description
        "Counts the number of received packets with partial CRC type 2.";
    }
    leaf counter_slice3_ifg_mac_pool83_rx_mac_partial2_invert_crc_cnt_reg2_rx_mac_partial2_invert_crc_cnt {
      type oc-yang:counter64;
      description
        "Counts the number of received packets with partial CRC type 2.";
    }
    leaf counter_slice3_ifg_mac_pool83_rx_mac_partial2_invert_crc_cnt_reg3_rx_mac_partial2_invert_crc_cnt {
      type oc-yang:counter64;
      description
        "Counts the number of received packets with partial CRC type 2.";
    }
    leaf counter_slice3_ifg_mac_pool83_rx_mac_partial2_invert_crc_cnt_reg4_rx_mac_partial2_invert_crc_cnt {
      type oc-yang:counter64;
      description
        "Counts the number of received packets with partial CRC type 2.";
    }
    leaf counter_slice3_ifg_mac_pool83_rx_mac_partial2_invert_crc_cnt_reg5_rx_mac_partial2_invert_crc_cnt {
      type oc-yang:counter64;
      description
        "Counts the number of received packets with partial CRC type 2.";
    }
    leaf counter_slice3_ifg_mac_pool83_rx_mac_partial2_invert_crc_cnt_reg6_rx_mac_partial2_invert_crc_cnt {
      type oc-yang:counter64;
      description
        "Counts the number of received packets with partial CRC type 2.";
    }
    leaf counter_slice3_ifg_mac_pool83_rx_mac_partial2_invert_crc_cnt_reg7_rx_mac_partial2_invert_crc_cnt {
      type oc-yang:counter64;
      description
        "Counts the number of received packets with partial CRC type 2.";
    }
    leaf counter_slice3_ifg_mac_pool84_rx_mac_partial2_invert_crc_cnt_reg0_rx_mac_partial2_invert_crc_cnt {
      type oc-yang:counter64;
      description
        "Counts the number of received packets with partial CRC type 2.";
    }
    leaf counter_slice3_ifg_mac_pool84_rx_mac_partial2_invert_crc_cnt_reg1_rx_mac_partial2_invert_crc_cnt {
      type oc-yang:counter64;
      description
        "Counts the number of received packets with partial CRC type 2.";
    }
    leaf counter_slice3_ifg_mac_pool84_rx_mac_partial2_invert_crc_cnt_reg2_rx_mac_partial2_invert_crc_cnt {
      type oc-yang:counter64;
      description
        "Counts the number of received packets with partial CRC type 2.";
    }
    leaf counter_slice3_ifg_mac_pool84_rx_mac_partial2_invert_crc_cnt_reg3_rx_mac_partial2_invert_crc_cnt {
      type oc-yang:counter64;
      description
        "Counts the number of received packets with partial CRC type 2.";
    }
    leaf counter_slice3_ifg_mac_pool84_rx_mac_partial2_invert_crc_cnt_reg4_rx_mac_partial2_invert_crc_cnt {
      type oc-yang:counter64;
      description
        "Counts the number of received packets with partial CRC type 2.";
    }
    leaf counter_slice3_ifg_mac_pool84_rx_mac_partial2_invert_crc_cnt_reg5_rx_mac_partial2_invert_crc_cnt {
      type oc-yang:counter64;
      description
        "Counts the number of received packets with partial CRC type 2.";
    }
    leaf counter_slice3_ifg_mac_pool84_rx_mac_partial2_invert_crc_cnt_reg6_rx_mac_partial2_invert_crc_cnt {
      type oc-yang:counter64;
      description
        "Counts the number of received packets with partial CRC type 2.";
    }
    leaf counter_slice3_ifg_mac_pool84_rx_mac_partial2_invert_crc_cnt_reg7_rx_mac_partial2_invert_crc_cnt {
      type oc-yang:counter64;
      description
        "Counts the number of received packets with partial CRC type 2.";
    }
    leaf counter_slice3_ifg_mac_pool85_rx_mac_partial2_invert_crc_cnt_reg0_rx_mac_partial2_invert_crc_cnt {
      type oc-yang:counter64;
      description
        "Counts the number of received packets with partial CRC type 2.";
    }
    leaf counter_slice3_ifg_mac_pool85_rx_mac_partial2_invert_crc_cnt_reg1_rx_mac_partial2_invert_crc_cnt {
      type oc-yang:counter64;
      description
        "Counts the number of received packets with partial CRC type 2.";
    }
    leaf counter_slice3_ifg_mac_pool85_rx_mac_partial2_invert_crc_cnt_reg2_rx_mac_partial2_invert_crc_cnt {
      type oc-yang:counter64;
      description
        "Counts the number of received packets with partial CRC type 2.";
    }
    leaf counter_slice3_ifg_mac_pool85_rx_mac_partial2_invert_crc_cnt_reg3_rx_mac_partial2_invert_crc_cnt {
      type oc-yang:counter64;
      description
        "Counts the number of received packets with partial CRC type 2.";
    }
    leaf counter_slice3_ifg_mac_pool85_rx_mac_partial2_invert_crc_cnt_reg4_rx_mac_partial2_invert_crc_cnt {
      type oc-yang:counter64;
      description
        "Counts the number of received packets with partial CRC type 2.";
    }
    leaf counter_slice3_ifg_mac_pool85_rx_mac_partial2_invert_crc_cnt_reg5_rx_mac_partial2_invert_crc_cnt {
      type oc-yang:counter64;
      description
        "Counts the number of received packets with partial CRC type 2.";
    }
    leaf counter_slice3_ifg_mac_pool85_rx_mac_partial2_invert_crc_cnt_reg6_rx_mac_partial2_invert_crc_cnt {
      type oc-yang:counter64;
      description
        "Counts the number of received packets with partial CRC type 2.";
    }
    leaf counter_slice3_ifg_mac_pool85_rx_mac_partial2_invert_crc_cnt_reg7_rx_mac_partial2_invert_crc_cnt {
      type oc-yang:counter64;
      description
        "Counts the number of received packets with partial CRC type 2.";
    }
    leaf counter_slice3_ifg_mac_pool86_rx_mac_partial2_invert_crc_cnt_reg0_rx_mac_partial2_invert_crc_cnt {
      type oc-yang:counter64;
      description
        "Counts the number of received packets with partial CRC type 2.";
    }
    leaf counter_slice3_ifg_mac_pool86_rx_mac_partial2_invert_crc_cnt_reg1_rx_mac_partial2_invert_crc_cnt {
      type oc-yang:counter64;
      description
        "Counts the number of received packets with partial CRC type 2.";
    }
    leaf counter_slice3_ifg_mac_pool86_rx_mac_partial2_invert_crc_cnt_reg2_rx_mac_partial2_invert_crc_cnt {
      type oc-yang:counter64;
      description
        "Counts the number of received packets with partial CRC type 2.";
    }
    leaf counter_slice3_ifg_mac_pool86_rx_mac_partial2_invert_crc_cnt_reg3_rx_mac_partial2_invert_crc_cnt {
      type oc-yang:counter64;
      description
        "Counts the number of received packets with partial CRC type 2.";
    }
    leaf counter_slice3_ifg_mac_pool86_rx_mac_partial2_invert_crc_cnt_reg4_rx_mac_partial2_invert_crc_cnt {
      type oc-yang:counter64;
      description
        "Counts the number of received packets with partial CRC type 2.";
    }
    leaf counter_slice3_ifg_mac_pool86_rx_mac_partial2_invert_crc_cnt_reg5_rx_mac_partial2_invert_crc_cnt {
      type oc-yang:counter64;
      description
        "Counts the number of received packets with partial CRC type 2.";
    }
    leaf counter_slice3_ifg_mac_pool86_rx_mac_partial2_invert_crc_cnt_reg6_rx_mac_partial2_invert_crc_cnt {
      type oc-yang:counter64;
      description
        "Counts the number of received packets with partial CRC type 2.";
    }
    leaf counter_slice3_ifg_mac_pool86_rx_mac_partial2_invert_crc_cnt_reg7_rx_mac_partial2_invert_crc_cnt {
      type oc-yang:counter64;
      description
        "Counts the number of received packets with partial CRC type 2.";
    }
    leaf counter_slice3_ifg_mac_pool87_rx_mac_partial2_invert_crc_cnt_reg0_rx_mac_partial2_invert_crc_cnt {
      type oc-yang:counter64;
      description
        "Counts the number of received packets with partial CRC type 2.";
    }
    leaf counter_slice3_ifg_mac_pool87_rx_mac_partial2_invert_crc_cnt_reg1_rx_mac_partial2_invert_crc_cnt {
      type oc-yang:counter64;
      description
        "Counts the number of received packets with partial CRC type 2.";
    }
    leaf counter_slice3_ifg_mac_pool87_rx_mac_partial2_invert_crc_cnt_reg2_rx_mac_partial2_invert_crc_cnt {
      type oc-yang:counter64;
      description
        "Counts the number of received packets with partial CRC type 2.";
    }
    leaf counter_slice3_ifg_mac_pool87_rx_mac_partial2_invert_crc_cnt_reg3_rx_mac_partial2_invert_crc_cnt {
      type oc-yang:counter64;
      description
        "Counts the number of received packets with partial CRC type 2.";
    }
    leaf counter_slice3_ifg_mac_pool87_rx_mac_partial2_invert_crc_cnt_reg4_rx_mac_partial2_invert_crc_cnt {
      type oc-yang:counter64;
      description
        "Counts the number of received packets with partial CRC type 2.";
    }
    leaf counter_slice3_ifg_mac_pool87_rx_mac_partial2_invert_crc_cnt_reg5_rx_mac_partial2_invert_crc_cnt {
      type oc-yang:counter64;
      description
        "Counts the number of received packets with partial CRC type 2.";
    }
    leaf counter_slice3_ifg_mac_pool87_rx_mac_partial2_invert_crc_cnt_reg6_rx_mac_partial2_invert_crc_cnt {
      type oc-yang:counter64;
      description
        "Counts the number of received packets with partial CRC type 2.";
    }
    leaf counter_slice3_ifg_mac_pool87_rx_mac_partial2_invert_crc_cnt_reg7_rx_mac_partial2_invert_crc_cnt {
      type oc-yang:counter64;
      description
        "Counts the number of received packets with partial CRC type 2.";
    }
    leaf counter_slice4_ifg_mac_pool80_rx_mac_partial2_invert_crc_cnt_reg0_rx_mac_partial2_invert_crc_cnt {
      type oc-yang:counter64;
      description
        "Counts the number of received packets with partial CRC type 2.";
    }
    leaf counter_slice4_ifg_mac_pool80_rx_mac_partial2_invert_crc_cnt_reg1_rx_mac_partial2_invert_crc_cnt {
      type oc-yang:counter64;
      description
        "Counts the number of received packets with partial CRC type 2.";
    }
    leaf counter_slice4_ifg_mac_pool80_rx_mac_partial2_invert_crc_cnt_reg2_rx_mac_partial2_invert_crc_cnt {
      type oc-yang:counter64;
      description
        "Counts the number of received packets with partial CRC type 2.";
    }
    leaf counter_slice4_ifg_mac_pool80_rx_mac_partial2_invert_crc_cnt_reg3_rx_mac_partial2_invert_crc_cnt {
      type oc-yang:counter64;
      description
        "Counts the number of received packets with partial CRC type 2.";
    }
    leaf counter_slice4_ifg_mac_pool80_rx_mac_partial2_invert_crc_cnt_reg4_rx_mac_partial2_invert_crc_cnt {
      type oc-yang:counter64;
      description
        "Counts the number of received packets with partial CRC type 2.";
    }
    leaf counter_slice4_ifg_mac_pool80_rx_mac_partial2_invert_crc_cnt_reg5_rx_mac_partial2_invert_crc_cnt {
      type oc-yang:counter64;
      description
        "Counts the number of received packets with partial CRC type 2.";
    }
    leaf counter_slice4_ifg_mac_pool80_rx_mac_partial2_invert_crc_cnt_reg6_rx_mac_partial2_invert_crc_cnt {
      type oc-yang:counter64;
      description
        "Counts the number of received packets with partial CRC type 2.";
    }
    leaf counter_slice4_ifg_mac_pool80_rx_mac_partial2_invert_crc_cnt_reg7_rx_mac_partial2_invert_crc_cnt {
      type oc-yang:counter64;
      description
        "Counts the number of received packets with partial CRC type 2.";
    }
    leaf counter_slice4_ifg_mac_pool81_rx_mac_partial2_invert_crc_cnt_reg0_rx_mac_partial2_invert_crc_cnt {
      type oc-yang:counter64;
      description
        "Counts the number of received packets with partial CRC type 2.";
    }
    leaf counter_slice4_ifg_mac_pool81_rx_mac_partial2_invert_crc_cnt_reg1_rx_mac_partial2_invert_crc_cnt {
      type oc-yang:counter64;
      description
        "Counts the number of received packets with partial CRC type 2.";
    }
    leaf counter_slice4_ifg_mac_pool81_rx_mac_partial2_invert_crc_cnt_reg2_rx_mac_partial2_invert_crc_cnt {
      type oc-yang:counter64;
      description
        "Counts the number of received packets with partial CRC type 2.";
    }
    leaf counter_slice4_ifg_mac_pool81_rx_mac_partial2_invert_crc_cnt_reg3_rx_mac_partial2_invert_crc_cnt {
      type oc-yang:counter64;
      description
        "Counts the number of received packets with partial CRC type 2.";
    }
    leaf counter_slice4_ifg_mac_pool81_rx_mac_partial2_invert_crc_cnt_reg4_rx_mac_partial2_invert_crc_cnt {
      type oc-yang:counter64;
      description
        "Counts the number of received packets with partial CRC type 2.";
    }
    leaf counter_slice4_ifg_mac_pool81_rx_mac_partial2_invert_crc_cnt_reg5_rx_mac_partial2_invert_crc_cnt {
      type oc-yang:counter64;
      description
        "Counts the number of received packets with partial CRC type 2.";
    }
    leaf counter_slice4_ifg_mac_pool81_rx_mac_partial2_invert_crc_cnt_reg6_rx_mac_partial2_invert_crc_cnt {
      type oc-yang:counter64;
      description
        "Counts the number of received packets with partial CRC type 2.";
    }
    leaf counter_slice4_ifg_mac_pool81_rx_mac_partial2_invert_crc_cnt_reg7_rx_mac_partial2_invert_crc_cnt {
      type oc-yang:counter64;
      description
        "Counts the number of received packets with partial CRC type 2.";
    }
    leaf counter_slice4_ifg_mac_pool82_rx_mac_partial2_invert_crc_cnt_reg0_rx_mac_partial2_invert_crc_cnt {
      type oc-yang:counter64;
      description
        "Counts the number of received packets with partial CRC type 2.";
    }
    leaf counter_slice4_ifg_mac_pool82_rx_mac_partial2_invert_crc_cnt_reg1_rx_mac_partial2_invert_crc_cnt {
      type oc-yang:counter64;
      description
        "Counts the number of received packets with partial CRC type 2.";
    }
    leaf counter_slice4_ifg_mac_pool82_rx_mac_partial2_invert_crc_cnt_reg2_rx_mac_partial2_invert_crc_cnt {
      type oc-yang:counter64;
      description
        "Counts the number of received packets with partial CRC type 2.";
    }
    leaf counter_slice4_ifg_mac_pool82_rx_mac_partial2_invert_crc_cnt_reg3_rx_mac_partial2_invert_crc_cnt {
      type oc-yang:counter64;
      description
        "Counts the number of received packets with partial CRC type 2.";
    }
    leaf counter_slice4_ifg_mac_pool82_rx_mac_partial2_invert_crc_cnt_reg4_rx_mac_partial2_invert_crc_cnt {
      type oc-yang:counter64;
      description
        "Counts the number of received packets with partial CRC type 2.";
    }
    leaf counter_slice4_ifg_mac_pool82_rx_mac_partial2_invert_crc_cnt_reg5_rx_mac_partial2_invert_crc_cnt {
      type oc-yang:counter64;
      description
        "Counts the number of received packets with partial CRC type 2.";
    }
    leaf counter_slice4_ifg_mac_pool82_rx_mac_partial2_invert_crc_cnt_reg6_rx_mac_partial2_invert_crc_cnt {
      type oc-yang:counter64;
      description
        "Counts the number of received packets with partial CRC type 2.";
    }
    leaf counter_slice4_ifg_mac_pool82_rx_mac_partial2_invert_crc_cnt_reg7_rx_mac_partial2_invert_crc_cnt {
      type oc-yang:counter64;
      description
        "Counts the number of received packets with partial CRC type 2.";
    }
    leaf counter_slice4_ifg_mac_pool83_rx_mac_partial2_invert_crc_cnt_reg0_rx_mac_partial2_invert_crc_cnt {
      type oc-yang:counter64;
      description
        "Counts the number of received packets with partial CRC type 2.";
    }
    leaf counter_slice4_ifg_mac_pool83_rx_mac_partial2_invert_crc_cnt_reg1_rx_mac_partial2_invert_crc_cnt {
      type oc-yang:counter64;
      description
        "Counts the number of received packets with partial CRC type 2.";
    }
    leaf counter_slice4_ifg_mac_pool83_rx_mac_partial2_invert_crc_cnt_reg2_rx_mac_partial2_invert_crc_cnt {
      type oc-yang:counter64;
      description
        "Counts the number of received packets with partial CRC type 2.";
    }
    leaf counter_slice4_ifg_mac_pool83_rx_mac_partial2_invert_crc_cnt_reg3_rx_mac_partial2_invert_crc_cnt {
      type oc-yang:counter64;
      description
        "Counts the number of received packets with partial CRC type 2.";
    }
    leaf counter_slice4_ifg_mac_pool83_rx_mac_partial2_invert_crc_cnt_reg4_rx_mac_partial2_invert_crc_cnt {
      type oc-yang:counter64;
      description
        "Counts the number of received packets with partial CRC type 2.";
    }
    leaf counter_slice4_ifg_mac_pool83_rx_mac_partial2_invert_crc_cnt_reg5_rx_mac_partial2_invert_crc_cnt {
      type oc-yang:counter64;
      description
        "Counts the number of received packets with partial CRC type 2.";
    }
    leaf counter_slice4_ifg_mac_pool83_rx_mac_partial2_invert_crc_cnt_reg6_rx_mac_partial2_invert_crc_cnt {
      type oc-yang:counter64;
      description
        "Counts the number of received packets with partial CRC type 2.";
    }
    leaf counter_slice4_ifg_mac_pool83_rx_mac_partial2_invert_crc_cnt_reg7_rx_mac_partial2_invert_crc_cnt {
      type oc-yang:counter64;
      description
        "Counts the number of received packets with partial CRC type 2.";
    }
    leaf counter_slice4_ifg_mac_pool84_rx_mac_partial2_invert_crc_cnt_reg0_rx_mac_partial2_invert_crc_cnt {
      type oc-yang:counter64;
      description
        "Counts the number of received packets with partial CRC type 2.";
    }
    leaf counter_slice4_ifg_mac_pool84_rx_mac_partial2_invert_crc_cnt_reg1_rx_mac_partial2_invert_crc_cnt {
      type oc-yang:counter64;
      description
        "Counts the number of received packets with partial CRC type 2.";
    }
    leaf counter_slice4_ifg_mac_pool84_rx_mac_partial2_invert_crc_cnt_reg2_rx_mac_partial2_invert_crc_cnt {
      type oc-yang:counter64;
      description
        "Counts the number of received packets with partial CRC type 2.";
    }
    leaf counter_slice4_ifg_mac_pool84_rx_mac_partial2_invert_crc_cnt_reg3_rx_mac_partial2_invert_crc_cnt {
      type oc-yang:counter64;
      description
        "Counts the number of received packets with partial CRC type 2.";
    }
    leaf counter_slice4_ifg_mac_pool84_rx_mac_partial2_invert_crc_cnt_reg4_rx_mac_partial2_invert_crc_cnt {
      type oc-yang:counter64;
      description
        "Counts the number of received packets with partial CRC type 2.";
    }
    leaf counter_slice4_ifg_mac_pool84_rx_mac_partial2_invert_crc_cnt_reg5_rx_mac_partial2_invert_crc_cnt {
      type oc-yang:counter64;
      description
        "Counts the number of received packets with partial CRC type 2.";
    }
    leaf counter_slice4_ifg_mac_pool84_rx_mac_partial2_invert_crc_cnt_reg6_rx_mac_partial2_invert_crc_cnt {
      type oc-yang:counter64;
      description
        "Counts the number of received packets with partial CRC type 2.";
    }
    leaf counter_slice4_ifg_mac_pool84_rx_mac_partial2_invert_crc_cnt_reg7_rx_mac_partial2_invert_crc_cnt {
      type oc-yang:counter64;
      description
        "Counts the number of received packets with partial CRC type 2.";
    }
    leaf counter_slice4_ifg_mac_pool85_rx_mac_partial2_invert_crc_cnt_reg0_rx_mac_partial2_invert_crc_cnt {
      type oc-yang:counter64;
      description
        "Counts the number of received packets with partial CRC type 2.";
    }
    leaf counter_slice4_ifg_mac_pool85_rx_mac_partial2_invert_crc_cnt_reg1_rx_mac_partial2_invert_crc_cnt {
      type oc-yang:counter64;
      description
        "Counts the number of received packets with partial CRC type 2.";
    }
    leaf counter_slice4_ifg_mac_pool85_rx_mac_partial2_invert_crc_cnt_reg2_rx_mac_partial2_invert_crc_cnt {
      type oc-yang:counter64;
      description
        "Counts the number of received packets with partial CRC type 2.";
    }
    leaf counter_slice4_ifg_mac_pool85_rx_mac_partial2_invert_crc_cnt_reg3_rx_mac_partial2_invert_crc_cnt {
      type oc-yang:counter64;
      description
        "Counts the number of received packets with partial CRC type 2.";
    }
    leaf counter_slice4_ifg_mac_pool85_rx_mac_partial2_invert_crc_cnt_reg4_rx_mac_partial2_invert_crc_cnt {
      type oc-yang:counter64;
      description
        "Counts the number of received packets with partial CRC type 2.";
    }
    leaf counter_slice4_ifg_mac_pool85_rx_mac_partial2_invert_crc_cnt_reg5_rx_mac_partial2_invert_crc_cnt {
      type oc-yang:counter64;
      description
        "Counts the number of received packets with partial CRC type 2.";
    }
    leaf counter_slice4_ifg_mac_pool85_rx_mac_partial2_invert_crc_cnt_reg6_rx_mac_partial2_invert_crc_cnt {
      type oc-yang:counter64;
      description
        "Counts the number of received packets with partial CRC type 2.";
    }
    leaf counter_slice4_ifg_mac_pool85_rx_mac_partial2_invert_crc_cnt_reg7_rx_mac_partial2_invert_crc_cnt {
      type oc-yang:counter64;
      description
        "Counts the number of received packets with partial CRC type 2.";
    }
    leaf counter_slice4_ifg_mac_pool86_rx_mac_partial2_invert_crc_cnt_reg0_rx_mac_partial2_invert_crc_cnt {
      type oc-yang:counter64;
      description
        "Counts the number of received packets with partial CRC type 2.";
    }
    leaf counter_slice4_ifg_mac_pool86_rx_mac_partial2_invert_crc_cnt_reg1_rx_mac_partial2_invert_crc_cnt {
      type oc-yang:counter64;
      description
        "Counts the number of received packets with partial CRC type 2.";
    }
    leaf counter_slice4_ifg_mac_pool86_rx_mac_partial2_invert_crc_cnt_reg2_rx_mac_partial2_invert_crc_cnt {
      type oc-yang:counter64;
      description
        "Counts the number of received packets with partial CRC type 2.";
    }
    leaf counter_slice4_ifg_mac_pool86_rx_mac_partial2_invert_crc_cnt_reg3_rx_mac_partial2_invert_crc_cnt {
      type oc-yang:counter64;
      description
        "Counts the number of received packets with partial CRC type 2.";
    }
    leaf counter_slice4_ifg_mac_pool86_rx_mac_partial2_invert_crc_cnt_reg4_rx_mac_partial2_invert_crc_cnt {
      type oc-yang:counter64;
      description
        "Counts the number of received packets with partial CRC type 2.";
    }
    leaf counter_slice4_ifg_mac_pool86_rx_mac_partial2_invert_crc_cnt_reg5_rx_mac_partial2_invert_crc_cnt {
      type oc-yang:counter64;
      description
        "Counts the number of received packets with partial CRC type 2.";
    }
    leaf counter_slice4_ifg_mac_pool86_rx_mac_partial2_invert_crc_cnt_reg6_rx_mac_partial2_invert_crc_cnt {
      type oc-yang:counter64;
      description
        "Counts the number of received packets with partial CRC type 2.";
    }
    leaf counter_slice4_ifg_mac_pool86_rx_mac_partial2_invert_crc_cnt_reg7_rx_mac_partial2_invert_crc_cnt {
      type oc-yang:counter64;
      description
        "Counts the number of received packets with partial CRC type 2.";
    }
    leaf counter_slice4_ifg_mac_pool87_rx_mac_partial2_invert_crc_cnt_reg0_rx_mac_partial2_invert_crc_cnt {
      type oc-yang:counter64;
      description
        "Counts the number of received packets with partial CRC type 2.";
    }
    leaf counter_slice4_ifg_mac_pool87_rx_mac_partial2_invert_crc_cnt_reg1_rx_mac_partial2_invert_crc_cnt {
      type oc-yang:counter64;
      description
        "Counts the number of received packets with partial CRC type 2.";
    }
    leaf counter_slice4_ifg_mac_pool87_rx_mac_partial2_invert_crc_cnt_reg2_rx_mac_partial2_invert_crc_cnt {
      type oc-yang:counter64;
      description
        "Counts the number of received packets with partial CRC type 2.";
    }
    leaf counter_slice4_ifg_mac_pool87_rx_mac_partial2_invert_crc_cnt_reg3_rx_mac_partial2_invert_crc_cnt {
      type oc-yang:counter64;
      description
        "Counts the number of received packets with partial CRC type 2.";
    }
    leaf counter_slice4_ifg_mac_pool87_rx_mac_partial2_invert_crc_cnt_reg4_rx_mac_partial2_invert_crc_cnt {
      type oc-yang:counter64;
      description
        "Counts the number of received packets with partial CRC type 2.";
    }
    leaf counter_slice4_ifg_mac_pool87_rx_mac_partial2_invert_crc_cnt_reg5_rx_mac_partial2_invert_crc_cnt {
      type oc-yang:counter64;
      description
        "Counts the number of received packets with partial CRC type 2.";
    }
    leaf counter_slice4_ifg_mac_pool87_rx_mac_partial2_invert_crc_cnt_reg6_rx_mac_partial2_invert_crc_cnt {
      type oc-yang:counter64;
      description
        "Counts the number of received packets with partial CRC type 2.";
    }
    leaf counter_slice4_ifg_mac_pool87_rx_mac_partial2_invert_crc_cnt_reg7_rx_mac_partial2_invert_crc_cnt {
      type oc-yang:counter64;
      description
        "Counts the number of received packets with partial CRC type 2.";
    }
    leaf counter_slice5_ifg_mac_pool80_rx_mac_partial2_invert_crc_cnt_reg0_rx_mac_partial2_invert_crc_cnt {
      type oc-yang:counter64;
      description
        "Counts the number of received packets with partial CRC type 2.";
    }
    leaf counter_slice5_ifg_mac_pool80_rx_mac_partial2_invert_crc_cnt_reg1_rx_mac_partial2_invert_crc_cnt {
      type oc-yang:counter64;
      description
        "Counts the number of received packets with partial CRC type 2.";
    }
    leaf counter_slice5_ifg_mac_pool80_rx_mac_partial2_invert_crc_cnt_reg2_rx_mac_partial2_invert_crc_cnt {
      type oc-yang:counter64;
      description
        "Counts the number of received packets with partial CRC type 2.";
    }
    leaf counter_slice5_ifg_mac_pool80_rx_mac_partial2_invert_crc_cnt_reg3_rx_mac_partial2_invert_crc_cnt {
      type oc-yang:counter64;
      description
        "Counts the number of received packets with partial CRC type 2.";
    }
    leaf counter_slice5_ifg_mac_pool80_rx_mac_partial2_invert_crc_cnt_reg4_rx_mac_partial2_invert_crc_cnt {
      type oc-yang:counter64;
      description
        "Counts the number of received packets with partial CRC type 2.";
    }
    leaf counter_slice5_ifg_mac_pool80_rx_mac_partial2_invert_crc_cnt_reg5_rx_mac_partial2_invert_crc_cnt {
      type oc-yang:counter64;
      description
        "Counts the number of received packets with partial CRC type 2.";
    }
    leaf counter_slice5_ifg_mac_pool80_rx_mac_partial2_invert_crc_cnt_reg6_rx_mac_partial2_invert_crc_cnt {
      type oc-yang:counter64;
      description
        "Counts the number of received packets with partial CRC type 2.";
    }
    leaf counter_slice5_ifg_mac_pool80_rx_mac_partial2_invert_crc_cnt_reg7_rx_mac_partial2_invert_crc_cnt {
      type oc-yang:counter64;
      description
        "Counts the number of received packets with partial CRC type 2.";
    }
    leaf counter_slice5_ifg_mac_pool81_rx_mac_partial2_invert_crc_cnt_reg0_rx_mac_partial2_invert_crc_cnt {
      type oc-yang:counter64;
      description
        "Counts the number of received packets with partial CRC type 2.";
    }
    leaf counter_slice5_ifg_mac_pool81_rx_mac_partial2_invert_crc_cnt_reg1_rx_mac_partial2_invert_crc_cnt {
      type oc-yang:counter64;
      description
        "Counts the number of received packets with partial CRC type 2.";
    }
    leaf counter_slice5_ifg_mac_pool81_rx_mac_partial2_invert_crc_cnt_reg2_rx_mac_partial2_invert_crc_cnt {
      type oc-yang:counter64;
      description
        "Counts the number of received packets with partial CRC type 2.";
    }
    leaf counter_slice5_ifg_mac_pool81_rx_mac_partial2_invert_crc_cnt_reg3_rx_mac_partial2_invert_crc_cnt {
      type oc-yang:counter64;
      description
        "Counts the number of received packets with partial CRC type 2.";
    }
    leaf counter_slice5_ifg_mac_pool81_rx_mac_partial2_invert_crc_cnt_reg4_rx_mac_partial2_invert_crc_cnt {
      type oc-yang:counter64;
      description
        "Counts the number of received packets with partial CRC type 2.";
    }
    leaf counter_slice5_ifg_mac_pool81_rx_mac_partial2_invert_crc_cnt_reg5_rx_mac_partial2_invert_crc_cnt {
      type oc-yang:counter64;
      description
        "Counts the number of received packets with partial CRC type 2.";
    }
    leaf counter_slice5_ifg_mac_pool81_rx_mac_partial2_invert_crc_cnt_reg6_rx_mac_partial2_invert_crc_cnt {
      type oc-yang:counter64;
      description
        "Counts the number of received packets with partial CRC type 2.";
    }
    leaf counter_slice5_ifg_mac_pool81_rx_mac_partial2_invert_crc_cnt_reg7_rx_mac_partial2_invert_crc_cnt {
      type oc-yang:counter64;
      description
        "Counts the number of received packets with partial CRC type 2.";
    }
    leaf counter_slice5_ifg_mac_pool82_rx_mac_partial2_invert_crc_cnt_reg0_rx_mac_partial2_invert_crc_cnt {
      type oc-yang:counter64;
      description
        "Counts the number of received packets with partial CRC type 2.";
    }
    leaf counter_slice5_ifg_mac_pool82_rx_mac_partial2_invert_crc_cnt_reg1_rx_mac_partial2_invert_crc_cnt {
      type oc-yang:counter64;
      description
        "Counts the number of received packets with partial CRC type 2.";
    }
    leaf counter_slice5_ifg_mac_pool82_rx_mac_partial2_invert_crc_cnt_reg2_rx_mac_partial2_invert_crc_cnt {
      type oc-yang:counter64;
      description
        "Counts the number of received packets with partial CRC type 2.";
    }
    leaf counter_slice5_ifg_mac_pool82_rx_mac_partial2_invert_crc_cnt_reg3_rx_mac_partial2_invert_crc_cnt {
      type oc-yang:counter64;
      description
        "Counts the number of received packets with partial CRC type 2.";
    }
    leaf counter_slice5_ifg_mac_pool82_rx_mac_partial2_invert_crc_cnt_reg4_rx_mac_partial2_invert_crc_cnt {
      type oc-yang:counter64;
      description
        "Counts the number of received packets with partial CRC type 2.";
    }
    leaf counter_slice5_ifg_mac_pool82_rx_mac_partial2_invert_crc_cnt_reg5_rx_mac_partial2_invert_crc_cnt {
      type oc-yang:counter64;
      description
        "Counts the number of received packets with partial CRC type 2.";
    }
    leaf counter_slice5_ifg_mac_pool82_rx_mac_partial2_invert_crc_cnt_reg6_rx_mac_partial2_invert_crc_cnt {
      type oc-yang:counter64;
      description
        "Counts the number of received packets with partial CRC type 2.";
    }
    leaf counter_slice5_ifg_mac_pool82_rx_mac_partial2_invert_crc_cnt_reg7_rx_mac_partial2_invert_crc_cnt {
      type oc-yang:counter64;
      description
        "Counts the number of received packets with partial CRC type 2.";
    }
    leaf counter_slice5_ifg_mac_pool83_rx_mac_partial2_invert_crc_cnt_reg0_rx_mac_partial2_invert_crc_cnt {
      type oc-yang:counter64;
      description
        "Counts the number of received packets with partial CRC type 2.";
    }
    leaf counter_slice5_ifg_mac_pool83_rx_mac_partial2_invert_crc_cnt_reg1_rx_mac_partial2_invert_crc_cnt {
      type oc-yang:counter64;
      description
        "Counts the number of received packets with partial CRC type 2.";
    }
    leaf counter_slice5_ifg_mac_pool83_rx_mac_partial2_invert_crc_cnt_reg2_rx_mac_partial2_invert_crc_cnt {
      type oc-yang:counter64;
      description
        "Counts the number of received packets with partial CRC type 2.";
    }
    leaf counter_slice5_ifg_mac_pool83_rx_mac_partial2_invert_crc_cnt_reg3_rx_mac_partial2_invert_crc_cnt {
      type oc-yang:counter64;
      description
        "Counts the number of received packets with partial CRC type 2.";
    }
    leaf counter_slice5_ifg_mac_pool83_rx_mac_partial2_invert_crc_cnt_reg4_rx_mac_partial2_invert_crc_cnt {
      type oc-yang:counter64;
      description
        "Counts the number of received packets with partial CRC type 2.";
    }
    leaf counter_slice5_ifg_mac_pool83_rx_mac_partial2_invert_crc_cnt_reg5_rx_mac_partial2_invert_crc_cnt {
      type oc-yang:counter64;
      description
        "Counts the number of received packets with partial CRC type 2.";
    }
    leaf counter_slice5_ifg_mac_pool83_rx_mac_partial2_invert_crc_cnt_reg6_rx_mac_partial2_invert_crc_cnt {
      type oc-yang:counter64;
      description
        "Counts the number of received packets with partial CRC type 2.";
    }
    leaf counter_slice5_ifg_mac_pool83_rx_mac_partial2_invert_crc_cnt_reg7_rx_mac_partial2_invert_crc_cnt {
      type oc-yang:counter64;
      description
        "Counts the number of received packets with partial CRC type 2.";
    }
    leaf counter_slice5_ifg_mac_pool84_rx_mac_partial2_invert_crc_cnt_reg0_rx_mac_partial2_invert_crc_cnt {
      type oc-yang:counter64;
      description
        "Counts the number of received packets with partial CRC type 2.";
    }
    leaf counter_slice5_ifg_mac_pool84_rx_mac_partial2_invert_crc_cnt_reg1_rx_mac_partial2_invert_crc_cnt {
      type oc-yang:counter64;
      description
        "Counts the number of received packets with partial CRC type 2.";
    }
    leaf counter_slice5_ifg_mac_pool84_rx_mac_partial2_invert_crc_cnt_reg2_rx_mac_partial2_invert_crc_cnt {
      type oc-yang:counter64;
      description
        "Counts the number of received packets with partial CRC type 2.";
    }
    leaf counter_slice5_ifg_mac_pool84_rx_mac_partial2_invert_crc_cnt_reg3_rx_mac_partial2_invert_crc_cnt {
      type oc-yang:counter64;
      description
        "Counts the number of received packets with partial CRC type 2.";
    }
    leaf counter_slice5_ifg_mac_pool84_rx_mac_partial2_invert_crc_cnt_reg4_rx_mac_partial2_invert_crc_cnt {
      type oc-yang:counter64;
      description
        "Counts the number of received packets with partial CRC type 2.";
    }
    leaf counter_slice5_ifg_mac_pool84_rx_mac_partial2_invert_crc_cnt_reg5_rx_mac_partial2_invert_crc_cnt {
      type oc-yang:counter64;
      description
        "Counts the number of received packets with partial CRC type 2.";
    }
    leaf counter_slice5_ifg_mac_pool84_rx_mac_partial2_invert_crc_cnt_reg6_rx_mac_partial2_invert_crc_cnt {
      type oc-yang:counter64;
      description
        "Counts the number of received packets with partial CRC type 2.";
    }
    leaf counter_slice5_ifg_mac_pool84_rx_mac_partial2_invert_crc_cnt_reg7_rx_mac_partial2_invert_crc_cnt {
      type oc-yang:counter64;
      description
        "Counts the number of received packets with partial CRC type 2.";
    }
    leaf counter_slice5_ifg_mac_pool85_rx_mac_partial2_invert_crc_cnt_reg0_rx_mac_partial2_invert_crc_cnt {
      type oc-yang:counter64;
      description
        "Counts the number of received packets with partial CRC type 2.";
    }
    leaf counter_slice5_ifg_mac_pool85_rx_mac_partial2_invert_crc_cnt_reg1_rx_mac_partial2_invert_crc_cnt {
      type oc-yang:counter64;
      description
        "Counts the number of received packets with partial CRC type 2.";
    }
    leaf counter_slice5_ifg_mac_pool85_rx_mac_partial2_invert_crc_cnt_reg2_rx_mac_partial2_invert_crc_cnt {
      type oc-yang:counter64;
      description
        "Counts the number of received packets with partial CRC type 2.";
    }
    leaf counter_slice5_ifg_mac_pool85_rx_mac_partial2_invert_crc_cnt_reg3_rx_mac_partial2_invert_crc_cnt {
      type oc-yang:counter64;
      description
        "Counts the number of received packets with partial CRC type 2.";
    }
    leaf counter_slice5_ifg_mac_pool85_rx_mac_partial2_invert_crc_cnt_reg4_rx_mac_partial2_invert_crc_cnt {
      type oc-yang:counter64;
      description
        "Counts the number of received packets with partial CRC type 2.";
    }
    leaf counter_slice5_ifg_mac_pool85_rx_mac_partial2_invert_crc_cnt_reg5_rx_mac_partial2_invert_crc_cnt {
      type oc-yang:counter64;
      description
        "Counts the number of received packets with partial CRC type 2.";
    }
    leaf counter_slice5_ifg_mac_pool85_rx_mac_partial2_invert_crc_cnt_reg6_rx_mac_partial2_invert_crc_cnt {
      type oc-yang:counter64;
      description
        "Counts the number of received packets with partial CRC type 2.";
    }
    leaf counter_slice5_ifg_mac_pool85_rx_mac_partial2_invert_crc_cnt_reg7_rx_mac_partial2_invert_crc_cnt {
      type oc-yang:counter64;
      description
        "Counts the number of received packets with partial CRC type 2.";
    }
    leaf counter_slice5_ifg_mac_pool86_rx_mac_partial2_invert_crc_cnt_reg0_rx_mac_partial2_invert_crc_cnt {
      type oc-yang:counter64;
      description
        "Counts the number of received packets with partial CRC type 2.";
    }
    leaf counter_slice5_ifg_mac_pool86_rx_mac_partial2_invert_crc_cnt_reg1_rx_mac_partial2_invert_crc_cnt {
      type oc-yang:counter64;
      description
        "Counts the number of received packets with partial CRC type 2.";
    }
    leaf counter_slice5_ifg_mac_pool86_rx_mac_partial2_invert_crc_cnt_reg2_rx_mac_partial2_invert_crc_cnt {
      type oc-yang:counter64;
      description
        "Counts the number of received packets with partial CRC type 2.";
    }
    leaf counter_slice5_ifg_mac_pool86_rx_mac_partial2_invert_crc_cnt_reg3_rx_mac_partial2_invert_crc_cnt {
      type oc-yang:counter64;
      description
        "Counts the number of received packets with partial CRC type 2.";
    }
    leaf counter_slice5_ifg_mac_pool86_rx_mac_partial2_invert_crc_cnt_reg4_rx_mac_partial2_invert_crc_cnt {
      type oc-yang:counter64;
      description
        "Counts the number of received packets with partial CRC type 2.";
    }
    leaf counter_slice5_ifg_mac_pool86_rx_mac_partial2_invert_crc_cnt_reg5_rx_mac_partial2_invert_crc_cnt {
      type oc-yang:counter64;
      description
        "Counts the number of received packets with partial CRC type 2.";
    }
    leaf counter_slice5_ifg_mac_pool86_rx_mac_partial2_invert_crc_cnt_reg6_rx_mac_partial2_invert_crc_cnt {
      type oc-yang:counter64;
      description
        "Counts the number of received packets with partial CRC type 2.";
    }
    leaf counter_slice5_ifg_mac_pool86_rx_mac_partial2_invert_crc_cnt_reg7_rx_mac_partial2_invert_crc_cnt {
      type oc-yang:counter64;
      description
        "Counts the number of received packets with partial CRC type 2.";
    }
    leaf counter_slice5_ifg_mac_pool87_rx_mac_partial2_invert_crc_cnt_reg0_rx_mac_partial2_invert_crc_cnt {
      type oc-yang:counter64;
      description
        "Counts the number of received packets with partial CRC type 2.";
    }
    leaf counter_slice5_ifg_mac_pool87_rx_mac_partial2_invert_crc_cnt_reg1_rx_mac_partial2_invert_crc_cnt {
      type oc-yang:counter64;
      description
        "Counts the number of received packets with partial CRC type 2.";
    }
    leaf counter_slice5_ifg_mac_pool87_rx_mac_partial2_invert_crc_cnt_reg2_rx_mac_partial2_invert_crc_cnt {
      type oc-yang:counter64;
      description
        "Counts the number of received packets with partial CRC type 2.";
    }
    leaf counter_slice5_ifg_mac_pool87_rx_mac_partial2_invert_crc_cnt_reg3_rx_mac_partial2_invert_crc_cnt {
      type oc-yang:counter64;
      description
        "Counts the number of received packets with partial CRC type 2.";
    }
    leaf counter_slice5_ifg_mac_pool87_rx_mac_partial2_invert_crc_cnt_reg4_rx_mac_partial2_invert_crc_cnt {
      type oc-yang:counter64;
      description
        "Counts the number of received packets with partial CRC type 2.";
    }
    leaf counter_slice5_ifg_mac_pool87_rx_mac_partial2_invert_crc_cnt_reg5_rx_mac_partial2_invert_crc_cnt {
      type oc-yang:counter64;
      description
        "Counts the number of received packets with partial CRC type 2.";
    }
    leaf counter_slice5_ifg_mac_pool87_rx_mac_partial2_invert_crc_cnt_reg6_rx_mac_partial2_invert_crc_cnt {
      type oc-yang:counter64;
      description
        "Counts the number of received packets with partial CRC type 2.";
    }
    leaf counter_slice5_ifg_mac_pool87_rx_mac_partial2_invert_crc_cnt_reg7_rx_mac_partial2_invert_crc_cnt {
      type oc-yang:counter64;
      description
        "Counts the number of received packets with partial CRC type 2.";
    }
    leaf counter_slice6_ifg_mac_pool80_rx_mac_partial2_invert_crc_cnt_reg0_rx_mac_partial2_invert_crc_cnt {
      type oc-yang:counter64;
      description
        "Counts the number of received packets with partial CRC type 2.";
    }
    leaf counter_slice6_ifg_mac_pool80_rx_mac_partial2_invert_crc_cnt_reg1_rx_mac_partial2_invert_crc_cnt {
      type oc-yang:counter64;
      description
        "Counts the number of received packets with partial CRC type 2.";
    }
    leaf counter_slice6_ifg_mac_pool80_rx_mac_partial2_invert_crc_cnt_reg2_rx_mac_partial2_invert_crc_cnt {
      type oc-yang:counter64;
      description
        "Counts the number of received packets with partial CRC type 2.";
    }
    leaf counter_slice6_ifg_mac_pool80_rx_mac_partial2_invert_crc_cnt_reg3_rx_mac_partial2_invert_crc_cnt {
      type oc-yang:counter64;
      description
        "Counts the number of received packets with partial CRC type 2.";
    }
    leaf counter_slice6_ifg_mac_pool80_rx_mac_partial2_invert_crc_cnt_reg4_rx_mac_partial2_invert_crc_cnt {
      type oc-yang:counter64;
      description
        "Counts the number of received packets with partial CRC type 2.";
    }
    leaf counter_slice6_ifg_mac_pool80_rx_mac_partial2_invert_crc_cnt_reg5_rx_mac_partial2_invert_crc_cnt {
      type oc-yang:counter64;
      description
        "Counts the number of received packets with partial CRC type 2.";
    }
    leaf counter_slice6_ifg_mac_pool80_rx_mac_partial2_invert_crc_cnt_reg6_rx_mac_partial2_invert_crc_cnt {
      type oc-yang:counter64;
      description
        "Counts the number of received packets with partial CRC type 2.";
    }
    leaf counter_slice6_ifg_mac_pool80_rx_mac_partial2_invert_crc_cnt_reg7_rx_mac_partial2_invert_crc_cnt {
      type oc-yang:counter64;
      description
        "Counts the number of received packets with partial CRC type 2.";
    }
    leaf counter_slice6_ifg_mac_pool81_rx_mac_partial2_invert_crc_cnt_reg0_rx_mac_partial2_invert_crc_cnt {
      type oc-yang:counter64;
      description
        "Counts the number of received packets with partial CRC type 2.";
    }
    leaf counter_slice6_ifg_mac_pool81_rx_mac_partial2_invert_crc_cnt_reg1_rx_mac_partial2_invert_crc_cnt {
      type oc-yang:counter64;
      description
        "Counts the number of received packets with partial CRC type 2.";
    }
    leaf counter_slice6_ifg_mac_pool81_rx_mac_partial2_invert_crc_cnt_reg2_rx_mac_partial2_invert_crc_cnt {
      type oc-yang:counter64;
      description
        "Counts the number of received packets with partial CRC type 2.";
    }
    leaf counter_slice6_ifg_mac_pool81_rx_mac_partial2_invert_crc_cnt_reg3_rx_mac_partial2_invert_crc_cnt {
      type oc-yang:counter64;
      description
        "Counts the number of received packets with partial CRC type 2.";
    }
    leaf counter_slice6_ifg_mac_pool81_rx_mac_partial2_invert_crc_cnt_reg4_rx_mac_partial2_invert_crc_cnt {
      type oc-yang:counter64;
      description
        "Counts the number of received packets with partial CRC type 2.";
    }
    leaf counter_slice6_ifg_mac_pool81_rx_mac_partial2_invert_crc_cnt_reg5_rx_mac_partial2_invert_crc_cnt {
      type oc-yang:counter64;
      description
        "Counts the number of received packets with partial CRC type 2.";
    }
    leaf counter_slice6_ifg_mac_pool81_rx_mac_partial2_invert_crc_cnt_reg6_rx_mac_partial2_invert_crc_cnt {
      type oc-yang:counter64;
      description
        "Counts the number of received packets with partial CRC type 2.";
    }
    leaf counter_slice6_ifg_mac_pool81_rx_mac_partial2_invert_crc_cnt_reg7_rx_mac_partial2_invert_crc_cnt {
      type oc-yang:counter64;
      description
        "Counts the number of received packets with partial CRC type 2.";
    }
    leaf counter_slice6_ifg_mac_pool82_rx_mac_partial2_invert_crc_cnt_reg0_rx_mac_partial2_invert_crc_cnt {
      type oc-yang:counter64;
      description
        "Counts the number of received packets with partial CRC type 2.";
    }
    leaf counter_slice6_ifg_mac_pool82_rx_mac_partial2_invert_crc_cnt_reg1_rx_mac_partial2_invert_crc_cnt {
      type oc-yang:counter64;
      description
        "Counts the number of received packets with partial CRC type 2.";
    }
    leaf counter_slice6_ifg_mac_pool82_rx_mac_partial2_invert_crc_cnt_reg2_rx_mac_partial2_invert_crc_cnt {
      type oc-yang:counter64;
      description
        "Counts the number of received packets with partial CRC type 2.";
    }
    leaf counter_slice6_ifg_mac_pool82_rx_mac_partial2_invert_crc_cnt_reg3_rx_mac_partial2_invert_crc_cnt {
      type oc-yang:counter64;
      description
        "Counts the number of received packets with partial CRC type 2.";
    }
    leaf counter_slice6_ifg_mac_pool82_rx_mac_partial2_invert_crc_cnt_reg4_rx_mac_partial2_invert_crc_cnt {
      type oc-yang:counter64;
      description
        "Counts the number of received packets with partial CRC type 2.";
    }
    leaf counter_slice6_ifg_mac_pool82_rx_mac_partial2_invert_crc_cnt_reg5_rx_mac_partial2_invert_crc_cnt {
      type oc-yang:counter64;
      description
        "Counts the number of received packets with partial CRC type 2.";
    }
    leaf counter_slice6_ifg_mac_pool82_rx_mac_partial2_invert_crc_cnt_reg6_rx_mac_partial2_invert_crc_cnt {
      type oc-yang:counter64;
      description
        "Counts the number of received packets with partial CRC type 2.";
    }
    leaf counter_slice6_ifg_mac_pool82_rx_mac_partial2_invert_crc_cnt_reg7_rx_mac_partial2_invert_crc_cnt {
      type oc-yang:counter64;
      description
        "Counts the number of received packets with partial CRC type 2.";
    }
    leaf counter_slice6_ifg_mac_pool83_rx_mac_partial2_invert_crc_cnt_reg0_rx_mac_partial2_invert_crc_cnt {
      type oc-yang:counter64;
      description
        "Counts the number of received packets with partial CRC type 2.";
    }
    leaf counter_slice6_ifg_mac_pool83_rx_mac_partial2_invert_crc_cnt_reg1_rx_mac_partial2_invert_crc_cnt {
      type oc-yang:counter64;
      description
        "Counts the number of received packets with partial CRC type 2.";
    }
    leaf counter_slice6_ifg_mac_pool83_rx_mac_partial2_invert_crc_cnt_reg2_rx_mac_partial2_invert_crc_cnt {
      type oc-yang:counter64;
      description
        "Counts the number of received packets with partial CRC type 2.";
    }
    leaf counter_slice6_ifg_mac_pool83_rx_mac_partial2_invert_crc_cnt_reg3_rx_mac_partial2_invert_crc_cnt {
      type oc-yang:counter64;
      description
        "Counts the number of received packets with partial CRC type 2.";
    }
    leaf counter_slice6_ifg_mac_pool83_rx_mac_partial2_invert_crc_cnt_reg4_rx_mac_partial2_invert_crc_cnt {
      type oc-yang:counter64;
      description
        "Counts the number of received packets with partial CRC type 2.";
    }
    leaf counter_slice6_ifg_mac_pool83_rx_mac_partial2_invert_crc_cnt_reg5_rx_mac_partial2_invert_crc_cnt {
      type oc-yang:counter64;
      description
        "Counts the number of received packets with partial CRC type 2.";
    }
    leaf counter_slice6_ifg_mac_pool83_rx_mac_partial2_invert_crc_cnt_reg6_rx_mac_partial2_invert_crc_cnt {
      type oc-yang:counter64;
      description
        "Counts the number of received packets with partial CRC type 2.";
    }
    leaf counter_slice6_ifg_mac_pool83_rx_mac_partial2_invert_crc_cnt_reg7_rx_mac_partial2_invert_crc_cnt {
      type oc-yang:counter64;
      description
        "Counts the number of received packets with partial CRC type 2.";
    }
    leaf counter_slice6_ifg_mac_pool84_rx_mac_partial2_invert_crc_cnt_reg0_rx_mac_partial2_invert_crc_cnt {
      type oc-yang:counter64;
      description
        "Counts the number of received packets with partial CRC type 2.";
    }
    leaf counter_slice6_ifg_mac_pool84_rx_mac_partial2_invert_crc_cnt_reg1_rx_mac_partial2_invert_crc_cnt {
      type oc-yang:counter64;
      description
        "Counts the number of received packets with partial CRC type 2.";
    }
    leaf counter_slice6_ifg_mac_pool84_rx_mac_partial2_invert_crc_cnt_reg2_rx_mac_partial2_invert_crc_cnt {
      type oc-yang:counter64;
      description
        "Counts the number of received packets with partial CRC type 2.";
    }
    leaf counter_slice6_ifg_mac_pool84_rx_mac_partial2_invert_crc_cnt_reg3_rx_mac_partial2_invert_crc_cnt {
      type oc-yang:counter64;
      description
        "Counts the number of received packets with partial CRC type 2.";
    }
    leaf counter_slice6_ifg_mac_pool84_rx_mac_partial2_invert_crc_cnt_reg4_rx_mac_partial2_invert_crc_cnt {
      type oc-yang:counter64;
      description
        "Counts the number of received packets with partial CRC type 2.";
    }
    leaf counter_slice6_ifg_mac_pool84_rx_mac_partial2_invert_crc_cnt_reg5_rx_mac_partial2_invert_crc_cnt {
      type oc-yang:counter64;
      description
        "Counts the number of received packets with partial CRC type 2.";
    }
    leaf counter_slice6_ifg_mac_pool84_rx_mac_partial2_invert_crc_cnt_reg6_rx_mac_partial2_invert_crc_cnt {
      type oc-yang:counter64;
      description
        "Counts the number of received packets with partial CRC type 2.";
    }
    leaf counter_slice6_ifg_mac_pool84_rx_mac_partial2_invert_crc_cnt_reg7_rx_mac_partial2_invert_crc_cnt {
      type oc-yang:counter64;
      description
        "Counts the number of received packets with partial CRC type 2.";
    }
    leaf counter_slice6_ifg_mac_pool85_rx_mac_partial2_invert_crc_cnt_reg0_rx_mac_partial2_invert_crc_cnt {
      type oc-yang:counter64;
      description
        "Counts the number of received packets with partial CRC type 2.";
    }
    leaf counter_slice6_ifg_mac_pool85_rx_mac_partial2_invert_crc_cnt_reg1_rx_mac_partial2_invert_crc_cnt {
      type oc-yang:counter64;
      description
        "Counts the number of received packets with partial CRC type 2.";
    }
    leaf counter_slice6_ifg_mac_pool85_rx_mac_partial2_invert_crc_cnt_reg2_rx_mac_partial2_invert_crc_cnt {
      type oc-yang:counter64;
      description
        "Counts the number of received packets with partial CRC type 2.";
    }
    leaf counter_slice6_ifg_mac_pool85_rx_mac_partial2_invert_crc_cnt_reg3_rx_mac_partial2_invert_crc_cnt {
      type oc-yang:counter64;
      description
        "Counts the number of received packets with partial CRC type 2.";
    }
    leaf counter_slice6_ifg_mac_pool85_rx_mac_partial2_invert_crc_cnt_reg4_rx_mac_partial2_invert_crc_cnt {
      type oc-yang:counter64;
      description
        "Counts the number of received packets with partial CRC type 2.";
    }
    leaf counter_slice6_ifg_mac_pool85_rx_mac_partial2_invert_crc_cnt_reg5_rx_mac_partial2_invert_crc_cnt {
      type oc-yang:counter64;
      description
        "Counts the number of received packets with partial CRC type 2.";
    }
    leaf counter_slice6_ifg_mac_pool85_rx_mac_partial2_invert_crc_cnt_reg6_rx_mac_partial2_invert_crc_cnt {
      type oc-yang:counter64;
      description
        "Counts the number of received packets with partial CRC type 2.";
    }
    leaf counter_slice6_ifg_mac_pool85_rx_mac_partial2_invert_crc_cnt_reg7_rx_mac_partial2_invert_crc_cnt {
      type oc-yang:counter64;
      description
        "Counts the number of received packets with partial CRC type 2.";
    }
    leaf counter_slice6_ifg_mac_pool86_rx_mac_partial2_invert_crc_cnt_reg0_rx_mac_partial2_invert_crc_cnt {
      type oc-yang:counter64;
      description
        "Counts the number of received packets with partial CRC type 2.";
    }
    leaf counter_slice6_ifg_mac_pool86_rx_mac_partial2_invert_crc_cnt_reg1_rx_mac_partial2_invert_crc_cnt {
      type oc-yang:counter64;
      description
        "Counts the number of received packets with partial CRC type 2.";
    }
    leaf counter_slice6_ifg_mac_pool86_rx_mac_partial2_invert_crc_cnt_reg2_rx_mac_partial2_invert_crc_cnt {
      type oc-yang:counter64;
      description
        "Counts the number of received packets with partial CRC type 2.";
    }
    leaf counter_slice6_ifg_mac_pool86_rx_mac_partial2_invert_crc_cnt_reg3_rx_mac_partial2_invert_crc_cnt {
      type oc-yang:counter64;
      description
        "Counts the number of received packets with partial CRC type 2.";
    }
    leaf counter_slice6_ifg_mac_pool86_rx_mac_partial2_invert_crc_cnt_reg4_rx_mac_partial2_invert_crc_cnt {
      type oc-yang:counter64;
      description
        "Counts the number of received packets with partial CRC type 2.";
    }
    leaf counter_slice6_ifg_mac_pool86_rx_mac_partial2_invert_crc_cnt_reg5_rx_mac_partial2_invert_crc_cnt {
      type oc-yang:counter64;
      description
        "Counts the number of received packets with partial CRC type 2.";
    }
    leaf counter_slice6_ifg_mac_pool86_rx_mac_partial2_invert_crc_cnt_reg6_rx_mac_partial2_invert_crc_cnt {
      type oc-yang:counter64;
      description
        "Counts the number of received packets with partial CRC type 2.";
    }
    leaf counter_slice6_ifg_mac_pool86_rx_mac_partial2_invert_crc_cnt_reg7_rx_mac_partial2_invert_crc_cnt {
      type oc-yang:counter64;
      description
        "Counts the number of received packets with partial CRC type 2.";
    }
    leaf counter_slice6_ifg_mac_pool87_rx_mac_partial2_invert_crc_cnt_reg0_rx_mac_partial2_invert_crc_cnt {
      type oc-yang:counter64;
      description
        "Counts the number of received packets with partial CRC type 2.";
    }
    leaf counter_slice6_ifg_mac_pool87_rx_mac_partial2_invert_crc_cnt_reg1_rx_mac_partial2_invert_crc_cnt {
      type oc-yang:counter64;
      description
        "Counts the number of received packets with partial CRC type 2.";
    }
    leaf counter_slice6_ifg_mac_pool87_rx_mac_partial2_invert_crc_cnt_reg2_rx_mac_partial2_invert_crc_cnt {
      type oc-yang:counter64;
      description
        "Counts the number of received packets with partial CRC type 2.";
    }
    leaf counter_slice6_ifg_mac_pool87_rx_mac_partial2_invert_crc_cnt_reg3_rx_mac_partial2_invert_crc_cnt {
      type oc-yang:counter64;
      description
        "Counts the number of received packets with partial CRC type 2.";
    }
    leaf counter_slice6_ifg_mac_pool87_rx_mac_partial2_invert_crc_cnt_reg4_rx_mac_partial2_invert_crc_cnt {
      type oc-yang:counter64;
      description
        "Counts the number of received packets with partial CRC type 2.";
    }
    leaf counter_slice6_ifg_mac_pool87_rx_mac_partial2_invert_crc_cnt_reg5_rx_mac_partial2_invert_crc_cnt {
      type oc-yang:counter64;
      description
        "Counts the number of received packets with partial CRC type 2.";
    }
    leaf counter_slice6_ifg_mac_pool87_rx_mac_partial2_invert_crc_cnt_reg6_rx_mac_partial2_invert_crc_cnt {
      type oc-yang:counter64;
      description
        "Counts the number of received packets with partial CRC type 2.";
    }
    leaf counter_slice6_ifg_mac_pool87_rx_mac_partial2_invert_crc_cnt_reg7_rx_mac_partial2_invert_crc_cnt {
      type oc-yang:counter64;
      description
        "Counts the number of received packets with partial CRC type 2.";
    }
    leaf counter_slice7_ifg_mac_pool80_rx_mac_partial2_invert_crc_cnt_reg0_rx_mac_partial2_invert_crc_cnt {
      type oc-yang:counter64;
      description
        "Counts the number of received packets with partial CRC type 2.";
    }
    leaf counter_slice7_ifg_mac_pool80_rx_mac_partial2_invert_crc_cnt_reg1_rx_mac_partial2_invert_crc_cnt {
      type oc-yang:counter64;
      description
        "Counts the number of received packets with partial CRC type 2.";
    }
    leaf counter_slice7_ifg_mac_pool80_rx_mac_partial2_invert_crc_cnt_reg2_rx_mac_partial2_invert_crc_cnt {
      type oc-yang:counter64;
      description
        "Counts the number of received packets with partial CRC type 2.";
    }
    leaf counter_slice7_ifg_mac_pool80_rx_mac_partial2_invert_crc_cnt_reg3_rx_mac_partial2_invert_crc_cnt {
      type oc-yang:counter64;
      description
        "Counts the number of received packets with partial CRC type 2.";
    }
    leaf counter_slice7_ifg_mac_pool80_rx_mac_partial2_invert_crc_cnt_reg4_rx_mac_partial2_invert_crc_cnt {
      type oc-yang:counter64;
      description
        "Counts the number of received packets with partial CRC type 2.";
    }
    leaf counter_slice7_ifg_mac_pool80_rx_mac_partial2_invert_crc_cnt_reg5_rx_mac_partial2_invert_crc_cnt {
      type oc-yang:counter64;
      description
        "Counts the number of received packets with partial CRC type 2.";
    }
    leaf counter_slice7_ifg_mac_pool80_rx_mac_partial2_invert_crc_cnt_reg6_rx_mac_partial2_invert_crc_cnt {
      type oc-yang:counter64;
      description
        "Counts the number of received packets with partial CRC type 2.";
    }
    leaf counter_slice7_ifg_mac_pool80_rx_mac_partial2_invert_crc_cnt_reg7_rx_mac_partial2_invert_crc_cnt {
      type oc-yang:counter64;
      description
        "Counts the number of received packets with partial CRC type 2.";
    }
    leaf counter_slice7_ifg_mac_pool81_rx_mac_partial2_invert_crc_cnt_reg0_rx_mac_partial2_invert_crc_cnt {
      type oc-yang:counter64;
      description
        "Counts the number of received packets with partial CRC type 2.";
    }
    leaf counter_slice7_ifg_mac_pool81_rx_mac_partial2_invert_crc_cnt_reg1_rx_mac_partial2_invert_crc_cnt {
      type oc-yang:counter64;
      description
        "Counts the number of received packets with partial CRC type 2.";
    }
    leaf counter_slice7_ifg_mac_pool81_rx_mac_partial2_invert_crc_cnt_reg2_rx_mac_partial2_invert_crc_cnt {
      type oc-yang:counter64;
      description
        "Counts the number of received packets with partial CRC type 2.";
    }
    leaf counter_slice7_ifg_mac_pool81_rx_mac_partial2_invert_crc_cnt_reg3_rx_mac_partial2_invert_crc_cnt {
      type oc-yang:counter64;
      description
        "Counts the number of received packets with partial CRC type 2.";
    }
    leaf counter_slice7_ifg_mac_pool81_rx_mac_partial2_invert_crc_cnt_reg4_rx_mac_partial2_invert_crc_cnt {
      type oc-yang:counter64;
      description
        "Counts the number of received packets with partial CRC type 2.";
    }
    leaf counter_slice7_ifg_mac_pool81_rx_mac_partial2_invert_crc_cnt_reg5_rx_mac_partial2_invert_crc_cnt {
      type oc-yang:counter64;
      description
        "Counts the number of received packets with partial CRC type 2.";
    }
    leaf counter_slice7_ifg_mac_pool81_rx_mac_partial2_invert_crc_cnt_reg6_rx_mac_partial2_invert_crc_cnt {
      type oc-yang:counter64;
      description
        "Counts the number of received packets with partial CRC type 2.";
    }
    leaf counter_slice7_ifg_mac_pool81_rx_mac_partial2_invert_crc_cnt_reg7_rx_mac_partial2_invert_crc_cnt {
      type oc-yang:counter64;
      description
        "Counts the number of received packets with partial CRC type 2.";
    }
    leaf counter_slice7_ifg_mac_pool82_rx_mac_partial2_invert_crc_cnt_reg0_rx_mac_partial2_invert_crc_cnt {
      type oc-yang:counter64;
      description
        "Counts the number of received packets with partial CRC type 2.";
    }
    leaf counter_slice7_ifg_mac_pool82_rx_mac_partial2_invert_crc_cnt_reg1_rx_mac_partial2_invert_crc_cnt {
      type oc-yang:counter64;
      description
        "Counts the number of received packets with partial CRC type 2.";
    }
    leaf counter_slice7_ifg_mac_pool82_rx_mac_partial2_invert_crc_cnt_reg2_rx_mac_partial2_invert_crc_cnt {
      type oc-yang:counter64;
      description
        "Counts the number of received packets with partial CRC type 2.";
    }
    leaf counter_slice7_ifg_mac_pool82_rx_mac_partial2_invert_crc_cnt_reg3_rx_mac_partial2_invert_crc_cnt {
      type oc-yang:counter64;
      description
        "Counts the number of received packets with partial CRC type 2.";
    }
    leaf counter_slice7_ifg_mac_pool82_rx_mac_partial2_invert_crc_cnt_reg4_rx_mac_partial2_invert_crc_cnt {
      type oc-yang:counter64;
      description
        "Counts the number of received packets with partial CRC type 2.";
    }
    leaf counter_slice7_ifg_mac_pool82_rx_mac_partial2_invert_crc_cnt_reg5_rx_mac_partial2_invert_crc_cnt {
      type oc-yang:counter64;
      description
        "Counts the number of received packets with partial CRC type 2.";
    }
    leaf counter_slice7_ifg_mac_pool82_rx_mac_partial2_invert_crc_cnt_reg6_rx_mac_partial2_invert_crc_cnt {
      type oc-yang:counter64;
      description
        "Counts the number of received packets with partial CRC type 2.";
    }
    leaf counter_slice7_ifg_mac_pool82_rx_mac_partial2_invert_crc_cnt_reg7_rx_mac_partial2_invert_crc_cnt {
      type oc-yang:counter64;
      description
        "Counts the number of received packets with partial CRC type 2.";
    }
    leaf counter_slice7_ifg_mac_pool83_rx_mac_partial2_invert_crc_cnt_reg0_rx_mac_partial2_invert_crc_cnt {
      type oc-yang:counter64;
      description
        "Counts the number of received packets with partial CRC type 2.";
    }
    leaf counter_slice7_ifg_mac_pool83_rx_mac_partial2_invert_crc_cnt_reg1_rx_mac_partial2_invert_crc_cnt {
      type oc-yang:counter64;
      description
        "Counts the number of received packets with partial CRC type 2.";
    }
    leaf counter_slice7_ifg_mac_pool83_rx_mac_partial2_invert_crc_cnt_reg2_rx_mac_partial2_invert_crc_cnt {
      type oc-yang:counter64;
      description
        "Counts the number of received packets with partial CRC type 2.";
    }
    leaf counter_slice7_ifg_mac_pool83_rx_mac_partial2_invert_crc_cnt_reg3_rx_mac_partial2_invert_crc_cnt {
      type oc-yang:counter64;
      description
        "Counts the number of received packets with partial CRC type 2.";
    }
    leaf counter_slice7_ifg_mac_pool83_rx_mac_partial2_invert_crc_cnt_reg4_rx_mac_partial2_invert_crc_cnt {
      type oc-yang:counter64;
      description
        "Counts the number of received packets with partial CRC type 2.";
    }
    leaf counter_slice7_ifg_mac_pool83_rx_mac_partial2_invert_crc_cnt_reg5_rx_mac_partial2_invert_crc_cnt {
      type oc-yang:counter64;
      description
        "Counts the number of received packets with partial CRC type 2.";
    }
    leaf counter_slice7_ifg_mac_pool83_rx_mac_partial2_invert_crc_cnt_reg6_rx_mac_partial2_invert_crc_cnt {
      type oc-yang:counter64;
      description
        "Counts the number of received packets with partial CRC type 2.";
    }
    leaf counter_slice7_ifg_mac_pool83_rx_mac_partial2_invert_crc_cnt_reg7_rx_mac_partial2_invert_crc_cnt {
      type oc-yang:counter64;
      description
        "Counts the number of received packets with partial CRC type 2.";
    }
    leaf counter_slice7_ifg_mac_pool84_rx_mac_partial2_invert_crc_cnt_reg0_rx_mac_partial2_invert_crc_cnt {
      type oc-yang:counter64;
      description
        "Counts the number of received packets with partial CRC type 2.";
    }
    leaf counter_slice7_ifg_mac_pool84_rx_mac_partial2_invert_crc_cnt_reg1_rx_mac_partial2_invert_crc_cnt {
      type oc-yang:counter64;
      description
        "Counts the number of received packets with partial CRC type 2.";
    }
    leaf counter_slice7_ifg_mac_pool84_rx_mac_partial2_invert_crc_cnt_reg2_rx_mac_partial2_invert_crc_cnt {
      type oc-yang:counter64;
      description
        "Counts the number of received packets with partial CRC type 2.";
    }
    leaf counter_slice7_ifg_mac_pool84_rx_mac_partial2_invert_crc_cnt_reg3_rx_mac_partial2_invert_crc_cnt {
      type oc-yang:counter64;
      description
        "Counts the number of received packets with partial CRC type 2.";
    }
    leaf counter_slice7_ifg_mac_pool84_rx_mac_partial2_invert_crc_cnt_reg4_rx_mac_partial2_invert_crc_cnt {
      type oc-yang:counter64;
      description
        "Counts the number of received packets with partial CRC type 2.";
    }
    leaf counter_slice7_ifg_mac_pool84_rx_mac_partial2_invert_crc_cnt_reg5_rx_mac_partial2_invert_crc_cnt {
      type oc-yang:counter64;
      description
        "Counts the number of received packets with partial CRC type 2.";
    }
    leaf counter_slice7_ifg_mac_pool84_rx_mac_partial2_invert_crc_cnt_reg6_rx_mac_partial2_invert_crc_cnt {
      type oc-yang:counter64;
      description
        "Counts the number of received packets with partial CRC type 2.";
    }
    leaf counter_slice7_ifg_mac_pool84_rx_mac_partial2_invert_crc_cnt_reg7_rx_mac_partial2_invert_crc_cnt {
      type oc-yang:counter64;
      description
        "Counts the number of received packets with partial CRC type 2.";
    }
    leaf counter_slice7_ifg_mac_pool85_rx_mac_partial2_invert_crc_cnt_reg0_rx_mac_partial2_invert_crc_cnt {
      type oc-yang:counter64;
      description
        "Counts the number of received packets with partial CRC type 2.";
    }
    leaf counter_slice7_ifg_mac_pool85_rx_mac_partial2_invert_crc_cnt_reg1_rx_mac_partial2_invert_crc_cnt {
      type oc-yang:counter64;
      description
        "Counts the number of received packets with partial CRC type 2.";
    }
    leaf counter_slice7_ifg_mac_pool85_rx_mac_partial2_invert_crc_cnt_reg2_rx_mac_partial2_invert_crc_cnt {
      type oc-yang:counter64;
      description
        "Counts the number of received packets with partial CRC type 2.";
    }
    leaf counter_slice7_ifg_mac_pool85_rx_mac_partial2_invert_crc_cnt_reg3_rx_mac_partial2_invert_crc_cnt {
      type oc-yang:counter64;
      description
        "Counts the number of received packets with partial CRC type 2.";
    }
    leaf counter_slice7_ifg_mac_pool85_rx_mac_partial2_invert_crc_cnt_reg4_rx_mac_partial2_invert_crc_cnt {
      type oc-yang:counter64;
      description
        "Counts the number of received packets with partial CRC type 2.";
    }
    leaf counter_slice7_ifg_mac_pool85_rx_mac_partial2_invert_crc_cnt_reg5_rx_mac_partial2_invert_crc_cnt {
      type oc-yang:counter64;
      description
        "Counts the number of received packets with partial CRC type 2.";
    }
    leaf counter_slice7_ifg_mac_pool85_rx_mac_partial2_invert_crc_cnt_reg6_rx_mac_partial2_invert_crc_cnt {
      type oc-yang:counter64;
      description
        "Counts the number of received packets with partial CRC type 2.";
    }
    leaf counter_slice7_ifg_mac_pool85_rx_mac_partial2_invert_crc_cnt_reg7_rx_mac_partial2_invert_crc_cnt {
      type oc-yang:counter64;
      description
        "Counts the number of received packets with partial CRC type 2.";
    }
    leaf counter_slice7_ifg_mac_pool86_rx_mac_partial2_invert_crc_cnt_reg0_rx_mac_partial2_invert_crc_cnt {
      type oc-yang:counter64;
      description
        "Counts the number of received packets with partial CRC type 2.";
    }
    leaf counter_slice7_ifg_mac_pool86_rx_mac_partial2_invert_crc_cnt_reg1_rx_mac_partial2_invert_crc_cnt {
      type oc-yang:counter64;
      description
        "Counts the number of received packets with partial CRC type 2.";
    }
    leaf counter_slice7_ifg_mac_pool86_rx_mac_partial2_invert_crc_cnt_reg2_rx_mac_partial2_invert_crc_cnt {
      type oc-yang:counter64;
      description
        "Counts the number of received packets with partial CRC type 2.";
    }
    leaf counter_slice7_ifg_mac_pool86_rx_mac_partial2_invert_crc_cnt_reg3_rx_mac_partial2_invert_crc_cnt {
      type oc-yang:counter64;
      description
        "Counts the number of received packets with partial CRC type 2.";
    }
    leaf counter_slice7_ifg_mac_pool86_rx_mac_partial2_invert_crc_cnt_reg4_rx_mac_partial2_invert_crc_cnt {
      type oc-yang:counter64;
      description
        "Counts the number of received packets with partial CRC type 2.";
    }
    leaf counter_slice7_ifg_mac_pool86_rx_mac_partial2_invert_crc_cnt_reg5_rx_mac_partial2_invert_crc_cnt {
      type oc-yang:counter64;
      description
        "Counts the number of received packets with partial CRC type 2.";
    }
    leaf counter_slice7_ifg_mac_pool86_rx_mac_partial2_invert_crc_cnt_reg6_rx_mac_partial2_invert_crc_cnt {
      type oc-yang:counter64;
      description
        "Counts the number of received packets with partial CRC type 2.";
    }
    leaf counter_slice7_ifg_mac_pool86_rx_mac_partial2_invert_crc_cnt_reg7_rx_mac_partial2_invert_crc_cnt {
      type oc-yang:counter64;
      description
        "Counts the number of received packets with partial CRC type 2.";
    }
    leaf counter_slice7_ifg_mac_pool87_rx_mac_partial2_invert_crc_cnt_reg0_rx_mac_partial2_invert_crc_cnt {
      type oc-yang:counter64;
      description
        "Counts the number of received packets with partial CRC type 2.";
    }
    leaf counter_slice7_ifg_mac_pool87_rx_mac_partial2_invert_crc_cnt_reg1_rx_mac_partial2_invert_crc_cnt {
      type oc-yang:counter64;
      description
        "Counts the number of received packets with partial CRC type 2.";
    }
    leaf counter_slice7_ifg_mac_pool87_rx_mac_partial2_invert_crc_cnt_reg2_rx_mac_partial2_invert_crc_cnt {
      type oc-yang:counter64;
      description
        "Counts the number of received packets with partial CRC type 2.";
    }
    leaf counter_slice7_ifg_mac_pool87_rx_mac_partial2_invert_crc_cnt_reg3_rx_mac_partial2_invert_crc_cnt {
      type oc-yang:counter64;
      description
        "Counts the number of received packets with partial CRC type 2.";
    }
    leaf counter_slice7_ifg_mac_pool87_rx_mac_partial2_invert_crc_cnt_reg4_rx_mac_partial2_invert_crc_cnt {
      type oc-yang:counter64;
      description
        "Counts the number of received packets with partial CRC type 2.";
    }
    leaf counter_slice7_ifg_mac_pool87_rx_mac_partial2_invert_crc_cnt_reg5_rx_mac_partial2_invert_crc_cnt {
      type oc-yang:counter64;
      description
        "Counts the number of received packets with partial CRC type 2.";
    }
    leaf counter_slice7_ifg_mac_pool87_rx_mac_partial2_invert_crc_cnt_reg6_rx_mac_partial2_invert_crc_cnt {
      type oc-yang:counter64;
      description
        "Counts the number of received packets with partial CRC type 2.";
    }
    leaf counter_slice7_ifg_mac_pool87_rx_mac_partial2_invert_crc_cnt_reg7_rx_mac_partial2_invert_crc_cnt {
      type oc-yang:counter64;
      description
        "Counts the number of received packets with partial CRC type 2.";
    }
    leaf counter_slice8_ifg_mac_pool80_rx_mac_partial2_invert_crc_cnt_reg0_rx_mac_partial2_invert_crc_cnt {
      type oc-yang:counter64;
      description
        "Counts the number of received packets with partial CRC type 2.";
    }
    leaf counter_slice8_ifg_mac_pool80_rx_mac_partial2_invert_crc_cnt_reg1_rx_mac_partial2_invert_crc_cnt {
      type oc-yang:counter64;
      description
        "Counts the number of received packets with partial CRC type 2.";
    }
    leaf counter_slice8_ifg_mac_pool80_rx_mac_partial2_invert_crc_cnt_reg2_rx_mac_partial2_invert_crc_cnt {
      type oc-yang:counter64;
      description
        "Counts the number of received packets with partial CRC type 2.";
    }
    leaf counter_slice8_ifg_mac_pool80_rx_mac_partial2_invert_crc_cnt_reg3_rx_mac_partial2_invert_crc_cnt {
      type oc-yang:counter64;
      description
        "Counts the number of received packets with partial CRC type 2.";
    }
    leaf counter_slice8_ifg_mac_pool80_rx_mac_partial2_invert_crc_cnt_reg4_rx_mac_partial2_invert_crc_cnt {
      type oc-yang:counter64;
      description
        "Counts the number of received packets with partial CRC type 2.";
    }
    leaf counter_slice8_ifg_mac_pool80_rx_mac_partial2_invert_crc_cnt_reg5_rx_mac_partial2_invert_crc_cnt {
      type oc-yang:counter64;
      description
        "Counts the number of received packets with partial CRC type 2.";
    }
    leaf counter_slice8_ifg_mac_pool80_rx_mac_partial2_invert_crc_cnt_reg6_rx_mac_partial2_invert_crc_cnt {
      type oc-yang:counter64;
      description
        "Counts the number of received packets with partial CRC type 2.";
    }
    leaf counter_slice8_ifg_mac_pool80_rx_mac_partial2_invert_crc_cnt_reg7_rx_mac_partial2_invert_crc_cnt {
      type oc-yang:counter64;
      description
        "Counts the number of received packets with partial CRC type 2.";
    }
    leaf counter_slice8_ifg_mac_pool81_rx_mac_partial2_invert_crc_cnt_reg0_rx_mac_partial2_invert_crc_cnt {
      type oc-yang:counter64;
      description
        "Counts the number of received packets with partial CRC type 2.";
    }
    leaf counter_slice8_ifg_mac_pool81_rx_mac_partial2_invert_crc_cnt_reg1_rx_mac_partial2_invert_crc_cnt {
      type oc-yang:counter64;
      description
        "Counts the number of received packets with partial CRC type 2.";
    }
    leaf counter_slice8_ifg_mac_pool81_rx_mac_partial2_invert_crc_cnt_reg2_rx_mac_partial2_invert_crc_cnt {
      type oc-yang:counter64;
      description
        "Counts the number of received packets with partial CRC type 2.";
    }
    leaf counter_slice8_ifg_mac_pool81_rx_mac_partial2_invert_crc_cnt_reg3_rx_mac_partial2_invert_crc_cnt {
      type oc-yang:counter64;
      description
        "Counts the number of received packets with partial CRC type 2.";
    }
    leaf counter_slice8_ifg_mac_pool81_rx_mac_partial2_invert_crc_cnt_reg4_rx_mac_partial2_invert_crc_cnt {
      type oc-yang:counter64;
      description
        "Counts the number of received packets with partial CRC type 2.";
    }
    leaf counter_slice8_ifg_mac_pool81_rx_mac_partial2_invert_crc_cnt_reg5_rx_mac_partial2_invert_crc_cnt {
      type oc-yang:counter64;
      description
        "Counts the number of received packets with partial CRC type 2.";
    }
    leaf counter_slice8_ifg_mac_pool81_rx_mac_partial2_invert_crc_cnt_reg6_rx_mac_partial2_invert_crc_cnt {
      type oc-yang:counter64;
      description
        "Counts the number of received packets with partial CRC type 2.";
    }
    leaf counter_slice8_ifg_mac_pool81_rx_mac_partial2_invert_crc_cnt_reg7_rx_mac_partial2_invert_crc_cnt {
      type oc-yang:counter64;
      description
        "Counts the number of received packets with partial CRC type 2.";
    }
    leaf counter_slice8_ifg_mac_pool82_rx_mac_partial2_invert_crc_cnt_reg0_rx_mac_partial2_invert_crc_cnt {
      type oc-yang:counter64;
      description
        "Counts the number of received packets with partial CRC type 2.";
    }
    leaf counter_slice8_ifg_mac_pool82_rx_mac_partial2_invert_crc_cnt_reg1_rx_mac_partial2_invert_crc_cnt {
      type oc-yang:counter64;
      description
        "Counts the number of received packets with partial CRC type 2.";
    }
    leaf counter_slice8_ifg_mac_pool82_rx_mac_partial2_invert_crc_cnt_reg2_rx_mac_partial2_invert_crc_cnt {
      type oc-yang:counter64;
      description
        "Counts the number of received packets with partial CRC type 2.";
    }
    leaf counter_slice8_ifg_mac_pool82_rx_mac_partial2_invert_crc_cnt_reg3_rx_mac_partial2_invert_crc_cnt {
      type oc-yang:counter64;
      description
        "Counts the number of received packets with partial CRC type 2.";
    }
    leaf counter_slice8_ifg_mac_pool82_rx_mac_partial2_invert_crc_cnt_reg4_rx_mac_partial2_invert_crc_cnt {
      type oc-yang:counter64;
      description
        "Counts the number of received packets with partial CRC type 2.";
    }
    leaf counter_slice8_ifg_mac_pool82_rx_mac_partial2_invert_crc_cnt_reg5_rx_mac_partial2_invert_crc_cnt {
      type oc-yang:counter64;
      description
        "Counts the number of received packets with partial CRC type 2.";
    }
    leaf counter_slice8_ifg_mac_pool82_rx_mac_partial2_invert_crc_cnt_reg6_rx_mac_partial2_invert_crc_cnt {
      type oc-yang:counter64;
      description
        "Counts the number of received packets with partial CRC type 2.";
    }
    leaf counter_slice8_ifg_mac_pool82_rx_mac_partial2_invert_crc_cnt_reg7_rx_mac_partial2_invert_crc_cnt {
      type oc-yang:counter64;
      description
        "Counts the number of received packets with partial CRC type 2.";
    }
    leaf counter_slice8_ifg_mac_pool83_rx_mac_partial2_invert_crc_cnt_reg0_rx_mac_partial2_invert_crc_cnt {
      type oc-yang:counter64;
      description
        "Counts the number of received packets with partial CRC type 2.";
    }
    leaf counter_slice8_ifg_mac_pool83_rx_mac_partial2_invert_crc_cnt_reg1_rx_mac_partial2_invert_crc_cnt {
      type oc-yang:counter64;
      description
        "Counts the number of received packets with partial CRC type 2.";
    }
    leaf counter_slice8_ifg_mac_pool83_rx_mac_partial2_invert_crc_cnt_reg2_rx_mac_partial2_invert_crc_cnt {
      type oc-yang:counter64;
      description
        "Counts the number of received packets with partial CRC type 2.";
    }
    leaf counter_slice8_ifg_mac_pool83_rx_mac_partial2_invert_crc_cnt_reg3_rx_mac_partial2_invert_crc_cnt {
      type oc-yang:counter64;
      description
        "Counts the number of received packets with partial CRC type 2.";
    }
    leaf counter_slice8_ifg_mac_pool83_rx_mac_partial2_invert_crc_cnt_reg4_rx_mac_partial2_invert_crc_cnt {
      type oc-yang:counter64;
      description
        "Counts the number of received packets with partial CRC type 2.";
    }
    leaf counter_slice8_ifg_mac_pool83_rx_mac_partial2_invert_crc_cnt_reg5_rx_mac_partial2_invert_crc_cnt {
      type oc-yang:counter64;
      description
        "Counts the number of received packets with partial CRC type 2.";
    }
    leaf counter_slice8_ifg_mac_pool83_rx_mac_partial2_invert_crc_cnt_reg6_rx_mac_partial2_invert_crc_cnt {
      type oc-yang:counter64;
      description
        "Counts the number of received packets with partial CRC type 2.";
    }
    leaf counter_slice8_ifg_mac_pool83_rx_mac_partial2_invert_crc_cnt_reg7_rx_mac_partial2_invert_crc_cnt {
      type oc-yang:counter64;
      description
        "Counts the number of received packets with partial CRC type 2.";
    }
    leaf counter_slice8_ifg_mac_pool84_rx_mac_partial2_invert_crc_cnt_reg0_rx_mac_partial2_invert_crc_cnt {
      type oc-yang:counter64;
      description
        "Counts the number of received packets with partial CRC type 2.";
    }
    leaf counter_slice8_ifg_mac_pool84_rx_mac_partial2_invert_crc_cnt_reg1_rx_mac_partial2_invert_crc_cnt {
      type oc-yang:counter64;
      description
        "Counts the number of received packets with partial CRC type 2.";
    }
    leaf counter_slice8_ifg_mac_pool84_rx_mac_partial2_invert_crc_cnt_reg2_rx_mac_partial2_invert_crc_cnt {
      type oc-yang:counter64;
      description
        "Counts the number of received packets with partial CRC type 2.";
    }
    leaf counter_slice8_ifg_mac_pool84_rx_mac_partial2_invert_crc_cnt_reg3_rx_mac_partial2_invert_crc_cnt {
      type oc-yang:counter64;
      description
        "Counts the number of received packets with partial CRC type 2.";
    }
    leaf counter_slice8_ifg_mac_pool84_rx_mac_partial2_invert_crc_cnt_reg4_rx_mac_partial2_invert_crc_cnt {
      type oc-yang:counter64;
      description
        "Counts the number of received packets with partial CRC type 2.";
    }
    leaf counter_slice8_ifg_mac_pool84_rx_mac_partial2_invert_crc_cnt_reg5_rx_mac_partial2_invert_crc_cnt {
      type oc-yang:counter64;
      description
        "Counts the number of received packets with partial CRC type 2.";
    }
    leaf counter_slice8_ifg_mac_pool84_rx_mac_partial2_invert_crc_cnt_reg6_rx_mac_partial2_invert_crc_cnt {
      type oc-yang:counter64;
      description
        "Counts the number of received packets with partial CRC type 2.";
    }
    leaf counter_slice8_ifg_mac_pool84_rx_mac_partial2_invert_crc_cnt_reg7_rx_mac_partial2_invert_crc_cnt {
      type oc-yang:counter64;
      description
        "Counts the number of received packets with partial CRC type 2.";
    }
    leaf counter_slice8_ifg_mac_pool85_rx_mac_partial2_invert_crc_cnt_reg0_rx_mac_partial2_invert_crc_cnt {
      type oc-yang:counter64;
      description
        "Counts the number of received packets with partial CRC type 2.";
    }
    leaf counter_slice8_ifg_mac_pool85_rx_mac_partial2_invert_crc_cnt_reg1_rx_mac_partial2_invert_crc_cnt {
      type oc-yang:counter64;
      description
        "Counts the number of received packets with partial CRC type 2.";
    }
    leaf counter_slice8_ifg_mac_pool85_rx_mac_partial2_invert_crc_cnt_reg2_rx_mac_partial2_invert_crc_cnt {
      type oc-yang:counter64;
      description
        "Counts the number of received packets with partial CRC type 2.";
    }
    leaf counter_slice8_ifg_mac_pool85_rx_mac_partial2_invert_crc_cnt_reg3_rx_mac_partial2_invert_crc_cnt {
      type oc-yang:counter64;
      description
        "Counts the number of received packets with partial CRC type 2.";
    }
    leaf counter_slice8_ifg_mac_pool85_rx_mac_partial2_invert_crc_cnt_reg4_rx_mac_partial2_invert_crc_cnt {
      type oc-yang:counter64;
      description
        "Counts the number of received packets with partial CRC type 2.";
    }
    leaf counter_slice8_ifg_mac_pool85_rx_mac_partial2_invert_crc_cnt_reg5_rx_mac_partial2_invert_crc_cnt {
      type oc-yang:counter64;
      description
        "Counts the number of received packets with partial CRC type 2.";
    }
    leaf counter_slice8_ifg_mac_pool85_rx_mac_partial2_invert_crc_cnt_reg6_rx_mac_partial2_invert_crc_cnt {
      type oc-yang:counter64;
      description
        "Counts the number of received packets with partial CRC type 2.";
    }
    leaf counter_slice8_ifg_mac_pool85_rx_mac_partial2_invert_crc_cnt_reg7_rx_mac_partial2_invert_crc_cnt {
      type oc-yang:counter64;
      description
        "Counts the number of received packets with partial CRC type 2.";
    }
    leaf counter_slice8_ifg_mac_pool86_rx_mac_partial2_invert_crc_cnt_reg0_rx_mac_partial2_invert_crc_cnt {
      type oc-yang:counter64;
      description
        "Counts the number of received packets with partial CRC type 2.";
    }
    leaf counter_slice8_ifg_mac_pool86_rx_mac_partial2_invert_crc_cnt_reg1_rx_mac_partial2_invert_crc_cnt {
      type oc-yang:counter64;
      description
        "Counts the number of received packets with partial CRC type 2.";
    }
    leaf counter_slice8_ifg_mac_pool86_rx_mac_partial2_invert_crc_cnt_reg2_rx_mac_partial2_invert_crc_cnt {
      type oc-yang:counter64;
      description
        "Counts the number of received packets with partial CRC type 2.";
    }
    leaf counter_slice8_ifg_mac_pool86_rx_mac_partial2_invert_crc_cnt_reg3_rx_mac_partial2_invert_crc_cnt {
      type oc-yang:counter64;
      description
        "Counts the number of received packets with partial CRC type 2.";
    }
    leaf counter_slice8_ifg_mac_pool86_rx_mac_partial2_invert_crc_cnt_reg4_rx_mac_partial2_invert_crc_cnt {
      type oc-yang:counter64;
      description
        "Counts the number of received packets with partial CRC type 2.";
    }
    leaf counter_slice8_ifg_mac_pool86_rx_mac_partial2_invert_crc_cnt_reg5_rx_mac_partial2_invert_crc_cnt {
      type oc-yang:counter64;
      description
        "Counts the number of received packets with partial CRC type 2.";
    }
    leaf counter_slice8_ifg_mac_pool86_rx_mac_partial2_invert_crc_cnt_reg6_rx_mac_partial2_invert_crc_cnt {
      type oc-yang:counter64;
      description
        "Counts the number of received packets with partial CRC type 2.";
    }
    leaf counter_slice8_ifg_mac_pool86_rx_mac_partial2_invert_crc_cnt_reg7_rx_mac_partial2_invert_crc_cnt {
      type oc-yang:counter64;
      description
        "Counts the number of received packets with partial CRC type 2.";
    }
    leaf counter_slice8_ifg_mac_pool87_rx_mac_partial2_invert_crc_cnt_reg0_rx_mac_partial2_invert_crc_cnt {
      type oc-yang:counter64;
      description
        "Counts the number of received packets with partial CRC type 2.";
    }
    leaf counter_slice8_ifg_mac_pool87_rx_mac_partial2_invert_crc_cnt_reg1_rx_mac_partial2_invert_crc_cnt {
      type oc-yang:counter64;
      description
        "Counts the number of received packets with partial CRC type 2.";
    }
    leaf counter_slice8_ifg_mac_pool87_rx_mac_partial2_invert_crc_cnt_reg2_rx_mac_partial2_invert_crc_cnt {
      type oc-yang:counter64;
      description
        "Counts the number of received packets with partial CRC type 2.";
    }
    leaf counter_slice8_ifg_mac_pool87_rx_mac_partial2_invert_crc_cnt_reg3_rx_mac_partial2_invert_crc_cnt {
      type oc-yang:counter64;
      description
        "Counts the number of received packets with partial CRC type 2.";
    }
    leaf counter_slice8_ifg_mac_pool87_rx_mac_partial2_invert_crc_cnt_reg4_rx_mac_partial2_invert_crc_cnt {
      type oc-yang:counter64;
      description
        "Counts the number of received packets with partial CRC type 2.";
    }
    leaf counter_slice8_ifg_mac_pool87_rx_mac_partial2_invert_crc_cnt_reg5_rx_mac_partial2_invert_crc_cnt {
      type oc-yang:counter64;
      description
        "Counts the number of received packets with partial CRC type 2.";
    }
    leaf counter_slice8_ifg_mac_pool87_rx_mac_partial2_invert_crc_cnt_reg6_rx_mac_partial2_invert_crc_cnt {
      type oc-yang:counter64;
      description
        "Counts the number of received packets with partial CRC type 2.";
    }
    leaf counter_slice8_ifg_mac_pool87_rx_mac_partial2_invert_crc_cnt_reg7_rx_mac_partial2_invert_crc_cnt {
      type oc-yang:counter64;
      description
        "Counts the number of received packets with partial CRC type 2.";
    }
    leaf counter_slice9_ifg_mac_pool80_rx_mac_partial2_invert_crc_cnt_reg0_rx_mac_partial2_invert_crc_cnt {
      type oc-yang:counter64;
      description
        "Counts the number of received packets with partial CRC type 2.";
    }
    leaf counter_slice9_ifg_mac_pool80_rx_mac_partial2_invert_crc_cnt_reg1_rx_mac_partial2_invert_crc_cnt {
      type oc-yang:counter64;
      description
        "Counts the number of received packets with partial CRC type 2.";
    }
    leaf counter_slice9_ifg_mac_pool80_rx_mac_partial2_invert_crc_cnt_reg2_rx_mac_partial2_invert_crc_cnt {
      type oc-yang:counter64;
      description
        "Counts the number of received packets with partial CRC type 2.";
    }
    leaf counter_slice9_ifg_mac_pool80_rx_mac_partial2_invert_crc_cnt_reg3_rx_mac_partial2_invert_crc_cnt {
      type oc-yang:counter64;
      description
        "Counts the number of received packets with partial CRC type 2.";
    }
    leaf counter_slice9_ifg_mac_pool80_rx_mac_partial2_invert_crc_cnt_reg4_rx_mac_partial2_invert_crc_cnt {
      type oc-yang:counter64;
      description
        "Counts the number of received packets with partial CRC type 2.";
    }
    leaf counter_slice9_ifg_mac_pool80_rx_mac_partial2_invert_crc_cnt_reg5_rx_mac_partial2_invert_crc_cnt {
      type oc-yang:counter64;
      description
        "Counts the number of received packets with partial CRC type 2.";
    }
    leaf counter_slice9_ifg_mac_pool80_rx_mac_partial2_invert_crc_cnt_reg6_rx_mac_partial2_invert_crc_cnt {
      type oc-yang:counter64;
      description
        "Counts the number of received packets with partial CRC type 2.";
    }
    leaf counter_slice9_ifg_mac_pool80_rx_mac_partial2_invert_crc_cnt_reg7_rx_mac_partial2_invert_crc_cnt {
      type oc-yang:counter64;
      description
        "Counts the number of received packets with partial CRC type 2.";
    }
    leaf counter_slice9_ifg_mac_pool81_rx_mac_partial2_invert_crc_cnt_reg0_rx_mac_partial2_invert_crc_cnt {
      type oc-yang:counter64;
      description
        "Counts the number of received packets with partial CRC type 2.";
    }
    leaf counter_slice9_ifg_mac_pool81_rx_mac_partial2_invert_crc_cnt_reg1_rx_mac_partial2_invert_crc_cnt {
      type oc-yang:counter64;
      description
        "Counts the number of received packets with partial CRC type 2.";
    }
    leaf counter_slice9_ifg_mac_pool81_rx_mac_partial2_invert_crc_cnt_reg2_rx_mac_partial2_invert_crc_cnt {
      type oc-yang:counter64;
      description
        "Counts the number of received packets with partial CRC type 2.";
    }
    leaf counter_slice9_ifg_mac_pool81_rx_mac_partial2_invert_crc_cnt_reg3_rx_mac_partial2_invert_crc_cnt {
      type oc-yang:counter64;
      description
        "Counts the number of received packets with partial CRC type 2.";
    }
    leaf counter_slice9_ifg_mac_pool81_rx_mac_partial2_invert_crc_cnt_reg4_rx_mac_partial2_invert_crc_cnt {
      type oc-yang:counter64;
      description
        "Counts the number of received packets with partial CRC type 2.";
    }
    leaf counter_slice9_ifg_mac_pool81_rx_mac_partial2_invert_crc_cnt_reg5_rx_mac_partial2_invert_crc_cnt {
      type oc-yang:counter64;
      description
        "Counts the number of received packets with partial CRC type 2.";
    }
    leaf counter_slice9_ifg_mac_pool81_rx_mac_partial2_invert_crc_cnt_reg6_rx_mac_partial2_invert_crc_cnt {
      type oc-yang:counter64;
      description
        "Counts the number of received packets with partial CRC type 2.";
    }
    leaf counter_slice9_ifg_mac_pool81_rx_mac_partial2_invert_crc_cnt_reg7_rx_mac_partial2_invert_crc_cnt {
      type oc-yang:counter64;
      description
        "Counts the number of received packets with partial CRC type 2.";
    }
    leaf counter_slice9_ifg_mac_pool82_rx_mac_partial2_invert_crc_cnt_reg0_rx_mac_partial2_invert_crc_cnt {
      type oc-yang:counter64;
      description
        "Counts the number of received packets with partial CRC type 2.";
    }
    leaf counter_slice9_ifg_mac_pool82_rx_mac_partial2_invert_crc_cnt_reg1_rx_mac_partial2_invert_crc_cnt {
      type oc-yang:counter64;
      description
        "Counts the number of received packets with partial CRC type 2.";
    }
    leaf counter_slice9_ifg_mac_pool82_rx_mac_partial2_invert_crc_cnt_reg2_rx_mac_partial2_invert_crc_cnt {
      type oc-yang:counter64;
      description
        "Counts the number of received packets with partial CRC type 2.";
    }
    leaf counter_slice9_ifg_mac_pool82_rx_mac_partial2_invert_crc_cnt_reg3_rx_mac_partial2_invert_crc_cnt {
      type oc-yang:counter64;
      description
        "Counts the number of received packets with partial CRC type 2.";
    }
    leaf counter_slice9_ifg_mac_pool82_rx_mac_partial2_invert_crc_cnt_reg4_rx_mac_partial2_invert_crc_cnt {
      type oc-yang:counter64;
      description
        "Counts the number of received packets with partial CRC type 2.";
    }
    leaf counter_slice9_ifg_mac_pool82_rx_mac_partial2_invert_crc_cnt_reg5_rx_mac_partial2_invert_crc_cnt {
      type oc-yang:counter64;
      description
        "Counts the number of received packets with partial CRC type 2.";
    }
    leaf counter_slice9_ifg_mac_pool82_rx_mac_partial2_invert_crc_cnt_reg6_rx_mac_partial2_invert_crc_cnt {
      type oc-yang:counter64;
      description
        "Counts the number of received packets with partial CRC type 2.";
    }
    leaf counter_slice9_ifg_mac_pool82_rx_mac_partial2_invert_crc_cnt_reg7_rx_mac_partial2_invert_crc_cnt {
      type oc-yang:counter64;
      description
        "Counts the number of received packets with partial CRC type 2.";
    }
    leaf counter_slice9_ifg_mac_pool83_rx_mac_partial2_invert_crc_cnt_reg0_rx_mac_partial2_invert_crc_cnt {
      type oc-yang:counter64;
      description
        "Counts the number of received packets with partial CRC type 2.";
    }
    leaf counter_slice9_ifg_mac_pool83_rx_mac_partial2_invert_crc_cnt_reg1_rx_mac_partial2_invert_crc_cnt {
      type oc-yang:counter64;
      description
        "Counts the number of received packets with partial CRC type 2.";
    }
    leaf counter_slice9_ifg_mac_pool83_rx_mac_partial2_invert_crc_cnt_reg2_rx_mac_partial2_invert_crc_cnt {
      type oc-yang:counter64;
      description
        "Counts the number of received packets with partial CRC type 2.";
    }
    leaf counter_slice9_ifg_mac_pool83_rx_mac_partial2_invert_crc_cnt_reg3_rx_mac_partial2_invert_crc_cnt {
      type oc-yang:counter64;
      description
        "Counts the number of received packets with partial CRC type 2.";
    }
    leaf counter_slice9_ifg_mac_pool83_rx_mac_partial2_invert_crc_cnt_reg4_rx_mac_partial2_invert_crc_cnt {
      type oc-yang:counter64;
      description
        "Counts the number of received packets with partial CRC type 2.";
    }
    leaf counter_slice9_ifg_mac_pool83_rx_mac_partial2_invert_crc_cnt_reg5_rx_mac_partial2_invert_crc_cnt {
      type oc-yang:counter64;
      description
        "Counts the number of received packets with partial CRC type 2.";
    }
    leaf counter_slice9_ifg_mac_pool83_rx_mac_partial2_invert_crc_cnt_reg6_rx_mac_partial2_invert_crc_cnt {
      type oc-yang:counter64;
      description
        "Counts the number of received packets with partial CRC type 2.";
    }
    leaf counter_slice9_ifg_mac_pool83_rx_mac_partial2_invert_crc_cnt_reg7_rx_mac_partial2_invert_crc_cnt {
      type oc-yang:counter64;
      description
        "Counts the number of received packets with partial CRC type 2.";
    }
    leaf counter_slice9_ifg_mac_pool84_rx_mac_partial2_invert_crc_cnt_reg0_rx_mac_partial2_invert_crc_cnt {
      type oc-yang:counter64;
      description
        "Counts the number of received packets with partial CRC type 2.";
    }
    leaf counter_slice9_ifg_mac_pool84_rx_mac_partial2_invert_crc_cnt_reg1_rx_mac_partial2_invert_crc_cnt {
      type oc-yang:counter64;
      description
        "Counts the number of received packets with partial CRC type 2.";
    }
    leaf counter_slice9_ifg_mac_pool84_rx_mac_partial2_invert_crc_cnt_reg2_rx_mac_partial2_invert_crc_cnt {
      type oc-yang:counter64;
      description
        "Counts the number of received packets with partial CRC type 2.";
    }
    leaf counter_slice9_ifg_mac_pool84_rx_mac_partial2_invert_crc_cnt_reg3_rx_mac_partial2_invert_crc_cnt {
      type oc-yang:counter64;
      description
        "Counts the number of received packets with partial CRC type 2.";
    }
    leaf counter_slice9_ifg_mac_pool84_rx_mac_partial2_invert_crc_cnt_reg4_rx_mac_partial2_invert_crc_cnt {
      type oc-yang:counter64;
      description
        "Counts the number of received packets with partial CRC type 2.";
    }
    leaf counter_slice9_ifg_mac_pool84_rx_mac_partial2_invert_crc_cnt_reg5_rx_mac_partial2_invert_crc_cnt {
      type oc-yang:counter64;
      description
        "Counts the number of received packets with partial CRC type 2.";
    }
    leaf counter_slice9_ifg_mac_pool84_rx_mac_partial2_invert_crc_cnt_reg6_rx_mac_partial2_invert_crc_cnt {
      type oc-yang:counter64;
      description
        "Counts the number of received packets with partial CRC type 2.";
    }
    leaf counter_slice9_ifg_mac_pool84_rx_mac_partial2_invert_crc_cnt_reg7_rx_mac_partial2_invert_crc_cnt {
      type oc-yang:counter64;
      description
        "Counts the number of received packets with partial CRC type 2.";
    }
    leaf counter_slice9_ifg_mac_pool85_rx_mac_partial2_invert_crc_cnt_reg0_rx_mac_partial2_invert_crc_cnt {
      type oc-yang:counter64;
      description
        "Counts the number of received packets with partial CRC type 2.";
    }
    leaf counter_slice9_ifg_mac_pool85_rx_mac_partial2_invert_crc_cnt_reg1_rx_mac_partial2_invert_crc_cnt {
      type oc-yang:counter64;
      description
        "Counts the number of received packets with partial CRC type 2.";
    }
    leaf counter_slice9_ifg_mac_pool85_rx_mac_partial2_invert_crc_cnt_reg2_rx_mac_partial2_invert_crc_cnt {
      type oc-yang:counter64;
      description
        "Counts the number of received packets with partial CRC type 2.";
    }
    leaf counter_slice9_ifg_mac_pool85_rx_mac_partial2_invert_crc_cnt_reg3_rx_mac_partial2_invert_crc_cnt {
      type oc-yang:counter64;
      description
        "Counts the number of received packets with partial CRC type 2.";
    }
    leaf counter_slice9_ifg_mac_pool85_rx_mac_partial2_invert_crc_cnt_reg4_rx_mac_partial2_invert_crc_cnt {
      type oc-yang:counter64;
      description
        "Counts the number of received packets with partial CRC type 2.";
    }
    leaf counter_slice9_ifg_mac_pool85_rx_mac_partial2_invert_crc_cnt_reg5_rx_mac_partial2_invert_crc_cnt {
      type oc-yang:counter64;
      description
        "Counts the number of received packets with partial CRC type 2.";
    }
    leaf counter_slice9_ifg_mac_pool85_rx_mac_partial2_invert_crc_cnt_reg6_rx_mac_partial2_invert_crc_cnt {
      type oc-yang:counter64;
      description
        "Counts the number of received packets with partial CRC type 2.";
    }
    leaf counter_slice9_ifg_mac_pool85_rx_mac_partial2_invert_crc_cnt_reg7_rx_mac_partial2_invert_crc_cnt {
      type oc-yang:counter64;
      description
        "Counts the number of received packets with partial CRC type 2.";
    }
    leaf counter_slice9_ifg_mac_pool86_rx_mac_partial2_invert_crc_cnt_reg0_rx_mac_partial2_invert_crc_cnt {
      type oc-yang:counter64;
      description
        "Counts the number of received packets with partial CRC type 2.";
    }
    leaf counter_slice9_ifg_mac_pool86_rx_mac_partial2_invert_crc_cnt_reg1_rx_mac_partial2_invert_crc_cnt {
      type oc-yang:counter64;
      description
        "Counts the number of received packets with partial CRC type 2.";
    }
    leaf counter_slice9_ifg_mac_pool86_rx_mac_partial2_invert_crc_cnt_reg2_rx_mac_partial2_invert_crc_cnt {
      type oc-yang:counter64;
      description
        "Counts the number of received packets with partial CRC type 2.";
    }
    leaf counter_slice9_ifg_mac_pool86_rx_mac_partial2_invert_crc_cnt_reg3_rx_mac_partial2_invert_crc_cnt {
      type oc-yang:counter64;
      description
        "Counts the number of received packets with partial CRC type 2.";
    }
    leaf counter_slice9_ifg_mac_pool86_rx_mac_partial2_invert_crc_cnt_reg4_rx_mac_partial2_invert_crc_cnt {
      type oc-yang:counter64;
      description
        "Counts the number of received packets with partial CRC type 2.";
    }
    leaf counter_slice9_ifg_mac_pool86_rx_mac_partial2_invert_crc_cnt_reg5_rx_mac_partial2_invert_crc_cnt {
      type oc-yang:counter64;
      description
        "Counts the number of received packets with partial CRC type 2.";
    }
    leaf counter_slice9_ifg_mac_pool86_rx_mac_partial2_invert_crc_cnt_reg6_rx_mac_partial2_invert_crc_cnt {
      type oc-yang:counter64;
      description
        "Counts the number of received packets with partial CRC type 2.";
    }
    leaf counter_slice9_ifg_mac_pool86_rx_mac_partial2_invert_crc_cnt_reg7_rx_mac_partial2_invert_crc_cnt {
      type oc-yang:counter64;
      description
        "Counts the number of received packets with partial CRC type 2.";
    }
    leaf counter_slice9_ifg_mac_pool87_rx_mac_partial2_invert_crc_cnt_reg0_rx_mac_partial2_invert_crc_cnt {
      type oc-yang:counter64;
      description
        "Counts the number of received packets with partial CRC type 2.";
    }
    leaf counter_slice9_ifg_mac_pool87_rx_mac_partial2_invert_crc_cnt_reg1_rx_mac_partial2_invert_crc_cnt {
      type oc-yang:counter64;
      description
        "Counts the number of received packets with partial CRC type 2.";
    }
    leaf counter_slice9_ifg_mac_pool87_rx_mac_partial2_invert_crc_cnt_reg2_rx_mac_partial2_invert_crc_cnt {
      type oc-yang:counter64;
      description
        "Counts the number of received packets with partial CRC type 2.";
    }
    leaf counter_slice9_ifg_mac_pool87_rx_mac_partial2_invert_crc_cnt_reg3_rx_mac_partial2_invert_crc_cnt {
      type oc-yang:counter64;
      description
        "Counts the number of received packets with partial CRC type 2.";
    }
    leaf counter_slice9_ifg_mac_pool87_rx_mac_partial2_invert_crc_cnt_reg4_rx_mac_partial2_invert_crc_cnt {
      type oc-yang:counter64;
      description
        "Counts the number of received packets with partial CRC type 2.";
    }
    leaf counter_slice9_ifg_mac_pool87_rx_mac_partial2_invert_crc_cnt_reg5_rx_mac_partial2_invert_crc_cnt {
      type oc-yang:counter64;
      description
        "Counts the number of received packets with partial CRC type 2.";
    }
    leaf counter_slice9_ifg_mac_pool87_rx_mac_partial2_invert_crc_cnt_reg6_rx_mac_partial2_invert_crc_cnt {
      type oc-yang:counter64;
      description
        "Counts the number of received packets with partial CRC type 2.";
    }
    leaf counter_slice9_ifg_mac_pool87_rx_mac_partial2_invert_crc_cnt_reg7_rx_mac_partial2_invert_crc_cnt {
      type oc-yang:counter64;
      description
        "Counts the number of received packets with partial CRC type 2.";
    }
    leaf counter_slice10_ifg_mac_pool80_rx_mac_partial2_invert_crc_cnt_reg0_rx_mac_partial2_invert_crc_cnt {
      type oc-yang:counter64;
      description
        "Counts the number of received packets with partial CRC type 2.";
    }
    leaf counter_slice10_ifg_mac_pool80_rx_mac_partial2_invert_crc_cnt_reg1_rx_mac_partial2_invert_crc_cnt {
      type oc-yang:counter64;
      description
        "Counts the number of received packets with partial CRC type 2.";
    }
    leaf counter_slice10_ifg_mac_pool80_rx_mac_partial2_invert_crc_cnt_reg2_rx_mac_partial2_invert_crc_cnt {
      type oc-yang:counter64;
      description
        "Counts the number of received packets with partial CRC type 2.";
    }
    leaf counter_slice10_ifg_mac_pool80_rx_mac_partial2_invert_crc_cnt_reg3_rx_mac_partial2_invert_crc_cnt {
      type oc-yang:counter64;
      description
        "Counts the number of received packets with partial CRC type 2.";
    }
    leaf counter_slice10_ifg_mac_pool80_rx_mac_partial2_invert_crc_cnt_reg4_rx_mac_partial2_invert_crc_cnt {
      type oc-yang:counter64;
      description
        "Counts the number of received packets with partial CRC type 2.";
    }
    leaf counter_slice10_ifg_mac_pool80_rx_mac_partial2_invert_crc_cnt_reg5_rx_mac_partial2_invert_crc_cnt {
      type oc-yang:counter64;
      description
        "Counts the number of received packets with partial CRC type 2.";
    }
    leaf counter_slice10_ifg_mac_pool80_rx_mac_partial2_invert_crc_cnt_reg6_rx_mac_partial2_invert_crc_cnt {
      type oc-yang:counter64;
      description
        "Counts the number of received packets with partial CRC type 2.";
    }
    leaf counter_slice10_ifg_mac_pool80_rx_mac_partial2_invert_crc_cnt_reg7_rx_mac_partial2_invert_crc_cnt {
      type oc-yang:counter64;
      description
        "Counts the number of received packets with partial CRC type 2.";
    }
    leaf counter_slice10_ifg_mac_pool81_rx_mac_partial2_invert_crc_cnt_reg0_rx_mac_partial2_invert_crc_cnt {
      type oc-yang:counter64;
      description
        "Counts the number of received packets with partial CRC type 2.";
    }
    leaf counter_slice10_ifg_mac_pool81_rx_mac_partial2_invert_crc_cnt_reg1_rx_mac_partial2_invert_crc_cnt {
      type oc-yang:counter64;
      description
        "Counts the number of received packets with partial CRC type 2.";
    }
    leaf counter_slice10_ifg_mac_pool81_rx_mac_partial2_invert_crc_cnt_reg2_rx_mac_partial2_invert_crc_cnt {
      type oc-yang:counter64;
      description
        "Counts the number of received packets with partial CRC type 2.";
    }
    leaf counter_slice10_ifg_mac_pool81_rx_mac_partial2_invert_crc_cnt_reg3_rx_mac_partial2_invert_crc_cnt {
      type oc-yang:counter64;
      description
        "Counts the number of received packets with partial CRC type 2.";
    }
    leaf counter_slice10_ifg_mac_pool81_rx_mac_partial2_invert_crc_cnt_reg4_rx_mac_partial2_invert_crc_cnt {
      type oc-yang:counter64;
      description
        "Counts the number of received packets with partial CRC type 2.";
    }
    leaf counter_slice10_ifg_mac_pool81_rx_mac_partial2_invert_crc_cnt_reg5_rx_mac_partial2_invert_crc_cnt {
      type oc-yang:counter64;
      description
        "Counts the number of received packets with partial CRC type 2.";
    }
    leaf counter_slice10_ifg_mac_pool81_rx_mac_partial2_invert_crc_cnt_reg6_rx_mac_partial2_invert_crc_cnt {
      type oc-yang:counter64;
      description
        "Counts the number of received packets with partial CRC type 2.";
    }
    leaf counter_slice10_ifg_mac_pool81_rx_mac_partial2_invert_crc_cnt_reg7_rx_mac_partial2_invert_crc_cnt {
      type oc-yang:counter64;
      description
        "Counts the number of received packets with partial CRC type 2.";
    }
    leaf counter_slice10_ifg_mac_pool82_rx_mac_partial2_invert_crc_cnt_reg0_rx_mac_partial2_invert_crc_cnt {
      type oc-yang:counter64;
      description
        "Counts the number of received packets with partial CRC type 2.";
    }
    leaf counter_slice10_ifg_mac_pool82_rx_mac_partial2_invert_crc_cnt_reg1_rx_mac_partial2_invert_crc_cnt {
      type oc-yang:counter64;
      description
        "Counts the number of received packets with partial CRC type 2.";
    }
    leaf counter_slice10_ifg_mac_pool82_rx_mac_partial2_invert_crc_cnt_reg2_rx_mac_partial2_invert_crc_cnt {
      type oc-yang:counter64;
      description
        "Counts the number of received packets with partial CRC type 2.";
    }
    leaf counter_slice10_ifg_mac_pool82_rx_mac_partial2_invert_crc_cnt_reg3_rx_mac_partial2_invert_crc_cnt {
      type oc-yang:counter64;
      description
        "Counts the number of received packets with partial CRC type 2.";
    }
    leaf counter_slice10_ifg_mac_pool82_rx_mac_partial2_invert_crc_cnt_reg4_rx_mac_partial2_invert_crc_cnt {
      type oc-yang:counter64;
      description
        "Counts the number of received packets with partial CRC type 2.";
    }
    leaf counter_slice10_ifg_mac_pool82_rx_mac_partial2_invert_crc_cnt_reg5_rx_mac_partial2_invert_crc_cnt {
      type oc-yang:counter64;
      description
        "Counts the number of received packets with partial CRC type 2.";
    }
    leaf counter_slice10_ifg_mac_pool82_rx_mac_partial2_invert_crc_cnt_reg6_rx_mac_partial2_invert_crc_cnt {
      type oc-yang:counter64;
      description
        "Counts the number of received packets with partial CRC type 2.";
    }
    leaf counter_slice10_ifg_mac_pool82_rx_mac_partial2_invert_crc_cnt_reg7_rx_mac_partial2_invert_crc_cnt {
      type oc-yang:counter64;
      description
        "Counts the number of received packets with partial CRC type 2.";
    }
    leaf counter_slice10_ifg_mac_pool83_rx_mac_partial2_invert_crc_cnt_reg0_rx_mac_partial2_invert_crc_cnt {
      type oc-yang:counter64;
      description
        "Counts the number of received packets with partial CRC type 2.";
    }
    leaf counter_slice10_ifg_mac_pool83_rx_mac_partial2_invert_crc_cnt_reg1_rx_mac_partial2_invert_crc_cnt {
      type oc-yang:counter64;
      description
        "Counts the number of received packets with partial CRC type 2.";
    }
    leaf counter_slice10_ifg_mac_pool83_rx_mac_partial2_invert_crc_cnt_reg2_rx_mac_partial2_invert_crc_cnt {
      type oc-yang:counter64;
      description
        "Counts the number of received packets with partial CRC type 2.";
    }
    leaf counter_slice10_ifg_mac_pool83_rx_mac_partial2_invert_crc_cnt_reg3_rx_mac_partial2_invert_crc_cnt {
      type oc-yang:counter64;
      description
        "Counts the number of received packets with partial CRC type 2.";
    }
    leaf counter_slice10_ifg_mac_pool83_rx_mac_partial2_invert_crc_cnt_reg4_rx_mac_partial2_invert_crc_cnt {
      type oc-yang:counter64;
      description
        "Counts the number of received packets with partial CRC type 2.";
    }
    leaf counter_slice10_ifg_mac_pool83_rx_mac_partial2_invert_crc_cnt_reg5_rx_mac_partial2_invert_crc_cnt {
      type oc-yang:counter64;
      description
        "Counts the number of received packets with partial CRC type 2.";
    }
    leaf counter_slice10_ifg_mac_pool83_rx_mac_partial2_invert_crc_cnt_reg6_rx_mac_partial2_invert_crc_cnt {
      type oc-yang:counter64;
      description
        "Counts the number of received packets with partial CRC type 2.";
    }
    leaf counter_slice10_ifg_mac_pool83_rx_mac_partial2_invert_crc_cnt_reg7_rx_mac_partial2_invert_crc_cnt {
      type oc-yang:counter64;
      description
        "Counts the number of received packets with partial CRC type 2.";
    }
    leaf counter_slice10_ifg_mac_pool84_rx_mac_partial2_invert_crc_cnt_reg0_rx_mac_partial2_invert_crc_cnt {
      type oc-yang:counter64;
      description
        "Counts the number of received packets with partial CRC type 2.";
    }
    leaf counter_slice10_ifg_mac_pool84_rx_mac_partial2_invert_crc_cnt_reg1_rx_mac_partial2_invert_crc_cnt {
      type oc-yang:counter64;
      description
        "Counts the number of received packets with partial CRC type 2.";
    }
    leaf counter_slice10_ifg_mac_pool84_rx_mac_partial2_invert_crc_cnt_reg2_rx_mac_partial2_invert_crc_cnt {
      type oc-yang:counter64;
      description
        "Counts the number of received packets with partial CRC type 2.";
    }
    leaf counter_slice10_ifg_mac_pool84_rx_mac_partial2_invert_crc_cnt_reg3_rx_mac_partial2_invert_crc_cnt {
      type oc-yang:counter64;
      description
        "Counts the number of received packets with partial CRC type 2.";
    }
    leaf counter_slice10_ifg_mac_pool84_rx_mac_partial2_invert_crc_cnt_reg4_rx_mac_partial2_invert_crc_cnt {
      type oc-yang:counter64;
      description
        "Counts the number of received packets with partial CRC type 2.";
    }
    leaf counter_slice10_ifg_mac_pool84_rx_mac_partial2_invert_crc_cnt_reg5_rx_mac_partial2_invert_crc_cnt {
      type oc-yang:counter64;
      description
        "Counts the number of received packets with partial CRC type 2.";
    }
    leaf counter_slice10_ifg_mac_pool84_rx_mac_partial2_invert_crc_cnt_reg6_rx_mac_partial2_invert_crc_cnt {
      type oc-yang:counter64;
      description
        "Counts the number of received packets with partial CRC type 2.";
    }
    leaf counter_slice10_ifg_mac_pool84_rx_mac_partial2_invert_crc_cnt_reg7_rx_mac_partial2_invert_crc_cnt {
      type oc-yang:counter64;
      description
        "Counts the number of received packets with partial CRC type 2.";
    }
    leaf counter_slice10_ifg_mac_pool85_rx_mac_partial2_invert_crc_cnt_reg0_rx_mac_partial2_invert_crc_cnt {
      type oc-yang:counter64;
      description
        "Counts the number of received packets with partial CRC type 2.";
    }
    leaf counter_slice10_ifg_mac_pool85_rx_mac_partial2_invert_crc_cnt_reg1_rx_mac_partial2_invert_crc_cnt {
      type oc-yang:counter64;
      description
        "Counts the number of received packets with partial CRC type 2.";
    }
    leaf counter_slice10_ifg_mac_pool85_rx_mac_partial2_invert_crc_cnt_reg2_rx_mac_partial2_invert_crc_cnt {
      type oc-yang:counter64;
      description
        "Counts the number of received packets with partial CRC type 2.";
    }
    leaf counter_slice10_ifg_mac_pool85_rx_mac_partial2_invert_crc_cnt_reg3_rx_mac_partial2_invert_crc_cnt {
      type oc-yang:counter64;
      description
        "Counts the number of received packets with partial CRC type 2.";
    }
    leaf counter_slice10_ifg_mac_pool85_rx_mac_partial2_invert_crc_cnt_reg4_rx_mac_partial2_invert_crc_cnt {
      type oc-yang:counter64;
      description
        "Counts the number of received packets with partial CRC type 2.";
    }
    leaf counter_slice10_ifg_mac_pool85_rx_mac_partial2_invert_crc_cnt_reg5_rx_mac_partial2_invert_crc_cnt {
      type oc-yang:counter64;
      description
        "Counts the number of received packets with partial CRC type 2.";
    }
    leaf counter_slice10_ifg_mac_pool85_rx_mac_partial2_invert_crc_cnt_reg6_rx_mac_partial2_invert_crc_cnt {
      type oc-yang:counter64;
      description
        "Counts the number of received packets with partial CRC type 2.";
    }
    leaf counter_slice10_ifg_mac_pool85_rx_mac_partial2_invert_crc_cnt_reg7_rx_mac_partial2_invert_crc_cnt {
      type oc-yang:counter64;
      description
        "Counts the number of received packets with partial CRC type 2.";
    }
    leaf counter_slice10_ifg_mac_pool86_rx_mac_partial2_invert_crc_cnt_reg0_rx_mac_partial2_invert_crc_cnt {
      type oc-yang:counter64;
      description
        "Counts the number of received packets with partial CRC type 2.";
    }
    leaf counter_slice10_ifg_mac_pool86_rx_mac_partial2_invert_crc_cnt_reg1_rx_mac_partial2_invert_crc_cnt {
      type oc-yang:counter64;
      description
        "Counts the number of received packets with partial CRC type 2.";
    }
    leaf counter_slice10_ifg_mac_pool86_rx_mac_partial2_invert_crc_cnt_reg2_rx_mac_partial2_invert_crc_cnt {
      type oc-yang:counter64;
      description
        "Counts the number of received packets with partial CRC type 2.";
    }
    leaf counter_slice10_ifg_mac_pool86_rx_mac_partial2_invert_crc_cnt_reg3_rx_mac_partial2_invert_crc_cnt {
      type oc-yang:counter64;
      description
        "Counts the number of received packets with partial CRC type 2.";
    }
    leaf counter_slice10_ifg_mac_pool86_rx_mac_partial2_invert_crc_cnt_reg4_rx_mac_partial2_invert_crc_cnt {
      type oc-yang:counter64;
      description
        "Counts the number of received packets with partial CRC type 2.";
    }
    leaf counter_slice10_ifg_mac_pool86_rx_mac_partial2_invert_crc_cnt_reg5_rx_mac_partial2_invert_crc_cnt {
      type oc-yang:counter64;
      description
        "Counts the number of received packets with partial CRC type 2.";
    }
    leaf counter_slice10_ifg_mac_pool86_rx_mac_partial2_invert_crc_cnt_reg6_rx_mac_partial2_invert_crc_cnt {
      type oc-yang:counter64;
      description
        "Counts the number of received packets with partial CRC type 2.";
    }
    leaf counter_slice10_ifg_mac_pool86_rx_mac_partial2_invert_crc_cnt_reg7_rx_mac_partial2_invert_crc_cnt {
      type oc-yang:counter64;
      description
        "Counts the number of received packets with partial CRC type 2.";
    }
    leaf counter_slice10_ifg_mac_pool87_rx_mac_partial2_invert_crc_cnt_reg0_rx_mac_partial2_invert_crc_cnt {
      type oc-yang:counter64;
      description
        "Counts the number of received packets with partial CRC type 2.";
    }
    leaf counter_slice10_ifg_mac_pool87_rx_mac_partial2_invert_crc_cnt_reg1_rx_mac_partial2_invert_crc_cnt {
      type oc-yang:counter64;
      description
        "Counts the number of received packets with partial CRC type 2.";
    }
    leaf counter_slice10_ifg_mac_pool87_rx_mac_partial2_invert_crc_cnt_reg2_rx_mac_partial2_invert_crc_cnt {
      type oc-yang:counter64;
      description
        "Counts the number of received packets with partial CRC type 2.";
    }
    leaf counter_slice10_ifg_mac_pool87_rx_mac_partial2_invert_crc_cnt_reg3_rx_mac_partial2_invert_crc_cnt {
      type oc-yang:counter64;
      description
        "Counts the number of received packets with partial CRC type 2.";
    }
    leaf counter_slice10_ifg_mac_pool87_rx_mac_partial2_invert_crc_cnt_reg4_rx_mac_partial2_invert_crc_cnt {
      type oc-yang:counter64;
      description
        "Counts the number of received packets with partial CRC type 2.";
    }
    leaf counter_slice10_ifg_mac_pool87_rx_mac_partial2_invert_crc_cnt_reg5_rx_mac_partial2_invert_crc_cnt {
      type oc-yang:counter64;
      description
        "Counts the number of received packets with partial CRC type 2.";
    }
    leaf counter_slice10_ifg_mac_pool87_rx_mac_partial2_invert_crc_cnt_reg6_rx_mac_partial2_invert_crc_cnt {
      type oc-yang:counter64;
      description
        "Counts the number of received packets with partial CRC type 2.";
    }
    leaf counter_slice10_ifg_mac_pool87_rx_mac_partial2_invert_crc_cnt_reg7_rx_mac_partial2_invert_crc_cnt {
      type oc-yang:counter64;
      description
        "Counts the number of received packets with partial CRC type 2.";
    }
    leaf counter_slice11_ifg_mac_pool80_rx_mac_partial2_invert_crc_cnt_reg0_rx_mac_partial2_invert_crc_cnt {
      type oc-yang:counter64;
      description
        "Counts the number of received packets with partial CRC type 2.";
    }
    leaf counter_slice11_ifg_mac_pool80_rx_mac_partial2_invert_crc_cnt_reg1_rx_mac_partial2_invert_crc_cnt {
      type oc-yang:counter64;
      description
        "Counts the number of received packets with partial CRC type 2.";
    }
    leaf counter_slice11_ifg_mac_pool80_rx_mac_partial2_invert_crc_cnt_reg2_rx_mac_partial2_invert_crc_cnt {
      type oc-yang:counter64;
      description
        "Counts the number of received packets with partial CRC type 2.";
    }
    leaf counter_slice11_ifg_mac_pool80_rx_mac_partial2_invert_crc_cnt_reg3_rx_mac_partial2_invert_crc_cnt {
      type oc-yang:counter64;
      description
        "Counts the number of received packets with partial CRC type 2.";
    }
    leaf counter_slice11_ifg_mac_pool80_rx_mac_partial2_invert_crc_cnt_reg4_rx_mac_partial2_invert_crc_cnt {
      type oc-yang:counter64;
      description
        "Counts the number of received packets with partial CRC type 2.";
    }
    leaf counter_slice11_ifg_mac_pool80_rx_mac_partial2_invert_crc_cnt_reg5_rx_mac_partial2_invert_crc_cnt {
      type oc-yang:counter64;
      description
        "Counts the number of received packets with partial CRC type 2.";
    }
    leaf counter_slice11_ifg_mac_pool80_rx_mac_partial2_invert_crc_cnt_reg6_rx_mac_partial2_invert_crc_cnt {
      type oc-yang:counter64;
      description
        "Counts the number of received packets with partial CRC type 2.";
    }
    leaf counter_slice11_ifg_mac_pool80_rx_mac_partial2_invert_crc_cnt_reg7_rx_mac_partial2_invert_crc_cnt {
      type oc-yang:counter64;
      description
        "Counts the number of received packets with partial CRC type 2.";
    }
    leaf counter_slice11_ifg_mac_pool81_rx_mac_partial2_invert_crc_cnt_reg0_rx_mac_partial2_invert_crc_cnt {
      type oc-yang:counter64;
      description
        "Counts the number of received packets with partial CRC type 2.";
    }
    leaf counter_slice11_ifg_mac_pool81_rx_mac_partial2_invert_crc_cnt_reg1_rx_mac_partial2_invert_crc_cnt {
      type oc-yang:counter64;
      description
        "Counts the number of received packets with partial CRC type 2.";
    }
    leaf counter_slice11_ifg_mac_pool81_rx_mac_partial2_invert_crc_cnt_reg2_rx_mac_partial2_invert_crc_cnt {
      type oc-yang:counter64;
      description
        "Counts the number of received packets with partial CRC type 2.";
    }
    leaf counter_slice11_ifg_mac_pool81_rx_mac_partial2_invert_crc_cnt_reg3_rx_mac_partial2_invert_crc_cnt {
      type oc-yang:counter64;
      description
        "Counts the number of received packets with partial CRC type 2.";
    }
    leaf counter_slice11_ifg_mac_pool81_rx_mac_partial2_invert_crc_cnt_reg4_rx_mac_partial2_invert_crc_cnt {
      type oc-yang:counter64;
      description
        "Counts the number of received packets with partial CRC type 2.";
    }
    leaf counter_slice11_ifg_mac_pool81_rx_mac_partial2_invert_crc_cnt_reg5_rx_mac_partial2_invert_crc_cnt {
      type oc-yang:counter64;
      description
        "Counts the number of received packets with partial CRC type 2.";
    }
    leaf counter_slice11_ifg_mac_pool81_rx_mac_partial2_invert_crc_cnt_reg6_rx_mac_partial2_invert_crc_cnt {
      type oc-yang:counter64;
      description
        "Counts the number of received packets with partial CRC type 2.";
    }
    leaf counter_slice11_ifg_mac_pool81_rx_mac_partial2_invert_crc_cnt_reg7_rx_mac_partial2_invert_crc_cnt {
      type oc-yang:counter64;
      description
        "Counts the number of received packets with partial CRC type 2.";
    }
    leaf counter_slice11_ifg_mac_pool82_rx_mac_partial2_invert_crc_cnt_reg0_rx_mac_partial2_invert_crc_cnt {
      type oc-yang:counter64;
      description
        "Counts the number of received packets with partial CRC type 2.";
    }
    leaf counter_slice11_ifg_mac_pool82_rx_mac_partial2_invert_crc_cnt_reg1_rx_mac_partial2_invert_crc_cnt {
      type oc-yang:counter64;
      description
        "Counts the number of received packets with partial CRC type 2.";
    }
    leaf counter_slice11_ifg_mac_pool82_rx_mac_partial2_invert_crc_cnt_reg2_rx_mac_partial2_invert_crc_cnt {
      type oc-yang:counter64;
      description
        "Counts the number of received packets with partial CRC type 2.";
    }
    leaf counter_slice11_ifg_mac_pool82_rx_mac_partial2_invert_crc_cnt_reg3_rx_mac_partial2_invert_crc_cnt {
      type oc-yang:counter64;
      description
        "Counts the number of received packets with partial CRC type 2.";
    }
    leaf counter_slice11_ifg_mac_pool82_rx_mac_partial2_invert_crc_cnt_reg4_rx_mac_partial2_invert_crc_cnt {
      type oc-yang:counter64;
      description
        "Counts the number of received packets with partial CRC type 2.";
    }
    leaf counter_slice11_ifg_mac_pool82_rx_mac_partial2_invert_crc_cnt_reg5_rx_mac_partial2_invert_crc_cnt {
      type oc-yang:counter64;
      description
        "Counts the number of received packets with partial CRC type 2.";
    }
    leaf counter_slice11_ifg_mac_pool82_rx_mac_partial2_invert_crc_cnt_reg6_rx_mac_partial2_invert_crc_cnt {
      type oc-yang:counter64;
      description
        "Counts the number of received packets with partial CRC type 2.";
    }
    leaf counter_slice11_ifg_mac_pool82_rx_mac_partial2_invert_crc_cnt_reg7_rx_mac_partial2_invert_crc_cnt {
      type oc-yang:counter64;
      description
        "Counts the number of received packets with partial CRC type 2.";
    }
    leaf counter_slice11_ifg_mac_pool83_rx_mac_partial2_invert_crc_cnt_reg0_rx_mac_partial2_invert_crc_cnt {
      type oc-yang:counter64;
      description
        "Counts the number of received packets with partial CRC type 2.";
    }
    leaf counter_slice11_ifg_mac_pool83_rx_mac_partial2_invert_crc_cnt_reg1_rx_mac_partial2_invert_crc_cnt {
      type oc-yang:counter64;
      description
        "Counts the number of received packets with partial CRC type 2.";
    }
    leaf counter_slice11_ifg_mac_pool83_rx_mac_partial2_invert_crc_cnt_reg2_rx_mac_partial2_invert_crc_cnt {
      type oc-yang:counter64;
      description
        "Counts the number of received packets with partial CRC type 2.";
    }
    leaf counter_slice11_ifg_mac_pool83_rx_mac_partial2_invert_crc_cnt_reg3_rx_mac_partial2_invert_crc_cnt {
      type oc-yang:counter64;
      description
        "Counts the number of received packets with partial CRC type 2.";
    }
    leaf counter_slice11_ifg_mac_pool83_rx_mac_partial2_invert_crc_cnt_reg4_rx_mac_partial2_invert_crc_cnt {
      type oc-yang:counter64;
      description
        "Counts the number of received packets with partial CRC type 2.";
    }
    leaf counter_slice11_ifg_mac_pool83_rx_mac_partial2_invert_crc_cnt_reg5_rx_mac_partial2_invert_crc_cnt {
      type oc-yang:counter64;
      description
        "Counts the number of received packets with partial CRC type 2.";
    }
    leaf counter_slice11_ifg_mac_pool83_rx_mac_partial2_invert_crc_cnt_reg6_rx_mac_partial2_invert_crc_cnt {
      type oc-yang:counter64;
      description
        "Counts the number of received packets with partial CRC type 2.";
    }
    leaf counter_slice11_ifg_mac_pool83_rx_mac_partial2_invert_crc_cnt_reg7_rx_mac_partial2_invert_crc_cnt {
      type oc-yang:counter64;
      description
        "Counts the number of received packets with partial CRC type 2.";
    }
    leaf counter_slice11_ifg_mac_pool84_rx_mac_partial2_invert_crc_cnt_reg0_rx_mac_partial2_invert_crc_cnt {
      type oc-yang:counter64;
      description
        "Counts the number of received packets with partial CRC type 2.";
    }
    leaf counter_slice11_ifg_mac_pool84_rx_mac_partial2_invert_crc_cnt_reg1_rx_mac_partial2_invert_crc_cnt {
      type oc-yang:counter64;
      description
        "Counts the number of received packets with partial CRC type 2.";
    }
    leaf counter_slice11_ifg_mac_pool84_rx_mac_partial2_invert_crc_cnt_reg2_rx_mac_partial2_invert_crc_cnt {
      type oc-yang:counter64;
      description
        "Counts the number of received packets with partial CRC type 2.";
    }
    leaf counter_slice11_ifg_mac_pool84_rx_mac_partial2_invert_crc_cnt_reg3_rx_mac_partial2_invert_crc_cnt {
      type oc-yang:counter64;
      description
        "Counts the number of received packets with partial CRC type 2.";
    }
    leaf counter_slice11_ifg_mac_pool84_rx_mac_partial2_invert_crc_cnt_reg4_rx_mac_partial2_invert_crc_cnt {
      type oc-yang:counter64;
      description
        "Counts the number of received packets with partial CRC type 2.";
    }
    leaf counter_slice11_ifg_mac_pool84_rx_mac_partial2_invert_crc_cnt_reg5_rx_mac_partial2_invert_crc_cnt {
      type oc-yang:counter64;
      description
        "Counts the number of received packets with partial CRC type 2.";
    }
    leaf counter_slice11_ifg_mac_pool84_rx_mac_partial2_invert_crc_cnt_reg6_rx_mac_partial2_invert_crc_cnt {
      type oc-yang:counter64;
      description
        "Counts the number of received packets with partial CRC type 2.";
    }
    leaf counter_slice11_ifg_mac_pool84_rx_mac_partial2_invert_crc_cnt_reg7_rx_mac_partial2_invert_crc_cnt {
      type oc-yang:counter64;
      description
        "Counts the number of received packets with partial CRC type 2.";
    }
    leaf counter_slice11_ifg_mac_pool85_rx_mac_partial2_invert_crc_cnt_reg0_rx_mac_partial2_invert_crc_cnt {
      type oc-yang:counter64;
      description
        "Counts the number of received packets with partial CRC type 2.";
    }
    leaf counter_slice11_ifg_mac_pool85_rx_mac_partial2_invert_crc_cnt_reg1_rx_mac_partial2_invert_crc_cnt {
      type oc-yang:counter64;
      description
        "Counts the number of received packets with partial CRC type 2.";
    }
    leaf counter_slice11_ifg_mac_pool85_rx_mac_partial2_invert_crc_cnt_reg2_rx_mac_partial2_invert_crc_cnt {
      type oc-yang:counter64;
      description
        "Counts the number of received packets with partial CRC type 2.";
    }
    leaf counter_slice11_ifg_mac_pool85_rx_mac_partial2_invert_crc_cnt_reg3_rx_mac_partial2_invert_crc_cnt {
      type oc-yang:counter64;
      description
        "Counts the number of received packets with partial CRC type 2.";
    }
    leaf counter_slice11_ifg_mac_pool85_rx_mac_partial2_invert_crc_cnt_reg4_rx_mac_partial2_invert_crc_cnt {
      type oc-yang:counter64;
      description
        "Counts the number of received packets with partial CRC type 2.";
    }
    leaf counter_slice11_ifg_mac_pool85_rx_mac_partial2_invert_crc_cnt_reg5_rx_mac_partial2_invert_crc_cnt {
      type oc-yang:counter64;
      description
        "Counts the number of received packets with partial CRC type 2.";
    }
    leaf counter_slice11_ifg_mac_pool85_rx_mac_partial2_invert_crc_cnt_reg6_rx_mac_partial2_invert_crc_cnt {
      type oc-yang:counter64;
      description
        "Counts the number of received packets with partial CRC type 2.";
    }
    leaf counter_slice11_ifg_mac_pool85_rx_mac_partial2_invert_crc_cnt_reg7_rx_mac_partial2_invert_crc_cnt {
      type oc-yang:counter64;
      description
        "Counts the number of received packets with partial CRC type 2.";
    }
    leaf counter_slice11_ifg_mac_pool86_rx_mac_partial2_invert_crc_cnt_reg0_rx_mac_partial2_invert_crc_cnt {
      type oc-yang:counter64;
      description
        "Counts the number of received packets with partial CRC type 2.";
    }
    leaf counter_slice11_ifg_mac_pool86_rx_mac_partial2_invert_crc_cnt_reg1_rx_mac_partial2_invert_crc_cnt {
      type oc-yang:counter64;
      description
        "Counts the number of received packets with partial CRC type 2.";
    }
    leaf counter_slice11_ifg_mac_pool86_rx_mac_partial2_invert_crc_cnt_reg2_rx_mac_partial2_invert_crc_cnt {
      type oc-yang:counter64;
      description
        "Counts the number of received packets with partial CRC type 2.";
    }
    leaf counter_slice11_ifg_mac_pool86_rx_mac_partial2_invert_crc_cnt_reg3_rx_mac_partial2_invert_crc_cnt {
      type oc-yang:counter64;
      description
        "Counts the number of received packets with partial CRC type 2.";
    }
    leaf counter_slice11_ifg_mac_pool86_rx_mac_partial2_invert_crc_cnt_reg4_rx_mac_partial2_invert_crc_cnt {
      type oc-yang:counter64;
      description
        "Counts the number of received packets with partial CRC type 2.";
    }
    leaf counter_slice11_ifg_mac_pool86_rx_mac_partial2_invert_crc_cnt_reg5_rx_mac_partial2_invert_crc_cnt {
      type oc-yang:counter64;
      description
        "Counts the number of received packets with partial CRC type 2.";
    }
    leaf counter_slice11_ifg_mac_pool86_rx_mac_partial2_invert_crc_cnt_reg6_rx_mac_partial2_invert_crc_cnt {
      type oc-yang:counter64;
      description
        "Counts the number of received packets with partial CRC type 2.";
    }
    leaf counter_slice11_ifg_mac_pool86_rx_mac_partial2_invert_crc_cnt_reg7_rx_mac_partial2_invert_crc_cnt {
      type oc-yang:counter64;
      description
        "Counts the number of received packets with partial CRC type 2.";
    }
    leaf counter_slice11_ifg_mac_pool87_rx_mac_partial2_invert_crc_cnt_reg0_rx_mac_partial2_invert_crc_cnt {
      type oc-yang:counter64;
      description
        "Counts the number of received packets with partial CRC type 2.";
    }
    leaf counter_slice11_ifg_mac_pool87_rx_mac_partial2_invert_crc_cnt_reg1_rx_mac_partial2_invert_crc_cnt {
      type oc-yang:counter64;
      description
        "Counts the number of received packets with partial CRC type 2.";
    }
    leaf counter_slice11_ifg_mac_pool87_rx_mac_partial2_invert_crc_cnt_reg2_rx_mac_partial2_invert_crc_cnt {
      type oc-yang:counter64;
      description
        "Counts the number of received packets with partial CRC type 2.";
    }
    leaf counter_slice11_ifg_mac_pool87_rx_mac_partial2_invert_crc_cnt_reg3_rx_mac_partial2_invert_crc_cnt {
      type oc-yang:counter64;
      description
        "Counts the number of received packets with partial CRC type 2.";
    }
    leaf counter_slice11_ifg_mac_pool87_rx_mac_partial2_invert_crc_cnt_reg4_rx_mac_partial2_invert_crc_cnt {
      type oc-yang:counter64;
      description
        "Counts the number of received packets with partial CRC type 2.";
    }
    leaf counter_slice11_ifg_mac_pool87_rx_mac_partial2_invert_crc_cnt_reg5_rx_mac_partial2_invert_crc_cnt {
      type oc-yang:counter64;
      description
        "Counts the number of received packets with partial CRC type 2.";
    }
    leaf counter_slice11_ifg_mac_pool87_rx_mac_partial2_invert_crc_cnt_reg6_rx_mac_partial2_invert_crc_cnt {
      type oc-yang:counter64;
      description
        "Counts the number of received packets with partial CRC type 2.";
    }
    leaf counter_slice11_ifg_mac_pool87_rx_mac_partial2_invert_crc_cnt_reg7_rx_mac_partial2_invert_crc_cnt {
      type oc-yang:counter64;
      description
        "Counts the number of received packets with partial CRC type 2.";
    }
    leaf counter_slice12_ifg_mac_pool80_rx_mac_partial2_invert_crc_cnt_reg0_rx_mac_partial2_invert_crc_cnt {
      type oc-yang:counter64;
      description
        "Counts the number of received packets with partial CRC type 2.";
    }
    leaf counter_slice12_ifg_mac_pool80_rx_mac_partial2_invert_crc_cnt_reg1_rx_mac_partial2_invert_crc_cnt {
      type oc-yang:counter64;
      description
        "Counts the number of received packets with partial CRC type 2.";
    }
    leaf counter_slice12_ifg_mac_pool80_rx_mac_partial2_invert_crc_cnt_reg2_rx_mac_partial2_invert_crc_cnt {
      type oc-yang:counter64;
      description
        "Counts the number of received packets with partial CRC type 2.";
    }
    leaf counter_slice12_ifg_mac_pool80_rx_mac_partial2_invert_crc_cnt_reg3_rx_mac_partial2_invert_crc_cnt {
      type oc-yang:counter64;
      description
        "Counts the number of received packets with partial CRC type 2.";
    }
    leaf counter_slice12_ifg_mac_pool80_rx_mac_partial2_invert_crc_cnt_reg4_rx_mac_partial2_invert_crc_cnt {
      type oc-yang:counter64;
      description
        "Counts the number of received packets with partial CRC type 2.";
    }
    leaf counter_slice12_ifg_mac_pool80_rx_mac_partial2_invert_crc_cnt_reg5_rx_mac_partial2_invert_crc_cnt {
      type oc-yang:counter64;
      description
        "Counts the number of received packets with partial CRC type 2.";
    }
    leaf counter_slice12_ifg_mac_pool80_rx_mac_partial2_invert_crc_cnt_reg6_rx_mac_partial2_invert_crc_cnt {
      type oc-yang:counter64;
      description
        "Counts the number of received packets with partial CRC type 2.";
    }
    leaf counter_slice12_ifg_mac_pool80_rx_mac_partial2_invert_crc_cnt_reg7_rx_mac_partial2_invert_crc_cnt {
      type oc-yang:counter64;
      description
        "Counts the number of received packets with partial CRC type 2.";
    }
    leaf counter_slice12_ifg_mac_pool81_rx_mac_partial2_invert_crc_cnt_reg0_rx_mac_partial2_invert_crc_cnt {
      type oc-yang:counter64;
      description
        "Counts the number of received packets with partial CRC type 2.";
    }
    leaf counter_slice12_ifg_mac_pool81_rx_mac_partial2_invert_crc_cnt_reg1_rx_mac_partial2_invert_crc_cnt {
      type oc-yang:counter64;
      description
        "Counts the number of received packets with partial CRC type 2.";
    }
    leaf counter_slice12_ifg_mac_pool81_rx_mac_partial2_invert_crc_cnt_reg2_rx_mac_partial2_invert_crc_cnt {
      type oc-yang:counter64;
      description
        "Counts the number of received packets with partial CRC type 2.";
    }
    leaf counter_slice12_ifg_mac_pool81_rx_mac_partial2_invert_crc_cnt_reg3_rx_mac_partial2_invert_crc_cnt {
      type oc-yang:counter64;
      description
        "Counts the number of received packets with partial CRC type 2.";
    }
    leaf counter_slice12_ifg_mac_pool81_rx_mac_partial2_invert_crc_cnt_reg4_rx_mac_partial2_invert_crc_cnt {
      type oc-yang:counter64;
      description
        "Counts the number of received packets with partial CRC type 2.";
    }
    leaf counter_slice12_ifg_mac_pool81_rx_mac_partial2_invert_crc_cnt_reg5_rx_mac_partial2_invert_crc_cnt {
      type oc-yang:counter64;
      description
        "Counts the number of received packets with partial CRC type 2.";
    }
    leaf counter_slice12_ifg_mac_pool81_rx_mac_partial2_invert_crc_cnt_reg6_rx_mac_partial2_invert_crc_cnt {
      type oc-yang:counter64;
      description
        "Counts the number of received packets with partial CRC type 2.";
    }
    leaf counter_slice12_ifg_mac_pool81_rx_mac_partial2_invert_crc_cnt_reg7_rx_mac_partial2_invert_crc_cnt {
      type oc-yang:counter64;
      description
        "Counts the number of received packets with partial CRC type 2.";
    }
    leaf counter_slice12_ifg_mac_pool82_rx_mac_partial2_invert_crc_cnt_reg0_rx_mac_partial2_invert_crc_cnt {
      type oc-yang:counter64;
      description
        "Counts the number of received packets with partial CRC type 2.";
    }
    leaf counter_slice12_ifg_mac_pool82_rx_mac_partial2_invert_crc_cnt_reg1_rx_mac_partial2_invert_crc_cnt {
      type oc-yang:counter64;
      description
        "Counts the number of received packets with partial CRC type 2.";
    }
    leaf counter_slice12_ifg_mac_pool82_rx_mac_partial2_invert_crc_cnt_reg2_rx_mac_partial2_invert_crc_cnt {
      type oc-yang:counter64;
      description
        "Counts the number of received packets with partial CRC type 2.";
    }
    leaf counter_slice12_ifg_mac_pool82_rx_mac_partial2_invert_crc_cnt_reg3_rx_mac_partial2_invert_crc_cnt {
      type oc-yang:counter64;
      description
        "Counts the number of received packets with partial CRC type 2.";
    }
    leaf counter_slice12_ifg_mac_pool82_rx_mac_partial2_invert_crc_cnt_reg4_rx_mac_partial2_invert_crc_cnt {
      type oc-yang:counter64;
      description
        "Counts the number of received packets with partial CRC type 2.";
    }
    leaf counter_slice12_ifg_mac_pool82_rx_mac_partial2_invert_crc_cnt_reg5_rx_mac_partial2_invert_crc_cnt {
      type oc-yang:counter64;
      description
        "Counts the number of received packets with partial CRC type 2.";
    }
    leaf counter_slice12_ifg_mac_pool82_rx_mac_partial2_invert_crc_cnt_reg6_rx_mac_partial2_invert_crc_cnt {
      type oc-yang:counter64;
      description
        "Counts the number of received packets with partial CRC type 2.";
    }
    leaf counter_slice12_ifg_mac_pool82_rx_mac_partial2_invert_crc_cnt_reg7_rx_mac_partial2_invert_crc_cnt {
      type oc-yang:counter64;
      description
        "Counts the number of received packets with partial CRC type 2.";
    }
    leaf counter_slice12_ifg_mac_pool83_rx_mac_partial2_invert_crc_cnt_reg0_rx_mac_partial2_invert_crc_cnt {
      type oc-yang:counter64;
      description
        "Counts the number of received packets with partial CRC type 2.";
    }
    leaf counter_slice12_ifg_mac_pool83_rx_mac_partial2_invert_crc_cnt_reg1_rx_mac_partial2_invert_crc_cnt {
      type oc-yang:counter64;
      description
        "Counts the number of received packets with partial CRC type 2.";
    }
    leaf counter_slice12_ifg_mac_pool83_rx_mac_partial2_invert_crc_cnt_reg2_rx_mac_partial2_invert_crc_cnt {
      type oc-yang:counter64;
      description
        "Counts the number of received packets with partial CRC type 2.";
    }
    leaf counter_slice12_ifg_mac_pool83_rx_mac_partial2_invert_crc_cnt_reg3_rx_mac_partial2_invert_crc_cnt {
      type oc-yang:counter64;
      description
        "Counts the number of received packets with partial CRC type 2.";
    }
    leaf counter_slice12_ifg_mac_pool83_rx_mac_partial2_invert_crc_cnt_reg4_rx_mac_partial2_invert_crc_cnt {
      type oc-yang:counter64;
      description
        "Counts the number of received packets with partial CRC type 2.";
    }
    leaf counter_slice12_ifg_mac_pool83_rx_mac_partial2_invert_crc_cnt_reg5_rx_mac_partial2_invert_crc_cnt {
      type oc-yang:counter64;
      description
        "Counts the number of received packets with partial CRC type 2.";
    }
    leaf counter_slice12_ifg_mac_pool83_rx_mac_partial2_invert_crc_cnt_reg6_rx_mac_partial2_invert_crc_cnt {
      type oc-yang:counter64;
      description
        "Counts the number of received packets with partial CRC type 2.";
    }
    leaf counter_slice12_ifg_mac_pool83_rx_mac_partial2_invert_crc_cnt_reg7_rx_mac_partial2_invert_crc_cnt {
      type oc-yang:counter64;
      description
        "Counts the number of received packets with partial CRC type 2.";
    }
    leaf counter_slice12_ifg_mac_pool84_rx_mac_partial2_invert_crc_cnt_reg0_rx_mac_partial2_invert_crc_cnt {
      type oc-yang:counter64;
      description
        "Counts the number of received packets with partial CRC type 2.";
    }
    leaf counter_slice12_ifg_mac_pool84_rx_mac_partial2_invert_crc_cnt_reg1_rx_mac_partial2_invert_crc_cnt {
      type oc-yang:counter64;
      description
        "Counts the number of received packets with partial CRC type 2.";
    }
    leaf counter_slice12_ifg_mac_pool84_rx_mac_partial2_invert_crc_cnt_reg2_rx_mac_partial2_invert_crc_cnt {
      type oc-yang:counter64;
      description
        "Counts the number of received packets with partial CRC type 2.";
    }
    leaf counter_slice12_ifg_mac_pool84_rx_mac_partial2_invert_crc_cnt_reg3_rx_mac_partial2_invert_crc_cnt {
      type oc-yang:counter64;
      description
        "Counts the number of received packets with partial CRC type 2.";
    }
    leaf counter_slice12_ifg_mac_pool84_rx_mac_partial2_invert_crc_cnt_reg4_rx_mac_partial2_invert_crc_cnt {
      type oc-yang:counter64;
      description
        "Counts the number of received packets with partial CRC type 2.";
    }
    leaf counter_slice12_ifg_mac_pool84_rx_mac_partial2_invert_crc_cnt_reg5_rx_mac_partial2_invert_crc_cnt {
      type oc-yang:counter64;
      description
        "Counts the number of received packets with partial CRC type 2.";
    }
    leaf counter_slice12_ifg_mac_pool84_rx_mac_partial2_invert_crc_cnt_reg6_rx_mac_partial2_invert_crc_cnt {
      type oc-yang:counter64;
      description
        "Counts the number of received packets with partial CRC type 2.";
    }
    leaf counter_slice12_ifg_mac_pool84_rx_mac_partial2_invert_crc_cnt_reg7_rx_mac_partial2_invert_crc_cnt {
      type oc-yang:counter64;
      description
        "Counts the number of received packets with partial CRC type 2.";
    }
    leaf counter_slice12_ifg_mac_pool85_rx_mac_partial2_invert_crc_cnt_reg0_rx_mac_partial2_invert_crc_cnt {
      type oc-yang:counter64;
      description
        "Counts the number of received packets with partial CRC type 2.";
    }
    leaf counter_slice12_ifg_mac_pool85_rx_mac_partial2_invert_crc_cnt_reg1_rx_mac_partial2_invert_crc_cnt {
      type oc-yang:counter64;
      description
        "Counts the number of received packets with partial CRC type 2.";
    }
    leaf counter_slice12_ifg_mac_pool85_rx_mac_partial2_invert_crc_cnt_reg2_rx_mac_partial2_invert_crc_cnt {
      type oc-yang:counter64;
      description
        "Counts the number of received packets with partial CRC type 2.";
    }
    leaf counter_slice12_ifg_mac_pool85_rx_mac_partial2_invert_crc_cnt_reg3_rx_mac_partial2_invert_crc_cnt {
      type oc-yang:counter64;
      description
        "Counts the number of received packets with partial CRC type 2.";
    }
    leaf counter_slice12_ifg_mac_pool85_rx_mac_partial2_invert_crc_cnt_reg4_rx_mac_partial2_invert_crc_cnt {
      type oc-yang:counter64;
      description
        "Counts the number of received packets with partial CRC type 2.";
    }
    leaf counter_slice12_ifg_mac_pool85_rx_mac_partial2_invert_crc_cnt_reg5_rx_mac_partial2_invert_crc_cnt {
      type oc-yang:counter64;
      description
        "Counts the number of received packets with partial CRC type 2.";
    }
    leaf counter_slice12_ifg_mac_pool85_rx_mac_partial2_invert_crc_cnt_reg6_rx_mac_partial2_invert_crc_cnt {
      type oc-yang:counter64;
      description
        "Counts the number of received packets with partial CRC type 2.";
    }
    leaf counter_slice12_ifg_mac_pool85_rx_mac_partial2_invert_crc_cnt_reg7_rx_mac_partial2_invert_crc_cnt {
      type oc-yang:counter64;
      description
        "Counts the number of received packets with partial CRC type 2.";
    }
    leaf counter_slice12_ifg_mac_pool86_rx_mac_partial2_invert_crc_cnt_reg0_rx_mac_partial2_invert_crc_cnt {
      type oc-yang:counter64;
      description
        "Counts the number of received packets with partial CRC type 2.";
    }
    leaf counter_slice12_ifg_mac_pool86_rx_mac_partial2_invert_crc_cnt_reg1_rx_mac_partial2_invert_crc_cnt {
      type oc-yang:counter64;
      description
        "Counts the number of received packets with partial CRC type 2.";
    }
    leaf counter_slice12_ifg_mac_pool86_rx_mac_partial2_invert_crc_cnt_reg2_rx_mac_partial2_invert_crc_cnt {
      type oc-yang:counter64;
      description
        "Counts the number of received packets with partial CRC type 2.";
    }
    leaf counter_slice12_ifg_mac_pool86_rx_mac_partial2_invert_crc_cnt_reg3_rx_mac_partial2_invert_crc_cnt {
      type oc-yang:counter64;
      description
        "Counts the number of received packets with partial CRC type 2.";
    }
    leaf counter_slice12_ifg_mac_pool86_rx_mac_partial2_invert_crc_cnt_reg4_rx_mac_partial2_invert_crc_cnt {
      type oc-yang:counter64;
      description
        "Counts the number of received packets with partial CRC type 2.";
    }
    leaf counter_slice12_ifg_mac_pool86_rx_mac_partial2_invert_crc_cnt_reg5_rx_mac_partial2_invert_crc_cnt {
      type oc-yang:counter64;
      description
        "Counts the number of received packets with partial CRC type 2.";
    }
    leaf counter_slice12_ifg_mac_pool86_rx_mac_partial2_invert_crc_cnt_reg6_rx_mac_partial2_invert_crc_cnt {
      type oc-yang:counter64;
      description
        "Counts the number of received packets with partial CRC type 2.";
    }
    leaf counter_slice12_ifg_mac_pool86_rx_mac_partial2_invert_crc_cnt_reg7_rx_mac_partial2_invert_crc_cnt {
      type oc-yang:counter64;
      description
        "Counts the number of received packets with partial CRC type 2.";
    }
    leaf counter_slice12_ifg_mac_pool87_rx_mac_partial2_invert_crc_cnt_reg0_rx_mac_partial2_invert_crc_cnt {
      type oc-yang:counter64;
      description
        "Counts the number of received packets with partial CRC type 2.";
    }
    leaf counter_slice12_ifg_mac_pool87_rx_mac_partial2_invert_crc_cnt_reg1_rx_mac_partial2_invert_crc_cnt {
      type oc-yang:counter64;
      description
        "Counts the number of received packets with partial CRC type 2.";
    }
    leaf counter_slice12_ifg_mac_pool87_rx_mac_partial2_invert_crc_cnt_reg2_rx_mac_partial2_invert_crc_cnt {
      type oc-yang:counter64;
      description
        "Counts the number of received packets with partial CRC type 2.";
    }
    leaf counter_slice12_ifg_mac_pool87_rx_mac_partial2_invert_crc_cnt_reg3_rx_mac_partial2_invert_crc_cnt {
      type oc-yang:counter64;
      description
        "Counts the number of received packets with partial CRC type 2.";
    }
    leaf counter_slice12_ifg_mac_pool87_rx_mac_partial2_invert_crc_cnt_reg4_rx_mac_partial2_invert_crc_cnt {
      type oc-yang:counter64;
      description
        "Counts the number of received packets with partial CRC type 2.";
    }
    leaf counter_slice12_ifg_mac_pool87_rx_mac_partial2_invert_crc_cnt_reg5_rx_mac_partial2_invert_crc_cnt {
      type oc-yang:counter64;
      description
        "Counts the number of received packets with partial CRC type 2.";
    }
    leaf counter_slice12_ifg_mac_pool87_rx_mac_partial2_invert_crc_cnt_reg6_rx_mac_partial2_invert_crc_cnt {
      type oc-yang:counter64;
      description
        "Counts the number of received packets with partial CRC type 2.";
    }
    leaf counter_slice12_ifg_mac_pool87_rx_mac_partial2_invert_crc_cnt_reg7_rx_mac_partial2_invert_crc_cnt {
      type oc-yang:counter64;
      description
        "Counts the number of received packets with partial CRC type 2.";
    }
    leaf counter_slice13_ifg_mac_pool80_rx_mac_partial2_invert_crc_cnt_reg0_rx_mac_partial2_invert_crc_cnt {
      type oc-yang:counter64;
      description
        "Counts the number of received packets with partial CRC type 2.";
    }
    leaf counter_slice13_ifg_mac_pool80_rx_mac_partial2_invert_crc_cnt_reg1_rx_mac_partial2_invert_crc_cnt {
      type oc-yang:counter64;
      description
        "Counts the number of received packets with partial CRC type 2.";
    }
    leaf counter_slice13_ifg_mac_pool80_rx_mac_partial2_invert_crc_cnt_reg2_rx_mac_partial2_invert_crc_cnt {
      type oc-yang:counter64;
      description
        "Counts the number of received packets with partial CRC type 2.";
    }
    leaf counter_slice13_ifg_mac_pool80_rx_mac_partial2_invert_crc_cnt_reg3_rx_mac_partial2_invert_crc_cnt {
      type oc-yang:counter64;
      description
        "Counts the number of received packets with partial CRC type 2.";
    }
    leaf counter_slice13_ifg_mac_pool80_rx_mac_partial2_invert_crc_cnt_reg4_rx_mac_partial2_invert_crc_cnt {
      type oc-yang:counter64;
      description
        "Counts the number of received packets with partial CRC type 2.";
    }
    leaf counter_slice13_ifg_mac_pool80_rx_mac_partial2_invert_crc_cnt_reg5_rx_mac_partial2_invert_crc_cnt {
      type oc-yang:counter64;
      description
        "Counts the number of received packets with partial CRC type 2.";
    }
    leaf counter_slice13_ifg_mac_pool80_rx_mac_partial2_invert_crc_cnt_reg6_rx_mac_partial2_invert_crc_cnt {
      type oc-yang:counter64;
      description
        "Counts the number of received packets with partial CRC type 2.";
    }
    leaf counter_slice13_ifg_mac_pool80_rx_mac_partial2_invert_crc_cnt_reg7_rx_mac_partial2_invert_crc_cnt {
      type oc-yang:counter64;
      description
        "Counts the number of received packets with partial CRC type 2.";
    }
    leaf counter_slice13_ifg_mac_pool81_rx_mac_partial2_invert_crc_cnt_reg0_rx_mac_partial2_invert_crc_cnt {
      type oc-yang:counter64;
      description
        "Counts the number of received packets with partial CRC type 2.";
    }
    leaf counter_slice13_ifg_mac_pool81_rx_mac_partial2_invert_crc_cnt_reg1_rx_mac_partial2_invert_crc_cnt {
      type oc-yang:counter64;
      description
        "Counts the number of received packets with partial CRC type 2.";
    }
    leaf counter_slice13_ifg_mac_pool81_rx_mac_partial2_invert_crc_cnt_reg2_rx_mac_partial2_invert_crc_cnt {
      type oc-yang:counter64;
      description
        "Counts the number of received packets with partial CRC type 2.";
    }
    leaf counter_slice13_ifg_mac_pool81_rx_mac_partial2_invert_crc_cnt_reg3_rx_mac_partial2_invert_crc_cnt {
      type oc-yang:counter64;
      description
        "Counts the number of received packets with partial CRC type 2.";
    }
    leaf counter_slice13_ifg_mac_pool81_rx_mac_partial2_invert_crc_cnt_reg4_rx_mac_partial2_invert_crc_cnt {
      type oc-yang:counter64;
      description
        "Counts the number of received packets with partial CRC type 2.";
    }
    leaf counter_slice13_ifg_mac_pool81_rx_mac_partial2_invert_crc_cnt_reg5_rx_mac_partial2_invert_crc_cnt {
      type oc-yang:counter64;
      description
        "Counts the number of received packets with partial CRC type 2.";
    }
    leaf counter_slice13_ifg_mac_pool81_rx_mac_partial2_invert_crc_cnt_reg6_rx_mac_partial2_invert_crc_cnt {
      type oc-yang:counter64;
      description
        "Counts the number of received packets with partial CRC type 2.";
    }
    leaf counter_slice13_ifg_mac_pool81_rx_mac_partial2_invert_crc_cnt_reg7_rx_mac_partial2_invert_crc_cnt {
      type oc-yang:counter64;
      description
        "Counts the number of received packets with partial CRC type 2.";
    }
    leaf counter_slice13_ifg_mac_pool82_rx_mac_partial2_invert_crc_cnt_reg0_rx_mac_partial2_invert_crc_cnt {
      type oc-yang:counter64;
      description
        "Counts the number of received packets with partial CRC type 2.";
    }
    leaf counter_slice13_ifg_mac_pool82_rx_mac_partial2_invert_crc_cnt_reg1_rx_mac_partial2_invert_crc_cnt {
      type oc-yang:counter64;
      description
        "Counts the number of received packets with partial CRC type 2.";
    }
    leaf counter_slice13_ifg_mac_pool82_rx_mac_partial2_invert_crc_cnt_reg2_rx_mac_partial2_invert_crc_cnt {
      type oc-yang:counter64;
      description
        "Counts the number of received packets with partial CRC type 2.";
    }
    leaf counter_slice13_ifg_mac_pool82_rx_mac_partial2_invert_crc_cnt_reg3_rx_mac_partial2_invert_crc_cnt {
      type oc-yang:counter64;
      description
        "Counts the number of received packets with partial CRC type 2.";
    }
    leaf counter_slice13_ifg_mac_pool82_rx_mac_partial2_invert_crc_cnt_reg4_rx_mac_partial2_invert_crc_cnt {
      type oc-yang:counter64;
      description
        "Counts the number of received packets with partial CRC type 2.";
    }
    leaf counter_slice13_ifg_mac_pool82_rx_mac_partial2_invert_crc_cnt_reg5_rx_mac_partial2_invert_crc_cnt {
      type oc-yang:counter64;
      description
        "Counts the number of received packets with partial CRC type 2.";
    }
    leaf counter_slice13_ifg_mac_pool82_rx_mac_partial2_invert_crc_cnt_reg6_rx_mac_partial2_invert_crc_cnt {
      type oc-yang:counter64;
      description
        "Counts the number of received packets with partial CRC type 2.";
    }
    leaf counter_slice13_ifg_mac_pool82_rx_mac_partial2_invert_crc_cnt_reg7_rx_mac_partial2_invert_crc_cnt {
      type oc-yang:counter64;
      description
        "Counts the number of received packets with partial CRC type 2.";
    }
    leaf counter_slice13_ifg_mac_pool83_rx_mac_partial2_invert_crc_cnt_reg0_rx_mac_partial2_invert_crc_cnt {
      type oc-yang:counter64;
      description
        "Counts the number of received packets with partial CRC type 2.";
    }
    leaf counter_slice13_ifg_mac_pool83_rx_mac_partial2_invert_crc_cnt_reg1_rx_mac_partial2_invert_crc_cnt {
      type oc-yang:counter64;
      description
        "Counts the number of received packets with partial CRC type 2.";
    }
    leaf counter_slice13_ifg_mac_pool83_rx_mac_partial2_invert_crc_cnt_reg2_rx_mac_partial2_invert_crc_cnt {
      type oc-yang:counter64;
      description
        "Counts the number of received packets with partial CRC type 2.";
    }
    leaf counter_slice13_ifg_mac_pool83_rx_mac_partial2_invert_crc_cnt_reg3_rx_mac_partial2_invert_crc_cnt {
      type oc-yang:counter64;
      description
        "Counts the number of received packets with partial CRC type 2.";
    }
    leaf counter_slice13_ifg_mac_pool83_rx_mac_partial2_invert_crc_cnt_reg4_rx_mac_partial2_invert_crc_cnt {
      type oc-yang:counter64;
      description
        "Counts the number of received packets with partial CRC type 2.";
    }
    leaf counter_slice13_ifg_mac_pool83_rx_mac_partial2_invert_crc_cnt_reg5_rx_mac_partial2_invert_crc_cnt {
      type oc-yang:counter64;
      description
        "Counts the number of received packets with partial CRC type 2.";
    }
    leaf counter_slice13_ifg_mac_pool83_rx_mac_partial2_invert_crc_cnt_reg6_rx_mac_partial2_invert_crc_cnt {
      type oc-yang:counter64;
      description
        "Counts the number of received packets with partial CRC type 2.";
    }
    leaf counter_slice13_ifg_mac_pool83_rx_mac_partial2_invert_crc_cnt_reg7_rx_mac_partial2_invert_crc_cnt {
      type oc-yang:counter64;
      description
        "Counts the number of received packets with partial CRC type 2.";
    }
    leaf counter_slice13_ifg_mac_pool84_rx_mac_partial2_invert_crc_cnt_reg0_rx_mac_partial2_invert_crc_cnt {
      type oc-yang:counter64;
      description
        "Counts the number of received packets with partial CRC type 2.";
    }
    leaf counter_slice13_ifg_mac_pool84_rx_mac_partial2_invert_crc_cnt_reg1_rx_mac_partial2_invert_crc_cnt {
      type oc-yang:counter64;
      description
        "Counts the number of received packets with partial CRC type 2.";
    }
    leaf counter_slice13_ifg_mac_pool84_rx_mac_partial2_invert_crc_cnt_reg2_rx_mac_partial2_invert_crc_cnt {
      type oc-yang:counter64;
      description
        "Counts the number of received packets with partial CRC type 2.";
    }
    leaf counter_slice13_ifg_mac_pool84_rx_mac_partial2_invert_crc_cnt_reg3_rx_mac_partial2_invert_crc_cnt {
      type oc-yang:counter64;
      description
        "Counts the number of received packets with partial CRC type 2.";
    }
    leaf counter_slice13_ifg_mac_pool84_rx_mac_partial2_invert_crc_cnt_reg4_rx_mac_partial2_invert_crc_cnt {
      type oc-yang:counter64;
      description
        "Counts the number of received packets with partial CRC type 2.";
    }
    leaf counter_slice13_ifg_mac_pool84_rx_mac_partial2_invert_crc_cnt_reg5_rx_mac_partial2_invert_crc_cnt {
      type oc-yang:counter64;
      description
        "Counts the number of received packets with partial CRC type 2.";
    }
    leaf counter_slice13_ifg_mac_pool84_rx_mac_partial2_invert_crc_cnt_reg6_rx_mac_partial2_invert_crc_cnt {
      type oc-yang:counter64;
      description
        "Counts the number of received packets with partial CRC type 2.";
    }
    leaf counter_slice13_ifg_mac_pool84_rx_mac_partial2_invert_crc_cnt_reg7_rx_mac_partial2_invert_crc_cnt {
      type oc-yang:counter64;
      description
        "Counts the number of received packets with partial CRC type 2.";
    }
    leaf counter_slice13_ifg_mac_pool85_rx_mac_partial2_invert_crc_cnt_reg0_rx_mac_partial2_invert_crc_cnt {
      type oc-yang:counter64;
      description
        "Counts the number of received packets with partial CRC type 2.";
    }
    leaf counter_slice13_ifg_mac_pool85_rx_mac_partial2_invert_crc_cnt_reg1_rx_mac_partial2_invert_crc_cnt {
      type oc-yang:counter64;
      description
        "Counts the number of received packets with partial CRC type 2.";
    }
    leaf counter_slice13_ifg_mac_pool85_rx_mac_partial2_invert_crc_cnt_reg2_rx_mac_partial2_invert_crc_cnt {
      type oc-yang:counter64;
      description
        "Counts the number of received packets with partial CRC type 2.";
    }
    leaf counter_slice13_ifg_mac_pool85_rx_mac_partial2_invert_crc_cnt_reg3_rx_mac_partial2_invert_crc_cnt {
      type oc-yang:counter64;
      description
        "Counts the number of received packets with partial CRC type 2.";
    }
    leaf counter_slice13_ifg_mac_pool85_rx_mac_partial2_invert_crc_cnt_reg4_rx_mac_partial2_invert_crc_cnt {
      type oc-yang:counter64;
      description
        "Counts the number of received packets with partial CRC type 2.";
    }
    leaf counter_slice13_ifg_mac_pool85_rx_mac_partial2_invert_crc_cnt_reg5_rx_mac_partial2_invert_crc_cnt {
      type oc-yang:counter64;
      description
        "Counts the number of received packets with partial CRC type 2.";
    }
    leaf counter_slice13_ifg_mac_pool85_rx_mac_partial2_invert_crc_cnt_reg6_rx_mac_partial2_invert_crc_cnt {
      type oc-yang:counter64;
      description
        "Counts the number of received packets with partial CRC type 2.";
    }
    leaf counter_slice13_ifg_mac_pool85_rx_mac_partial2_invert_crc_cnt_reg7_rx_mac_partial2_invert_crc_cnt {
      type oc-yang:counter64;
      description
        "Counts the number of received packets with partial CRC type 2.";
    }
    leaf counter_slice13_ifg_mac_pool86_rx_mac_partial2_invert_crc_cnt_reg0_rx_mac_partial2_invert_crc_cnt {
      type oc-yang:counter64;
      description
        "Counts the number of received packets with partial CRC type 2.";
    }
    leaf counter_slice13_ifg_mac_pool86_rx_mac_partial2_invert_crc_cnt_reg1_rx_mac_partial2_invert_crc_cnt {
      type oc-yang:counter64;
      description
        "Counts the number of received packets with partial CRC type 2.";
    }
    leaf counter_slice13_ifg_mac_pool86_rx_mac_partial2_invert_crc_cnt_reg2_rx_mac_partial2_invert_crc_cnt {
      type oc-yang:counter64;
      description
        "Counts the number of received packets with partial CRC type 2.";
    }
    leaf counter_slice13_ifg_mac_pool86_rx_mac_partial2_invert_crc_cnt_reg3_rx_mac_partial2_invert_crc_cnt {
      type oc-yang:counter64;
      description
        "Counts the number of received packets with partial CRC type 2.";
    }
    leaf counter_slice13_ifg_mac_pool86_rx_mac_partial2_invert_crc_cnt_reg4_rx_mac_partial2_invert_crc_cnt {
      type oc-yang:counter64;
      description
        "Counts the number of received packets with partial CRC type 2.";
    }
    leaf counter_slice13_ifg_mac_pool86_rx_mac_partial2_invert_crc_cnt_reg5_rx_mac_partial2_invert_crc_cnt {
      type oc-yang:counter64;
      description
        "Counts the number of received packets with partial CRC type 2.";
    }
    leaf counter_slice13_ifg_mac_pool86_rx_mac_partial2_invert_crc_cnt_reg6_rx_mac_partial2_invert_crc_cnt {
      type oc-yang:counter64;
      description
        "Counts the number of received packets with partial CRC type 2.";
    }
    leaf counter_slice13_ifg_mac_pool86_rx_mac_partial2_invert_crc_cnt_reg7_rx_mac_partial2_invert_crc_cnt {
      type oc-yang:counter64;
      description
        "Counts the number of received packets with partial CRC type 2.";
    }
    leaf counter_slice13_ifg_mac_pool87_rx_mac_partial2_invert_crc_cnt_reg0_rx_mac_partial2_invert_crc_cnt {
      type oc-yang:counter64;
      description
        "Counts the number of received packets with partial CRC type 2.";
    }
    leaf counter_slice13_ifg_mac_pool87_rx_mac_partial2_invert_crc_cnt_reg1_rx_mac_partial2_invert_crc_cnt {
      type oc-yang:counter64;
      description
        "Counts the number of received packets with partial CRC type 2.";
    }
    leaf counter_slice13_ifg_mac_pool87_rx_mac_partial2_invert_crc_cnt_reg2_rx_mac_partial2_invert_crc_cnt {
      type oc-yang:counter64;
      description
        "Counts the number of received packets with partial CRC type 2.";
    }
    leaf counter_slice13_ifg_mac_pool87_rx_mac_partial2_invert_crc_cnt_reg3_rx_mac_partial2_invert_crc_cnt {
      type oc-yang:counter64;
      description
        "Counts the number of received packets with partial CRC type 2.";
    }
    leaf counter_slice13_ifg_mac_pool87_rx_mac_partial2_invert_crc_cnt_reg4_rx_mac_partial2_invert_crc_cnt {
      type oc-yang:counter64;
      description
        "Counts the number of received packets with partial CRC type 2.";
    }
    leaf counter_slice13_ifg_mac_pool87_rx_mac_partial2_invert_crc_cnt_reg5_rx_mac_partial2_invert_crc_cnt {
      type oc-yang:counter64;
      description
        "Counts the number of received packets with partial CRC type 2.";
    }
    leaf counter_slice13_ifg_mac_pool87_rx_mac_partial2_invert_crc_cnt_reg6_rx_mac_partial2_invert_crc_cnt {
      type oc-yang:counter64;
      description
        "Counts the number of received packets with partial CRC type 2.";
    }
    leaf counter_slice13_ifg_mac_pool87_rx_mac_partial2_invert_crc_cnt_reg7_rx_mac_partial2_invert_crc_cnt {
      type oc-yang:counter64;
      description
        "Counts the number of received packets with partial CRC type 2.";
    }
    leaf counter_slice14_ifg_mac_pool80_rx_mac_partial2_invert_crc_cnt_reg0_rx_mac_partial2_invert_crc_cnt {
      type oc-yang:counter64;
      description
        "Counts the number of received packets with partial CRC type 2.";
    }
    leaf counter_slice14_ifg_mac_pool80_rx_mac_partial2_invert_crc_cnt_reg1_rx_mac_partial2_invert_crc_cnt {
      type oc-yang:counter64;
      description
        "Counts the number of received packets with partial CRC type 2.";
    }
    leaf counter_slice14_ifg_mac_pool80_rx_mac_partial2_invert_crc_cnt_reg2_rx_mac_partial2_invert_crc_cnt {
      type oc-yang:counter64;
      description
        "Counts the number of received packets with partial CRC type 2.";
    }
    leaf counter_slice14_ifg_mac_pool80_rx_mac_partial2_invert_crc_cnt_reg3_rx_mac_partial2_invert_crc_cnt {
      type oc-yang:counter64;
      description
        "Counts the number of received packets with partial CRC type 2.";
    }
    leaf counter_slice14_ifg_mac_pool80_rx_mac_partial2_invert_crc_cnt_reg4_rx_mac_partial2_invert_crc_cnt {
      type oc-yang:counter64;
      description
        "Counts the number of received packets with partial CRC type 2.";
    }
    leaf counter_slice14_ifg_mac_pool80_rx_mac_partial2_invert_crc_cnt_reg5_rx_mac_partial2_invert_crc_cnt {
      type oc-yang:counter64;
      description
        "Counts the number of received packets with partial CRC type 2.";
    }
    leaf counter_slice14_ifg_mac_pool80_rx_mac_partial2_invert_crc_cnt_reg6_rx_mac_partial2_invert_crc_cnt {
      type oc-yang:counter64;
      description
        "Counts the number of received packets with partial CRC type 2.";
    }
    leaf counter_slice14_ifg_mac_pool80_rx_mac_partial2_invert_crc_cnt_reg7_rx_mac_partial2_invert_crc_cnt {
      type oc-yang:counter64;
      description
        "Counts the number of received packets with partial CRC type 2.";
    }
    leaf counter_slice14_ifg_mac_pool81_rx_mac_partial2_invert_crc_cnt_reg0_rx_mac_partial2_invert_crc_cnt {
      type oc-yang:counter64;
      description
        "Counts the number of received packets with partial CRC type 2.";
    }
    leaf counter_slice14_ifg_mac_pool81_rx_mac_partial2_invert_crc_cnt_reg1_rx_mac_partial2_invert_crc_cnt {
      type oc-yang:counter64;
      description
        "Counts the number of received packets with partial CRC type 2.";
    }
    leaf counter_slice14_ifg_mac_pool81_rx_mac_partial2_invert_crc_cnt_reg2_rx_mac_partial2_invert_crc_cnt {
      type oc-yang:counter64;
      description
        "Counts the number of received packets with partial CRC type 2.";
    }
    leaf counter_slice14_ifg_mac_pool81_rx_mac_partial2_invert_crc_cnt_reg3_rx_mac_partial2_invert_crc_cnt {
      type oc-yang:counter64;
      description
        "Counts the number of received packets with partial CRC type 2.";
    }
    leaf counter_slice14_ifg_mac_pool81_rx_mac_partial2_invert_crc_cnt_reg4_rx_mac_partial2_invert_crc_cnt {
      type oc-yang:counter64;
      description
        "Counts the number of received packets with partial CRC type 2.";
    }
    leaf counter_slice14_ifg_mac_pool81_rx_mac_partial2_invert_crc_cnt_reg5_rx_mac_partial2_invert_crc_cnt {
      type oc-yang:counter64;
      description
        "Counts the number of received packets with partial CRC type 2.";
    }
    leaf counter_slice14_ifg_mac_pool81_rx_mac_partial2_invert_crc_cnt_reg6_rx_mac_partial2_invert_crc_cnt {
      type oc-yang:counter64;
      description
        "Counts the number of received packets with partial CRC type 2.";
    }
    leaf counter_slice14_ifg_mac_pool81_rx_mac_partial2_invert_crc_cnt_reg7_rx_mac_partial2_invert_crc_cnt {
      type oc-yang:counter64;
      description
        "Counts the number of received packets with partial CRC type 2.";
    }
    leaf counter_slice14_ifg_mac_pool82_rx_mac_partial2_invert_crc_cnt_reg0_rx_mac_partial2_invert_crc_cnt {
      type oc-yang:counter64;
      description
        "Counts the number of received packets with partial CRC type 2.";
    }
    leaf counter_slice14_ifg_mac_pool82_rx_mac_partial2_invert_crc_cnt_reg1_rx_mac_partial2_invert_crc_cnt {
      type oc-yang:counter64;
      description
        "Counts the number of received packets with partial CRC type 2.";
    }
    leaf counter_slice14_ifg_mac_pool82_rx_mac_partial2_invert_crc_cnt_reg2_rx_mac_partial2_invert_crc_cnt {
      type oc-yang:counter64;
      description
        "Counts the number of received packets with partial CRC type 2.";
    }
    leaf counter_slice14_ifg_mac_pool82_rx_mac_partial2_invert_crc_cnt_reg3_rx_mac_partial2_invert_crc_cnt {
      type oc-yang:counter64;
      description
        "Counts the number of received packets with partial CRC type 2.";
    }
    leaf counter_slice14_ifg_mac_pool82_rx_mac_partial2_invert_crc_cnt_reg4_rx_mac_partial2_invert_crc_cnt {
      type oc-yang:counter64;
      description
        "Counts the number of received packets with partial CRC type 2.";
    }
    leaf counter_slice14_ifg_mac_pool82_rx_mac_partial2_invert_crc_cnt_reg5_rx_mac_partial2_invert_crc_cnt {
      type oc-yang:counter64;
      description
        "Counts the number of received packets with partial CRC type 2.";
    }
    leaf counter_slice14_ifg_mac_pool82_rx_mac_partial2_invert_crc_cnt_reg6_rx_mac_partial2_invert_crc_cnt {
      type oc-yang:counter64;
      description
        "Counts the number of received packets with partial CRC type 2.";
    }
    leaf counter_slice14_ifg_mac_pool82_rx_mac_partial2_invert_crc_cnt_reg7_rx_mac_partial2_invert_crc_cnt {
      type oc-yang:counter64;
      description
        "Counts the number of received packets with partial CRC type 2.";
    }
    leaf counter_slice14_ifg_mac_pool83_rx_mac_partial2_invert_crc_cnt_reg0_rx_mac_partial2_invert_crc_cnt {
      type oc-yang:counter64;
      description
        "Counts the number of received packets with partial CRC type 2.";
    }
    leaf counter_slice14_ifg_mac_pool83_rx_mac_partial2_invert_crc_cnt_reg1_rx_mac_partial2_invert_crc_cnt {
      type oc-yang:counter64;
      description
        "Counts the number of received packets with partial CRC type 2.";
    }
    leaf counter_slice14_ifg_mac_pool83_rx_mac_partial2_invert_crc_cnt_reg2_rx_mac_partial2_invert_crc_cnt {
      type oc-yang:counter64;
      description
        "Counts the number of received packets with partial CRC type 2.";
    }
    leaf counter_slice14_ifg_mac_pool83_rx_mac_partial2_invert_crc_cnt_reg3_rx_mac_partial2_invert_crc_cnt {
      type oc-yang:counter64;
      description
        "Counts the number of received packets with partial CRC type 2.";
    }
    leaf counter_slice14_ifg_mac_pool83_rx_mac_partial2_invert_crc_cnt_reg4_rx_mac_partial2_invert_crc_cnt {
      type oc-yang:counter64;
      description
        "Counts the number of received packets with partial CRC type 2.";
    }
    leaf counter_slice14_ifg_mac_pool83_rx_mac_partial2_invert_crc_cnt_reg5_rx_mac_partial2_invert_crc_cnt {
      type oc-yang:counter64;
      description
        "Counts the number of received packets with partial CRC type 2.";
    }
    leaf counter_slice14_ifg_mac_pool83_rx_mac_partial2_invert_crc_cnt_reg6_rx_mac_partial2_invert_crc_cnt {
      type oc-yang:counter64;
      description
        "Counts the number of received packets with partial CRC type 2.";
    }
    leaf counter_slice14_ifg_mac_pool83_rx_mac_partial2_invert_crc_cnt_reg7_rx_mac_partial2_invert_crc_cnt {
      type oc-yang:counter64;
      description
        "Counts the number of received packets with partial CRC type 2.";
    }
    leaf counter_slice14_ifg_mac_pool84_rx_mac_partial2_invert_crc_cnt_reg0_rx_mac_partial2_invert_crc_cnt {
      type oc-yang:counter64;
      description
        "Counts the number of received packets with partial CRC type 2.";
    }
    leaf counter_slice14_ifg_mac_pool84_rx_mac_partial2_invert_crc_cnt_reg1_rx_mac_partial2_invert_crc_cnt {
      type oc-yang:counter64;
      description
        "Counts the number of received packets with partial CRC type 2.";
    }
    leaf counter_slice14_ifg_mac_pool84_rx_mac_partial2_invert_crc_cnt_reg2_rx_mac_partial2_invert_crc_cnt {
      type oc-yang:counter64;
      description
        "Counts the number of received packets with partial CRC type 2.";
    }
    leaf counter_slice14_ifg_mac_pool84_rx_mac_partial2_invert_crc_cnt_reg3_rx_mac_partial2_invert_crc_cnt {
      type oc-yang:counter64;
      description
        "Counts the number of received packets with partial CRC type 2.";
    }
    leaf counter_slice14_ifg_mac_pool84_rx_mac_partial2_invert_crc_cnt_reg4_rx_mac_partial2_invert_crc_cnt {
      type oc-yang:counter64;
      description
        "Counts the number of received packets with partial CRC type 2.";
    }
    leaf counter_slice14_ifg_mac_pool84_rx_mac_partial2_invert_crc_cnt_reg5_rx_mac_partial2_invert_crc_cnt {
      type oc-yang:counter64;
      description
        "Counts the number of received packets with partial CRC type 2.";
    }
    leaf counter_slice14_ifg_mac_pool84_rx_mac_partial2_invert_crc_cnt_reg6_rx_mac_partial2_invert_crc_cnt {
      type oc-yang:counter64;
      description
        "Counts the number of received packets with partial CRC type 2.";
    }
    leaf counter_slice14_ifg_mac_pool84_rx_mac_partial2_invert_crc_cnt_reg7_rx_mac_partial2_invert_crc_cnt {
      type oc-yang:counter64;
      description
        "Counts the number of received packets with partial CRC type 2.";
    }
    leaf counter_slice14_ifg_mac_pool85_rx_mac_partial2_invert_crc_cnt_reg0_rx_mac_partial2_invert_crc_cnt {
      type oc-yang:counter64;
      description
        "Counts the number of received packets with partial CRC type 2.";
    }
    leaf counter_slice14_ifg_mac_pool85_rx_mac_partial2_invert_crc_cnt_reg1_rx_mac_partial2_invert_crc_cnt {
      type oc-yang:counter64;
      description
        "Counts the number of received packets with partial CRC type 2.";
    }
    leaf counter_slice14_ifg_mac_pool85_rx_mac_partial2_invert_crc_cnt_reg2_rx_mac_partial2_invert_crc_cnt {
      type oc-yang:counter64;
      description
        "Counts the number of received packets with partial CRC type 2.";
    }
    leaf counter_slice14_ifg_mac_pool85_rx_mac_partial2_invert_crc_cnt_reg3_rx_mac_partial2_invert_crc_cnt {
      type oc-yang:counter64;
      description
        "Counts the number of received packets with partial CRC type 2.";
    }
    leaf counter_slice14_ifg_mac_pool85_rx_mac_partial2_invert_crc_cnt_reg4_rx_mac_partial2_invert_crc_cnt {
      type oc-yang:counter64;
      description
        "Counts the number of received packets with partial CRC type 2.";
    }
    leaf counter_slice14_ifg_mac_pool85_rx_mac_partial2_invert_crc_cnt_reg5_rx_mac_partial2_invert_crc_cnt {
      type oc-yang:counter64;
      description
        "Counts the number of received packets with partial CRC type 2.";
    }
    leaf counter_slice14_ifg_mac_pool85_rx_mac_partial2_invert_crc_cnt_reg6_rx_mac_partial2_invert_crc_cnt {
      type oc-yang:counter64;
      description
        "Counts the number of received packets with partial CRC type 2.";
    }
    leaf counter_slice14_ifg_mac_pool85_rx_mac_partial2_invert_crc_cnt_reg7_rx_mac_partial2_invert_crc_cnt {
      type oc-yang:counter64;
      description
        "Counts the number of received packets with partial CRC type 2.";
    }
    leaf counter_slice14_ifg_mac_pool86_rx_mac_partial2_invert_crc_cnt_reg0_rx_mac_partial2_invert_crc_cnt {
      type oc-yang:counter64;
      description
        "Counts the number of received packets with partial CRC type 2.";
    }
    leaf counter_slice14_ifg_mac_pool86_rx_mac_partial2_invert_crc_cnt_reg1_rx_mac_partial2_invert_crc_cnt {
      type oc-yang:counter64;
      description
        "Counts the number of received packets with partial CRC type 2.";
    }
    leaf counter_slice14_ifg_mac_pool86_rx_mac_partial2_invert_crc_cnt_reg2_rx_mac_partial2_invert_crc_cnt {
      type oc-yang:counter64;
      description
        "Counts the number of received packets with partial CRC type 2.";
    }
    leaf counter_slice14_ifg_mac_pool86_rx_mac_partial2_invert_crc_cnt_reg3_rx_mac_partial2_invert_crc_cnt {
      type oc-yang:counter64;
      description
        "Counts the number of received packets with partial CRC type 2.";
    }
    leaf counter_slice14_ifg_mac_pool86_rx_mac_partial2_invert_crc_cnt_reg4_rx_mac_partial2_invert_crc_cnt {
      type oc-yang:counter64;
      description
        "Counts the number of received packets with partial CRC type 2.";
    }
    leaf counter_slice14_ifg_mac_pool86_rx_mac_partial2_invert_crc_cnt_reg5_rx_mac_partial2_invert_crc_cnt {
      type oc-yang:counter64;
      description
        "Counts the number of received packets with partial CRC type 2.";
    }
    leaf counter_slice14_ifg_mac_pool86_rx_mac_partial2_invert_crc_cnt_reg6_rx_mac_partial2_invert_crc_cnt {
      type oc-yang:counter64;
      description
        "Counts the number of received packets with partial CRC type 2.";
    }
    leaf counter_slice14_ifg_mac_pool86_rx_mac_partial2_invert_crc_cnt_reg7_rx_mac_partial2_invert_crc_cnt {
      type oc-yang:counter64;
      description
        "Counts the number of received packets with partial CRC type 2.";
    }
    leaf counter_slice14_ifg_mac_pool87_rx_mac_partial2_invert_crc_cnt_reg0_rx_mac_partial2_invert_crc_cnt {
      type oc-yang:counter64;
      description
        "Counts the number of received packets with partial CRC type 2.";
    }
    leaf counter_slice14_ifg_mac_pool87_rx_mac_partial2_invert_crc_cnt_reg1_rx_mac_partial2_invert_crc_cnt {
      type oc-yang:counter64;
      description
        "Counts the number of received packets with partial CRC type 2.";
    }
    leaf counter_slice14_ifg_mac_pool87_rx_mac_partial2_invert_crc_cnt_reg2_rx_mac_partial2_invert_crc_cnt {
      type oc-yang:counter64;
      description
        "Counts the number of received packets with partial CRC type 2.";
    }
    leaf counter_slice14_ifg_mac_pool87_rx_mac_partial2_invert_crc_cnt_reg3_rx_mac_partial2_invert_crc_cnt {
      type oc-yang:counter64;
      description
        "Counts the number of received packets with partial CRC type 2.";
    }
    leaf counter_slice14_ifg_mac_pool87_rx_mac_partial2_invert_crc_cnt_reg4_rx_mac_partial2_invert_crc_cnt {
      type oc-yang:counter64;
      description
        "Counts the number of received packets with partial CRC type 2.";
    }
    leaf counter_slice14_ifg_mac_pool87_rx_mac_partial2_invert_crc_cnt_reg5_rx_mac_partial2_invert_crc_cnt {
      type oc-yang:counter64;
      description
        "Counts the number of received packets with partial CRC type 2.";
    }
    leaf counter_slice14_ifg_mac_pool87_rx_mac_partial2_invert_crc_cnt_reg6_rx_mac_partial2_invert_crc_cnt {
      type oc-yang:counter64;
      description
        "Counts the number of received packets with partial CRC type 2.";
    }
    leaf counter_slice14_ifg_mac_pool87_rx_mac_partial2_invert_crc_cnt_reg7_rx_mac_partial2_invert_crc_cnt {
      type oc-yang:counter64;
      description
        "Counts the number of received packets with partial CRC type 2.";
    }
    leaf counter_slice15_ifg_mac_pool80_rx_mac_partial2_invert_crc_cnt_reg0_rx_mac_partial2_invert_crc_cnt {
      type oc-yang:counter64;
      description
        "Counts the number of received packets with partial CRC type 2.";
    }
    leaf counter_slice15_ifg_mac_pool80_rx_mac_partial2_invert_crc_cnt_reg1_rx_mac_partial2_invert_crc_cnt {
      type oc-yang:counter64;
      description
        "Counts the number of received packets with partial CRC type 2.";
    }
    leaf counter_slice15_ifg_mac_pool80_rx_mac_partial2_invert_crc_cnt_reg2_rx_mac_partial2_invert_crc_cnt {
      type oc-yang:counter64;
      description
        "Counts the number of received packets with partial CRC type 2.";
    }
    leaf counter_slice15_ifg_mac_pool80_rx_mac_partial2_invert_crc_cnt_reg3_rx_mac_partial2_invert_crc_cnt {
      type oc-yang:counter64;
      description
        "Counts the number of received packets with partial CRC type 2.";
    }
    leaf counter_slice15_ifg_mac_pool80_rx_mac_partial2_invert_crc_cnt_reg4_rx_mac_partial2_invert_crc_cnt {
      type oc-yang:counter64;
      description
        "Counts the number of received packets with partial CRC type 2.";
    }
    leaf counter_slice15_ifg_mac_pool80_rx_mac_partial2_invert_crc_cnt_reg5_rx_mac_partial2_invert_crc_cnt {
      type oc-yang:counter64;
      description
        "Counts the number of received packets with partial CRC type 2.";
    }
    leaf counter_slice15_ifg_mac_pool80_rx_mac_partial2_invert_crc_cnt_reg6_rx_mac_partial2_invert_crc_cnt {
      type oc-yang:counter64;
      description
        "Counts the number of received packets with partial CRC type 2.";
    }
    leaf counter_slice15_ifg_mac_pool80_rx_mac_partial2_invert_crc_cnt_reg7_rx_mac_partial2_invert_crc_cnt {
      type oc-yang:counter64;
      description
        "Counts the number of received packets with partial CRC type 2.";
    }
    leaf counter_slice15_ifg_mac_pool81_rx_mac_partial2_invert_crc_cnt_reg0_rx_mac_partial2_invert_crc_cnt {
      type oc-yang:counter64;
      description
        "Counts the number of received packets with partial CRC type 2.";
    }
    leaf counter_slice15_ifg_mac_pool81_rx_mac_partial2_invert_crc_cnt_reg1_rx_mac_partial2_invert_crc_cnt {
      type oc-yang:counter64;
      description
        "Counts the number of received packets with partial CRC type 2.";
    }
    leaf counter_slice15_ifg_mac_pool81_rx_mac_partial2_invert_crc_cnt_reg2_rx_mac_partial2_invert_crc_cnt {
      type oc-yang:counter64;
      description
        "Counts the number of received packets with partial CRC type 2.";
    }
    leaf counter_slice15_ifg_mac_pool81_rx_mac_partial2_invert_crc_cnt_reg3_rx_mac_partial2_invert_crc_cnt {
      type oc-yang:counter64;
      description
        "Counts the number of received packets with partial CRC type 2.";
    }
    leaf counter_slice15_ifg_mac_pool81_rx_mac_partial2_invert_crc_cnt_reg4_rx_mac_partial2_invert_crc_cnt {
      type oc-yang:counter64;
      description
        "Counts the number of received packets with partial CRC type 2.";
    }
    leaf counter_slice15_ifg_mac_pool81_rx_mac_partial2_invert_crc_cnt_reg5_rx_mac_partial2_invert_crc_cnt {
      type oc-yang:counter64;
      description
        "Counts the number of received packets with partial CRC type 2.";
    }
    leaf counter_slice15_ifg_mac_pool81_rx_mac_partial2_invert_crc_cnt_reg6_rx_mac_partial2_invert_crc_cnt {
      type oc-yang:counter64;
      description
        "Counts the number of received packets with partial CRC type 2.";
    }
    leaf counter_slice15_ifg_mac_pool81_rx_mac_partial2_invert_crc_cnt_reg7_rx_mac_partial2_invert_crc_cnt {
      type oc-yang:counter64;
      description
        "Counts the number of received packets with partial CRC type 2.";
    }
    leaf counter_slice15_ifg_mac_pool82_rx_mac_partial2_invert_crc_cnt_reg0_rx_mac_partial2_invert_crc_cnt {
      type oc-yang:counter64;
      description
        "Counts the number of received packets with partial CRC type 2.";
    }
    leaf counter_slice15_ifg_mac_pool82_rx_mac_partial2_invert_crc_cnt_reg1_rx_mac_partial2_invert_crc_cnt {
      type oc-yang:counter64;
      description
        "Counts the number of received packets with partial CRC type 2.";
    }
    leaf counter_slice15_ifg_mac_pool82_rx_mac_partial2_invert_crc_cnt_reg2_rx_mac_partial2_invert_crc_cnt {
      type oc-yang:counter64;
      description
        "Counts the number of received packets with partial CRC type 2.";
    }
    leaf counter_slice15_ifg_mac_pool82_rx_mac_partial2_invert_crc_cnt_reg3_rx_mac_partial2_invert_crc_cnt {
      type oc-yang:counter64;
      description
        "Counts the number of received packets with partial CRC type 2.";
    }
    leaf counter_slice15_ifg_mac_pool82_rx_mac_partial2_invert_crc_cnt_reg4_rx_mac_partial2_invert_crc_cnt {
      type oc-yang:counter64;
      description
        "Counts the number of received packets with partial CRC type 2.";
    }
    leaf counter_slice15_ifg_mac_pool82_rx_mac_partial2_invert_crc_cnt_reg5_rx_mac_partial2_invert_crc_cnt {
      type oc-yang:counter64;
      description
        "Counts the number of received packets with partial CRC type 2.";
    }
    leaf counter_slice15_ifg_mac_pool82_rx_mac_partial2_invert_crc_cnt_reg6_rx_mac_partial2_invert_crc_cnt {
      type oc-yang:counter64;
      description
        "Counts the number of received packets with partial CRC type 2.";
    }
    leaf counter_slice15_ifg_mac_pool82_rx_mac_partial2_invert_crc_cnt_reg7_rx_mac_partial2_invert_crc_cnt {
      type oc-yang:counter64;
      description
        "Counts the number of received packets with partial CRC type 2.";
    }
    leaf counter_slice15_ifg_mac_pool83_rx_mac_partial2_invert_crc_cnt_reg0_rx_mac_partial2_invert_crc_cnt {
      type oc-yang:counter64;
      description
        "Counts the number of received packets with partial CRC type 2.";
    }
    leaf counter_slice15_ifg_mac_pool83_rx_mac_partial2_invert_crc_cnt_reg1_rx_mac_partial2_invert_crc_cnt {
      type oc-yang:counter64;
      description
        "Counts the number of received packets with partial CRC type 2.";
    }
    leaf counter_slice15_ifg_mac_pool83_rx_mac_partial2_invert_crc_cnt_reg2_rx_mac_partial2_invert_crc_cnt {
      type oc-yang:counter64;
      description
        "Counts the number of received packets with partial CRC type 2.";
    }
    leaf counter_slice15_ifg_mac_pool83_rx_mac_partial2_invert_crc_cnt_reg3_rx_mac_partial2_invert_crc_cnt {
      type oc-yang:counter64;
      description
        "Counts the number of received packets with partial CRC type 2.";
    }
    leaf counter_slice15_ifg_mac_pool83_rx_mac_partial2_invert_crc_cnt_reg4_rx_mac_partial2_invert_crc_cnt {
      type oc-yang:counter64;
      description
        "Counts the number of received packets with partial CRC type 2.";
    }
    leaf counter_slice15_ifg_mac_pool83_rx_mac_partial2_invert_crc_cnt_reg5_rx_mac_partial2_invert_crc_cnt {
      type oc-yang:counter64;
      description
        "Counts the number of received packets with partial CRC type 2.";
    }
    leaf counter_slice15_ifg_mac_pool83_rx_mac_partial2_invert_crc_cnt_reg6_rx_mac_partial2_invert_crc_cnt {
      type oc-yang:counter64;
      description
        "Counts the number of received packets with partial CRC type 2.";
    }
    leaf counter_slice15_ifg_mac_pool83_rx_mac_partial2_invert_crc_cnt_reg7_rx_mac_partial2_invert_crc_cnt {
      type oc-yang:counter64;
      description
        "Counts the number of received packets with partial CRC type 2.";
    }
    leaf counter_slice15_ifg_mac_pool84_rx_mac_partial2_invert_crc_cnt_reg0_rx_mac_partial2_invert_crc_cnt {
      type oc-yang:counter64;
      description
        "Counts the number of received packets with partial CRC type 2.";
    }
    leaf counter_slice15_ifg_mac_pool84_rx_mac_partial2_invert_crc_cnt_reg1_rx_mac_partial2_invert_crc_cnt {
      type oc-yang:counter64;
      description
        "Counts the number of received packets with partial CRC type 2.";
    }
    leaf counter_slice15_ifg_mac_pool84_rx_mac_partial2_invert_crc_cnt_reg2_rx_mac_partial2_invert_crc_cnt {
      type oc-yang:counter64;
      description
        "Counts the number of received packets with partial CRC type 2.";
    }
    leaf counter_slice15_ifg_mac_pool84_rx_mac_partial2_invert_crc_cnt_reg3_rx_mac_partial2_invert_crc_cnt {
      type oc-yang:counter64;
      description
        "Counts the number of received packets with partial CRC type 2.";
    }
    leaf counter_slice15_ifg_mac_pool84_rx_mac_partial2_invert_crc_cnt_reg4_rx_mac_partial2_invert_crc_cnt {
      type oc-yang:counter64;
      description
        "Counts the number of received packets with partial CRC type 2.";
    }
    leaf counter_slice15_ifg_mac_pool84_rx_mac_partial2_invert_crc_cnt_reg5_rx_mac_partial2_invert_crc_cnt {
      type oc-yang:counter64;
      description
        "Counts the number of received packets with partial CRC type 2.";
    }
    leaf counter_slice15_ifg_mac_pool84_rx_mac_partial2_invert_crc_cnt_reg6_rx_mac_partial2_invert_crc_cnt {
      type oc-yang:counter64;
      description
        "Counts the number of received packets with partial CRC type 2.";
    }
    leaf counter_slice15_ifg_mac_pool84_rx_mac_partial2_invert_crc_cnt_reg7_rx_mac_partial2_invert_crc_cnt {
      type oc-yang:counter64;
      description
        "Counts the number of received packets with partial CRC type 2.";
    }
    leaf counter_slice15_ifg_mac_pool85_rx_mac_partial2_invert_crc_cnt_reg0_rx_mac_partial2_invert_crc_cnt {
      type oc-yang:counter64;
      description
        "Counts the number of received packets with partial CRC type 2.";
    }
    leaf counter_slice15_ifg_mac_pool85_rx_mac_partial2_invert_crc_cnt_reg1_rx_mac_partial2_invert_crc_cnt {
      type oc-yang:counter64;
      description
        "Counts the number of received packets with partial CRC type 2.";
    }
    leaf counter_slice15_ifg_mac_pool85_rx_mac_partial2_invert_crc_cnt_reg2_rx_mac_partial2_invert_crc_cnt {
      type oc-yang:counter64;
      description
        "Counts the number of received packets with partial CRC type 2.";
    }
    leaf counter_slice15_ifg_mac_pool85_rx_mac_partial2_invert_crc_cnt_reg3_rx_mac_partial2_invert_crc_cnt {
      type oc-yang:counter64;
      description
        "Counts the number of received packets with partial CRC type 2.";
    }
    leaf counter_slice15_ifg_mac_pool85_rx_mac_partial2_invert_crc_cnt_reg4_rx_mac_partial2_invert_crc_cnt {
      type oc-yang:counter64;
      description
        "Counts the number of received packets with partial CRC type 2.";
    }
    leaf counter_slice15_ifg_mac_pool85_rx_mac_partial2_invert_crc_cnt_reg5_rx_mac_partial2_invert_crc_cnt {
      type oc-yang:counter64;
      description
        "Counts the number of received packets with partial CRC type 2.";
    }
    leaf counter_slice15_ifg_mac_pool85_rx_mac_partial2_invert_crc_cnt_reg6_rx_mac_partial2_invert_crc_cnt {
      type oc-yang:counter64;
      description
        "Counts the number of received packets with partial CRC type 2.";
    }
    leaf counter_slice15_ifg_mac_pool85_rx_mac_partial2_invert_crc_cnt_reg7_rx_mac_partial2_invert_crc_cnt {
      type oc-yang:counter64;
      description
        "Counts the number of received packets with partial CRC type 2.";
    }
    leaf counter_slice15_ifg_mac_pool86_rx_mac_partial2_invert_crc_cnt_reg0_rx_mac_partial2_invert_crc_cnt {
      type oc-yang:counter64;
      description
        "Counts the number of received packets with partial CRC type 2.";
    }
    leaf counter_slice15_ifg_mac_pool86_rx_mac_partial2_invert_crc_cnt_reg1_rx_mac_partial2_invert_crc_cnt {
      type oc-yang:counter64;
      description
        "Counts the number of received packets with partial CRC type 2.";
    }
    leaf counter_slice15_ifg_mac_pool86_rx_mac_partial2_invert_crc_cnt_reg2_rx_mac_partial2_invert_crc_cnt {
      type oc-yang:counter64;
      description
        "Counts the number of received packets with partial CRC type 2.";
    }
    leaf counter_slice15_ifg_mac_pool86_rx_mac_partial2_invert_crc_cnt_reg3_rx_mac_partial2_invert_crc_cnt {
      type oc-yang:counter64;
      description
        "Counts the number of received packets with partial CRC type 2.";
    }
    leaf counter_slice15_ifg_mac_pool86_rx_mac_partial2_invert_crc_cnt_reg4_rx_mac_partial2_invert_crc_cnt {
      type oc-yang:counter64;
      description
        "Counts the number of received packets with partial CRC type 2.";
    }
    leaf counter_slice15_ifg_mac_pool86_rx_mac_partial2_invert_crc_cnt_reg5_rx_mac_partial2_invert_crc_cnt {
      type oc-yang:counter64;
      description
        "Counts the number of received packets with partial CRC type 2.";
    }
    leaf counter_slice15_ifg_mac_pool86_rx_mac_partial2_invert_crc_cnt_reg6_rx_mac_partial2_invert_crc_cnt {
      type oc-yang:counter64;
      description
        "Counts the number of received packets with partial CRC type 2.";
    }
    leaf counter_slice15_ifg_mac_pool86_rx_mac_partial2_invert_crc_cnt_reg7_rx_mac_partial2_invert_crc_cnt {
      type oc-yang:counter64;
      description
        "Counts the number of received packets with partial CRC type 2.";
    }
    leaf counter_slice15_ifg_mac_pool87_rx_mac_partial2_invert_crc_cnt_reg0_rx_mac_partial2_invert_crc_cnt {
      type oc-yang:counter64;
      description
        "Counts the number of received packets with partial CRC type 2.";
    }
    leaf counter_slice15_ifg_mac_pool87_rx_mac_partial2_invert_crc_cnt_reg1_rx_mac_partial2_invert_crc_cnt {
      type oc-yang:counter64;
      description
        "Counts the number of received packets with partial CRC type 2.";
    }
    leaf counter_slice15_ifg_mac_pool87_rx_mac_partial2_invert_crc_cnt_reg2_rx_mac_partial2_invert_crc_cnt {
      type oc-yang:counter64;
      description
        "Counts the number of received packets with partial CRC type 2.";
    }
    leaf counter_slice15_ifg_mac_pool87_rx_mac_partial2_invert_crc_cnt_reg3_rx_mac_partial2_invert_crc_cnt {
      type oc-yang:counter64;
      description
        "Counts the number of received packets with partial CRC type 2.";
    }
    leaf counter_slice15_ifg_mac_pool87_rx_mac_partial2_invert_crc_cnt_reg4_rx_mac_partial2_invert_crc_cnt {
      type oc-yang:counter64;
      description
        "Counts the number of received packets with partial CRC type 2.";
    }
    leaf counter_slice15_ifg_mac_pool87_rx_mac_partial2_invert_crc_cnt_reg5_rx_mac_partial2_invert_crc_cnt {
      type oc-yang:counter64;
      description
        "Counts the number of received packets with partial CRC type 2.";
    }
    leaf counter_slice15_ifg_mac_pool87_rx_mac_partial2_invert_crc_cnt_reg6_rx_mac_partial2_invert_crc_cnt {
      type oc-yang:counter64;
      description
        "Counts the number of received packets with partial CRC type 2.";
    }
    leaf counter_slice15_ifg_mac_pool87_rx_mac_partial2_invert_crc_cnt_reg7_rx_mac_partial2_invert_crc_cnt {
      type oc-yang:counter64;
      description
        "Counts the number of received packets with partial CRC type 2.";
    }
    leaf counter_slice0_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice0_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice0_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice0_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice1_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice1_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice1_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice1_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice2_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice2_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice2_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice2_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice3_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice3_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice3_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice3_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice4_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice4_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice4_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice4_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice5_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice5_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice5_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice5_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice6_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice6_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice6_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice6_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice7_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice7_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice7_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice7_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice8_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice8_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice8_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice8_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice9_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice9_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice9_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice9_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice10_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice10_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice10_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice10_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice11_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice11_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice11_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice11_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice12_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice12_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice12_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice12_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice13_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice13_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice13_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice13_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice14_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice14_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice14_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice14_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool82_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool82_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool82_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool82_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool83_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool83_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool83_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool83_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool84_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool84_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool84_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool84_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool85_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool85_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool85_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool85_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool86_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool86_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool86_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool86_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice15_ifg_mac_pool87_rx_oob_mac_type_err_cnt_reg0_rx_oob_mac_type_err_cnt {
      type oc-yang:counter64;
      description
        "Counts in interleaving mode OOB packets that are received with none OOB packet type. Those are dropped when RxOobIntrlvTypeFiltEn is set.";
    }
    leaf counter_slice15_ifg_mac_pool87_rx_oob_mac_type_err_cnt_reg1_rx_oob_mac_type_err_cnt {
      type oc-yang:counter64;
      description
        "Counts in interleaving mode OOB packets that are received with none OOB packet type. Those are dropped when RxOobIntrlvTypeFiltEn is set.";
    }
    leaf counter_slice15_ifg_mac_pool87_rx_oob_mac_type_err_cnt_reg2_rx_oob_mac_type_err_cnt {
      type oc-yang:counter64;
      description
        "Counts in interleaving mode OOB packets that are received with none OOB packet type. Those are dropped when RxOobIntrlvTypeFiltEn is set.";
    }
    leaf counter_slice15_ifg_mac_pool87_rx_oob_mac_type_err_cnt_reg3_rx_oob_mac_type_err_cnt {
      type oc-yang:counter64;
      description
        "Counts in interleaving mode OOB packets that are received with none OOB packet type. Those are dropped when RxOobIntrlvTypeFiltEn is set.";
    }
    leaf counter_slice0_ifg_mac_pool80_tx_drained_pkt_cnt_reg0_tx_drained_pkt_cnt {
      type oc-yang:counter64;
      description
        "Count number of packets that are transmitted by mac and dropped by the RS layer because the link is in fault state.";
    }
    leaf counter_slice0_ifg_mac_pool80_tx_drained_pkt_cnt_reg1_tx_drained_pkt_cnt {
      type oc-yang:counter64;
      description
        "Count number of packets that are transmitted by mac and dropped by the RS layer because the link is in fault state.";
    }
    leaf counter_slice0_ifg_mac_pool80_tx_drained_pkt_cnt_reg2_tx_drained_pkt_cnt {
      type oc-yang:counter64;
      description
        "Count number of packets that are transmitted by mac and dropped by the RS layer because the link is in fault state.";
    }
    leaf counter_slice0_ifg_mac_pool80_tx_drained_pkt_cnt_reg3_tx_drained_pkt_cnt {
      type oc-yang:counter64;
      description
        "Count number of packets that are transmitted by mac and dropped by the RS layer because the link is in fault state.";
    }
    leaf counter_slice0_ifg_mac_pool80_tx_drained_pkt_cnt_reg4_tx_drained_pkt_cnt {
      type oc-yang:counter64;
      description
        "Count number of packets that are transmitted by mac and dropped by the RS layer because the link is in fault state.";
    }
    leaf counter_slice0_ifg_mac_pool80_tx_drained_pkt_cnt_reg5_tx_drained_pkt_cnt {
      type oc-yang:counter64;
      description
        "Count number of packets that are transmitted by mac and dropped by the RS layer because the link is in fault state.";
    }
    leaf counter_slice0_ifg_mac_pool80_tx_drained_pkt_cnt_reg6_tx_drained_pkt_cnt {
      type oc-yang:counter64;
      description
        "Count number of packets that are transmitted by mac and dropped by the RS layer because the link is in fault state.";
    }
    leaf counter_slice0_ifg_mac_pool80_tx_drained_pkt_cnt_reg7_tx_drained_pkt_cnt {
      type oc-yang:counter64;
      description
        "Count number of packets that are transmitted by mac and dropped by the RS layer because the link is in fault state.";
    }
    leaf counter_slice0_ifg_mac_pool81_tx_drained_pkt_cnt_reg0_tx_drained_pkt_cnt {
      type oc-yang:counter64;
      description
        "Count number of packets that are transmitted by mac and dropped by the RS layer because the link is in fault state.";
    }
    leaf counter_slice0_ifg_mac_pool81_tx_drained_pkt_cnt_reg1_tx_drained_pkt_cnt {
      type oc-yang:counter64;
      description
        "Count number of packets that are transmitted by mac and dropped by the RS layer because the link is in fault state.";
    }
    leaf counter_slice0_ifg_mac_pool81_tx_drained_pkt_cnt_reg2_tx_drained_pkt_cnt {
      type oc-yang:counter64;
      description
        "Count number of packets that are transmitted by mac and dropped by the RS layer because the link is in fault state.";
    }
    leaf counter_slice0_ifg_mac_pool81_tx_drained_pkt_cnt_reg3_tx_drained_pkt_cnt {
      type oc-yang:counter64;
      description
        "Count number of packets that are transmitted by mac and dropped by the RS layer because the link is in fault state.";
    }
    leaf counter_slice0_ifg_mac_pool81_tx_drained_pkt_cnt_reg4_tx_drained_pkt_cnt {
      type oc-yang:counter64;
      description
        "Count number of packets that are transmitted by mac and dropped by the RS layer because the link is in fault state.";
    }
    leaf counter_slice0_ifg_mac_pool81_tx_drained_pkt_cnt_reg5_tx_drained_pkt_cnt {
      type oc-yang:counter64;
      description
        "Count number of packets that are transmitted by mac and dropped by the RS layer because the link is in fault state.";
    }
    leaf counter_slice0_ifg_mac_pool81_tx_drained_pkt_cnt_reg6_tx_drained_pkt_cnt {
      type oc-yang:counter64;
      description
        "Count number of packets that are transmitted by mac and dropped by the RS layer because the link is in fault state.";
    }
    leaf counter_slice0_ifg_mac_pool81_tx_drained_pkt_cnt_reg7_tx_drained_pkt_cnt {
      type oc-yang:counter64;
      description
        "Count number of packets that are transmitted by mac and dropped by the RS layer because the link is in fault state.";
    }
    leaf counter_slice0_ifg_mac_pool82_tx_drained_pkt_cnt_reg0_tx_drained_pkt_cnt {
      type oc-yang:counter64;
      description
        "Count number of packets that are transmitted by mac and dropped by the RS layer because the link is in fault state.";
    }
    leaf counter_slice0_ifg_mac_pool82_tx_drained_pkt_cnt_reg1_tx_drained_pkt_cnt {
      type oc-yang:counter64;
      description
        "Count number of packets that are transmitted by mac and dropped by the RS layer because the link is in fault state.";
    }
    leaf counter_slice0_ifg_mac_pool82_tx_drained_pkt_cnt_reg2_tx_drained_pkt_cnt {
      type oc-yang:counter64;
      description
        "Count number of packets that are transmitted by mac and dropped by the RS layer because the link is in fault state.";
    }
    leaf counter_slice0_ifg_mac_pool82_tx_drained_pkt_cnt_reg3_tx_drained_pkt_cnt {
      type oc-yang:counter64;
      description
        "Count number of packets that are transmitted by mac and dropped by the RS layer because the link is in fault state.";
    }
    leaf counter_slice0_ifg_mac_pool82_tx_drained_pkt_cnt_reg4_tx_drained_pkt_cnt {
      type oc-yang:counter64;
      description
        "Count number of packets that are transmitted by mac and dropped by the RS layer because the link is in fault state.";
    }
    leaf counter_slice0_ifg_mac_pool82_tx_drained_pkt_cnt_reg5_tx_drained_pkt_cnt {
      type oc-yang:counter64;
      description
        "Count number of packets that are transmitted by mac and dropped by the RS layer because the link is in fault state.";
    }
    leaf counter_slice0_ifg_mac_pool82_tx_drained_pkt_cnt_reg6_tx_drained_pkt_cnt {
      type oc-yang:counter64;
      description
        "Count number of packets that are transmitted by mac and dropped by the RS layer because the link is in fault state.";
    }
    leaf counter_slice0_ifg_mac_pool82_tx_drained_pkt_cnt_reg7_tx_drained_pkt_cnt {
      type oc-yang:counter64;
      description
        "Count number of packets that are transmitted by mac and dropped by the RS layer because the link is in fault state.";
    }
    leaf counter_slice0_ifg_mac_pool83_tx_drained_pkt_cnt_reg0_tx_drained_pkt_cnt {
      type oc-yang:counter64;
      description
        "Count number of packets that are transmitted by mac and dropped by the RS layer because the link is in fault state.";
    }
    leaf counter_slice0_ifg_mac_pool83_tx_drained_pkt_cnt_reg1_tx_drained_pkt_cnt {
      type oc-yang:counter64;
      description
        "Count number of packets that are transmitted by mac and dropped by the RS layer because the link is in fault state.";
    }
    leaf counter_slice0_ifg_mac_pool83_tx_drained_pkt_cnt_reg2_tx_drained_pkt_cnt {
      type oc-yang:counter64;
      description
        "Count number of packets that are transmitted by mac and dropped by the RS layer because the link is in fault state.";
    }
    leaf counter_slice0_ifg_mac_pool83_tx_drained_pkt_cnt_reg3_tx_drained_pkt_cnt {
      type oc-yang:counter64;
      description
        "Count number of packets that are transmitted by mac and dropped by the RS layer because the link is in fault state.";
    }
    leaf counter_slice0_ifg_mac_pool83_tx_drained_pkt_cnt_reg4_tx_drained_pkt_cnt {
      type oc-yang:counter64;
      description
        "Count number of packets that are transmitted by mac and dropped by the RS layer because the link is in fault state.";
    }
    leaf counter_slice0_ifg_mac_pool83_tx_drained_pkt_cnt_reg5_tx_drained_pkt_cnt {
      type oc-yang:counter64;
      description
        "Count number of packets that are transmitted by mac and dropped by the RS layer because the link is in fault state.";
    }
    leaf counter_slice0_ifg_mac_pool83_tx_drained_pkt_cnt_reg6_tx_drained_pkt_cnt {
      type oc-yang:counter64;
      description
        "Count number of packets that are transmitted by mac and dropped by the RS layer because the link is in fault state.";
    }
    leaf counter_slice0_ifg_mac_pool83_tx_drained_pkt_cnt_reg7_tx_drained_pkt_cnt {
      type oc-yang:counter64;
      description
        "Count number of packets that are transmitted by mac and dropped by the RS layer because the link is in fault state.";
    }
    leaf counter_slice0_ifg_mac_pool84_tx_drained_pkt_cnt_reg0_tx_drained_pkt_cnt {
      type oc-yang:counter64;
      description
        "Count number of packets that are transmitted by mac and dropped by the RS layer because the link is in fault state.";
    }
    leaf counter_slice0_ifg_mac_pool84_tx_drained_pkt_cnt_reg1_tx_drained_pkt_cnt {
      type oc-yang:counter64;
      description
        "Count number of packets that are transmitted by mac and dropped by the RS layer because the link is in fault state.";
    }
    leaf counter_slice0_ifg_mac_pool84_tx_drained_pkt_cnt_reg2_tx_drained_pkt_cnt {
      type oc-yang:counter64;
      description
        "Count number of packets that are transmitted by mac and dropped by the RS layer because the link is in fault state.";
    }
    leaf counter_slice0_ifg_mac_pool84_tx_drained_pkt_cnt_reg3_tx_drained_pkt_cnt {
      type oc-yang:counter64;
      description
        "Count number of packets that are transmitted by mac and dropped by the RS layer because the link is in fault state.";
    }
    leaf counter_slice0_ifg_mac_pool84_tx_drained_pkt_cnt_reg4_tx_drained_pkt_cnt {
      type oc-yang:counter64;
      description
        "Count number of packets that are transmitted by mac and dropped by the RS layer because the link is in fault state.";
    }
    leaf counter_slice0_ifg_mac_pool84_tx_drained_pkt_cnt_reg5_tx_drained_pkt_cnt {
      type oc-yang:counter64;
      description
        "Count number of packets that are transmitted by mac and dropped by the RS layer because the link is in fault state.";
    }
    leaf counter_slice0_ifg_mac_pool84_tx_drained_pkt_cnt_reg6_tx_drained_pkt_cnt {
      type oc-yang:counter64;
      description
        "Count number of packets that are transmitted by mac and dropped by the RS layer because the link is in fault state.";
    }
    leaf counter_slice0_ifg_mac_pool84_tx_drained_pkt_cnt_reg7_tx_drained_pkt_cnt {
      type oc-yang:counter64;
      description
        "Count number of packets that are transmitted by mac and dropped by the RS layer because the link is in fault state.";
    }
    leaf counter_slice0_ifg_mac_pool85_tx_drained_pkt_cnt_reg0_tx_drained_pkt_cnt {
      type oc-yang:counter64;
      description
        "Count number of packets that are transmitted by mac and dropped by the RS layer because the link is in fault state.";
    }
    leaf counter_slice0_ifg_mac_pool85_tx_drained_pkt_cnt_reg1_tx_drained_pkt_cnt {
      type oc-yang:counter64;
      description
        "Count number of packets that are transmitted by mac and dropped by the RS layer because the link is in fault state.";
    }
    leaf counter_slice0_ifg_mac_pool85_tx_drained_pkt_cnt_reg2_tx_drained_pkt_cnt {
      type oc-yang:counter64;
      description
        "Count number of packets that are transmitted by mac and dropped by the RS layer because the link is in fault state.";
    }
    leaf counter_slice0_ifg_mac_pool85_tx_drained_pkt_cnt_reg3_tx_drained_pkt_cnt {
      type oc-yang:counter64;
      description
        "Count number of packets that are transmitted by mac and dropped by the RS layer because the link is in fault state.";
    }
    leaf counter_slice0_ifg_mac_pool85_tx_drained_pkt_cnt_reg4_tx_drained_pkt_cnt {
      type oc-yang:counter64;
      description
        "Count number of packets that are transmitted by mac and dropped by the RS layer because the link is in fault state.";
    }
    leaf counter_slice0_ifg_mac_pool85_tx_drained_pkt_cnt_reg5_tx_drained_pkt_cnt {
      type oc-yang:counter64;
      description
        "Count number of packets that are transmitted by mac and dropped by the RS layer because the link is in fault state.";
    }
    leaf counter_slice0_ifg_mac_pool85_tx_drained_pkt_cnt_reg6_tx_drained_pkt_cnt {
      type oc-yang:counter64;
      description
        "Count number of packets that are transmitted by mac and dropped by the RS layer because the link is in fault state.";
    }
    leaf counter_slice0_ifg_mac_pool85_tx_drained_pkt_cnt_reg7_tx_drained_pkt_cnt {
      type oc-yang:counter64;
      description
        "Count number of packets that are transmitted by mac and dropped by the RS layer because the link is in fault state.";
    }
    leaf counter_slice0_ifg_mac_pool86_tx_drained_pkt_cnt_reg0_tx_drained_pkt_cnt {
      type oc-yang:counter64;
      description
        "Count number of packets that are transmitted by mac and dropped by the RS layer because the link is in fault state.";
    }
    leaf counter_slice0_ifg_mac_pool86_tx_drained_pkt_cnt_reg1_tx_drained_pkt_cnt {
      type oc-yang:counter64;
      description
        "Count number of packets that are transmitted by mac and dropped by the RS layer because the link is in fault state.";
    }
    leaf counter_slice0_ifg_mac_pool86_tx_drained_pkt_cnt_reg2_tx_drained_pkt_cnt {
      type oc-yang:counter64;
      description
        "Count number of packets that are transmitted by mac and dropped by the RS layer because the link is in fault state.";
    }
    leaf counter_slice0_ifg_mac_pool86_tx_drained_pkt_cnt_reg3_tx_drained_pkt_cnt {
      type oc-yang:counter64;
      description
        "Count number of packets that are transmitted by mac and dropped by the RS layer because the link is in fault state.";
    }
    leaf counter_slice0_ifg_mac_pool86_tx_drained_pkt_cnt_reg4_tx_drained_pkt_cnt {
      type oc-yang:counter64;
      description
        "Count number of packets that are transmitted by mac and dropped by the RS layer because the link is in fault state.";
    }
    leaf counter_slice0_ifg_mac_pool86_tx_drained_pkt_cnt_reg5_tx_drained_pkt_cnt {
      type oc-yang:counter64;
      description
        "Count number of packets that are transmitted by mac and dropped by the RS layer because the link is in fault state.";
    }
    leaf counter_slice0_ifg_mac_pool86_tx_drained_pkt_cnt_reg6_tx_drained_pkt_cnt {
      type oc-yang:counter64;
      description
        "Count number of packets that are transmitted by mac and dropped by the RS layer because the link is in fault state.";
    }
    leaf counter_slice0_ifg_mac_pool86_tx_drained_pkt_cnt_reg7_tx_drained_pkt_cnt {
      type oc-yang:counter64;
      description
        "Count number of packets that are transmitted by mac and dropped by the RS layer because the link is in fault state.";
    }
    leaf counter_slice0_ifg_mac_pool87_tx_drained_pkt_cnt_reg0_tx_drained_pkt_cnt {
      type oc-yang:counter64;
      description
        "Count number of packets that are transmitted by mac and dropped by the RS layer because the link is in fault state.";
    }
    leaf counter_slice0_ifg_mac_pool87_tx_drained_pkt_cnt_reg1_tx_drained_pkt_cnt {
      type oc-yang:counter64;
      description
        "Count number of packets that are transmitted by mac and dropped by the RS layer because the link is in fault state.";
    }
    leaf counter_slice0_ifg_mac_pool87_tx_drained_pkt_cnt_reg2_tx_drained_pkt_cnt {
      type oc-yang:counter64;
      description
        "Count number of packets that are transmitted by mac and dropped by the RS layer because the link is in fault state.";
    }
    leaf counter_slice0_ifg_mac_pool87_tx_drained_pkt_cnt_reg3_tx_drained_pkt_cnt {
      type oc-yang:counter64;
      description
        "Count number of packets that are transmitted by mac and dropped by the RS layer because the link is in fault state.";
    }
    leaf counter_slice0_ifg_mac_pool87_tx_drained_pkt_cnt_reg4_tx_drained_pkt_cnt {
      type oc-yang:counter64;
      description
        "Count number of packets that are transmitted by mac and dropped by the RS layer because the link is in fault state.";
    }
    leaf counter_slice0_ifg_mac_pool87_tx_drained_pkt_cnt_reg5_tx_drained_pkt_cnt {
      type oc-yang:counter64;
      description
        "Count number of packets that are transmitted by mac and dropped by the RS layer because the link is in fault state.";
    }
    leaf counter_slice0_ifg_mac_pool87_tx_drained_pkt_cnt_reg6_tx_drained_pkt_cnt {
      type oc-yang:counter64;
      description
        "Count number of packets that are transmitted by mac and dropped by the RS layer because the link is in fault state.";
    }
    leaf counter_slice0_ifg_mac_pool87_tx_drained_pkt_cnt_reg7_tx_drained_pkt_cnt {
      type oc-yang:counter64;
      description
        "Count number of packets that are transmitted by mac and dropped by the RS layer because the link is in fault state.";
    }
    leaf counter_slice1_ifg_mac_pool80_tx_drained_pkt_cnt_reg0_tx_drained_pkt_cnt {
      type oc-yang:counter64;
      description
        "Count number of packets that are transmitted by mac and dropped by the RS layer because the link is in fault state.";
    }
    leaf counter_slice1_ifg_mac_pool80_tx_drained_pkt_cnt_reg1_tx_drained_pkt_cnt {
      type oc-yang:counter64;
      description
        "Count number of packets that are transmitted by mac and dropped by the RS layer because the link is in fault state.";
    }
    leaf counter_slice1_ifg_mac_pool80_tx_drained_pkt_cnt_reg2_tx_drained_pkt_cnt {
      type oc-yang:counter64;
      description
        "Count number of packets that are transmitted by mac and dropped by the RS layer because the link is in fault state.";
    }
    leaf counter_slice1_ifg_mac_pool80_tx_drained_pkt_cnt_reg3_tx_drained_pkt_cnt {
      type oc-yang:counter64;
      description
        "Count number of packets that are transmitted by mac and dropped by the RS layer because the link is in fault state.";
    }
    leaf counter_slice1_ifg_mac_pool80_tx_drained_pkt_cnt_reg4_tx_drained_pkt_cnt {
      type oc-yang:counter64;
      description
        "Count number of packets that are transmitted by mac and dropped by the RS layer because the link is in fault state.";
    }
    leaf counter_slice1_ifg_mac_pool80_tx_drained_pkt_cnt_reg5_tx_drained_pkt_cnt {
      type oc-yang:counter64;
      description
        "Count number of packets that are transmitted by mac and dropped by the RS layer because the link is in fault state.";
    }
    leaf counter_slice1_ifg_mac_pool80_tx_drained_pkt_cnt_reg6_tx_drained_pkt_cnt {
      type oc-yang:counter64;
      description
        "Count number of packets that are transmitted by mac and dropped by the RS layer because the link is in fault state.";
    }
    leaf counter_slice1_ifg_mac_pool80_tx_drained_pkt_cnt_reg7_tx_drained_pkt_cnt {
      type oc-yang:counter64;
      description
        "Count number of packets that are transmitted by mac and dropped by the RS layer because the link is in fault state.";
    }
    leaf counter_slice1_ifg_mac_pool81_tx_drained_pkt_cnt_reg0_tx_drained_pkt_cnt {
      type oc-yang:counter64;
      description
        "Count number of packets that are transmitted by mac and dropped by the RS layer because the link is in fault state.";
    }
    leaf counter_slice1_ifg_mac_pool81_tx_drained_pkt_cnt_reg1_tx_drained_pkt_cnt {
      type oc-yang:counter64;
      description
        "Count number of packets that are transmitted by mac and dropped by the RS layer because the link is in fault state.";
    }
    leaf counter_slice1_ifg_mac_pool81_tx_drained_pkt_cnt_reg2_tx_drained_pkt_cnt {
      type oc-yang:counter64;
      description
        "Count number of packets that are transmitted by mac and dropped by the RS layer because the link is in fault state.";
    }
    leaf counter_slice1_ifg_mac_pool81_tx_drained_pkt_cnt_reg3_tx_drained_pkt_cnt {
      type oc-yang:counter64;
      description
        "Count number of packets that are transmitted by mac and dropped by the RS layer because the link is in fault state.";
    }
    leaf counter_slice1_ifg_mac_pool81_tx_drained_pkt_cnt_reg4_tx_drained_pkt_cnt {
      type oc-yang:counter64;
      description
        "Count number of packets that are transmitted by mac and dropped by the RS layer because the link is in fault state.";
    }
    leaf counter_slice1_ifg_mac_pool81_tx_drained_pkt_cnt_reg5_tx_drained_pkt_cnt {
      type oc-yang:counter64;
      description
        "Count number of packets that are transmitted by mac and dropped by the RS layer because the link is in fault state.";
    }
    leaf counter_slice1_ifg_mac_pool81_tx_drained_pkt_cnt_reg6_tx_drained_pkt_cnt {
      type oc-yang:counter64;
      description
        "Count number of packets that are transmitted by mac and dropped by the RS layer because the link is in fault state.";
    }
    leaf counter_slice1_ifg_mac_pool81_tx_drained_pkt_cnt_reg7_tx_drained_pkt_cnt {
      type oc-yang:counter64;
      description
        "Count number of packets that are transmitted by mac and dropped by the RS layer because the link is in fault state.";
    }
    leaf counter_slice1_ifg_mac_pool82_tx_drained_pkt_cnt_reg0_tx_drained_pkt_cnt {
      type oc-yang:counter64;
      description
        "Count number of packets that are transmitted by mac and dropped by the RS layer because the link is in fault state.";
    }
    leaf counter_slice1_ifg_mac_pool82_tx_drained_pkt_cnt_reg1_tx_drained_pkt_cnt {
      type oc-yang:counter64;
      description
        "Count number of packets that are transmitted by mac and dropped by the RS layer because the link is in fault state.";
    }
    leaf counter_slice1_ifg_mac_pool82_tx_drained_pkt_cnt_reg2_tx_drained_pkt_cnt {
      type oc-yang:counter64;
      description
        "Count number of packets that are transmitted by mac and dropped by the RS layer because the link is in fault state.";
    }
    leaf counter_slice1_ifg_mac_pool82_tx_drained_pkt_cnt_reg3_tx_drained_pkt_cnt {
      type oc-yang:counter64;
      description
        "Count number of packets that are transmitted by mac and dropped by the RS layer because the link is in fault state.";
    }
    leaf counter_slice1_ifg_mac_pool82_tx_drained_pkt_cnt_reg4_tx_drained_pkt_cnt {
      type oc-yang:counter64;
      description
        "Count number of packets that are transmitted by mac and dropped by the RS layer because the link is in fault state.";
    }
    leaf counter_slice1_ifg_mac_pool82_tx_drained_pkt_cnt_reg5_tx_drained_pkt_cnt {
      type oc-yang:counter64;
      description
        "Count number of packets that are transmitted by mac and dropped by the RS layer because the link is in fault state.";
    }
    leaf counter_slice1_ifg_mac_pool82_tx_drained_pkt_cnt_reg6_tx_drained_pkt_cnt {
      type oc-yang:counter64;
      description
        "Count number of packets that are transmitted by mac and dropped by the RS layer because the link is in fault state.";
    }
    leaf counter_slice1_ifg_mac_pool82_tx_drained_pkt_cnt_reg7_tx_drained_pkt_cnt {
      type oc-yang:counter64;
      description
        "Count number of packets that are transmitted by mac and dropped by the RS layer because the link is in fault state.";
    }
    leaf counter_slice1_ifg_mac_pool83_tx_drained_pkt_cnt_reg0_tx_drained_pkt_cnt {
      type oc-yang:counter64;
      description
        "Count number of packets that are transmitted by mac and dropped by the RS layer because the link is in fault state.";
    }
    leaf counter_slice1_ifg_mac_pool83_tx_drained_pkt_cnt_reg1_tx_drained_pkt_cnt {
      type oc-yang:counter64;
      description
        "Count number of packets that are transmitted by mac and dropped by the RS layer because the link is in fault state.";
    }
    leaf counter_slice1_ifg_mac_pool83_tx_drained_pkt_cnt_reg2_tx_drained_pkt_cnt {
      type oc-yang:counter64;
      description
        "Count number of packets that are transmitted by mac and dropped by the RS layer because the link is in fault state.";
    }
    leaf counter_slice1_ifg_mac_pool83_tx_drained_pkt_cnt_reg3_tx_drained_pkt_cnt {
      type oc-yang:counter64;
      description
        "Count number of packets that are transmitted by mac and dropped by the RS layer because the link is in fault state.";
    }
    leaf counter_slice1_ifg_mac_pool83_tx_drained_pkt_cnt_reg4_tx_drained_pkt_cnt {
      type oc-yang:counter64;
      description
        "Count number of packets that are transmitted by mac and dropped by the RS layer because the link is in fault state.";
    }
    leaf counter_slice1_ifg_mac_pool83_tx_drained_pkt_cnt_reg5_tx_drained_pkt_cnt {
      type oc-yang:counter64;
      description
        "Count number of packets that are transmitted by mac and dropped by the RS layer because the link is in fault state.";
    }
    leaf counter_slice1_ifg_mac_pool83_tx_drained_pkt_cnt_reg6_tx_drained_pkt_cnt {
      type oc-yang:counter64;
      description
        "Count number of packets that are transmitted by mac and dropped by the RS layer because the link is in fault state.";
    }
    leaf counter_slice1_ifg_mac_pool83_tx_drained_pkt_cnt_reg7_tx_drained_pkt_cnt {
      type oc-yang:counter64;
      description
        "Count number of packets that are transmitted by mac and dropped by the RS layer because the link is in fault state.";
    }
    leaf counter_slice1_ifg_mac_pool84_tx_drained_pkt_cnt_reg0_tx_drained_pkt_cnt {
      type oc-yang:counter64;
      description
        "Count number of packets that are transmitted by mac and dropped by the RS layer because the link is in fault state.";
    }
    leaf counter_slice1_ifg_mac_pool84_tx_drained_pkt_cnt_reg1_tx_drained_pkt_cnt {
      type oc-yang:counter64;
      description
        "Count number of packets that are transmitted by mac and dropped by the RS layer because the link is in fault state.";
    }
    leaf counter_slice1_ifg_mac_pool84_tx_drained_pkt_cnt_reg2_tx_drained_pkt_cnt {
      type oc-yang:counter64;
      description
        "Count number of packets that are transmitted by mac and dropped by the RS layer because the link is in fault state.";
    }
    leaf counter_slice1_ifg_mac_pool84_tx_drained_pkt_cnt_reg3_tx_drained_pkt_cnt {
      type oc-yang:counter64;
      description
        "Count number of packets that are transmitted by mac and dropped by the RS layer because the link is in fault state.";
    }
    leaf counter_slice1_ifg_mac_pool84_tx_drained_pkt_cnt_reg4_tx_drained_pkt_cnt {
      type oc-yang:counter64;
      description
        "Count number of packets that are transmitted by mac and dropped by the RS layer because the link is in fault state.";
    }
    leaf counter_slice1_ifg_mac_pool84_tx_drained_pkt_cnt_reg5_tx_drained_pkt_cnt {
      type oc-yang:counter64;
      description
        "Count number of packets that are transmitted by mac and dropped by the RS layer because the link is in fault state.";
    }
    leaf counter_slice1_ifg_mac_pool84_tx_drained_pkt_cnt_reg6_tx_drained_pkt_cnt {
      type oc-yang:counter64;
      description
        "Count number of packets that are transmitted by mac and dropped by the RS layer because the link is in fault state.";
    }
    leaf counter_slice1_ifg_mac_pool84_tx_drained_pkt_cnt_reg7_tx_drained_pkt_cnt {
      type oc-yang:counter64;
      description
        "Count number of packets that are transmitted by mac and dropped by the RS layer because the link is in fault state.";
    }
    leaf counter_slice1_ifg_mac_pool85_tx_drained_pkt_cnt_reg0_tx_drained_pkt_cnt {
      type oc-yang:counter64;
      description
        "Count number of packets that are transmitted by mac and dropped by the RS layer because the link is in fault state.";
    }
    leaf counter_slice1_ifg_mac_pool85_tx_drained_pkt_cnt_reg1_tx_drained_pkt_cnt {
      type oc-yang:counter64;
      description
        "Count number of packets that are transmitted by mac and dropped by the RS layer because the link is in fault state.";
    }
    leaf counter_slice1_ifg_mac_pool85_tx_drained_pkt_cnt_reg2_tx_drained_pkt_cnt {
      type oc-yang:counter64;
      description
        "Count number of packets that are transmitted by mac and dropped by the RS layer because the link is in fault state.";
    }
    leaf counter_slice1_ifg_mac_pool85_tx_drained_pkt_cnt_reg3_tx_drained_pkt_cnt {
      type oc-yang:counter64;
      description
        "Count number of packets that are transmitted by mac and dropped by the RS layer because the link is in fault state.";
    }
    leaf counter_slice1_ifg_mac_pool85_tx_drained_pkt_cnt_reg4_tx_drained_pkt_cnt {
      type oc-yang:counter64;
      description
        "Count number of packets that are transmitted by mac and dropped by the RS layer because the link is in fault state.";
    }
    leaf counter_slice1_ifg_mac_pool85_tx_drained_pkt_cnt_reg5_tx_drained_pkt_cnt {
      type oc-yang:counter64;
      description
        "Count number of packets that are transmitted by mac and dropped by the RS layer because the link is in fault state.";
    }
    leaf counter_slice1_ifg_mac_pool85_tx_drained_pkt_cnt_reg6_tx_drained_pkt_cnt {
      type oc-yang:counter64;
      description
        "Count number of packets that are transmitted by mac and dropped by the RS layer because the link is in fault state.";
    }
    leaf counter_slice1_ifg_mac_pool85_tx_drained_pkt_cnt_reg7_tx_drained_pkt_cnt {
      type oc-yang:counter64;
      description
        "Count number of packets that are transmitted by mac and dropped by the RS layer because the link is in fault state.";
    }
    leaf counter_slice1_ifg_mac_pool86_tx_drained_pkt_cnt_reg0_tx_drained_pkt_cnt {
      type oc-yang:counter64;
      description
        "Count number of packets that are transmitted by mac and dropped by the RS layer because the link is in fault state.";
    }
    leaf counter_slice1_ifg_mac_pool86_tx_drained_pkt_cnt_reg1_tx_drained_pkt_cnt {
      type oc-yang:counter64;
      description
        "Count number of packets that are transmitted by mac and dropped by the RS layer because the link is in fault state.";
    }
    leaf counter_slice1_ifg_mac_pool86_tx_drained_pkt_cnt_reg2_tx_drained_pkt_cnt {
      type oc-yang:counter64;
      description
        "Count number of packets that are transmitted by mac and dropped by the RS layer because the link is in fault state.";
    }
    leaf counter_slice1_ifg_mac_pool86_tx_drained_pkt_cnt_reg3_tx_drained_pkt_cnt {
      type oc-yang:counter64;
      description
        "Count number of packets that are transmitted by mac and dropped by the RS layer because the link is in fault state.";
    }
    leaf counter_slice1_ifg_mac_pool86_tx_drained_pkt_cnt_reg4_tx_drained_pkt_cnt {
      type oc-yang:counter64;
      description
        "Count number of packets that are transmitted by mac and dropped by the RS layer because the link is in fault state.";
    }
    leaf counter_slice1_ifg_mac_pool86_tx_drained_pkt_cnt_reg5_tx_drained_pkt_cnt {
      type oc-yang:counter64;
      description
        "Count number of packets that are transmitted by mac and dropped by the RS layer because the link is in fault state.";
    }
    leaf counter_slice1_ifg_mac_pool86_tx_drained_pkt_cnt_reg6_tx_drained_pkt_cnt {
      type oc-yang:counter64;
      description
        "Count number of packets that are transmitted by mac and dropped by the RS layer because the link is in fault state.";
    }
    leaf counter_slice1_ifg_mac_pool86_tx_drained_pkt_cnt_reg7_tx_drained_pkt_cnt {
      type oc-yang:counter64;
      description
        "Count number of packets that are transmitted by mac and dropped by the RS layer because the link is in fault state.";
    }
    leaf counter_slice1_ifg_mac_pool87_tx_drained_pkt_cnt_reg0_tx_drained_pkt_cnt {
      type oc-yang:counter64;
      description
        "Count number of packets that are transmitted by mac and dropped by the RS layer because the link is in fault state.";
    }
    leaf counter_slice1_ifg_mac_pool87_tx_drained_pkt_cnt_reg1_tx_drained_pkt_cnt {
      type oc-yang:counter64;
      description
        "Count number of packets that are transmitted by mac and dropped by the RS layer because the link is in fault state.";
    }
    leaf counter_slice1_ifg_mac_pool87_tx_drained_pkt_cnt_reg2_tx_drained_pkt_cnt {
      type oc-yang:counter64;
      description
        "Count number of packets that are transmitted by mac and dropped by the RS layer because the link is in fault state.";
    }
    leaf counter_slice1_ifg_mac_pool87_tx_drained_pkt_cnt_reg3_tx_drained_pkt_cnt {
      type oc-yang:counter64;
      description
        "Count number of packets that are transmitted by mac and dropped by the RS layer because the link is in fault state.";
    }
    leaf counter_slice1_ifg_mac_pool87_tx_drained_pkt_cnt_reg4_tx_drained_pkt_cnt {
      type oc-yang:counter64;
      description
        "Count number of packets that are transmitted by mac and dropped by the RS layer because the link is in fault state.";
    }
    leaf counter_slice1_ifg_mac_pool87_tx_drained_pkt_cnt_reg5_tx_drained_pkt_cnt {
      type oc-yang:counter64;
      description
        "Count number of packets that are transmitted by mac and dropped by the RS layer because the link is in fault state.";
    }
    leaf counter_slice1_ifg_mac_pool87_tx_drained_pkt_cnt_reg6_tx_drained_pkt_cnt {
      type oc-yang:counter64;
      description
        "Count number of packets that are transmitted by mac and dropped by the RS layer because the link is in fault state.";
    }
    leaf counter_slice1_ifg_mac_pool87_tx_drained_pkt_cnt_reg7_tx_drained_pkt_cnt {
      type oc-yang:counter64;
      description
        "Count number of packets that are transmitted by mac and dropped by the RS layer because the link is in fault state.";
    }
    leaf counter_slice2_ifg_mac_pool80_tx_drained_pkt_cnt_reg0_tx_drained_pkt_cnt {
      type oc-yang:counter64;
      description
        "Count number of packets that are transmitted by mac and dropped by the RS layer because the link is in fault state.";
    }
    leaf counter_slice2_ifg_mac_pool80_tx_drained_pkt_cnt_reg1_tx_drained_pkt_cnt {
      type oc-yang:counter64;
      description
        "Count number of packets that are transmitted by mac and dropped by the RS layer because the link is in fault state.";
    }
    leaf counter_slice2_ifg_mac_pool80_tx_drained_pkt_cnt_reg2_tx_drained_pkt_cnt {
      type oc-yang:counter64;
      description
        "Count number of packets that are transmitted by mac and dropped by the RS layer because the link is in fault state.";
    }
    leaf counter_slice2_ifg_mac_pool80_tx_drained_pkt_cnt_reg3_tx_drained_pkt_cnt {
      type oc-yang:counter64;
      description
        "Count number of packets that are transmitted by mac and dropped by the RS layer because the link is in fault state.";
    }
    leaf counter_slice2_ifg_mac_pool80_tx_drained_pkt_cnt_reg4_tx_drained_pkt_cnt {
      type oc-yang:counter64;
      description
        "Count number of packets that are transmitted by mac and dropped by the RS layer because the link is in fault state.";
    }
    leaf counter_slice2_ifg_mac_pool80_tx_drained_pkt_cnt_reg5_tx_drained_pkt_cnt {
      type oc-yang:counter64;
      description
        "Count number of packets that are transmitted by mac and dropped by the RS layer because the link is in fault state.";
    }
    leaf counter_slice2_ifg_mac_pool80_tx_drained_pkt_cnt_reg6_tx_drained_pkt_cnt {
      type oc-yang:counter64;
      description
        "Count number of packets that are transmitted by mac and dropped by the RS layer because the link is in fault state.";
    }
    leaf counter_slice2_ifg_mac_pool80_tx_drained_pkt_cnt_reg7_tx_drained_pkt_cnt {
      type oc-yang:counter64;
      description
        "Count number of packets that are transmitted by mac and dropped by the RS layer because the link is in fault state.";
    }
    leaf counter_slice2_ifg_mac_pool81_tx_drained_pkt_cnt_reg0_tx_drained_pkt_cnt {
      type oc-yang:counter64;
      description
        "Count number of packets that are transmitted by mac and dropped by the RS layer because the link is in fault state.";
    }
    leaf counter_slice2_ifg_mac_pool81_tx_drained_pkt_cnt_reg1_tx_drained_pkt_cnt {
      type oc-yang:counter64;
      description
        "Count number of packets that are transmitted by mac and dropped by the RS layer because the link is in fault state.";
    }
    leaf counter_slice2_ifg_mac_pool81_tx_drained_pkt_cnt_reg2_tx_drained_pkt_cnt {
      type oc-yang:counter64;
      description
        "Count number of packets that are transmitted by mac and dropped by the RS layer because the link is in fault state.";
    }
    leaf counter_slice2_ifg_mac_pool81_tx_drained_pkt_cnt_reg3_tx_drained_pkt_cnt {
      type oc-yang:counter64;
      description
        "Count number of packets that are transmitted by mac and dropped by the RS layer because the link is in fault state.";
    }
    leaf counter_slice2_ifg_mac_pool81_tx_drained_pkt_cnt_reg4_tx_drained_pkt_cnt {
      type oc-yang:counter64;
      description
        "Count number of packets that are transmitted by mac and dropped by the RS layer because the link is in fault state.";
    }
    leaf counter_slice2_ifg_mac_pool81_tx_drained_pkt_cnt_reg5_tx_drained_pkt_cnt {
      type oc-yang:counter64;
      description
        "Count number of packets that are transmitted by mac and dropped by the RS layer because the link is in fault state.";
    }
    leaf counter_slice2_ifg_mac_pool81_tx_drained_pkt_cnt_reg6_tx_drained_pkt_cnt {
      type oc-yang:counter64;
      description
        "Count number of packets that are transmitted by mac and dropped by the RS layer because the link is in fault state.";
    }
    leaf counter_slice2_ifg_mac_pool81_tx_drained_pkt_cnt_reg7_tx_drained_pkt_cnt {
      type oc-yang:counter64;
      description
        "Count number of packets that are transmitted by mac and dropped by the RS layer because the link is in fault state.";
    }
    leaf counter_slice2_ifg_mac_pool82_tx_drained_pkt_cnt_reg0_tx_drained_pkt_cnt {
      type oc-yang:counter64;
      description
        "Count number of packets that are transmitted by mac and dropped by the RS layer because the link is in fault state.";
    }
    leaf counter_slice2_ifg_mac_pool82_tx_drained_pkt_cnt_reg1_tx_drained_pkt_cnt {
      type oc-yang:counter64;
      description
        "Count number of packets that are transmitted by mac and dropped by the RS layer because the link is in fault state.";
    }
    leaf counter_slice2_ifg_mac_pool82_tx_drained_pkt_cnt_reg2_tx_drained_pkt_cnt {
      type oc-yang:counter64;
      description
        "Count number of packets that are transmitted by mac and dropped by the RS layer because the link is in fault state.";
    }
    leaf counter_slice2_ifg_mac_pool82_tx_drained_pkt_cnt_reg3_tx_drained_pkt_cnt {
      type oc-yang:counter64;
      description
        "Count number of packets that are transmitted by mac and dropped by the RS layer because the link is in fault state.";
    }
    leaf counter_slice2_ifg_mac_pool82_tx_drained_pkt_cnt_reg4_tx_drained_pkt_cnt {
      type oc-yang:counter64;
      description
        "Count number of packets that are transmitted by mac and dropped by the RS layer because the link is in fault state.";
    }
    leaf counter_slice2_ifg_mac_pool82_tx_drained_pkt_cnt_reg5_tx_drained_pkt_cnt {
      type oc-yang:counter64;
      description
        "Count number of packets that are transmitted by mac and dropped by the RS layer because the link is in fault state.";
    }
    leaf counter_slice2_ifg_mac_pool82_tx_drained_pkt_cnt_reg6_tx_drained_pkt_cnt {
      type oc-yang:counter64;
      description
        "Count number of packets that are transmitted by mac and dropped by the RS layer because the link is in fault state.";
    }
    leaf counter_slice2_ifg_mac_pool82_tx_drained_pkt_cnt_reg7_tx_drained_pkt_cnt {
      type oc-yang:counter64;
      description
        "Count number of packets that are transmitted by mac and dropped by the RS layer because the link is in fault state.";
    }
    leaf counter_slice2_ifg_mac_pool83_tx_drained_pkt_cnt_reg0_tx_drained_pkt_cnt {
      type oc-yang:counter64;
      description
        "Count number of packets that are transmitted by mac and dropped by the RS layer because the link is in fault state.";
    }
    leaf counter_slice2_ifg_mac_pool83_tx_drained_pkt_cnt_reg1_tx_drained_pkt_cnt {
      type oc-yang:counter64;
      description
        "Count number of packets that are transmitted by mac and dropped by the RS layer because the link is in fault state.";
    }
    leaf counter_slice2_ifg_mac_pool83_tx_drained_pkt_cnt_reg2_tx_drained_pkt_cnt {
      type oc-yang:counter64;
      description
        "Count number of packets that are transmitted by mac and dropped by the RS layer because the link is in fault state.";
    }
    leaf counter_slice2_ifg_mac_pool83_tx_drained_pkt_cnt_reg3_tx_drained_pkt_cnt {
      type oc-yang:counter64;
      description
        "Count number of packets that are transmitted by mac and dropped by the RS layer because the link is in fault state.";
    }
    leaf counter_slice2_ifg_mac_pool83_tx_drained_pkt_cnt_reg4_tx_drained_pkt_cnt {
      type oc-yang:counter64;
      description
        "Count number of packets that are transmitted by mac and dropped by the RS layer because the link is in fault state.";
    }
    leaf counter_slice2_ifg_mac_pool83_tx_drained_pkt_cnt_reg5_tx_drained_pkt_cnt {
      type oc-yang:counter64;
      description
        "Count number of packets that are transmitted by mac and dropped by the RS layer because the link is in fault state.";
    }
    leaf counter_slice2_ifg_mac_pool83_tx_drained_pkt_cnt_reg6_tx_drained_pkt_cnt {
      type oc-yang:counter64;
      description
        "Count number of packets that are transmitted by mac and dropped by the RS layer because the link is in fault state.";
    }
    leaf counter_slice2_ifg_mac_pool83_tx_drained_pkt_cnt_reg7_tx_drained_pkt_cnt {
      type oc-yang:counter64;
      description
        "Count number of packets that are transmitted by mac and dropped by the RS layer because the link is in fault state.";
    }
    leaf counter_slice2_ifg_mac_pool84_tx_drained_pkt_cnt_reg0_tx_drained_pkt_cnt {
      type oc-yang:counter64;
      description
        "Count number of packets that are transmitted by mac and dropped by the RS layer because the link is in fault state.";
    }
    leaf counter_slice2_ifg_mac_pool84_tx_drained_pkt_cnt_reg1_tx_drained_pkt_cnt {
      type oc-yang:counter64;
      description
        "Count number of packets that are transmitted by mac and dropped by the RS layer because the link is in fault state.";
    }
    leaf counter_slice2_ifg_mac_pool84_tx_drained_pkt_cnt_reg2_tx_drained_pkt_cnt {
      type oc-yang:counter64;
      description
        "Count number of packets that are transmitted by mac and dropped by the RS layer because the link is in fault state.";
    }
    leaf counter_slice2_ifg_mac_pool84_tx_drained_pkt_cnt_reg3_tx_drained_pkt_cnt {
      type oc-yang:counter64;
      description
        "Count number of packets that are transmitted by mac and dropped by the RS layer because the link is in fault state.";
    }
    leaf counter_slice2_ifg_mac_pool84_tx_drained_pkt_cnt_reg4_tx_drained_pkt_cnt {
      type oc-yang:counter64;
      description
        "Count number of packets that are transmitted by mac and dropped by the RS layer because the link is in fault state.";
    }
    leaf counter_slice2_ifg_mac_pool84_tx_drained_pkt_cnt_reg5_tx_drained_pkt_cnt {
      type oc-yang:counter64;
      description
        "Count number of packets that are transmitted by mac and dropped by the RS layer because the link is in fault state.";
    }
    leaf counter_slice2_ifg_mac_pool84_tx_drained_pkt_cnt_reg6_tx_drained_pkt_cnt {
      type oc-yang:counter64;
      description
        "Count number of packets that are transmitted by mac and dropped by the RS layer because the link is in fault state.";
    }
    leaf counter_slice2_ifg_mac_pool84_tx_drained_pkt_cnt_reg7_tx_drained_pkt_cnt {
      type oc-yang:counter64;
      description
        "Count number of packets that are transmitted by mac and dropped by the RS layer because the link is in fault state.";
    }
    leaf counter_slice2_ifg_mac_pool85_tx_drained_pkt_cnt_reg0_tx_drained_pkt_cnt {
      type oc-yang:counter64;
      description
        "Count number of packets that are transmitted by mac and dropped by the RS layer because the link is in fault state.";
    }
    leaf counter_slice2_ifg_mac_pool85_tx_drained_pkt_cnt_reg1_tx_drained_pkt_cnt {
      type oc-yang:counter64;
      description
        "Count number of packets that are transmitted by mac and dropped by the RS layer because the link is in fault state.";
    }
    leaf counter_slice2_ifg_mac_pool85_tx_drained_pkt_cnt_reg2_tx_drained_pkt_cnt {
      type oc-yang:counter64;
      description
        "Count number of packets that are transmitted by mac and dropped by the RS layer because the link is in fault state.";
    }
    leaf counter_slice2_ifg_mac_pool85_tx_drained_pkt_cnt_reg3_tx_drained_pkt_cnt {
      type oc-yang:counter64;
      description
        "Count number of packets that are transmitted by mac and dropped by the RS layer because the link is in fault state.";
    }
    leaf counter_slice2_ifg_mac_pool85_tx_drained_pkt_cnt_reg4_tx_drained_pkt_cnt {
      type oc-yang:counter64;
      description
        "Count number of packets that are transmitted by mac and dropped by the RS layer because the link is in fault state.";
    }
    leaf counter_slice2_ifg_mac_pool85_tx_drained_pkt_cnt_reg5_tx_drained_pkt_cnt {
      type oc-yang:counter64;
      description
        "Count number of packets that are transmitted by mac and dropped by the RS layer because the link is in fault state.";
    }
    leaf counter_slice2_ifg_mac_pool85_tx_drained_pkt_cnt_reg6_tx_drained_pkt_cnt {
      type oc-yang:counter64;
      description
        "Count number of packets that are transmitted by mac and dropped by the RS layer because the link is in fault state.";
    }
    leaf counter_slice2_ifg_mac_pool85_tx_drained_pkt_cnt_reg7_tx_drained_pkt_cnt {
      type oc-yang:counter64;
      description
        "Count number of packets that are transmitted by mac and dropped by the RS layer because the link is in fault state.";
    }
    leaf counter_slice2_ifg_mac_pool86_tx_drained_pkt_cnt_reg0_tx_drained_pkt_cnt {
      type oc-yang:counter64;
      description
        "Count number of packets that are transmitted by mac and dropped by the RS layer because the link is in fault state.";
    }
    leaf counter_slice2_ifg_mac_pool86_tx_drained_pkt_cnt_reg1_tx_drained_pkt_cnt {
      type oc-yang:counter64;
      description
        "Count number of packets that are transmitted by mac and dropped by the RS layer because the link is in fault state.";
    }
    leaf counter_slice2_ifg_mac_pool86_tx_drained_pkt_cnt_reg2_tx_drained_pkt_cnt {
      type oc-yang:counter64;
      description
        "Count number of packets that are transmitted by mac and dropped by the RS layer because the link is in fault state.";
    }
    leaf counter_slice2_ifg_mac_pool86_tx_drained_pkt_cnt_reg3_tx_drained_pkt_cnt {
      type oc-yang:counter64;
      description
        "Count number of packets that are transmitted by mac and dropped by the RS layer because the link is in fault state.";
    }
    leaf counter_slice2_ifg_mac_pool86_tx_drained_pkt_cnt_reg4_tx_drained_pkt_cnt {
      type oc-yang:counter64;
      description
        "Count number of packets that are transmitted by mac and dropped by the RS layer because the link is in fault state.";
    }
    leaf counter_slice2_ifg_mac_pool86_tx_drained_pkt_cnt_reg5_tx_drained_pkt_cnt {
      type oc-yang:counter64;
      description
        "Count number of packets that are transmitted by mac and dropped by the RS layer because the link is in fault state.";
    }
    leaf counter_slice2_ifg_mac_pool86_tx_drained_pkt_cnt_reg6_tx_drained_pkt_cnt {
      type oc-yang:counter64;
      description
        "Count number of packets that are transmitted by mac and dropped by the RS layer because the link is in fault state.";
    }
    leaf counter_slice2_ifg_mac_pool86_tx_drained_pkt_cnt_reg7_tx_drained_pkt_cnt {
      type oc-yang:counter64;
      description
        "Count number of packets that are transmitted by mac and dropped by the RS layer because the link is in fault state.";
    }
    leaf counter_slice2_ifg_mac_pool87_tx_drained_pkt_cnt_reg0_tx_drained_pkt_cnt {
      type oc-yang:counter64;
      description
        "Count number of packets that are transmitted by mac and dropped by the RS layer because the link is in fault state.";
    }
    leaf counter_slice2_ifg_mac_pool87_tx_drained_pkt_cnt_reg1_tx_drained_pkt_cnt {
      type oc-yang:counter64;
      description
        "Count number of packets that are transmitted by mac and dropped by the RS layer because the link is in fault state.";
    }
    leaf counter_slice2_ifg_mac_pool87_tx_drained_pkt_cnt_reg2_tx_drained_pkt_cnt {
      type oc-yang:counter64;
      description
        "Count number of packets that are transmitted by mac and dropped by the RS layer because the link is in fault state.";
    }
    leaf counter_slice2_ifg_mac_pool87_tx_drained_pkt_cnt_reg3_tx_drained_pkt_cnt {
      type oc-yang:counter64;
      description
        "Count number of packets that are transmitted by mac and dropped by the RS layer because the link is in fault state.";
    }
    leaf counter_slice2_ifg_mac_pool87_tx_drained_pkt_cnt_reg4_tx_drained_pkt_cnt {
      type oc-yang:counter64;
      description
        "Count number of packets that are transmitted by mac and dropped by the RS layer because the link is in fault state.";
    }
    leaf counter_slice2_ifg_mac_pool87_tx_drained_pkt_cnt_reg5_tx_drained_pkt_cnt {
      type oc-yang:counter64;
      description
        "Count number of packets that are transmitted by mac and dropped by the RS layer because the link is in fault state.";
    }
    leaf counter_slice2_ifg_mac_pool87_tx_drained_pkt_cnt_reg6_tx_drained_pkt_cnt {
      type oc-yang:counter64;
      description
        "Count number of packets that are transmitted by mac and dropped by the RS layer because the link is in fault state.";
    }
    leaf counter_slice2_ifg_mac_pool87_tx_drained_pkt_cnt_reg7_tx_drained_pkt_cnt {
      type oc-yang:counter64;
      description
        "Count number of packets that are transmitted by mac and dropped by the RS layer because the link is in fault state.";
    }
    leaf counter_slice3_ifg_mac_pool80_tx_drained_pkt_cnt_reg0_tx_drained_pkt_cnt {
      type oc-yang:counter64;
      description
        "Count number of packets that are transmitted by mac and dropped by the RS layer because the link is in fault state.";
    }
    leaf counter_slice3_ifg_mac_pool80_tx_drained_pkt_cnt_reg1_tx_drained_pkt_cnt {
      type oc-yang:counter64;
      description
        "Count number of packets that are transmitted by mac and dropped by the RS layer because the link is in fault state.";
    }
    leaf counter_slice3_ifg_mac_pool80_tx_drained_pkt_cnt_reg2_tx_drained_pkt_cnt {
      type oc-yang:counter64;
      description
        "Count number of packets that are transmitted by mac and dropped by the RS layer because the link is in fault state.";
    }
    leaf counter_slice3_ifg_mac_pool80_tx_drained_pkt_cnt_reg3_tx_drained_pkt_cnt {
      type oc-yang:counter64;
      description
        "Count number of packets that are transmitted by mac and dropped by the RS layer because the link is in fault state.";
    }
    leaf counter_slice3_ifg_mac_pool80_tx_drained_pkt_cnt_reg4_tx_drained_pkt_cnt {
      type oc-yang:counter64;
      description
        "Count number of packets that are transmitted by mac and dropped by the RS layer because the link is in fault state.";
    }
    leaf counter_slice3_ifg_mac_pool80_tx_drained_pkt_cnt_reg5_tx_drained_pkt_cnt {
      type oc-yang:counter64;
      description
        "Count number of packets that are transmitted by mac and dropped by the RS layer because the link is in fault state.";
    }
    leaf counter_slice3_ifg_mac_pool80_tx_drained_pkt_cnt_reg6_tx_drained_pkt_cnt {
      type oc-yang:counter64;
      description
        "Count number of packets that are transmitted by mac and dropped by the RS layer because the link is in fault state.";
    }
    leaf counter_slice3_ifg_mac_pool80_tx_drained_pkt_cnt_reg7_tx_drained_pkt_cnt {
      type oc-yang:counter64;
      description
        "Count number of packets that are transmitted by mac and dropped by the RS layer because the link is in fault state.";
    }
    leaf counter_slice3_ifg_mac_pool81_tx_drained_pkt_cnt_reg0_tx_drained_pkt_cnt {
      type oc-yang:counter64;
      description
        "Count number of packets that are transmitted by mac and dropped by the RS layer because the link is in fault state.";
    }
    leaf counter_slice3_ifg_mac_pool81_tx_drained_pkt_cnt_reg1_tx_drained_pkt_cnt {
      type oc-yang:counter64;
      description
        "Count number of packets that are transmitted by mac and dropped by the RS layer because the link is in fault state.";
    }
    leaf counter_slice3_ifg_mac_pool81_tx_drained_pkt_cnt_reg2_tx_drained_pkt_cnt {
      type oc-yang:counter64;
      description
        "Count number of packets that are transmitted by mac and dropped by the RS layer because the link is in fault state.";
    }
    leaf counter_slice3_ifg_mac_pool81_tx_drained_pkt_cnt_reg3_tx_drained_pkt_cnt {
      type oc-yang:counter64;
      description
        "Count number of packets that are transmitted by mac and dropped by the RS layer because the link is in fault state.";
    }
    leaf counter_slice3_ifg_mac_pool81_tx_drained_pkt_cnt_reg4_tx_drained_pkt_cnt {
      type oc-yang:counter64;
      description
        "Count number of packets that are transmitted by mac and dropped by the RS layer because the link is in fault state.";
    }
    leaf counter_slice3_ifg_mac_pool81_tx_drained_pkt_cnt_reg5_tx_drained_pkt_cnt {
      type oc-yang:counter64;
      description
        "Count number of packets that are transmitted by mac and dropped by the RS layer because the link is in fault state.";
    }
    leaf counter_slice3_ifg_mac_pool81_tx_drained_pkt_cnt_reg6_tx_drained_pkt_cnt {
      type oc-yang:counter64;
      description
        "Count number of packets that are transmitted by mac and dropped by the RS layer because the link is in fault state.";
    }
    leaf counter_slice3_ifg_mac_pool81_tx_drained_pkt_cnt_reg7_tx_drained_pkt_cnt {
      type oc-yang:counter64;
      description
        "Count number of packets that are transmitted by mac and dropped by the RS layer because the link is in fault state.";
    }
    leaf counter_slice3_ifg_mac_pool82_tx_drained_pkt_cnt_reg0_tx_drained_pkt_cnt {
      type oc-yang:counter64;
      description
        "Count number of packets that are transmitted by mac and dropped by the RS layer because the link is in fault state.";
    }
    leaf counter_slice3_ifg_mac_pool82_tx_drained_pkt_cnt_reg1_tx_drained_pkt_cnt {
      type oc-yang:counter64;
      description
        "Count number of packets that are transmitted by mac and dropped by the RS layer because the link is in fault state.";
    }
    leaf counter_slice3_ifg_mac_pool82_tx_drained_pkt_cnt_reg2_tx_drained_pkt_cnt {
      type oc-yang:counter64;
      description
        "Count number of packets that are transmitted by mac and dropped by the RS layer because the link is in fault state.";
    }
    leaf counter_slice3_ifg_mac_pool82_tx_drained_pkt_cnt_reg3_tx_drained_pkt_cnt {
      type oc-yang:counter64;
      description
        "Count number of packets that are transmitted by mac and dropped by the RS layer because the link is in fault state.";
    }
    leaf counter_slice3_ifg_mac_pool82_tx_drained_pkt_cnt_reg4_tx_drained_pkt_cnt {
      type oc-yang:counter64;
      description
        "Count number of packets that are transmitted by mac and dropped by the RS layer because the link is in fault state.";
    }
    leaf counter_slice3_ifg_mac_pool82_tx_drained_pkt_cnt_reg5_tx_drained_pkt_cnt {
      type oc-yang:counter64;
      description
        "Count number of packets that are transmitted by mac and dropped by the RS layer because the link is in fault state.";
    }
    leaf counter_slice3_ifg_mac_pool82_tx_drained_pkt_cnt_reg6_tx_drained_pkt_cnt {
      type oc-yang:counter64;
      description
        "Count number of packets that are transmitted by mac and dropped by the RS layer because the link is in fault state.";
    }
    leaf counter_slice3_ifg_mac_pool82_tx_drained_pkt_cnt_reg7_tx_drained_pkt_cnt {
      type oc-yang:counter64;
      description
        "Count number of packets that are transmitted by mac and dropped by the RS layer because the link is in fault state.";
    }
    leaf counter_slice3_ifg_mac_pool83_tx_drained_pkt_cnt_reg0_tx_drained_pkt_cnt {
      type oc-yang:counter64;
      description
        "Count number of packets that are transmitted by mac and dropped by the RS layer because the link is in fault state.";
    }
    leaf counter_slice3_ifg_mac_pool83_tx_drained_pkt_cnt_reg1_tx_drained_pkt_cnt {
      type oc-yang:counter64;
      description
        "Count number of packets that are transmitted by mac and dropped by the RS layer because the link is in fault state.";
    }
    leaf counter_slice3_ifg_mac_pool83_tx_drained_pkt_cnt_reg2_tx_drained_pkt_cnt {
      type oc-yang:counter64;
      description
        "Count number of packets that are transmitted by mac and dropped by the RS layer because the link is in fault state.";
    }
    leaf counter_slice3_ifg_mac_pool83_tx_drained_pkt_cnt_reg3_tx_drained_pkt_cnt {
      type oc-yang:counter64;
      description
        "Count number of packets that are transmitted by mac and dropped by the RS layer because the link is in fault state.";
    }
    leaf counter_slice3_ifg_mac_pool83_tx_drained_pkt_cnt_reg4_tx_drained_pkt_cnt {
      type oc-yang:counter64;
      description
        "Count number of packets that are transmitted by mac and dropped by the RS layer because the link is in fault state.";
    }
    leaf counter_slice3_ifg_mac_pool83_tx_drained_pkt_cnt_reg5_tx_drained_pkt_cnt {
      type oc-yang:counter64;
      description
        "Count number of packets that are transmitted by mac and dropped by the RS layer because the link is in fault state.";
    }
    leaf counter_slice3_ifg_mac_pool83_tx_drained_pkt_cnt_reg6_tx_drained_pkt_cnt {
      type oc-yang:counter64;
      description
        "Count number of packets that are transmitted by mac and dropped by the RS layer because the link is in fault state.";
    }
    leaf counter_slice3_ifg_mac_pool83_tx_drained_pkt_cnt_reg7_tx_drained_pkt_cnt {
      type oc-yang:counter64;
      description
        "Count number of packets that are transmitted by mac and dropped by the RS layer because the link is in fault state.";
    }
    leaf counter_slice3_ifg_mac_pool84_tx_drained_pkt_cnt_reg0_tx_drained_pkt_cnt {
      type oc-yang:counter64;
      description
        "Count number of packets that are transmitted by mac and dropped by the RS layer because the link is in fault state.";
    }
    leaf counter_slice3_ifg_mac_pool84_tx_drained_pkt_cnt_reg1_tx_drained_pkt_cnt {
      type oc-yang:counter64;
      description
        "Count number of packets that are transmitted by mac and dropped by the RS layer because the link is in fault state.";
    }
    leaf counter_slice3_ifg_mac_pool84_tx_drained_pkt_cnt_reg2_tx_drained_pkt_cnt {
      type oc-yang:counter64;
      description
        "Count number of packets that are transmitted by mac and dropped by the RS layer because the link is in fault state.";
    }
    leaf counter_slice3_ifg_mac_pool84_tx_drained_pkt_cnt_reg3_tx_drained_pkt_cnt {
      type oc-yang:counter64;
      description
        "Count number of packets that are transmitted by mac and dropped by the RS layer because the link is in fault state.";
    }
    leaf counter_slice3_ifg_mac_pool84_tx_drained_pkt_cnt_reg4_tx_drained_pkt_cnt {
      type oc-yang:counter64;
      description
        "Count number of packets that are transmitted by mac and dropped by the RS layer because the link is in fault state.";
    }
    leaf counter_slice3_ifg_mac_pool84_tx_drained_pkt_cnt_reg5_tx_drained_pkt_cnt {
      type oc-yang:counter64;
      description
        "Count number of packets that are transmitted by mac and dropped by the RS layer because the link is in fault state.";
    }
    leaf counter_slice3_ifg_mac_pool84_tx_drained_pkt_cnt_reg6_tx_drained_pkt_cnt {
      type oc-yang:counter64;
      description
        "Count number of packets that are transmitted by mac and dropped by the RS layer because the link is in fault state.";
    }
    leaf counter_slice3_ifg_mac_pool84_tx_drained_pkt_cnt_reg7_tx_drained_pkt_cnt {
      type oc-yang:counter64;
      description
        "Count number of packets that are transmitted by mac and dropped by the RS layer because the link is in fault state.";
    }
    leaf counter_slice3_ifg_mac_pool85_tx_drained_pkt_cnt_reg0_tx_drained_pkt_cnt {
      type oc-yang:counter64;
      description
        "Count number of packets that are transmitted by mac and dropped by the RS layer because the link is in fault state.";
    }
    leaf counter_slice3_ifg_mac_pool85_tx_drained_pkt_cnt_reg1_tx_drained_pkt_cnt {
      type oc-yang:counter64;
      description
        "Count number of packets that are transmitted by mac and dropped by the RS layer because the link is in fault state.";
    }
    leaf counter_slice3_ifg_mac_pool85_tx_drained_pkt_cnt_reg2_tx_drained_pkt_cnt {
      type oc-yang:counter64;
      description
        "Count number of packets that are transmitted by mac and dropped by the RS layer because the link is in fault state.";
    }
    leaf counter_slice3_ifg_mac_pool85_tx_drained_pkt_cnt_reg3_tx_drained_pkt_cnt {
      type oc-yang:counter64;
      description
        "Count number of packets that are transmitted by mac and dropped by the RS layer because the link is in fault state.";
    }
    leaf counter_slice3_ifg_mac_pool85_tx_drained_pkt_cnt_reg4_tx_drained_pkt_cnt {
      type oc-yang:counter64;
      description
        "Count number of packets that are transmitted by mac and dropped by the RS layer because the link is in fault state.";
    }
    leaf counter_slice3_ifg_mac_pool85_tx_drained_pkt_cnt_reg5_tx_drained_pkt_cnt {
      type oc-yang:counter64;
      description
        "Count number of packets that are transmitted by mac and dropped by the RS layer because the link is in fault state.";
    }
    leaf counter_slice3_ifg_mac_pool85_tx_drained_pkt_cnt_reg6_tx_drained_pkt_cnt {
      type oc-yang:counter64;
      description
        "Count number of packets that are transmitted by mac and dropped by the RS layer because the link is in fault state.";
    }
    leaf counter_slice3_ifg_mac_pool85_tx_drained_pkt_cnt_reg7_tx_drained_pkt_cnt {
      type oc-yang:counter64;
      description
        "Count number of packets that are transmitted by mac and dropped by the RS layer because the link is in fault state.";
    }
    leaf counter_slice3_ifg_mac_pool86_tx_drained_pkt_cnt_reg0_tx_drained_pkt_cnt {
      type oc-yang:counter64;
      description
        "Count number of packets that are transmitted by mac and dropped by the RS layer because the link is in fault state.";
    }
    leaf counter_slice3_ifg_mac_pool86_tx_drained_pkt_cnt_reg1_tx_drained_pkt_cnt {
      type oc-yang:counter64;
      description
        "Count number of packets that are transmitted by mac and dropped by the RS layer because the link is in fault state.";
    }
    leaf counter_slice3_ifg_mac_pool86_tx_drained_pkt_cnt_reg2_tx_drained_pkt_cnt {
      type oc-yang:counter64;
      description
        "Count number of packets that are transmitted by mac and dropped by the RS layer because the link is in fault state.";
    }
    leaf counter_slice3_ifg_mac_pool86_tx_drained_pkt_cnt_reg3_tx_drained_pkt_cnt {
      type oc-yang:counter64;
      description
        "Count number of packets that are transmitted by mac and dropped by the RS layer because the link is in fault state.";
    }
    leaf counter_slice3_ifg_mac_pool86_tx_drained_pkt_cnt_reg4_tx_drained_pkt_cnt {
      type oc-yang:counter64;
      description
        "Count number of packets that are transmitted by mac and dropped by the RS layer because the link is in fault state.";
    }
    leaf counter_slice3_ifg_mac_pool86_tx_drained_pkt_cnt_reg5_tx_drained_pkt_cnt {
      type oc-yang:counter64;
      description
        "Count number of packets that are transmitted by mac and dropped by the RS layer because the link is in fault state.";
    }
    leaf counter_slice3_ifg_mac_pool86_tx_drained_pkt_cnt_reg6_tx_drained_pkt_cnt {
      type oc-yang:counter64;
      description
        "Count number of packets that are transmitted by mac and dropped by the RS layer because the link is in fault state.";
    }
    leaf counter_slice3_ifg_mac_pool86_tx_drained_pkt_cnt_reg7_tx_drained_pkt_cnt {
      type oc-yang:counter64;
      description
        "Count number of packets that are transmitted by mac and dropped by the RS layer because the link is in fault state.";
    }
    leaf counter_slice3_ifg_mac_pool87_tx_drained_pkt_cnt_reg0_tx_drained_pkt_cnt {
      type oc-yang:counter64;
      description
        "Count number of packets that are transmitted by mac and dropped by the RS layer because the link is in fault state.";
    }
    leaf counter_slice3_ifg_mac_pool87_tx_drained_pkt_cnt_reg1_tx_drained_pkt_cnt {
      type oc-yang:counter64;
      description
        "Count number of packets that are transmitted by mac and dropped by the RS layer because the link is in fault state.";
    }
    leaf counter_slice3_ifg_mac_pool87_tx_drained_pkt_cnt_reg2_tx_drained_pkt_cnt {
      type oc-yang:counter64;
      description
        "Count number of packets that are transmitted by mac and dropped by the RS layer because the link is in fault state.";
    }
    leaf counter_slice3_ifg_mac_pool87_tx_drained_pkt_cnt_reg3_tx_drained_pkt_cnt {
      type oc-yang:counter64;
      description
        "Count number of packets that are transmitted by mac and dropped by the RS layer because the link is in fault state.";
    }
    leaf counter_slice3_ifg_mac_pool87_tx_drained_pkt_cnt_reg4_tx_drained_pkt_cnt {
      type oc-yang:counter64;
      description
        "Count number of packets that are transmitted by mac and dropped by the RS layer because the link is in fault state.";
    }
    leaf counter_slice3_ifg_mac_pool87_tx_drained_pkt_cnt_reg5_tx_drained_pkt_cnt {
      type oc-yang:counter64;
      description
        "Count number of packets that are transmitted by mac and dropped by the RS layer because the link is in fault state.";
    }
    leaf counter_slice3_ifg_mac_pool87_tx_drained_pkt_cnt_reg6_tx_drained_pkt_cnt {
      type oc-yang:counter64;
      description
        "Count number of packets that are transmitted by mac and dropped by the RS layer because the link is in fault state.";
    }
    leaf counter_slice3_ifg_mac_pool87_tx_drained_pkt_cnt_reg7_tx_drained_pkt_cnt {
      type oc-yang:counter64;
      description
        "Count number of packets that are transmitted by mac and dropped by the RS layer because the link is in fault state.";
    }
    leaf counter_slice4_ifg_mac_pool80_tx_drained_pkt_cnt_reg0_tx_drained_pkt_cnt {
      type oc-yang:counter64;
      description
        "Count number of packets that are transmitted by mac and dropped by the RS layer because the link is in fault state.";
    }
    leaf counter_slice4_ifg_mac_pool80_tx_drained_pkt_cnt_reg1_tx_drained_pkt_cnt {
      type oc-yang:counter64;
      description
        "Count number of packets that are transmitted by mac and dropped by the RS layer because the link is in fault state.";
    }
    leaf counter_slice4_ifg_mac_pool80_tx_drained_pkt_cnt_reg2_tx_drained_pkt_cnt {
      type oc-yang:counter64;
      description
        "Count number of packets that are transmitted by mac and dropped by the RS layer because the link is in fault state.";
    }
    leaf counter_slice4_ifg_mac_pool80_tx_drained_pkt_cnt_reg3_tx_drained_pkt_cnt {
      type oc-yang:counter64;
      description
        "Count number of packets that are transmitted by mac and dropped by the RS layer because the link is in fault state.";
    }
    leaf counter_slice4_ifg_mac_pool80_tx_drained_pkt_cnt_reg4_tx_drained_pkt_cnt {
      type oc-yang:counter64;
      description
        "Count number of packets that are transmitted by mac and dropped by the RS layer because the link is in fault state.";
    }
    leaf counter_slice4_ifg_mac_pool80_tx_drained_pkt_cnt_reg5_tx_drained_pkt_cnt {
      type oc-yang:counter64;
      description
        "Count number of packets that are transmitted by mac and dropped by the RS layer because the link is in fault state.";
    }
    leaf counter_slice4_ifg_mac_pool80_tx_drained_pkt_cnt_reg6_tx_drained_pkt_cnt {
      type oc-yang:counter64;
      description
        "Count number of packets that are transmitted by mac and dropped by the RS layer because the link is in fault state.";
    }
    leaf counter_slice4_ifg_mac_pool80_tx_drained_pkt_cnt_reg7_tx_drained_pkt_cnt {
      type oc-yang:counter64;
      description
        "Count number of packets that are transmitted by mac and dropped by the RS layer because the link is in fault state.";
    }
    leaf counter_slice4_ifg_mac_pool81_tx_drained_pkt_cnt_reg0_tx_drained_pkt_cnt {
      type oc-yang:counter64;
      description
        "Count number of packets that are transmitted by mac and dropped by the RS layer because the link is in fault state.";
    }
    leaf counter_slice4_ifg_mac_pool81_tx_drained_pkt_cnt_reg1_tx_drained_pkt_cnt {
      type oc-yang:counter64;
      description
        "Count number of packets that are transmitted by mac and dropped by the RS layer because the link is in fault state.";
    }
    leaf counter_slice4_ifg_mac_pool81_tx_drained_pkt_cnt_reg2_tx_drained_pkt_cnt {
      type oc-yang:counter64;
      description
        "Count number of packets that are transmitted by mac and dropped by the RS layer because the link is in fault state.";
    }
    leaf counter_slice4_ifg_mac_pool81_tx_drained_pkt_cnt_reg3_tx_drained_pkt_cnt {
      type oc-yang:counter64;
      description
        "Count number of packets that are transmitted by mac and dropped by the RS layer because the link is in fault state.";
    }
    leaf counter_slice4_ifg_mac_pool81_tx_drained_pkt_cnt_reg4_tx_drained_pkt_cnt {
      type oc-yang:counter64;
      description
        "Count number of packets that are transmitted by mac and dropped by the RS layer because the link is in fault state.";
    }
    leaf counter_slice4_ifg_mac_pool81_tx_drained_pkt_cnt_reg5_tx_drained_pkt_cnt {
      type oc-yang:counter64;
      description
        "Count number of packets that are transmitted by mac and dropped by the RS layer because the link is in fault state.";
    }
    leaf counter_slice4_ifg_mac_pool81_tx_drained_pkt_cnt_reg6_tx_drained_pkt_cnt {
      type oc-yang:counter64;
      description
        "Count number of packets that are transmitted by mac and dropped by the RS layer because the link is in fault state.";
    }
    leaf counter_slice4_ifg_mac_pool81_tx_drained_pkt_cnt_reg7_tx_drained_pkt_cnt {
      type oc-yang:counter64;
      description
        "Count number of packets that are transmitted by mac and dropped by the RS layer because the link is in fault state.";
    }
    leaf counter_slice4_ifg_mac_pool82_tx_drained_pkt_cnt_reg0_tx_drained_pkt_cnt {
      type oc-yang:counter64;
      description
        "Count number of packets that are transmitted by mac and dropped by the RS layer because the link is in fault state.";
    }
    leaf counter_slice4_ifg_mac_pool82_tx_drained_pkt_cnt_reg1_tx_drained_pkt_cnt {
      type oc-yang:counter64;
      description
        "Count number of packets that are transmitted by mac and dropped by the RS layer because the link is in fault state.";
    }
    leaf counter_slice4_ifg_mac_pool82_tx_drained_pkt_cnt_reg2_tx_drained_pkt_cnt {
      type oc-yang:counter64;
      description
        "Count number of packets that are transmitted by mac and dropped by the RS layer because the link is in fault state.";
    }
    leaf counter_slice4_ifg_mac_pool82_tx_drained_pkt_cnt_reg3_tx_drained_pkt_cnt {
      type oc-yang:counter64;
      description
        "Count number of packets that are transmitted by mac and dropped by the RS layer because the link is in fault state.";
    }
    leaf counter_slice4_ifg_mac_pool82_tx_drained_pkt_cnt_reg4_tx_drained_pkt_cnt {
      type oc-yang:counter64;
      description
        "Count number of packets that are transmitted by mac and dropped by the RS layer because the link is in fault state.";
    }
    leaf counter_slice4_ifg_mac_pool82_tx_drained_pkt_cnt_reg5_tx_drained_pkt_cnt {
      type oc-yang:counter64;
      description
        "Count number of packets that are transmitted by mac and dropped by the RS layer because the link is in fault state.";
    }
    leaf counter_slice4_ifg_mac_pool82_tx_drained_pkt_cnt_reg6_tx_drained_pkt_cnt {
      type oc-yang:counter64;
      description
        "Count number of packets that are transmitted by mac and dropped by the RS layer because the link is in fault state.";
    }
    leaf counter_slice4_ifg_mac_pool82_tx_drained_pkt_cnt_reg7_tx_drained_pkt_cnt {
      type oc-yang:counter64;
      description
        "Count number of packets that are transmitted by mac and dropped by the RS layer because the link is in fault state.";
    }
    leaf counter_slice4_ifg_mac_pool83_tx_drained_pkt_cnt_reg0_tx_drained_pkt_cnt {
      type oc-yang:counter64;
      description
        "Count number of packets that are transmitted by mac and dropped by the RS layer because the link is in fault state.";
    }
    leaf counter_slice4_ifg_mac_pool83_tx_drained_pkt_cnt_reg1_tx_drained_pkt_cnt {
      type oc-yang:counter64;
      description
        "Count number of packets that are transmitted by mac and dropped by the RS layer because the link is in fault state.";
    }
    leaf counter_slice4_ifg_mac_pool83_tx_drained_pkt_cnt_reg2_tx_drained_pkt_cnt {
      type oc-yang:counter64;
      description
        "Count number of packets that are transmitted by mac and dropped by the RS layer because the link is in fault state.";
    }
    leaf counter_slice4_ifg_mac_pool83_tx_drained_pkt_cnt_reg3_tx_drained_pkt_cnt {
      type oc-yang:counter64;
      description
        "Count number of packets that are transmitted by mac and dropped by the RS layer because the link is in fault state.";
    }
    leaf counter_slice4_ifg_mac_pool83_tx_drained_pkt_cnt_reg4_tx_drained_pkt_cnt {
      type oc-yang:counter64;
      description
        "Count number of packets that are transmitted by mac and dropped by the RS layer because the link is in fault state.";
    }
    leaf counter_slice4_ifg_mac_pool83_tx_drained_pkt_cnt_reg5_tx_drained_pkt_cnt {
      type oc-yang:counter64;
      description
        "Count number of packets that are transmitted by mac and dropped by the RS layer because the link is in fault state.";
    }
    leaf counter_slice4_ifg_mac_pool83_tx_drained_pkt_cnt_reg6_tx_drained_pkt_cnt {
      type oc-yang:counter64;
      description
        "Count number of packets that are transmitted by mac and dropped by the RS layer because the link is in fault state.";
    }
    leaf counter_slice4_ifg_mac_pool83_tx_drained_pkt_cnt_reg7_tx_drained_pkt_cnt {
      type oc-yang:counter64;
      description
        "Count number of packets that are transmitted by mac and dropped by the RS layer because the link is in fault state.";
    }
    leaf counter_slice4_ifg_mac_pool84_tx_drained_pkt_cnt_reg0_tx_drained_pkt_cnt {
      type oc-yang:counter64;
      description
        "Count number of packets that are transmitted by mac and dropped by the RS layer because the link is in fault state.";
    }
    leaf counter_slice4_ifg_mac_pool84_tx_drained_pkt_cnt_reg1_tx_drained_pkt_cnt {
      type oc-yang:counter64;
      description
        "Count number of packets that are transmitted by mac and dropped by the RS layer because the link is in fault state.";
    }
    leaf counter_slice4_ifg_mac_pool84_tx_drained_pkt_cnt_reg2_tx_drained_pkt_cnt {
      type oc-yang:counter64;
      description
        "Count number of packets that are transmitted by mac and dropped by the RS layer because the link is in fault state.";
    }
    leaf counter_slice4_ifg_mac_pool84_tx_drained_pkt_cnt_reg3_tx_drained_pkt_cnt {
      type oc-yang:counter64;
      description
        "Count number of packets that are transmitted by mac and dropped by the RS layer because the link is in fault state.";
    }
    leaf counter_slice4_ifg_mac_pool84_tx_drained_pkt_cnt_reg4_tx_drained_pkt_cnt {
      type oc-yang:counter64;
      description
        "Count number of packets that are transmitted by mac and dropped by the RS layer because the link is in fault state.";
    }
    leaf counter_slice4_ifg_mac_pool84_tx_drained_pkt_cnt_reg5_tx_drained_pkt_cnt {
      type oc-yang:counter64;
      description
        "Count number of packets that are transmitted by mac and dropped by the RS layer because the link is in fault state.";
    }
    leaf counter_slice4_ifg_mac_pool84_tx_drained_pkt_cnt_reg6_tx_drained_pkt_cnt {
      type oc-yang:counter64;
      description
        "Count number of packets that are transmitted by mac and dropped by the RS layer because the link is in fault state.";
    }
    leaf counter_slice4_ifg_mac_pool84_tx_drained_pkt_cnt_reg7_tx_drained_pkt_cnt {
      type oc-yang:counter64;
      description
        "Count number of packets that are transmitted by mac and dropped by the RS layer because the link is in fault state.";
    }
    leaf counter_slice4_ifg_mac_pool85_tx_drained_pkt_cnt_reg0_tx_drained_pkt_cnt {
      type oc-yang:counter64;
      description
        "Count number of packets that are transmitted by mac and dropped by the RS layer because the link is in fault state.";
    }
    leaf counter_slice4_ifg_mac_pool85_tx_drained_pkt_cnt_reg1_tx_drained_pkt_cnt {
      type oc-yang:counter64;
      description
        "Count number of packets that are transmitted by mac and dropped by the RS layer because the link is in fault state.";
    }
    leaf counter_slice4_ifg_mac_pool85_tx_drained_pkt_cnt_reg2_tx_drained_pkt_cnt {
      type oc-yang:counter64;
      description
        "Count number of packets that are transmitted by mac and dropped by the RS layer because the link is in fault state.";
    }
    leaf counter_slice4_ifg_mac_pool85_tx_drained_pkt_cnt_reg3_tx_drained_pkt_cnt {
      type oc-yang:counter64;
      description
        "Count number of packets that are transmitted by mac and dropped by the RS layer because the link is in fault state.";
    }
    leaf counter_slice4_ifg_mac_pool85_tx_drained_pkt_cnt_reg4_tx_drained_pkt_cnt {
      type oc-yang:counter64;
      description
        "Count number of packets that are transmitted by mac and dropped by the RS layer because the link is in fault state.";
    }
    leaf counter_slice4_ifg_mac_pool85_tx_drained_pkt_cnt_reg5_tx_drained_pkt_cnt {
      type oc-yang:counter64;
      description
        "Count number of packets that are transmitted by mac and dropped by the RS layer because the link is in fault state.";
    }
    leaf counter_slice4_ifg_mac_pool85_tx_drained_pkt_cnt_reg6_tx_drained_pkt_cnt {
      type oc-yang:counter64;
      description
        "Count number of packets that are transmitted by mac and dropped by the RS layer because the link is in fault state.";
    }
    leaf counter_slice4_ifg_mac_pool85_tx_drained_pkt_cnt_reg7_tx_drained_pkt_cnt {
      type oc-yang:counter64;
      description
        "Count number of packets that are transmitted by mac and dropped by the RS layer because the link is in fault state.";
    }
    leaf counter_slice4_ifg_mac_pool86_tx_drained_pkt_cnt_reg0_tx_drained_pkt_cnt {
      type oc-yang:counter64;
      description
        "Count number of packets that are transmitted by mac and dropped by the RS layer because the link is in fault state.";
    }
    leaf counter_slice4_ifg_mac_pool86_tx_drained_pkt_cnt_reg1_tx_drained_pkt_cnt {
      type oc-yang:counter64;
      description
        "Count number of packets that are transmitted by mac and dropped by the RS layer because the link is in fault state.";
    }
    leaf counter_slice4_ifg_mac_pool86_tx_drained_pkt_cnt_reg2_tx_drained_pkt_cnt {
      type oc-yang:counter64;
      description
        "Count number of packets that are transmitted by mac and dropped by the RS layer because the link is in fault state.";
    }
    leaf counter_slice4_ifg_mac_pool86_tx_drained_pkt_cnt_reg3_tx_drained_pkt_cnt {
      type oc-yang:counter64;
      description
        "Count number of packets that are transmitted by mac and dropped by the RS layer because the link is in fault state.";
    }
    leaf counter_slice4_ifg_mac_pool86_tx_drained_pkt_cnt_reg4_tx_drained_pkt_cnt {
      type oc-yang:counter64;
      description
        "Count number of packets that are transmitted by mac and dropped by the RS layer because the link is in fault state.";
    }
    leaf counter_slice4_ifg_mac_pool86_tx_drained_pkt_cnt_reg5_tx_drained_pkt_cnt {
      type oc-yang:counter64;
      description
        "Count number of packets that are transmitted by mac and dropped by the RS layer because the link is in fault state.";
    }
    leaf counter_slice4_ifg_mac_pool86_tx_drained_pkt_cnt_reg6_tx_drained_pkt_cnt {
      type oc-yang:counter64;
      description
        "Count number of packets that are transmitted by mac and dropped by the RS layer because the link is in fault state.";
    }
    leaf counter_slice4_ifg_mac_pool86_tx_drained_pkt_cnt_reg7_tx_drained_pkt_cnt {
      type oc-yang:counter64;
      description
        "Count number of packets that are transmitted by mac and dropped by the RS layer because the link is in fault state.";
    }
    leaf counter_slice4_ifg_mac_pool87_tx_drained_pkt_cnt_reg0_tx_drained_pkt_cnt {
      type oc-yang:counter64;
      description
        "Count number of packets that are transmitted by mac and dropped by the RS layer because the link is in fault state.";
    }
    leaf counter_slice4_ifg_mac_pool87_tx_drained_pkt_cnt_reg1_tx_drained_pkt_cnt {
      type oc-yang:counter64;
      description
        "Count number of packets that are transmitted by mac and dropped by the RS layer because the link is in fault state.";
    }
    leaf counter_slice4_ifg_mac_pool87_tx_drained_pkt_cnt_reg2_tx_drained_pkt_cnt {
      type oc-yang:counter64;
      description
        "Count number of packets that are transmitted by mac and dropped by the RS layer because the link is in fault state.";
    }
    leaf counter_slice4_ifg_mac_pool87_tx_drained_pkt_cnt_reg3_tx_drained_pkt_cnt {
      type oc-yang:counter64;
      description
        "Count number of packets that are transmitted by mac and dropped by the RS layer because the link is in fault state.";
    }
    leaf counter_slice4_ifg_mac_pool87_tx_drained_pkt_cnt_reg4_tx_drained_pkt_cnt {
      type oc-yang:counter64;
      description
        "Count number of packets that are transmitted by mac and dropped by the RS layer because the link is in fault state.";
    }
    leaf counter_slice4_ifg_mac_pool87_tx_drained_pkt_cnt_reg5_tx_drained_pkt_cnt {
      type oc-yang:counter64;
      description
        "Count number of packets that are transmitted by mac and dropped by the RS layer because the link is in fault state.";
    }
    leaf counter_slice4_ifg_mac_pool87_tx_drained_pkt_cnt_reg6_tx_drained_pkt_cnt {
      type oc-yang:counter64;
      description
        "Count number of packets that are transmitted by mac and dropped by the RS layer because the link is in fault state.";
    }
    leaf counter_slice4_ifg_mac_pool87_tx_drained_pkt_cnt_reg7_tx_drained_pkt_cnt {
      type oc-yang:counter64;
      description
        "Count number of packets that are transmitted by mac and dropped by the RS layer because the link is in fault state.";
    }
    leaf counter_slice5_ifg_mac_pool80_tx_drained_pkt_cnt_reg0_tx_drained_pkt_cnt {
      type oc-yang:counter64;
      description
        "Count number of packets that are transmitted by mac and dropped by the RS layer because the link is in fault state.";
    }
    leaf counter_slice5_ifg_mac_pool80_tx_drained_pkt_cnt_reg1_tx_drained_pkt_cnt {
      type oc-yang:counter64;
      description
        "Count number of packets that are transmitted by mac and dropped by the RS layer because the link is in fault state.";
    }
    leaf counter_slice5_ifg_mac_pool80_tx_drained_pkt_cnt_reg2_tx_drained_pkt_cnt {
      type oc-yang:counter64;
      description
        "Count number of packets that are transmitted by mac and dropped by the RS layer because the link is in fault state.";
    }
    leaf counter_slice5_ifg_mac_pool80_tx_drained_pkt_cnt_reg3_tx_drained_pkt_cnt {
      type oc-yang:counter64;
      description
        "Count number of packets that are transmitted by mac and dropped by the RS layer because the link is in fault state.";
    }
    leaf counter_slice5_ifg_mac_pool80_tx_drained_pkt_cnt_reg4_tx_drained_pkt_cnt {
      type oc-yang:counter64;
      description
        "Count number of packets that are transmitted by mac and dropped by the RS layer because the link is in fault state.";
    }
    leaf counter_slice5_ifg_mac_pool80_tx_drained_pkt_cnt_reg5_tx_drained_pkt_cnt {
      type oc-yang:counter64;
      description
        "Count number of packets that are transmitted by mac and dropped by the RS layer because the link is in fault state.";
    }
    leaf counter_slice5_ifg_mac_pool80_tx_drained_pkt_cnt_reg6_tx_drained_pkt_cnt {
      type oc-yang:counter64;
      description
        "Count number of packets that are transmitted by mac and dropped by the RS layer because the link is in fault state.";
    }
    leaf counter_slice5_ifg_mac_pool80_tx_drained_pkt_cnt_reg7_tx_drained_pkt_cnt {
      type oc-yang:counter64;
      description
        "Count number of packets that are transmitted by mac and dropped by the RS layer because the link is in fault state.";
    }
    leaf counter_slice5_ifg_mac_pool81_tx_drained_pkt_cnt_reg0_tx_drained_pkt_cnt {
      type oc-yang:counter64;
      description
        "Count number of packets that are transmitted by mac and dropped by the RS layer because the link is in fault state.";
    }
    leaf counter_slice5_ifg_mac_pool81_tx_drained_pkt_cnt_reg1_tx_drained_pkt_cnt {
      type oc-yang:counter64;
      description
        "Count number of packets that are transmitted by mac and dropped by the RS layer because the link is in fault state.";
    }
    leaf counter_slice5_ifg_mac_pool81_tx_drained_pkt_cnt_reg2_tx_drained_pkt_cnt {
      type oc-yang:counter64;
      description
        "Count number of packets that are transmitted by mac and dropped by the RS layer because the link is in fault state.";
    }
    leaf counter_slice5_ifg_mac_pool81_tx_drained_pkt_cnt_reg3_tx_drained_pkt_cnt {
      type oc-yang:counter64;
      description
        "Count number of packets that are transmitted by mac and dropped by the RS layer because the link is in fault state.";
    }
    leaf counter_slice5_ifg_mac_pool81_tx_drained_pkt_cnt_reg4_tx_drained_pkt_cnt {
      type oc-yang:counter64;
      description
        "Count number of packets that are transmitted by mac and dropped by the RS layer because the link is in fault state.";
    }
    leaf counter_slice5_ifg_mac_pool81_tx_drained_pkt_cnt_reg5_tx_drained_pkt_cnt {
      type oc-yang:counter64;
      description
        "Count number of packets that are transmitted by mac and dropped by the RS layer because the link is in fault state.";
    }
    leaf counter_slice5_ifg_mac_pool81_tx_drained_pkt_cnt_reg6_tx_drained_pkt_cnt {
      type oc-yang:counter64;
      description
        "Count number of packets that are transmitted by mac and dropped by the RS layer because the link is in fault state.";
    }
    leaf counter_slice5_ifg_mac_pool81_tx_drained_pkt_cnt_reg7_tx_drained_pkt_cnt {
      type oc-yang:counter64;
      description
        "Count number of packets that are transmitted by mac and dropped by the RS layer because the link is in fault state.";
    }
    leaf counter_slice5_ifg_mac_pool82_tx_drained_pkt_cnt_reg0_tx_drained_pkt_cnt {
      type oc-yang:counter64;
      description
        "Count number of packets that are transmitted by mac and dropped by the RS layer because the link is in fault state.";
    }
    leaf counter_slice5_ifg_mac_pool82_tx_drained_pkt_cnt_reg1_tx_drained_pkt_cnt {
      type oc-yang:counter64;
      description
        "Count number of packets that are transmitted by mac and dropped by the RS layer because the link is in fault state.";
    }
    leaf counter_slice5_ifg_mac_pool82_tx_drained_pkt_cnt_reg2_tx_drained_pkt_cnt {
      type oc-yang:counter64;
      description
        "Count number of packets that are transmitted by mac and dropped by the RS layer because the link is in fault state.";
    }
    leaf counter_slice5_ifg_mac_pool82_tx_drained_pkt_cnt_reg3_tx_drained_pkt_cnt {
      type oc-yang:counter64;
      description
        "Count number of packets that are transmitted by mac and dropped by the RS layer because the link is in fault state.";
    }
    leaf counter_slice5_ifg_mac_pool82_tx_drained_pkt_cnt_reg4_tx_drained_pkt_cnt {
      type oc-yang:counter64;
      description
        "Count number of packets that are transmitted by mac and dropped by the RS layer because the link is in fault state.";
    }
    leaf counter_slice5_ifg_mac_pool82_tx_drained_pkt_cnt_reg5_tx_drained_pkt_cnt {
      type oc-yang:counter64;
      description
        "Count number of packets that are transmitted by mac and dropped by the RS layer because the link is in fault state.";
    }
    leaf counter_slice5_ifg_mac_pool82_tx_drained_pkt_cnt_reg6_tx_drained_pkt_cnt {
      type oc-yang:counter64;
      description
        "Count number of packets that are transmitted by mac and dropped by the RS layer because the link is in fault state.";
    }
    leaf counter_slice5_ifg_mac_pool82_tx_drained_pkt_cnt_reg7_tx_drained_pkt_cnt {
      type oc-yang:counter64;
      description
        "Count number of packets that are transmitted by mac and dropped by the RS layer because the link is in fault state.";
    }
    leaf counter_slice5_ifg_mac_pool83_tx_drained_pkt_cnt_reg0_tx_drained_pkt_cnt {
      type oc-yang:counter64;
      description
        "Count number of packets that are transmitted by mac and dropped by the RS layer because the link is in fault state.";
    }
    leaf counter_slice5_ifg_mac_pool83_tx_drained_pkt_cnt_reg1_tx_drained_pkt_cnt {
      type oc-yang:counter64;
      description
        "Count number of packets that are transmitted by mac and dropped by the RS layer because the link is in fault state.";
    }
    leaf counter_slice5_ifg_mac_pool83_tx_drained_pkt_cnt_reg2_tx_drained_pkt_cnt {
      type oc-yang:counter64;
      description
        "Count number of packets that are transmitted by mac and dropped by the RS layer because the link is in fault state.";
    }
    leaf counter_slice5_ifg_mac_pool83_tx_drained_pkt_cnt_reg3_tx_drained_pkt_cnt {
      type oc-yang:counter64;
      description
        "Count number of packets that are transmitted by mac and dropped by the RS layer because the link is in fault state.";
    }
    leaf counter_slice5_ifg_mac_pool83_tx_drained_pkt_cnt_reg4_tx_drained_pkt_cnt {
      type oc-yang:counter64;
      description
        "Count number of packets that are transmitted by mac and dropped by the RS layer because the link is in fault state.";
    }
    leaf counter_slice5_ifg_mac_pool83_tx_drained_pkt_cnt_reg5_tx_drained_pkt_cnt {
      type oc-yang:counter64;
      description
        "Count number of packets that are transmitted by mac and dropped by the RS layer because the link is in fault state.";
    }
    leaf counter_slice5_ifg_mac_pool83_tx_drained_pkt_cnt_reg6_tx_drained_pkt_cnt {
      type oc-yang:counter64;
      description
        "Count number of packets that are transmitted by mac and dropped by the RS layer because the link is in fault state.";
    }
    leaf counter_slice5_ifg_mac_pool83_tx_drained_pkt_cnt_reg7_tx_drained_pkt_cnt {
      type oc-yang:counter64;
      description
        "Count number of packets that are transmitted by mac and dropped by the RS layer because the link is in fault state.";
    }
    leaf counter_slice5_ifg_mac_pool84_tx_drained_pkt_cnt_reg0_tx_drained_pkt_cnt {
      type oc-yang:counter64;
      description
        "Count number of packets that are transmitted by mac and dropped by the RS layer because the link is in fault state.";
    }
    leaf counter_slice5_ifg_mac_pool84_tx_drained_pkt_cnt_reg1_tx_drained_pkt_cnt {
      type oc-yang:counter64;
      description
        "Count number of packets that are transmitted by mac and dropped by the RS layer because the link is in fault state.";
    }
    leaf counter_slice5_ifg_mac_pool84_tx_drained_pkt_cnt_reg2_tx_drained_pkt_cnt {
      type oc-yang:counter64;
      description
        "Count number of packets that are transmitted by mac and dropped by the RS layer because the link is in fault state.";
    }
    leaf counter_slice5_ifg_mac_pool84_tx_drained_pkt_cnt_reg3_tx_drained_pkt_cnt {
      type oc-yang:counter64;
      description
        "Count number of packets that are transmitted by mac and dropped by the RS layer because the link is in fault state.";
    }
    leaf counter_slice5_ifg_mac_pool84_tx_drained_pkt_cnt_reg4_tx_drained_pkt_cnt {
      type oc-yang:counter64;
      description
        "Count number of packets that are transmitted by mac and dropped by the RS layer because the link is in fault state.";
    }
    leaf counter_slice5_ifg_mac_pool84_tx_drained_pkt_cnt_reg5_tx_drained_pkt_cnt {
      type oc-yang:counter64;
      description
        "Count number of packets that are transmitted by mac and dropped by the RS layer because the link is in fault state.";
    }
    leaf counter_slice5_ifg_mac_pool84_tx_drained_pkt_cnt_reg6_tx_drained_pkt_cnt {
      type oc-yang:counter64;
      description
        "Count number of packets that are transmitted by mac and dropped by the RS layer because the link is in fault state.";
    }
    leaf counter_slice5_ifg_mac_pool84_tx_drained_pkt_cnt_reg7_tx_drained_pkt_cnt {
      type oc-yang:counter64;
      description
        "Count number of packets that are transmitted by mac and dropped by the RS layer because the link is in fault state.";
    }
    leaf counter_slice5_ifg_mac_pool85_tx_drained_pkt_cnt_reg0_tx_drained_pkt_cnt {
      type oc-yang:counter64;
      description
        "Count number of packets that are transmitted by mac and dropped by the RS layer because the link is in fault state.";
    }
    leaf counter_slice5_ifg_mac_pool85_tx_drained_pkt_cnt_reg1_tx_drained_pkt_cnt {
      type oc-yang:counter64;
      description
        "Count number of packets that are transmitted by mac and dropped by the RS layer because the link is in fault state.";
    }
    leaf counter_slice5_ifg_mac_pool85_tx_drained_pkt_cnt_reg2_tx_drained_pkt_cnt {
      type oc-yang:counter64;
      description
        "Count number of packets that are transmitted by mac and dropped by the RS layer because the link is in fault state.";
    }
    leaf counter_slice5_ifg_mac_pool85_tx_drained_pkt_cnt_reg3_tx_drained_pkt_cnt {
      type oc-yang:counter64;
      description
        "Count number of packets that are transmitted by mac and dropped by the RS layer because the link is in fault state.";
    }
    leaf counter_slice5_ifg_mac_pool85_tx_drained_pkt_cnt_reg4_tx_drained_pkt_cnt {
      type oc-yang:counter64;
      description
        "Count number of packets that are transmitted by mac and dropped by the RS layer because the link is in fault state.";
    }
    leaf counter_slice5_ifg_mac_pool85_tx_drained_pkt_cnt_reg5_tx_drained_pkt_cnt {
      type oc-yang:counter64;
      description
        "Count number of packets that are transmitted by mac and dropped by the RS layer because the link is in fault state.";
    }
    leaf counter_slice5_ifg_mac_pool85_tx_drained_pkt_cnt_reg6_tx_drained_pkt_cnt {
      type oc-yang:counter64;
      description
        "Count number of packets that are transmitted by mac and dropped by the RS layer because the link is in fault state.";
    }
    leaf counter_slice5_ifg_mac_pool85_tx_drained_pkt_cnt_reg7_tx_drained_pkt_cnt {
      type oc-yang:counter64;
      description
        "Count number of packets that are transmitted by mac and dropped by the RS layer because the link is in fault state.";
    }
    leaf counter_slice5_ifg_mac_pool86_tx_drained_pkt_cnt_reg0_tx_drained_pkt_cnt {
      type oc-yang:counter64;
      description
        "Count number of packets that are transmitted by mac and dropped by the RS layer because the link is in fault state.";
    }
    leaf counter_slice5_ifg_mac_pool86_tx_drained_pkt_cnt_reg1_tx_drained_pkt_cnt {
      type oc-yang:counter64;
      description
        "Count number of packets that are transmitted by mac and dropped by the RS layer because the link is in fault state.";
    }
    leaf counter_slice5_ifg_mac_pool86_tx_drained_pkt_cnt_reg2_tx_drained_pkt_cnt {
      type oc-yang:counter64;
      description
        "Count number of packets that are transmitted by mac and dropped by the RS layer because the link is in fault state.";
    }
    leaf counter_slice5_ifg_mac_pool86_tx_drained_pkt_cnt_reg3_tx_drained_pkt_cnt {
      type oc-yang:counter64;
      description
        "Count number of packets that are transmitted by mac and dropped by the RS layer because the link is in fault state.";
    }
    leaf counter_slice5_ifg_mac_pool86_tx_drained_pkt_cnt_reg4_tx_drained_pkt_cnt {
      type oc-yang:counter64;
      description
        "Count number of packets that are transmitted by mac and dropped by the RS layer because the link is in fault state.";
    }
    leaf counter_slice5_ifg_mac_pool86_tx_drained_pkt_cnt_reg5_tx_drained_pkt_cnt {
      type oc-yang:counter64;
      description
        "Count number of packets that are transmitted by mac and dropped by the RS layer because the link is in fault state.";
    }
    leaf counter_slice5_ifg_mac_pool86_tx_drained_pkt_cnt_reg6_tx_drained_pkt_cnt {
      type oc-yang:counter64;
      description
        "Count number of packets that are transmitted by mac and dropped by the RS layer because the link is in fault state.";
    }
    leaf counter_slice5_ifg_mac_pool86_tx_drained_pkt_cnt_reg7_tx_drained_pkt_cnt {
      type oc-yang:counter64;
      description
        "Count number of packets that are transmitted by mac and dropped by the RS layer because the link is in fault state.";
    }
    leaf counter_slice5_ifg_mac_pool87_tx_drained_pkt_cnt_reg0_tx_drained_pkt_cnt {
      type oc-yang:counter64;
      description
        "Count number of packets that are transmitted by mac and dropped by the RS layer because the link is in fault state.";
    }
    leaf counter_slice5_ifg_mac_pool87_tx_drained_pkt_cnt_reg1_tx_drained_pkt_cnt {
      type oc-yang:counter64;
      description
        "Count number of packets that are transmitted by mac and dropped by the RS layer because the link is in fault state.";
    }
    leaf counter_slice5_ifg_mac_pool87_tx_drained_pkt_cnt_reg2_tx_drained_pkt_cnt {
      type oc-yang:counter64;
      description
        "Count number of packets that are transmitted by mac and dropped by the RS layer because the link is in fault state.";
    }
    leaf counter_slice5_ifg_mac_pool87_tx_drained_pkt_cnt_reg3_tx_drained_pkt_cnt {
      type oc-yang:counter64;
      description
        "Count number of packets that are transmitted by mac and dropped by the RS layer because the link is in fault state.";
    }
    leaf counter_slice5_ifg_mac_pool87_tx_drained_pkt_cnt_reg4_tx_drained_pkt_cnt {
      type oc-yang:counter64;
      description
        "Count number of packets that are transmitted by mac and dropped by the RS layer because the link is in fault state.";
    }
    leaf counter_slice5_ifg_mac_pool87_tx_drained_pkt_cnt_reg5_tx_drained_pkt_cnt {
      type oc-yang:counter64;
      description
        "Count number of packets that are transmitted by mac and dropped by the RS layer because the link is in fault state.";
    }
    leaf counter_slice5_ifg_mac_pool87_tx_drained_pkt_cnt_reg6_tx_drained_pkt_cnt {
      type oc-yang:counter64;
      description
        "Count number of packets that are transmitted by mac and dropped by the RS layer because the link is in fault state.";
    }
    leaf counter_slice5_ifg_mac_pool87_tx_drained_pkt_cnt_reg7_tx_drained_pkt_cnt {
      type oc-yang:counter64;
      description
        "Count number of packets that are transmitted by mac and dropped by the RS layer because the link is in fault state.";
    }
    leaf counter_slice6_ifg_mac_pool80_tx_drained_pkt_cnt_reg0_tx_drained_pkt_cnt {
      type oc-yang:counter64;
      description
        "Count number of packets that are transmitted by mac and dropped by the RS layer because the link is in fault state.";
    }
    leaf counter_slice6_ifg_mac_pool80_tx_drained_pkt_cnt_reg1_tx_drained_pkt_cnt {
      type oc-yang:counter64;
      description
        "Count number of packets that are transmitted by mac and dropped by the RS layer because the link is in fault state.";
    }
    leaf counter_slice6_ifg_mac_pool80_tx_drained_pkt_cnt_reg2_tx_drained_pkt_cnt {
      type oc-yang:counter64;
      description
        "Count number of packets that are transmitted by mac and dropped by the RS layer because the link is in fault state.";
    }
    leaf counter_slice6_ifg_mac_pool80_tx_drained_pkt_cnt_reg3_tx_drained_pkt_cnt {
      type oc-yang:counter64;
      description
        "Count number of packets that are transmitted by mac and dropped by the RS layer because the link is in fault state.";
    }
    leaf counter_slice6_ifg_mac_pool80_tx_drained_pkt_cnt_reg4_tx_drained_pkt_cnt {
      type oc-yang:counter64;
      description
        "Count number of packets that are transmitted by mac and dropped by the RS layer because the link is in fault state.";
    }
    leaf counter_slice6_ifg_mac_pool80_tx_drained_pkt_cnt_reg5_tx_drained_pkt_cnt {
      type oc-yang:counter64;
      description
        "Count number of packets that are transmitted by mac and dropped by the RS layer because the link is in fault state.";
    }
    leaf counter_slice6_ifg_mac_pool80_tx_drained_pkt_cnt_reg6_tx_drained_pkt_cnt {
      type oc-yang:counter64;
      description
        "Count number of packets that are transmitted by mac and dropped by the RS layer because the link is in fault state.";
    }
    leaf counter_slice6_ifg_mac_pool80_tx_drained_pkt_cnt_reg7_tx_drained_pkt_cnt {
      type oc-yang:counter64;
      description
        "Count number of packets that are transmitted by mac and dropped by the RS layer because the link is in fault state.";
    }
    leaf counter_slice6_ifg_mac_pool81_tx_drained_pkt_cnt_reg0_tx_drained_pkt_cnt {
      type oc-yang:counter64;
      description
        "Count number of packets that are transmitted by mac and dropped by the RS layer because the link is in fault state.";
    }
    leaf counter_slice6_ifg_mac_pool81_tx_drained_pkt_cnt_reg1_tx_drained_pkt_cnt {
      type oc-yang:counter64;
      description
        "Count number of packets that are transmitted by mac and dropped by the RS layer because the link is in fault state.";
    }
    leaf counter_slice6_ifg_mac_pool81_tx_drained_pkt_cnt_reg2_tx_drained_pkt_cnt {
      type oc-yang:counter64;
      description
        "Count number of packets that are transmitted by mac and dropped by the RS layer because the link is in fault state.";
    }
    leaf counter_slice6_ifg_mac_pool81_tx_drained_pkt_cnt_reg3_tx_drained_pkt_cnt {
      type oc-yang:counter64;
      description
        "Count number of packets that are transmitted by mac and dropped by the RS layer because the link is in fault state.";
    }
    leaf counter_slice6_ifg_mac_pool81_tx_drained_pkt_cnt_reg4_tx_drained_pkt_cnt {
      type oc-yang:counter64;
      description
        "Count number of packets that are transmitted by mac and dropped by the RS layer because the link is in fault state.";
    }
    leaf counter_slice6_ifg_mac_pool81_tx_drained_pkt_cnt_reg5_tx_drained_pkt_cnt {
      type oc-yang:counter64;
      description
        "Count number of packets that are transmitted by mac and dropped by the RS layer because the link is in fault state.";
    }
    leaf counter_slice6_ifg_mac_pool81_tx_drained_pkt_cnt_reg6_tx_drained_pkt_cnt {
      type oc-yang:counter64;
      description
        "Count number of packets that are transmitted by mac and dropped by the RS layer because the link is in fault state.";
    }
    leaf counter_slice6_ifg_mac_pool81_tx_drained_pkt_cnt_reg7_tx_drained_pkt_cnt {
      type oc-yang:counter64;
      description
        "Count number of packets that are transmitted by mac and dropped by the RS layer because the link is in fault state.";
    }
    leaf counter_slice6_ifg_mac_pool82_tx_drained_pkt_cnt_reg0_tx_drained_pkt_cnt {
      type oc-yang:counter64;
      description
        "Count number of packets that are transmitted by mac and dropped by the RS layer because the link is in fault state.";
    }
    leaf counter_slice6_ifg_mac_pool82_tx_drained_pkt_cnt_reg1_tx_drained_pkt_cnt {
      type oc-yang:counter64;
      description
        "Count number of packets that are transmitted by mac and dropped by the RS layer because the link is in fault state.";
    }
    leaf counter_slice6_ifg_mac_pool82_tx_drained_pkt_cnt_reg2_tx_drained_pkt_cnt {
      type oc-yang:counter64;
      description
        "Count number of packets that are transmitted by mac and dropped by the RS layer because the link is in fault state.";
    }
    leaf counter_slice6_ifg_mac_pool82_tx_drained_pkt_cnt_reg3_tx_drained_pkt_cnt {
      type oc-yang:counter64;
      description
        "Count number of packets that are transmitted by mac and dropped by the RS layer because the link is in fault state.";
    }
    leaf counter_slice6_ifg_mac_pool82_tx_drained_pkt_cnt_reg4_tx_drained_pkt_cnt {
      type oc-yang:counter64;
      description
        "Count number of packets that are transmitted by mac and dropped by the RS layer because the link is in fault state.";
    }
    leaf counter_slice6_ifg_mac_pool82_tx_drained_pkt_cnt_reg5_tx_drained_pkt_cnt {
      type oc-yang:counter64;
      description
        "Count number of packets that are transmitted by mac and dropped by the RS layer because the link is in fault state.";
    }
    leaf counter_slice6_ifg_mac_pool82_tx_drained_pkt_cnt_reg6_tx_drained_pkt_cnt {
      type oc-yang:counter64;
      description
        "Count number of packets that are transmitted by mac and dropped by the RS layer because the link is in fault state.";
    }
    leaf counter_slice6_ifg_mac_pool82_tx_drained_pkt_cnt_reg7_tx_drained_pkt_cnt {
      type oc-yang:counter64;
      description
        "Count number of packets that are transmitted by mac and dropped by the RS layer because the link is in fault state.";
    }
    leaf counter_slice6_ifg_mac_pool83_tx_drained_pkt_cnt_reg0_tx_drained_pkt_cnt {
      type oc-yang:counter64;
      description
        "Count number of packets that are transmitted by mac and dropped by the RS layer because the link is in fault state.";
    }
    leaf counter_slice6_ifg_mac_pool83_tx_drained_pkt_cnt_reg1_tx_drained_pkt_cnt {
      type oc-yang:counter64;
      description
        "Count number of packets that are transmitted by mac and dropped by the RS layer because the link is in fault state.";
    }
    leaf counter_slice6_ifg_mac_pool83_tx_drained_pkt_cnt_reg2_tx_drained_pkt_cnt {
      type oc-yang:counter64;
      description
        "Count number of packets that are transmitted by mac and dropped by the RS layer because the link is in fault state.";
    }
    leaf counter_slice6_ifg_mac_pool83_tx_drained_pkt_cnt_reg3_tx_drained_pkt_cnt {
      type oc-yang:counter64;
      description
        "Count number of packets that are transmitted by mac and dropped by the RS layer because the link is in fault state.";
    }
    leaf counter_slice6_ifg_mac_pool83_tx_drained_pkt_cnt_reg4_tx_drained_pkt_cnt {
      type oc-yang:counter64;
      description
        "Count number of packets that are transmitted by mac and dropped by the RS layer because the link is in fault state.";
    }
    leaf counter_slice6_ifg_mac_pool83_tx_drained_pkt_cnt_reg5_tx_drained_pkt_cnt {
      type oc-yang:counter64;
      description
        "Count number of packets that are transmitted by mac and dropped by the RS layer because the link is in fault state.";
    }
    leaf counter_slice6_ifg_mac_pool83_tx_drained_pkt_cnt_reg6_tx_drained_pkt_cnt {
      type oc-yang:counter64;
      description
        "Count number of packets that are transmitted by mac and dropped by the RS layer because the link is in fault state.";
    }
    leaf counter_slice6_ifg_mac_pool83_tx_drained_pkt_cnt_reg7_tx_drained_pkt_cnt {
      type oc-yang:counter64;
      description
        "Count number of packets that are transmitted by mac and dropped by the RS layer because the link is in fault state.";
    }
    leaf counter_slice6_ifg_mac_pool84_tx_drained_pkt_cnt_reg0_tx_drained_pkt_cnt {
      type oc-yang:counter64;
      description
        "Count number of packets that are transmitted by mac and dropped by the RS layer because the link is in fault state.";
    }
    leaf counter_slice6_ifg_mac_pool84_tx_drained_pkt_cnt_reg1_tx_drained_pkt_cnt {
      type oc-yang:counter64;
      description
        "Count number of packets that are transmitted by mac and dropped by the RS layer because the link is in fault state.";
    }
    leaf counter_slice6_ifg_mac_pool84_tx_drained_pkt_cnt_reg2_tx_drained_pkt_cnt {
      type oc-yang:counter64;
      description
        "Count number of packets that are transmitted by mac and dropped by the RS layer because the link is in fault state.";
    }
    leaf counter_slice6_ifg_mac_pool84_tx_drained_pkt_cnt_reg3_tx_drained_pkt_cnt {
      type oc-yang:counter64;
      description
        "Count number of packets that are transmitted by mac and dropped by the RS layer because the link is in fault state.";
    }
    leaf counter_slice6_ifg_mac_pool84_tx_drained_pkt_cnt_reg4_tx_drained_pkt_cnt {
      type oc-yang:counter64;
      description
        "Count number of packets that are transmitted by mac and dropped by the RS layer because the link is in fault state.";
    }
    leaf counter_slice6_ifg_mac_pool84_tx_drained_pkt_cnt_reg5_tx_drained_pkt_cnt {
      type oc-yang:counter64;
      description
        "Count number of packets that are transmitted by mac and dropped by the RS layer because the link is in fault state.";
    }
    leaf counter_slice6_ifg_mac_pool84_tx_drained_pkt_cnt_reg6_tx_drained_pkt_cnt {
      type oc-yang:counter64;
      description
        "Count number of packets that are transmitted by mac and dropped by the RS layer because the link is in fault state.";
    }
    leaf counter_slice6_ifg_mac_pool84_tx_drained_pkt_cnt_reg7_tx_drained_pkt_cnt {
      type oc-yang:counter64;
      description
        "Count number of packets that are transmitted by mac and dropped by the RS layer because the link is in fault state.";
    }
    leaf counter_slice6_ifg_mac_pool85_tx_drained_pkt_cnt_reg0_tx_drained_pkt_cnt {
      type oc-yang:counter64;
      description
        "Count number of packets that are transmitted by mac and dropped by the RS layer because the link is in fault state.";
    }
    leaf counter_slice6_ifg_mac_pool85_tx_drained_pkt_cnt_reg1_tx_drained_pkt_cnt {
      type oc-yang:counter64;
      description
        "Count number of packets that are transmitted by mac and dropped by the RS layer because the link is in fault state.";
    }
    leaf counter_slice6_ifg_mac_pool85_tx_drained_pkt_cnt_reg2_tx_drained_pkt_cnt {
      type oc-yang:counter64;
      description
        "Count number of packets that are transmitted by mac and dropped by the RS layer because the link is in fault state.";
    }
    leaf counter_slice6_ifg_mac_pool85_tx_drained_pkt_cnt_reg3_tx_drained_pkt_cnt {
      type oc-yang:counter64;
      description
        "Count number of packets that are transmitted by mac and dropped by the RS layer because the link is in fault state.";
    }
    leaf counter_slice6_ifg_mac_pool85_tx_drained_pkt_cnt_reg4_tx_drained_pkt_cnt {
      type oc-yang:counter64;
      description
        "Count number of packets that are transmitted by mac and dropped by the RS layer because the link is in fault state.";
    }
    leaf counter_slice6_ifg_mac_pool85_tx_drained_pkt_cnt_reg5_tx_drained_pkt_cnt {
      type oc-yang:counter64;
      description
        "Count number of packets that are transmitted by mac and dropped by the RS layer because the link is in fault state.";
    }
    leaf counter_slice6_ifg_mac_pool85_tx_drained_pkt_cnt_reg6_tx_drained_pkt_cnt {
      type oc-yang:counter64;
      description
        "Count number of packets that are transmitted by mac and dropped by the RS layer because the link is in fault state.";
    }
    leaf counter_slice6_ifg_mac_pool85_tx_drained_pkt_cnt_reg7_tx_drained_pkt_cnt {
      type oc-yang:counter64;
      description
        "Count number of packets that are transmitted by mac and dropped by the RS layer because the link is in fault state.";
    }
    leaf counter_slice6_ifg_mac_pool86_tx_drained_pkt_cnt_reg0_tx_drained_pkt_cnt {
      type oc-yang:counter64;
      description
        "Count number of packets that are transmitted by mac and dropped by the RS layer because the link is in fault state.";
    }
    leaf counter_slice6_ifg_mac_pool86_tx_drained_pkt_cnt_reg1_tx_drained_pkt_cnt {
      type oc-yang:counter64;
      description
        "Count number of packets that are transmitted by mac and dropped by the RS layer because the link is in fault state.";
    }
    leaf counter_slice6_ifg_mac_pool86_tx_drained_pkt_cnt_reg2_tx_drained_pkt_cnt {
      type oc-yang:counter64;
      description
        "Count number of packets that are transmitted by mac and dropped by the RS layer because the link is in fault state.";
    }
    leaf counter_slice6_ifg_mac_pool86_tx_drained_pkt_cnt_reg3_tx_drained_pkt_cnt {
      type oc-yang:counter64;
      description
        "Count number of packets that are transmitted by mac and dropped by the RS layer because the link is in fault state.";
    }
    leaf counter_slice6_ifg_mac_pool86_tx_drained_pkt_cnt_reg4_tx_drained_pkt_cnt {
      type oc-yang:counter64;
      description
        "Count number of packets that are transmitted by mac and dropped by the RS layer because the link is in fault state.";
    }
    leaf counter_slice6_ifg_mac_pool86_tx_drained_pkt_cnt_reg5_tx_drained_pkt_cnt {
      type oc-yang:counter64;
      description
        "Count number of packets that are transmitted by mac and dropped by the RS layer because the link is in fault state.";
    }
    leaf counter_slice6_ifg_mac_pool86_tx_drained_pkt_cnt_reg6_tx_drained_pkt_cnt {
      type oc-yang:counter64;
      description
        "Count number of packets that are transmitted by mac and dropped by the RS layer because the link is in fault state.";
    }
    leaf counter_slice6_ifg_mac_pool86_tx_drained_pkt_cnt_reg7_tx_drained_pkt_cnt {
      type oc-yang:counter64;
      description
        "Count number of packets that are transmitted by mac and dropped by the RS layer because the link is in fault state.";
    }
    leaf counter_slice6_ifg_mac_pool87_tx_drained_pkt_cnt_reg0_tx_drained_pkt_cnt {
      type oc-yang:counter64;
      description
        "Count number of packets that are transmitted by mac and dropped by the RS layer because the link is in fault state.";
    }
    leaf counter_slice6_ifg_mac_pool87_tx_drained_pkt_cnt_reg1_tx_drained_pkt_cnt {
      type oc-yang:counter64;
      description
        "Count number of packets that are transmitted by mac and dropped by the RS layer because the link is in fault state.";
    }
    leaf counter_slice6_ifg_mac_pool87_tx_drained_pkt_cnt_reg2_tx_drained_pkt_cnt {
      type oc-yang:counter64;
      description
        "Count number of packets that are transmitted by mac and dropped by the RS layer because the link is in fault state.";
    }
    leaf counter_slice6_ifg_mac_pool87_tx_drained_pkt_cnt_reg3_tx_drained_pkt_cnt {
      type oc-yang:counter64;
      description
        "Count number of packets that are transmitted by mac and dropped by the RS layer because the link is in fault state.";
    }
    leaf counter_slice6_ifg_mac_pool87_tx_drained_pkt_cnt_reg4_tx_drained_pkt_cnt {
      type oc-yang:counter64;
      description
        "Count number of packets that are transmitted by mac and dropped by the RS layer because the link is in fault state.";
    }
    leaf counter_slice6_ifg_mac_pool87_tx_drained_pkt_cnt_reg5_tx_drained_pkt_cnt {
      type oc-yang:counter64;
      description
        "Count number of packets that are transmitted by mac and dropped by the RS layer because the link is in fault state.";
    }
    leaf counter_slice6_ifg_mac_pool87_tx_drained_pkt_cnt_reg6_tx_drained_pkt_cnt {
      type oc-yang:counter64;
      description
        "Count number of packets that are transmitted by mac and dropped by the RS layer because the link is in fault state.";
    }
    leaf counter_slice6_ifg_mac_pool87_tx_drained_pkt_cnt_reg7_tx_drained_pkt_cnt {
      type oc-yang:counter64;
      description
        "Count number of packets that are transmitted by mac and dropped by the RS layer because the link is in fault state.";
    }
    leaf counter_slice7_ifg_mac_pool80_tx_drained_pkt_cnt_reg0_tx_drained_pkt_cnt {
      type oc-yang:counter64;
      description
        "Count number of packets that are transmitted by mac and dropped by the RS layer because the link is in fault state.";
    }
    leaf counter_slice7_ifg_mac_pool80_tx_drained_pkt_cnt_reg1_tx_drained_pkt_cnt {
      type oc-yang:counter64;
      description
        "Count number of packets that are transmitted by mac and dropped by the RS layer because the link is in fault state.";
    }
    leaf counter_slice7_ifg_mac_pool80_tx_drained_pkt_cnt_reg2_tx_drained_pkt_cnt {
      type oc-yang:counter64;
      description
        "Count number of packets that are transmitted by mac and dropped by the RS layer because the link is in fault state.";
    }
    leaf counter_slice7_ifg_mac_pool80_tx_drained_pkt_cnt_reg3_tx_drained_pkt_cnt {
      type oc-yang:counter64;
      description
        "Count number of packets that are transmitted by mac and dropped by the RS layer because the link is in fault state.";
    }
    leaf counter_slice7_ifg_mac_pool80_tx_drained_pkt_cnt_reg4_tx_drained_pkt_cnt {
      type oc-yang:counter64;
      description
        "Count number of packets that are transmitted by mac and dropped by the RS layer because the link is in fault state.";
    }
    leaf counter_slice7_ifg_mac_pool80_tx_drained_pkt_cnt_reg5_tx_drained_pkt_cnt {
      type oc-yang:counter64;
      description
        "Count number of packets that are transmitted by mac and dropped by the RS layer because the link is in fault state.";
    }
    leaf counter_slice7_ifg_mac_pool80_tx_drained_pkt_cnt_reg6_tx_drained_pkt_cnt {
      type oc-yang:counter64;
      description
        "Count number of packets that are transmitted by mac and dropped by the RS layer because the link is in fault state.";
    }
    leaf counter_slice7_ifg_mac_pool80_tx_drained_pkt_cnt_reg7_tx_drained_pkt_cnt {
      type oc-yang:counter64;
      description
        "Count number of packets that are transmitted by mac and dropped by the RS layer because the link is in fault state.";
    }
    leaf counter_slice7_ifg_mac_pool81_tx_drained_pkt_cnt_reg0_tx_drained_pkt_cnt {
      type oc-yang:counter64;
      description
        "Count number of packets that are transmitted by mac and dropped by the RS layer because the link is in fault state.";
    }
    leaf counter_slice7_ifg_mac_pool81_tx_drained_pkt_cnt_reg1_tx_drained_pkt_cnt {
      type oc-yang:counter64;
      description
        "Count number of packets that are transmitted by mac and dropped by the RS layer because the link is in fault state.";
    }
    leaf counter_slice7_ifg_mac_pool81_tx_drained_pkt_cnt_reg2_tx_drained_pkt_cnt {
      type oc-yang:counter64;
      description
        "Count number of packets that are transmitted by mac and dropped by the RS layer because the link is in fault state.";
    }
    leaf counter_slice7_ifg_mac_pool81_tx_drained_pkt_cnt_reg3_tx_drained_pkt_cnt {
      type oc-yang:counter64;
      description
        "Count number of packets that are transmitted by mac and dropped by the RS layer because the link is in fault state.";
    }
    leaf counter_slice7_ifg_mac_pool81_tx_drained_pkt_cnt_reg4_tx_drained_pkt_cnt {
      type oc-yang:counter64;
      description
        "Count number of packets that are transmitted by mac and dropped by the RS layer because the link is in fault state.";
    }
    leaf counter_slice7_ifg_mac_pool81_tx_drained_pkt_cnt_reg5_tx_drained_pkt_cnt {
      type oc-yang:counter64;
      description
        "Count number of packets that are transmitted by mac and dropped by the RS layer because the link is in fault state.";
    }
    leaf counter_slice7_ifg_mac_pool81_tx_drained_pkt_cnt_reg6_tx_drained_pkt_cnt {
      type oc-yang:counter64;
      description
        "Count number of packets that are transmitted by mac and dropped by the RS layer because the link is in fault state.";
    }
    leaf counter_slice7_ifg_mac_pool81_tx_drained_pkt_cnt_reg7_tx_drained_pkt_cnt {
      type oc-yang:counter64;
      description
        "Count number of packets that are transmitted by mac and dropped by the RS layer because the link is in fault state.";
    }
    leaf counter_slice7_ifg_mac_pool82_tx_drained_pkt_cnt_reg0_tx_drained_pkt_cnt {
      type oc-yang:counter64;
      description
        "Count number of packets that are transmitted by mac and dropped by the RS layer because the link is in fault state.";
    }
    leaf counter_slice7_ifg_mac_pool82_tx_drained_pkt_cnt_reg1_tx_drained_pkt_cnt {
      type oc-yang:counter64;
      description
        "Count number of packets that are transmitted by mac and dropped by the RS layer because the link is in fault state.";
    }
    leaf counter_slice7_ifg_mac_pool82_tx_drained_pkt_cnt_reg2_tx_drained_pkt_cnt {
      type oc-yang:counter64;
      description
        "Count number of packets that are transmitted by mac and dropped by the RS layer because the link is in fault state.";
    }
    leaf counter_slice7_ifg_mac_pool82_tx_drained_pkt_cnt_reg3_tx_drained_pkt_cnt {
      type oc-yang:counter64;
      description
        "Count number of packets that are transmitted by mac and dropped by the RS layer because the link is in fault state.";
    }
    leaf counter_slice7_ifg_mac_pool82_tx_drained_pkt_cnt_reg4_tx_drained_pkt_cnt {
      type oc-yang:counter64;
      description
        "Count number of packets that are transmitted by mac and dropped by the RS layer because the link is in fault state.";
    }
    leaf counter_slice7_ifg_mac_pool82_tx_drained_pkt_cnt_reg5_tx_drained_pkt_cnt {
      type oc-yang:counter64;
      description
        "Count number of packets that are transmitted by mac and dropped by the RS layer because the link is in fault state.";
    }
    leaf counter_slice7_ifg_mac_pool82_tx_drained_pkt_cnt_reg6_tx_drained_pkt_cnt {
      type oc-yang:counter64;
      description
        "Count number of packets that are transmitted by mac and dropped by the RS layer because the link is in fault state.";
    }
    leaf counter_slice7_ifg_mac_pool82_tx_drained_pkt_cnt_reg7_tx_drained_pkt_cnt {
      type oc-yang:counter64;
      description
        "Count number of packets that are transmitted by mac and dropped by the RS layer because the link is in fault state.";
    }
    leaf counter_slice7_ifg_mac_pool83_tx_drained_pkt_cnt_reg0_tx_drained_pkt_cnt {
      type oc-yang:counter64;
      description
        "Count number of packets that are transmitted by mac and dropped by the RS layer because the link is in fault state.";
    }
    leaf counter_slice7_ifg_mac_pool83_tx_drained_pkt_cnt_reg1_tx_drained_pkt_cnt {
      type oc-yang:counter64;
      description
        "Count number of packets that are transmitted by mac and dropped by the RS layer because the link is in fault state.";
    }
    leaf counter_slice7_ifg_mac_pool83_tx_drained_pkt_cnt_reg2_tx_drained_pkt_cnt {
      type oc-yang:counter64;
      description
        "Count number of packets that are transmitted by mac and dropped by the RS layer because the link is in fault state.";
    }
    leaf counter_slice7_ifg_mac_pool83_tx_drained_pkt_cnt_reg3_tx_drained_pkt_cnt {
      type oc-yang:counter64;
      description
        "Count number of packets that are transmitted by mac and dropped by the RS layer because the link is in fault state.";
    }
    leaf counter_slice7_ifg_mac_pool83_tx_drained_pkt_cnt_reg4_tx_drained_pkt_cnt {
      type oc-yang:counter64;
      description
        "Count number of packets that are transmitted by mac and dropped by the RS layer because the link is in fault state.";
    }
    leaf counter_slice7_ifg_mac_pool83_tx_drained_pkt_cnt_reg5_tx_drained_pkt_cnt {
      type oc-yang:counter64;
      description
        "Count number of packets that are transmitted by mac and dropped by the RS layer because the link is in fault state.";
    }
    leaf counter_slice7_ifg_mac_pool83_tx_drained_pkt_cnt_reg6_tx_drained_pkt_cnt {
      type oc-yang:counter64;
      description
        "Count number of packets that are transmitted by mac and dropped by the RS layer because the link is in fault state.";
    }
    leaf counter_slice7_ifg_mac_pool83_tx_drained_pkt_cnt_reg7_tx_drained_pkt_cnt {
      type oc-yang:counter64;
      description
        "Count number of packets that are transmitted by mac and dropped by the RS layer because the link is in fault state.";
    }
    leaf counter_slice7_ifg_mac_pool84_tx_drained_pkt_cnt_reg0_tx_drained_pkt_cnt {
      type oc-yang:counter64;
      description
        "Count number of packets that are transmitted by mac and dropped by the RS layer because the link is in fault state.";
    }
    leaf counter_slice7_ifg_mac_pool84_tx_drained_pkt_cnt_reg1_tx_drained_pkt_cnt {
      type oc-yang:counter64;
      description
        "Count number of packets that are transmitted by mac and dropped by the RS layer because the link is in fault state.";
    }
    leaf counter_slice7_ifg_mac_pool84_tx_drained_pkt_cnt_reg2_tx_drained_pkt_cnt {
      type oc-yang:counter64;
      description
        "Count number of packets that are transmitted by mac and dropped by the RS layer because the link is in fault state.";
    }
    leaf counter_slice7_ifg_mac_pool84_tx_drained_pkt_cnt_reg3_tx_drained_pkt_cnt {
      type oc-yang:counter64;
      description
        "Count number of packets that are transmitted by mac and dropped by the RS layer because the link is in fault state.";
    }
    leaf counter_slice7_ifg_mac_pool84_tx_drained_pkt_cnt_reg4_tx_drained_pkt_cnt {
      type oc-yang:counter64;
      description
        "Count number of packets that are transmitted by mac and dropped by the RS layer because the link is in fault state.";
    }
    leaf counter_slice7_ifg_mac_pool84_tx_drained_pkt_cnt_reg5_tx_drained_pkt_cnt {
      type oc-yang:counter64;
      description
        "Count number of packets that are transmitted by mac and dropped by the RS layer because the link is in fault state.";
    }
    leaf counter_slice7_ifg_mac_pool84_tx_drained_pkt_cnt_reg6_tx_drained_pkt_cnt {
      type oc-yang:counter64;
      description
        "Count number of packets that are transmitted by mac and dropped by the RS layer because the link is in fault state.";
    }
    leaf counter_slice7_ifg_mac_pool84_tx_drained_pkt_cnt_reg7_tx_drained_pkt_cnt {
      type oc-yang:counter64;
      description
        "Count number of packets that are transmitted by mac and dropped by the RS layer because the link is in fault state.";
    }
    leaf counter_slice7_ifg_mac_pool85_tx_drained_pkt_cnt_reg0_tx_drained_pkt_cnt {
      type oc-yang:counter64;
      description
        "Count number of packets that are transmitted by mac and dropped by the RS layer because the link is in fault state.";
    }
    leaf counter_slice7_ifg_mac_pool85_tx_drained_pkt_cnt_reg1_tx_drained_pkt_cnt {
      type oc-yang:counter64;
      description
        "Count number of packets that are transmitted by mac and dropped by the RS layer because the link is in fault state.";
    }
    leaf counter_slice7_ifg_mac_pool85_tx_drained_pkt_cnt_reg2_tx_drained_pkt_cnt {
      type oc-yang:counter64;
      description
        "Count number of packets that are transmitted by mac and dropped by the RS layer because the link is in fault state.";
    }
    leaf counter_slice7_ifg_mac_pool85_tx_drained_pkt_cnt_reg3_tx_drained_pkt_cnt {
      type oc-yang:counter64;
      description
        "Count number of packets that are transmitted by mac and dropped by the RS layer because the link is in fault state.";
    }
    leaf counter_slice7_ifg_mac_pool85_tx_drained_pkt_cnt_reg4_tx_drained_pkt_cnt {
      type oc-yang:counter64;
      description
        "Count number of packets that are transmitted by mac and dropped by the RS layer because the link is in fault state.";
    }
    leaf counter_slice7_ifg_mac_pool85_tx_drained_pkt_cnt_reg5_tx_drained_pkt_cnt {
      type oc-yang:counter64;
      description
        "Count number of packets that are transmitted by mac and dropped by the RS layer because the link is in fault state.";
    }
    leaf counter_slice7_ifg_mac_pool85_tx_drained_pkt_cnt_reg6_tx_drained_pkt_cnt {
      type oc-yang:counter64;
      description
        "Count number of packets that are transmitted by mac and dropped by the RS layer because the link is in fault state.";
    }
    leaf counter_slice7_ifg_mac_pool85_tx_drained_pkt_cnt_reg7_tx_drained_pkt_cnt {
      type oc-yang:counter64;
      description
        "Count number of packets that are transmitted by mac and dropped by the RS layer because the link is in fault state.";
    }
    leaf counter_slice7_ifg_mac_pool86_tx_drained_pkt_cnt_reg0_tx_drained_pkt_cnt {
      type oc-yang:counter64;
      description
        "Count number of packets that are transmitted by mac and dropped by the RS layer because the link is in fault state.";
    }
    leaf counter_slice7_ifg_mac_pool86_tx_drained_pkt_cnt_reg1_tx_drained_pkt_cnt {
      type oc-yang:counter64;
      description
        "Count number of packets that are transmitted by mac and dropped by the RS layer because the link is in fault state.";
    }
    leaf counter_slice7_ifg_mac_pool86_tx_drained_pkt_cnt_reg2_tx_drained_pkt_cnt {
      type oc-yang:counter64;
      description
        "Count number of packets that are transmitted by mac and dropped by the RS layer because the link is in fault state.";
    }
    leaf counter_slice7_ifg_mac_pool86_tx_drained_pkt_cnt_reg3_tx_drained_pkt_cnt {
      type oc-yang:counter64;
      description
        "Count number of packets that are transmitted by mac and dropped by the RS layer because the link is in fault state.";
    }
    leaf counter_slice7_ifg_mac_pool86_tx_drained_pkt_cnt_reg4_tx_drained_pkt_cnt {
      type oc-yang:counter64;
      description
        "Count number of packets that are transmitted by mac and dropped by the RS layer because the link is in fault state.";
    }
    leaf counter_slice7_ifg_mac_pool86_tx_drained_pkt_cnt_reg5_tx_drained_pkt_cnt {
      type oc-yang:counter64;
      description
        "Count number of packets that are transmitted by mac and dropped by the RS layer because the link is in fault state.";
    }
    leaf counter_slice7_ifg_mac_pool86_tx_drained_pkt_cnt_reg6_tx_drained_pkt_cnt {
      type oc-yang:counter64;
      description
        "Count number of packets that are transmitted by mac and dropped by the RS layer because the link is in fault state.";
    }
    leaf counter_slice7_ifg_mac_pool86_tx_drained_pkt_cnt_reg7_tx_drained_pkt_cnt {
      type oc-yang:counter64;
      description
        "Count number of packets that are transmitted by mac and dropped by the RS layer because the link is in fault state.";
    }
    leaf counter_slice7_ifg_mac_pool87_tx_drained_pkt_cnt_reg0_tx_drained_pkt_cnt {
      type oc-yang:counter64;
      description
        "Count number of packets that are transmitted by mac and dropped by the RS layer because the link is in fault state.";
    }
    leaf counter_slice7_ifg_mac_pool87_tx_drained_pkt_cnt_reg1_tx_drained_pkt_cnt {
      type oc-yang:counter64;
      description
        "Count number of packets that are transmitted by mac and dropped by the RS layer because the link is in fault state.";
    }
    leaf counter_slice7_ifg_mac_pool87_tx_drained_pkt_cnt_reg2_tx_drained_pkt_cnt {
      type oc-yang:counter64;
      description
        "Count number of packets that are transmitted by mac and dropped by the RS layer because the link is in fault state.";
    }
    leaf counter_slice7_ifg_mac_pool87_tx_drained_pkt_cnt_reg3_tx_drained_pkt_cnt {
      type oc-yang:counter64;
      description
        "Count number of packets that are transmitted by mac and dropped by the RS layer because the link is in fault state.";
    }
    leaf counter_slice7_ifg_mac_pool87_tx_drained_pkt_cnt_reg4_tx_drained_pkt_cnt {
      type oc-yang:counter64;
      description
        "Count number of packets that are transmitted by mac and dropped by the RS layer because the link is in fault state.";
    }
    leaf counter_slice7_ifg_mac_pool87_tx_drained_pkt_cnt_reg5_tx_drained_pkt_cnt {
      type oc-yang:counter64;
      description
        "Count number of packets that are transmitted by mac and dropped by the RS layer because the link is in fault state.";
    }
    leaf counter_slice7_ifg_mac_pool87_tx_drained_pkt_cnt_reg6_tx_drained_pkt_cnt {
      type oc-yang:counter64;
      description
        "Count number of packets that are transmitted by mac and dropped by the RS layer because the link is in fault state.";
    }
    leaf counter_slice7_ifg_mac_pool87_tx_drained_pkt_cnt_reg7_tx_drained_pkt_cnt {
      type oc-yang:counter64;
      description
        "Count number of packets that are transmitted by mac and dropped by the RS layer because the link is in fault state.";
    }
    leaf counter_slice8_ifg_mac_pool80_tx_drained_pkt_cnt_reg0_tx_drained_pkt_cnt {
      type oc-yang:counter64;
      description
        "Count number of packets that are transmitted by mac and dropped by the RS layer because the link is in fault state.";
    }
    leaf counter_slice8_ifg_mac_pool80_tx_drained_pkt_cnt_reg1_tx_drained_pkt_cnt {
      type oc-yang:counter64;
      description
        "Count number of packets that are transmitted by mac and dropped by the RS layer because the link is in fault state.";
    }
    leaf counter_slice8_ifg_mac_pool80_tx_drained_pkt_cnt_reg2_tx_drained_pkt_cnt {
      type oc-yang:counter64;
      description
        "Count number of packets that are transmitted by mac and dropped by the RS layer because the link is in fault state.";
    }
    leaf counter_slice8_ifg_mac_pool80_tx_drained_pkt_cnt_reg3_tx_drained_pkt_cnt {
      type oc-yang:counter64;
      description
        "Count number of packets that are transmitted by mac and dropped by the RS layer because the link is in fault state.";
    }
    leaf counter_slice8_ifg_mac_pool80_tx_drained_pkt_cnt_reg4_tx_drained_pkt_cnt {
      type oc-yang:counter64;
      description
        "Count number of packets that are transmitted by mac and dropped by the RS layer because the link is in fault state.";
    }
    leaf counter_slice8_ifg_mac_pool80_tx_drained_pkt_cnt_reg5_tx_drained_pkt_cnt {
      type oc-yang:counter64;
      description
        "Count number of packets that are transmitted by mac and dropped by the RS layer because the link is in fault state.";
    }
    leaf counter_slice8_ifg_mac_pool80_tx_drained_pkt_cnt_reg6_tx_drained_pkt_cnt {
      type oc-yang:counter64;
      description
        "Count number of packets that are transmitted by mac and dropped by the RS layer because the link is in fault state.";
    }
    leaf counter_slice8_ifg_mac_pool80_tx_drained_pkt_cnt_reg7_tx_drained_pkt_cnt {
      type oc-yang:counter64;
      description
        "Count number of packets that are transmitted by mac and dropped by the RS layer because the link is in fault state.";
    }
    leaf counter_slice8_ifg_mac_pool81_tx_drained_pkt_cnt_reg0_tx_drained_pkt_cnt {
      type oc-yang:counter64;
      description
        "Count number of packets that are transmitted by mac and dropped by the RS layer because the link is in fault state.";
    }
    leaf counter_slice8_ifg_mac_pool81_tx_drained_pkt_cnt_reg1_tx_drained_pkt_cnt {
      type oc-yang:counter64;
      description
        "Count number of packets that are transmitted by mac and dropped by the RS layer because the link is in fault state.";
    }
    leaf counter_slice8_ifg_mac_pool81_tx_drained_pkt_cnt_reg2_tx_drained_pkt_cnt {
      type oc-yang:counter64;
      description
        "Count number of packets that are transmitted by mac and dropped by the RS layer because the link is in fault state.";
    }
    leaf counter_slice8_ifg_mac_pool81_tx_drained_pkt_cnt_reg3_tx_drained_pkt_cnt {
      type oc-yang:counter64;
      description
        "Count number of packets that are transmitted by mac and dropped by the RS layer because the link is in fault state.";
    }
    leaf counter_slice8_ifg_mac_pool81_tx_drained_pkt_cnt_reg4_tx_drained_pkt_cnt {
      type oc-yang:counter64;
      description
        "Count number of packets that are transmitted by mac and dropped by the RS layer because the link is in fault state.";
    }
    leaf counter_slice8_ifg_mac_pool81_tx_drained_pkt_cnt_reg5_tx_drained_pkt_cnt {
      type oc-yang:counter64;
      description
        "Count number of packets that are transmitted by mac and dropped by the RS layer because the link is in fault state.";
    }
    leaf counter_slice8_ifg_mac_pool81_tx_drained_pkt_cnt_reg6_tx_drained_pkt_cnt {
      type oc-yang:counter64;
      description
        "Count number of packets that are transmitted by mac and dropped by the RS layer because the link is in fault state.";
    }
    leaf counter_slice8_ifg_mac_pool81_tx_drained_pkt_cnt_reg7_tx_drained_pkt_cnt {
      type oc-yang:counter64;
      description
        "Count number of packets that are transmitted by mac and dropped by the RS layer because the link is in fault state.";
    }
    leaf counter_slice8_ifg_mac_pool82_tx_drained_pkt_cnt_reg0_tx_drained_pkt_cnt {
      type oc-yang:counter64;
      description
        "Count number of packets that are transmitted by mac and dropped by the RS layer because the link is in fault state.";
    }
    leaf counter_slice8_ifg_mac_pool82_tx_drained_pkt_cnt_reg1_tx_drained_pkt_cnt {
      type oc-yang:counter64;
      description
        "Count number of packets that are transmitted by mac and dropped by the RS layer because the link is in fault state.";
    }
    leaf counter_slice8_ifg_mac_pool82_tx_drained_pkt_cnt_reg2_tx_drained_pkt_cnt {
      type oc-yang:counter64;
      description
        "Count number of packets that are transmitted by mac and dropped by the RS layer because the link is in fault state.";
    }
    leaf counter_slice8_ifg_mac_pool82_tx_drained_pkt_cnt_reg3_tx_drained_pkt_cnt {
      type oc-yang:counter64;
      description
        "Count number of packets that are transmitted by mac and dropped by the RS layer because the link is in fault state.";
    }
    leaf counter_slice8_ifg_mac_pool82_tx_drained_pkt_cnt_reg4_tx_drained_pkt_cnt {
      type oc-yang:counter64;
      description
        "Count number of packets that are transmitted by mac and dropped by the RS layer because the link is in fault state.";
    }
    leaf counter_slice8_ifg_mac_pool82_tx_drained_pkt_cnt_reg5_tx_drained_pkt_cnt {
      type oc-yang:counter64;
      description
        "Count number of packets that are transmitted by mac and dropped by the RS layer because the link is in fault state.";
    }
    leaf counter_slice8_ifg_mac_pool82_tx_drained_pkt_cnt_reg6_tx_drained_pkt_cnt {
      type oc-yang:counter64;
      description
        "Count number of packets that are transmitted by mac and dropped by the RS layer because the link is in fault state.";
    }
    leaf counter_slice8_ifg_mac_pool82_tx_drained_pkt_cnt_reg7_tx_drained_pkt_cnt {
      type oc-yang:counter64;
      description
        "Count number of packets that are transmitted by mac and dropped by the RS layer because the link is in fault state.";
    }
    leaf counter_slice8_ifg_mac_pool83_tx_drained_pkt_cnt_reg0_tx_drained_pkt_cnt {
      type oc-yang:counter64;
      description
        "Count number of packets that are transmitted by mac and dropped by the RS layer because the link is in fault state.";
    }
    leaf counter_slice8_ifg_mac_pool83_tx_drained_pkt_cnt_reg1_tx_drained_pkt_cnt {
      type oc-yang:counter64;
      description
        "Count number of packets that are transmitted by mac and dropped by the RS layer because the link is in fault state.";
    }
    leaf counter_slice8_ifg_mac_pool83_tx_drained_pkt_cnt_reg2_tx_drained_pkt_cnt {
      type oc-yang:counter64;
      description
        "Count number of packets that are transmitted by mac and dropped by the RS layer because the link is in fault state.";
    }
    leaf counter_slice8_ifg_mac_pool83_tx_drained_pkt_cnt_reg3_tx_drained_pkt_cnt {
      type oc-yang:counter64;
      description
        "Count number of packets that are transmitted by mac and dropped by the RS layer because the link is in fault state.";
    }
    leaf counter_slice8_ifg_mac_pool83_tx_drained_pkt_cnt_reg4_tx_drained_pkt_cnt {
      type oc-yang:counter64;
      description
        "Count number of packets that are transmitted by mac and dropped by the RS layer because the link is in fault state.";
    }
    leaf counter_slice8_ifg_mac_pool83_tx_drained_pkt_cnt_reg5_tx_drained_pkt_cnt {
      type oc-yang:counter64;
      description
        "Count number of packets that are transmitted by mac and dropped by the RS layer because the link is in fault state.";
    }
    leaf counter_slice8_ifg_mac_pool83_tx_drained_pkt_cnt_reg6_tx_drained_pkt_cnt {
      type oc-yang:counter64;
      description
        "Count number of packets that are transmitted by mac and dropped by the RS layer because the link is in fault state.";
    }
    leaf counter_slice8_ifg_mac_pool83_tx_drained_pkt_cnt_reg7_tx_drained_pkt_cnt {
      type oc-yang:counter64;
      description
        "Count number of packets that are transmitted by mac and dropped by the RS layer because the link is in fault state.";
    }
    leaf counter_slice8_ifg_mac_pool84_tx_drained_pkt_cnt_reg0_tx_drained_pkt_cnt {
      type oc-yang:counter64;
      description
        "Count number of packets that are transmitted by mac and dropped by the RS layer because the link is in fault state.";
    }
    leaf counter_slice8_ifg_mac_pool84_tx_drained_pkt_cnt_reg1_tx_drained_pkt_cnt {
      type oc-yang:counter64;
      description
        "Count number of packets that are transmitted by mac and dropped by the RS layer because the link is in fault state.";
    }
    leaf counter_slice8_ifg_mac_pool84_tx_drained_pkt_cnt_reg2_tx_drained_pkt_cnt {
      type oc-yang:counter64;
      description
        "Count number of packets that are transmitted by mac and dropped by the RS layer because the link is in fault state.";
    }
    leaf counter_slice8_ifg_mac_pool84_tx_drained_pkt_cnt_reg3_tx_drained_pkt_cnt {
      type oc-yang:counter64;
      description
        "Count number of packets that are transmitted by mac and dropped by the RS layer because the link is in fault state.";
    }
    leaf counter_slice8_ifg_mac_pool84_tx_drained_pkt_cnt_reg4_tx_drained_pkt_cnt {
      type oc-yang:counter64;
      description
        "Count number of packets that are transmitted by mac and dropped by the RS layer because the link is in fault state.";
    }
    leaf counter_slice8_ifg_mac_pool84_tx_drained_pkt_cnt_reg5_tx_drained_pkt_cnt {
      type oc-yang:counter64;
      description
        "Count number of packets that are transmitted by mac and dropped by the RS layer because the link is in fault state.";
    }
    leaf counter_slice8_ifg_mac_pool84_tx_drained_pkt_cnt_reg6_tx_drained_pkt_cnt {
      type oc-yang:counter64;
      description
        "Count number of packets that are transmitted by mac and dropped by the RS layer because the link is in fault state.";
    }
    leaf counter_slice8_ifg_mac_pool84_tx_drained_pkt_cnt_reg7_tx_drained_pkt_cnt {
      type oc-yang:counter64;
      description
        "Count number of packets that are transmitted by mac and dropped by the RS layer because the link is in fault state.";
    }
    leaf counter_slice8_ifg_mac_pool85_tx_drained_pkt_cnt_reg0_tx_drained_pkt_cnt {
      type oc-yang:counter64;
      description
        "Count number of packets that are transmitted by mac and dropped by the RS layer because the link is in fault state.";
    }
    leaf counter_slice8_ifg_mac_pool85_tx_drained_pkt_cnt_reg1_tx_drained_pkt_cnt {
      type oc-yang:counter64;
      description
        "Count number of packets that are transmitted by mac and dropped by the RS layer because the link is in fault state.";
    }
    leaf counter_slice8_ifg_mac_pool85_tx_drained_pkt_cnt_reg2_tx_drained_pkt_cnt {
      type oc-yang:counter64;
      description
        "Count number of packets that are transmitted by mac and dropped by the RS layer because the link is in fault state.";
    }
    leaf counter_slice8_ifg_mac_pool85_tx_drained_pkt_cnt_reg3_tx_drained_pkt_cnt {
      type oc-yang:counter64;
      description
        "Count number of packets that are transmitted by mac and dropped by the RS layer because the link is in fault state.";
    }
    leaf counter_slice8_ifg_mac_pool85_tx_drained_pkt_cnt_reg4_tx_drained_pkt_cnt {
      type oc-yang:counter64;
      description
        "Count number of packets that are transmitted by mac and dropped by the RS layer because the link is in fault state.";
    }
    leaf counter_slice8_ifg_mac_pool85_tx_drained_pkt_cnt_reg5_tx_drained_pkt_cnt {
      type oc-yang:counter64;
      description
        "Count number of packets that are transmitted by mac and dropped by the RS layer because the link is in fault state.";
    }
    leaf counter_slice8_ifg_mac_pool85_tx_drained_pkt_cnt_reg6_tx_drained_pkt_cnt {
      type oc-yang:counter64;
      description
        "Count number of packets that are transmitted by mac and dropped by the RS layer because the link is in fault state.";
    }
    leaf counter_slice8_ifg_mac_pool85_tx_drained_pkt_cnt_reg7_tx_drained_pkt_cnt {
      type oc-yang:counter64;
      description
        "Count number of packets that are transmitted by mac and dropped by the RS layer because the link is in fault state.";
    }
    leaf counter_slice8_ifg_mac_pool86_tx_drained_pkt_cnt_reg0_tx_drained_pkt_cnt {
      type oc-yang:counter64;
      description
        "Count number of packets that are transmitted by mac and dropped by the RS layer because the link is in fault state.";
    }
    leaf counter_slice8_ifg_mac_pool86_tx_drained_pkt_cnt_reg1_tx_drained_pkt_cnt {
      type oc-yang:counter64;
      description
        "Count number of packets that are transmitted by mac and dropped by the RS layer because the link is in fault state.";
    }
    leaf counter_slice8_ifg_mac_pool86_tx_drained_pkt_cnt_reg2_tx_drained_pkt_cnt {
      type oc-yang:counter64;
      description
        "Count number of packets that are transmitted by mac and dropped by the RS layer because the link is in fault state.";
    }
    leaf counter_slice8_ifg_mac_pool86_tx_drained_pkt_cnt_reg3_tx_drained_pkt_cnt {
      type oc-yang:counter64;
      description
        "Count number of packets that are transmitted by mac and dropped by the RS layer because the link is in fault state.";
    }
    leaf counter_slice8_ifg_mac_pool86_tx_drained_pkt_cnt_reg4_tx_drained_pkt_cnt {
      type oc-yang:counter64;
      description
        "Count number of packets that are transmitted by mac and dropped by the RS layer because the link is in fault state.";
    }
    leaf counter_slice8_ifg_mac_pool86_tx_drained_pkt_cnt_reg5_tx_drained_pkt_cnt {
      type oc-yang:counter64;
      description
        "Count number of packets that are transmitted by mac and dropped by the RS layer because the link is in fault state.";
    }
    leaf counter_slice8_ifg_mac_pool86_tx_drained_pkt_cnt_reg6_tx_drained_pkt_cnt {
      type oc-yang:counter64;
      description
        "Count number of packets that are transmitted by mac and dropped by the RS layer because the link is in fault state.";
    }
    leaf counter_slice8_ifg_mac_pool86_tx_drained_pkt_cnt_reg7_tx_drained_pkt_cnt {
      type oc-yang:counter64;
      description
        "Count number of packets that are transmitted by mac and dropped by the RS layer because the link is in fault state.";
    }
    leaf counter_slice8_ifg_mac_pool87_tx_drained_pkt_cnt_reg0_tx_drained_pkt_cnt {
      type oc-yang:counter64;
      description
        "Count number of packets that are transmitted by mac and dropped by the RS layer because the link is in fault state.";
    }
    leaf counter_slice8_ifg_mac_pool87_tx_drained_pkt_cnt_reg1_tx_drained_pkt_cnt {
      type oc-yang:counter64;
      description
        "Count number of packets that are transmitted by mac and dropped by the RS layer because the link is in fault state.";
    }
    leaf counter_slice8_ifg_mac_pool87_tx_drained_pkt_cnt_reg2_tx_drained_pkt_cnt {
      type oc-yang:counter64;
      description
        "Count number of packets that are transmitted by mac and dropped by the RS layer because the link is in fault state.";
    }
    leaf counter_slice8_ifg_mac_pool87_tx_drained_pkt_cnt_reg3_tx_drained_pkt_cnt {
      type oc-yang:counter64;
      description
        "Count number of packets that are transmitted by mac and dropped by the RS layer because the link is in fault state.";
    }
    leaf counter_slice8_ifg_mac_pool87_tx_drained_pkt_cnt_reg4_tx_drained_pkt_cnt {
      type oc-yang:counter64;
      description
        "Count number of packets that are transmitted by mac and dropped by the RS layer because the link is in fault state.";
    }
    leaf counter_slice8_ifg_mac_pool87_tx_drained_pkt_cnt_reg5_tx_drained_pkt_cnt {
      type oc-yang:counter64;
      description
        "Count number of packets that are transmitted by mac and dropped by the RS layer because the link is in fault state.";
    }
    leaf counter_slice8_ifg_mac_pool87_tx_drained_pkt_cnt_reg6_tx_drained_pkt_cnt {
      type oc-yang:counter64;
      description
        "Count number of packets that are transmitted by mac and dropped by the RS layer because the link is in fault state.";
    }
    leaf counter_slice8_ifg_mac_pool87_tx_drained_pkt_cnt_reg7_tx_drained_pkt_cnt {
      type oc-yang:counter64;
      description
        "Count number of packets that are transmitted by mac and dropped by the RS layer because the link is in fault state.";
    }
    leaf counter_slice9_ifg_mac_pool80_tx_drained_pkt_cnt_reg0_tx_drained_pkt_cnt {
      type oc-yang:counter64;
      description
        "Count number of packets that are transmitted by mac and dropped by the RS layer because the link is in fault state.";
    }
    leaf counter_slice9_ifg_mac_pool80_tx_drained_pkt_cnt_reg1_tx_drained_pkt_cnt {
      type oc-yang:counter64;
      description
        "Count number of packets that are transmitted by mac and dropped by the RS layer because the link is in fault state.";
    }
    leaf counter_slice9_ifg_mac_pool80_tx_drained_pkt_cnt_reg2_tx_drained_pkt_cnt {
      type oc-yang:counter64;
      description
        "Count number of packets that are transmitted by mac and dropped by the RS layer because the link is in fault state.";
    }
    leaf counter_slice9_ifg_mac_pool80_tx_drained_pkt_cnt_reg3_tx_drained_pkt_cnt {
      type oc-yang:counter64;
      description
        "Count number of packets that are transmitted by mac and dropped by the RS layer because the link is in fault state.";
    }
    leaf counter_slice9_ifg_mac_pool80_tx_drained_pkt_cnt_reg4_tx_drained_pkt_cnt {
      type oc-yang:counter64;
      description
        "Count number of packets that are transmitted by mac and dropped by the RS layer because the link is in fault state.";
    }
    leaf counter_slice9_ifg_mac_pool80_tx_drained_pkt_cnt_reg5_tx_drained_pkt_cnt {
      type oc-yang:counter64;
      description
        "Count number of packets that are transmitted by mac and dropped by the RS layer because the link is in fault state.";
    }
    leaf counter_slice9_ifg_mac_pool80_tx_drained_pkt_cnt_reg6_tx_drained_pkt_cnt {
      type oc-yang:counter64;
      description
        "Count number of packets that are transmitted by mac and dropped by the RS layer because the link is in fault state.";
    }
    leaf counter_slice9_ifg_mac_pool80_tx_drained_pkt_cnt_reg7_tx_drained_pkt_cnt {
      type oc-yang:counter64;
      description
        "Count number of packets that are transmitted by mac and dropped by the RS layer because the link is in fault state.";
    }
    leaf counter_slice9_ifg_mac_pool81_tx_drained_pkt_cnt_reg0_tx_drained_pkt_cnt {
      type oc-yang:counter64;
      description
        "Count number of packets that are transmitted by mac and dropped by the RS layer because the link is in fault state.";
    }
    leaf counter_slice9_ifg_mac_pool81_tx_drained_pkt_cnt_reg1_tx_drained_pkt_cnt {
      type oc-yang:counter64;
      description
        "Count number of packets that are transmitted by mac and dropped by the RS layer because the link is in fault state.";
    }
    leaf counter_slice9_ifg_mac_pool81_tx_drained_pkt_cnt_reg2_tx_drained_pkt_cnt {
      type oc-yang:counter64;
      description
        "Count number of packets that are transmitted by mac and dropped by the RS layer because the link is in fault state.";
    }
    leaf counter_slice9_ifg_mac_pool81_tx_drained_pkt_cnt_reg3_tx_drained_pkt_cnt {
      type oc-yang:counter64;
      description
        "Count number of packets that are transmitted by mac and dropped by the RS layer because the link is in fault state.";
    }
    leaf counter_slice9_ifg_mac_pool81_tx_drained_pkt_cnt_reg4_tx_drained_pkt_cnt {
      type oc-yang:counter64;
      description
        "Count number of packets that are transmitted by mac and dropped by the RS layer because the link is in fault state.";
    }
    leaf counter_slice9_ifg_mac_pool81_tx_drained_pkt_cnt_reg5_tx_drained_pkt_cnt {
      type oc-yang:counter64;
      description
        "Count number of packets that are transmitted by mac and dropped by the RS layer because the link is in fault state.";
    }
    leaf counter_slice9_ifg_mac_pool81_tx_drained_pkt_cnt_reg6_tx_drained_pkt_cnt {
      type oc-yang:counter64;
      description
        "Count number of packets that are transmitted by mac and dropped by the RS layer because the link is in fault state.";
    }
    leaf counter_slice9_ifg_mac_pool81_tx_drained_pkt_cnt_reg7_tx_drained_pkt_cnt {
      type oc-yang:counter64;
      description
        "Count number of packets that are transmitted by mac and dropped by the RS layer because the link is in fault state.";
    }
    leaf counter_slice9_ifg_mac_pool82_tx_drained_pkt_cnt_reg0_tx_drained_pkt_cnt {
      type oc-yang:counter64;
      description
        "Count number of packets that are transmitted by mac and dropped by the RS layer because the link is in fault state.";
    }
    leaf counter_slice9_ifg_mac_pool82_tx_drained_pkt_cnt_reg1_tx_drained_pkt_cnt {
      type oc-yang:counter64;
      description
        "Count number of packets that are transmitted by mac and dropped by the RS layer because the link is in fault state.";
    }
    leaf counter_slice9_ifg_mac_pool82_tx_drained_pkt_cnt_reg2_tx_drained_pkt_cnt {
      type oc-yang:counter64;
      description
        "Count number of packets that are transmitted by mac and dropped by the RS layer because the link is in fault state.";
    }
    leaf counter_slice9_ifg_mac_pool82_tx_drained_pkt_cnt_reg3_tx_drained_pkt_cnt {
      type oc-yang:counter64;
      description
        "Count number of packets that are transmitted by mac and dropped by the RS layer because the link is in fault state.";
    }
    leaf counter_slice9_ifg_mac_pool82_tx_drained_pkt_cnt_reg4_tx_drained_pkt_cnt {
      type oc-yang:counter64;
      description
        "Count number of packets that are transmitted by mac and dropped by the RS layer because the link is in fault state.";
    }
    leaf counter_slice9_ifg_mac_pool82_tx_drained_pkt_cnt_reg5_tx_drained_pkt_cnt {
      type oc-yang:counter64;
      description
        "Count number of packets that are transmitted by mac and dropped by the RS layer because the link is in fault state.";
    }
    leaf counter_slice9_ifg_mac_pool82_tx_drained_pkt_cnt_reg6_tx_drained_pkt_cnt {
      type oc-yang:counter64;
      description
        "Count number of packets that are transmitted by mac and dropped by the RS layer because the link is in fault state.";
    }
    leaf counter_slice9_ifg_mac_pool82_tx_drained_pkt_cnt_reg7_tx_drained_pkt_cnt {
      type oc-yang:counter64;
      description
        "Count number of packets that are transmitted by mac and dropped by the RS layer because the link is in fault state.";
    }
    leaf counter_slice9_ifg_mac_pool83_tx_drained_pkt_cnt_reg0_tx_drained_pkt_cnt {
      type oc-yang:counter64;
      description
        "Count number of packets that are transmitted by mac and dropped by the RS layer because the link is in fault state.";
    }
    leaf counter_slice9_ifg_mac_pool83_tx_drained_pkt_cnt_reg1_tx_drained_pkt_cnt {
      type oc-yang:counter64;
      description
        "Count number of packets that are transmitted by mac and dropped by the RS layer because the link is in fault state.";
    }
    leaf counter_slice9_ifg_mac_pool83_tx_drained_pkt_cnt_reg2_tx_drained_pkt_cnt {
      type oc-yang:counter64;
      description
        "Count number of packets that are transmitted by mac and dropped by the RS layer because the link is in fault state.";
    }
    leaf counter_slice9_ifg_mac_pool83_tx_drained_pkt_cnt_reg3_tx_drained_pkt_cnt {
      type oc-yang:counter64;
      description
        "Count number of packets that are transmitted by mac and dropped by the RS layer because the link is in fault state.";
    }
    leaf counter_slice9_ifg_mac_pool83_tx_drained_pkt_cnt_reg4_tx_drained_pkt_cnt {
      type oc-yang:counter64;
      description
        "Count number of packets that are transmitted by mac and dropped by the RS layer because the link is in fault state.";
    }
    leaf counter_slice9_ifg_mac_pool83_tx_drained_pkt_cnt_reg5_tx_drained_pkt_cnt {
      type oc-yang:counter64;
      description
        "Count number of packets that are transmitted by mac and dropped by the RS layer because the link is in fault state.";
    }
    leaf counter_slice9_ifg_mac_pool83_tx_drained_pkt_cnt_reg6_tx_drained_pkt_cnt {
      type oc-yang:counter64;
      description
        "Count number of packets that are transmitted by mac and dropped by the RS layer because the link is in fault state.";
    }
    leaf counter_slice9_ifg_mac_pool83_tx_drained_pkt_cnt_reg7_tx_drained_pkt_cnt {
      type oc-yang:counter64;
      description
        "Count number of packets that are transmitted by mac and dropped by the RS layer because the link is in fault state.";
    }
    leaf counter_slice9_ifg_mac_pool84_tx_drained_pkt_cnt_reg0_tx_drained_pkt_cnt {
      type oc-yang:counter64;
      description
        "Count number of packets that are transmitted by mac and dropped by the RS layer because the link is in fault state.";
    }
    leaf counter_slice9_ifg_mac_pool84_tx_drained_pkt_cnt_reg1_tx_drained_pkt_cnt {
      type oc-yang:counter64;
      description
        "Count number of packets that are transmitted by mac and dropped by the RS layer because the link is in fault state.";
    }
    leaf counter_slice9_ifg_mac_pool84_tx_drained_pkt_cnt_reg2_tx_drained_pkt_cnt {
      type oc-yang:counter64;
      description
        "Count number of packets that are transmitted by mac and dropped by the RS layer because the link is in fault state.";
    }
    leaf counter_slice9_ifg_mac_pool84_tx_drained_pkt_cnt_reg3_tx_drained_pkt_cnt {
      type oc-yang:counter64;
      description
        "Count number of packets that are transmitted by mac and dropped by the RS layer because the link is in fault state.";
    }
    leaf counter_slice9_ifg_mac_pool84_tx_drained_pkt_cnt_reg4_tx_drained_pkt_cnt {
      type oc-yang:counter64;
      description
        "Count number of packets that are transmitted by mac and dropped by the RS layer because the link is in fault state.";
    }
    leaf counter_slice9_ifg_mac_pool84_tx_drained_pkt_cnt_reg5_tx_drained_pkt_cnt {
      type oc-yang:counter64;
      description
        "Count number of packets that are transmitted by mac and dropped by the RS layer because the link is in fault state.";
    }
    leaf counter_slice9_ifg_mac_pool84_tx_drained_pkt_cnt_reg6_tx_drained_pkt_cnt {
      type oc-yang:counter64;
      description
        "Count number of packets that are transmitted by mac and dropped by the RS layer because the link is in fault state.";
    }
    leaf counter_slice9_ifg_mac_pool84_tx_drained_pkt_cnt_reg7_tx_drained_pkt_cnt {
      type oc-yang:counter64;
      description
        "Count number of packets that are transmitted by mac and dropped by the RS layer because the link is in fault state.";
    }
    leaf counter_slice9_ifg_mac_pool85_tx_drained_pkt_cnt_reg0_tx_drained_pkt_cnt {
      type oc-yang:counter64;
      description
        "Count number of packets that are transmitted by mac and dropped by the RS layer because the link is in fault state.";
    }
    leaf counter_slice9_ifg_mac_pool85_tx_drained_pkt_cnt_reg1_tx_drained_pkt_cnt {
      type oc-yang:counter64;
      description
        "Count number of packets that are transmitted by mac and dropped by the RS layer because the link is in fault state.";
    }
    leaf counter_slice9_ifg_mac_pool85_tx_drained_pkt_cnt_reg2_tx_drained_pkt_cnt {
      type oc-yang:counter64;
      description
        "Count number of packets that are transmitted by mac and dropped by the RS layer because the link is in fault state.";
    }
    leaf counter_slice9_ifg_mac_pool85_tx_drained_pkt_cnt_reg3_tx_drained_pkt_cnt {
      type oc-yang:counter64;
      description
        "Count number of packets that are transmitted by mac and dropped by the RS layer because the link is in fault state.";
    }
    leaf counter_slice9_ifg_mac_pool85_tx_drained_pkt_cnt_reg4_tx_drained_pkt_cnt {
      type oc-yang:counter64;
      description
        "Count number of packets that are transmitted by mac and dropped by the RS layer because the link is in fault state.";
    }
    leaf counter_slice9_ifg_mac_pool85_tx_drained_pkt_cnt_reg5_tx_drained_pkt_cnt {
      type oc-yang:counter64;
      description
        "Count number of packets that are transmitted by mac and dropped by the RS layer because the link is in fault state.";
    }
    leaf counter_slice9_ifg_mac_pool85_tx_drained_pkt_cnt_reg6_tx_drained_pkt_cnt {
      type oc-yang:counter64;
      description
        "Count number of packets that are transmitted by mac and dropped by the RS layer because the link is in fault state.";
    }
    leaf counter_slice9_ifg_mac_pool85_tx_drained_pkt_cnt_reg7_tx_drained_pkt_cnt {
      type oc-yang:counter64;
      description
        "Count number of packets that are transmitted by mac and dropped by the RS layer because the link is in fault state.";
    }
    leaf counter_slice9_ifg_mac_pool86_tx_drained_pkt_cnt_reg0_tx_drained_pkt_cnt {
      type oc-yang:counter64;
      description
        "Count number of packets that are transmitted by mac and dropped by the RS layer because the link is in fault state.";
    }
    leaf counter_slice9_ifg_mac_pool86_tx_drained_pkt_cnt_reg1_tx_drained_pkt_cnt {
      type oc-yang:counter64;
      description
        "Count number of packets that are transmitted by mac and dropped by the RS layer because the link is in fault state.";
    }
    leaf counter_slice9_ifg_mac_pool86_tx_drained_pkt_cnt_reg2_tx_drained_pkt_cnt {
      type oc-yang:counter64;
      description
        "Count number of packets that are transmitted by mac and dropped by the RS layer because the link is in fault state.";
    }
    leaf counter_slice9_ifg_mac_pool86_tx_drained_pkt_cnt_reg3_tx_drained_pkt_cnt {
      type oc-yang:counter64;
      description
        "Count number of packets that are transmitted by mac and dropped by the RS layer because the link is in fault state.";
    }
    leaf counter_slice9_ifg_mac_pool86_tx_drained_pkt_cnt_reg4_tx_drained_pkt_cnt {
      type oc-yang:counter64;
      description
        "Count number of packets that are transmitted by mac and dropped by the RS layer because the link is in fault state.";
    }
    leaf counter_slice9_ifg_mac_pool86_tx_drained_pkt_cnt_reg5_tx_drained_pkt_cnt {
      type oc-yang:counter64;
      description
        "Count number of packets that are transmitted by mac and dropped by the RS layer because the link is in fault state.";
    }
    leaf counter_slice9_ifg_mac_pool86_tx_drained_pkt_cnt_reg6_tx_drained_pkt_cnt {
      type oc-yang:counter64;
      description
        "Count number of packets that are transmitted by mac and dropped by the RS layer because the link is in fault state.";
    }
    leaf counter_slice9_ifg_mac_pool86_tx_drained_pkt_cnt_reg7_tx_drained_pkt_cnt {
      type oc-yang:counter64;
      description
        "Count number of packets that are transmitted by mac and dropped by the RS layer because the link is in fault state.";
    }
    leaf counter_slice9_ifg_mac_pool87_tx_drained_pkt_cnt_reg0_tx_drained_pkt_cnt {
      type oc-yang:counter64;
      description
        "Count number of packets that are transmitted by mac and dropped by the RS layer because the link is in fault state.";
    }
    leaf counter_slice9_ifg_mac_pool87_tx_drained_pkt_cnt_reg1_tx_drained_pkt_cnt {
      type oc-yang:counter64;
      description
        "Count number of packets that are transmitted by mac and dropped by the RS layer because the link is in fault state.";
    }
    leaf counter_slice9_ifg_mac_pool87_tx_drained_pkt_cnt_reg2_tx_drained_pkt_cnt {
      type oc-yang:counter64;
      description
        "Count number of packets that are transmitted by mac and dropped by the RS layer because the link is in fault state.";
    }
    leaf counter_slice9_ifg_mac_pool87_tx_drained_pkt_cnt_reg3_tx_drained_pkt_cnt {
      type oc-yang:counter64;
      description
        "Count number of packets that are transmitted by mac and dropped by the RS layer because the link is in fault state.";
    }
    leaf counter_slice9_ifg_mac_pool87_tx_drained_pkt_cnt_reg4_tx_drained_pkt_cnt {
      type oc-yang:counter64;
      description
        "Count number of packets that are transmitted by mac and dropped by the RS layer because the link is in fault state.";
    }
    leaf counter_slice9_ifg_mac_pool87_tx_drained_pkt_cnt_reg5_tx_drained_pkt_cnt {
      type oc-yang:counter64;
      description
        "Count number of packets that are transmitted by mac and dropped by the RS layer because the link is in fault state.";
    }
    leaf counter_slice9_ifg_mac_pool87_tx_drained_pkt_cnt_reg6_tx_drained_pkt_cnt {
      type oc-yang:counter64;
      description
        "Count number of packets that are transmitted by mac and dropped by the RS layer because the link is in fault state.";
    }
    leaf counter_slice9_ifg_mac_pool87_tx_drained_pkt_cnt_reg7_tx_drained_pkt_cnt {
      type oc-yang:counter64;
      description
        "Count number of packets that are transmitted by mac and dropped by the RS layer because the link is in fault state.";
    }
    leaf counter_slice10_ifg_mac_pool80_tx_drained_pkt_cnt_reg0_tx_drained_pkt_cnt {
      type oc-yang:counter64;
      description
        "Count number of packets that are transmitted by mac and dropped by the RS layer because the link is in fault state.";
    }
    leaf counter_slice10_ifg_mac_pool80_tx_drained_pkt_cnt_reg1_tx_drained_pkt_cnt {
      type oc-yang:counter64;
      description
        "Count number of packets that are transmitted by mac and dropped by the RS layer because the link is in fault state.";
    }
    leaf counter_slice10_ifg_mac_pool80_tx_drained_pkt_cnt_reg2_tx_drained_pkt_cnt {
      type oc-yang:counter64;
      description
        "Count number of packets that are transmitted by mac and dropped by the RS layer because the link is in fault state.";
    }
    leaf counter_slice10_ifg_mac_pool80_tx_drained_pkt_cnt_reg3_tx_drained_pkt_cnt {
      type oc-yang:counter64;
      description
        "Count number of packets that are transmitted by mac and dropped by the RS layer because the link is in fault state.";
    }
    leaf counter_slice10_ifg_mac_pool80_tx_drained_pkt_cnt_reg4_tx_drained_pkt_cnt {
      type oc-yang:counter64;
      description
        "Count number of packets that are transmitted by mac and dropped by the RS layer because the link is in fault state.";
    }
    leaf counter_slice10_ifg_mac_pool80_tx_drained_pkt_cnt_reg5_tx_drained_pkt_cnt {
      type oc-yang:counter64;
      description
        "Count number of packets that are transmitted by mac and dropped by the RS layer because the link is in fault state.";
    }
    leaf counter_slice10_ifg_mac_pool80_tx_drained_pkt_cnt_reg6_tx_drained_pkt_cnt {
      type oc-yang:counter64;
      description
        "Count number of packets that are transmitted by mac and dropped by the RS layer because the link is in fault state.";
    }
    leaf counter_slice10_ifg_mac_pool80_tx_drained_pkt_cnt_reg7_tx_drained_pkt_cnt {
      type oc-yang:counter64;
      description
        "Count number of packets that are transmitted by mac and dropped by the RS layer because the link is in fault state.";
    }
    leaf counter_slice10_ifg_mac_pool81_tx_drained_pkt_cnt_reg0_tx_drained_pkt_cnt {
      type oc-yang:counter64;
      description
        "Count number of packets that are transmitted by mac and dropped by the RS layer because the link is in fault state.";
    }
    leaf counter_slice10_ifg_mac_pool81_tx_drained_pkt_cnt_reg1_tx_drained_pkt_cnt {
      type oc-yang:counter64;
      description
        "Count number of packets that are transmitted by mac and dropped by the RS layer because the link is in fault state.";
    }
    leaf counter_slice10_ifg_mac_pool81_tx_drained_pkt_cnt_reg2_tx_drained_pkt_cnt {
      type oc-yang:counter64;
      description
        "Count number of packets that are transmitted by mac and dropped by the RS layer because the link is in fault state.";
    }
    leaf counter_slice10_ifg_mac_pool81_tx_drained_pkt_cnt_reg3_tx_drained_pkt_cnt {
      type oc-yang:counter64;
      description
        "Count number of packets that are transmitted by mac and dropped by the RS layer because the link is in fault state.";
    }
    leaf counter_slice10_ifg_mac_pool81_tx_drained_pkt_cnt_reg4_tx_drained_pkt_cnt {
      type oc-yang:counter64;
      description
        "Count number of packets that are transmitted by mac and dropped by the RS layer because the link is in fault state.";
    }
    leaf counter_slice10_ifg_mac_pool81_tx_drained_pkt_cnt_reg5_tx_drained_pkt_cnt {
      type oc-yang:counter64;
      description
        "Count number of packets that are transmitted by mac and dropped by the RS layer because the link is in fault state.";
    }
    leaf counter_slice10_ifg_mac_pool81_tx_drained_pkt_cnt_reg6_tx_drained_pkt_cnt {
      type oc-yang:counter64;
      description
        "Count number of packets that are transmitted by mac and dropped by the RS layer because the link is in fault state.";
    }
    leaf counter_slice10_ifg_mac_pool81_tx_drained_pkt_cnt_reg7_tx_drained_pkt_cnt {
      type oc-yang:counter64;
      description
        "Count number of packets that are transmitted by mac and dropped by the RS layer because the link is in fault state.";
    }
    leaf counter_slice10_ifg_mac_pool82_tx_drained_pkt_cnt_reg0_tx_drained_pkt_cnt {
      type oc-yang:counter64;
      description
        "Count number of packets that are transmitted by mac and dropped by the RS layer because the link is in fault state.";
    }
    leaf counter_slice10_ifg_mac_pool82_tx_drained_pkt_cnt_reg1_tx_drained_pkt_cnt {
      type oc-yang:counter64;
      description
        "Count number of packets that are transmitted by mac and dropped by the RS layer because the link is in fault state.";
    }
    leaf counter_slice10_ifg_mac_pool82_tx_drained_pkt_cnt_reg2_tx_drained_pkt_cnt {
      type oc-yang:counter64;
      description
        "Count number of packets that are transmitted by mac and dropped by the RS layer because the link is in fault state.";
    }
    leaf counter_slice10_ifg_mac_pool82_tx_drained_pkt_cnt_reg3_tx_drained_pkt_cnt {
      type oc-yang:counter64;
      description
        "Count number of packets that are transmitted by mac and dropped by the RS layer because the link is in fault state.";
    }
    leaf counter_slice10_ifg_mac_pool82_tx_drained_pkt_cnt_reg4_tx_drained_pkt_cnt {
      type oc-yang:counter64;
      description
        "Count number of packets that are transmitted by mac and dropped by the RS layer because the link is in fault state.";
    }
    leaf counter_slice10_ifg_mac_pool82_tx_drained_pkt_cnt_reg5_tx_drained_pkt_cnt {
      type oc-yang:counter64;
      description
        "Count number of packets that are transmitted by mac and dropped by the RS layer because the link is in fault state.";
    }
    leaf counter_slice10_ifg_mac_pool82_tx_drained_pkt_cnt_reg6_tx_drained_pkt_cnt {
      type oc-yang:counter64;
      description
        "Count number of packets that are transmitted by mac and dropped by the RS layer because the link is in fault state.";
    }
    leaf counter_slice10_ifg_mac_pool82_tx_drained_pkt_cnt_reg7_tx_drained_pkt_cnt {
      type oc-yang:counter64;
      description
        "Count number of packets that are transmitted by mac and dropped by the RS layer because the link is in fault state.";
    }
    leaf counter_slice10_ifg_mac_pool83_tx_drained_pkt_cnt_reg0_tx_drained_pkt_cnt {
      type oc-yang:counter64;
      description
        "Count number of packets that are transmitted by mac and dropped by the RS layer because the link is in fault state.";
    }
    leaf counter_slice10_ifg_mac_pool83_tx_drained_pkt_cnt_reg1_tx_drained_pkt_cnt {
      type oc-yang:counter64;
      description
        "Count number of packets that are transmitted by mac and dropped by the RS layer because the link is in fault state.";
    }
    leaf counter_slice10_ifg_mac_pool83_tx_drained_pkt_cnt_reg2_tx_drained_pkt_cnt {
      type oc-yang:counter64;
      description
        "Count number of packets that are transmitted by mac and dropped by the RS layer because the link is in fault state.";
    }
    leaf counter_slice10_ifg_mac_pool83_tx_drained_pkt_cnt_reg3_tx_drained_pkt_cnt {
      type oc-yang:counter64;
      description
        "Count number of packets that are transmitted by mac and dropped by the RS layer because the link is in fault state.";
    }
    leaf counter_slice10_ifg_mac_pool83_tx_drained_pkt_cnt_reg4_tx_drained_pkt_cnt {
      type oc-yang:counter64;
      description
        "Count number of packets that are transmitted by mac and dropped by the RS layer because the link is in fault state.";
    }
    leaf counter_slice10_ifg_mac_pool83_tx_drained_pkt_cnt_reg5_tx_drained_pkt_cnt {
      type oc-yang:counter64;
      description
        "Count number of packets that are transmitted by mac and dropped by the RS layer because the link is in fault state.";
    }
    leaf counter_slice10_ifg_mac_pool83_tx_drained_pkt_cnt_reg6_tx_drained_pkt_cnt {
      type oc-yang:counter64;
      description
        "Count number of packets that are transmitted by mac and dropped by the RS layer because the link is in fault state.";
    }
    leaf counter_slice10_ifg_mac_pool83_tx_drained_pkt_cnt_reg7_tx_drained_pkt_cnt {
      type oc-yang:counter64;
      description
        "Count number of packets that are transmitted by mac and dropped by the RS layer because the link is in fault state.";
    }
    leaf counter_slice10_ifg_mac_pool84_tx_drained_pkt_cnt_reg0_tx_drained_pkt_cnt {
      type oc-yang:counter64;
      description
        "Count number of packets that are transmitted by mac and dropped by the RS layer because the link is in fault state.";
    }
    leaf counter_slice10_ifg_mac_pool84_tx_drained_pkt_cnt_reg1_tx_drained_pkt_cnt {
      type oc-yang:counter64;
      description
        "Count number of packets that are transmitted by mac and dropped by the RS layer because the link is in fault state.";
    }
    leaf counter_slice10_ifg_mac_pool84_tx_drained_pkt_cnt_reg2_tx_drained_pkt_cnt {
      type oc-yang:counter64;
      description
        "Count number of packets that are transmitted by mac and dropped by the RS layer because the link is in fault state.";
    }
    leaf counter_slice10_ifg_mac_pool84_tx_drained_pkt_cnt_reg3_tx_drained_pkt_cnt {
      type oc-yang:counter64;
      description
        "Count number of packets that are transmitted by mac and dropped by the RS layer because the link is in fault state.";
    }
    leaf counter_slice10_ifg_mac_pool84_tx_drained_pkt_cnt_reg4_tx_drained_pkt_cnt {
      type oc-yang:counter64;
      description
        "Count number of packets that are transmitted by mac and dropped by the RS layer because the link is in fault state.";
    }
    leaf counter_slice10_ifg_mac_pool84_tx_drained_pkt_cnt_reg5_tx_drained_pkt_cnt {
      type oc-yang:counter64;
      description
        "Count number of packets that are transmitted by mac and dropped by the RS layer because the link is in fault state.";
    }
    leaf counter_slice10_ifg_mac_pool84_tx_drained_pkt_cnt_reg6_tx_drained_pkt_cnt {
      type oc-yang:counter64;
      description
        "Count number of packets that are transmitted by mac and dropped by the RS layer because the link is in fault state.";
    }
    leaf counter_slice10_ifg_mac_pool84_tx_drained_pkt_cnt_reg7_tx_drained_pkt_cnt {
      type oc-yang:counter64;
      description
        "Count number of packets that are transmitted by mac and dropped by the RS layer because the link is in fault state.";
    }
    leaf counter_slice10_ifg_mac_pool85_tx_drained_pkt_cnt_reg0_tx_drained_pkt_cnt {
      type oc-yang:counter64;
      description
        "Count number of packets that are transmitted by mac and dropped by the RS layer because the link is in fault state.";
    }
    leaf counter_slice10_ifg_mac_pool85_tx_drained_pkt_cnt_reg1_tx_drained_pkt_cnt {
      type oc-yang:counter64;
      description
        "Count number of packets that are transmitted by mac and dropped by the RS layer because the link is in fault state.";
    }
    leaf counter_slice10_ifg_mac_pool85_tx_drained_pkt_cnt_reg2_tx_drained_pkt_cnt {
      type oc-yang:counter64;
      description
        "Count number of packets that are transmitted by mac and dropped by the RS layer because the link is in fault state.";
    }
    leaf counter_slice10_ifg_mac_pool85_tx_drained_pkt_cnt_reg3_tx_drained_pkt_cnt {
      type oc-yang:counter64;
      description
        "Count number of packets that are transmitted by mac and dropped by the RS layer because the link is in fault state.";
    }
    leaf counter_slice10_ifg_mac_pool85_tx_drained_pkt_cnt_reg4_tx_drained_pkt_cnt {
      type oc-yang:counter64;
      description
        "Count number of packets that are transmitted by mac and dropped by the RS layer because the link is in fault state.";
    }
    leaf counter_slice10_ifg_mac_pool85_tx_drained_pkt_cnt_reg5_tx_drained_pkt_cnt {
      type oc-yang:counter64;
      description
        "Count number of packets that are transmitted by mac and dropped by the RS layer because the link is in fault state.";
    }
    leaf counter_slice10_ifg_mac_pool85_tx_drained_pkt_cnt_reg6_tx_drained_pkt_cnt {
      type oc-yang:counter64;
      description
        "Count number of packets that are transmitted by mac and dropped by the RS layer because the link is in fault state.";
    }
    leaf counter_slice10_ifg_mac_pool85_tx_drained_pkt_cnt_reg7_tx_drained_pkt_cnt {
      type oc-yang:counter64;
      description
        "Count number of packets that are transmitted by mac and dropped by the RS layer because the link is in fault state.";
    }
    leaf counter_slice10_ifg_mac_pool86_tx_drained_pkt_cnt_reg0_tx_drained_pkt_cnt {
      type oc-yang:counter64;
      description
        "Count number of packets that are transmitted by mac and dropped by the RS layer because the link is in fault state.";
    }
    leaf counter_slice10_ifg_mac_pool86_tx_drained_pkt_cnt_reg1_tx_drained_pkt_cnt {
      type oc-yang:counter64;
      description
        "Count number of packets that are transmitted by mac and dropped by the RS layer because the link is in fault state.";
    }
    leaf counter_slice10_ifg_mac_pool86_tx_drained_pkt_cnt_reg2_tx_drained_pkt_cnt {
      type oc-yang:counter64;
      description
        "Count number of packets that are transmitted by mac and dropped by the RS layer because the link is in fault state.";
    }
    leaf counter_slice10_ifg_mac_pool86_tx_drained_pkt_cnt_reg3_tx_drained_pkt_cnt {
      type oc-yang:counter64;
      description
        "Count number of packets that are transmitted by mac and dropped by the RS layer because the link is in fault state.";
    }
    leaf counter_slice10_ifg_mac_pool86_tx_drained_pkt_cnt_reg4_tx_drained_pkt_cnt {
      type oc-yang:counter64;
      description
        "Count number of packets that are transmitted by mac and dropped by the RS layer because the link is in fault state.";
    }
    leaf counter_slice10_ifg_mac_pool86_tx_drained_pkt_cnt_reg5_tx_drained_pkt_cnt {
      type oc-yang:counter64;
      description
        "Count number of packets that are transmitted by mac and dropped by the RS layer because the link is in fault state.";
    }
    leaf counter_slice10_ifg_mac_pool86_tx_drained_pkt_cnt_reg6_tx_drained_pkt_cnt {
      type oc-yang:counter64;
      description
        "Count number of packets that are transmitted by mac and dropped by the RS layer because the link is in fault state.";
    }
    leaf counter_slice10_ifg_mac_pool86_tx_drained_pkt_cnt_reg7_tx_drained_pkt_cnt {
      type oc-yang:counter64;
      description
        "Count number of packets that are transmitted by mac and dropped by the RS layer because the link is in fault state.";
    }
    leaf counter_slice10_ifg_mac_pool87_tx_drained_pkt_cnt_reg0_tx_drained_pkt_cnt {
      type oc-yang:counter64;
      description
        "Count number of packets that are transmitted by mac and dropped by the RS layer because the link is in fault state.";
    }
    leaf counter_slice10_ifg_mac_pool87_tx_drained_pkt_cnt_reg1_tx_drained_pkt_cnt {
      type oc-yang:counter64;
      description
        "Count number of packets that are transmitted by mac and dropped by the RS layer because the link is in fault state.";
    }
    leaf counter_slice10_ifg_mac_pool87_tx_drained_pkt_cnt_reg2_tx_drained_pkt_cnt {
      type oc-yang:counter64;
      description
        "Count number of packets that are transmitted by mac and dropped by the RS layer because the link is in fault state.";
    }
    leaf counter_slice10_ifg_mac_pool87_tx_drained_pkt_cnt_reg3_tx_drained_pkt_cnt {
      type oc-yang:counter64;
      description
        "Count number of packets that are transmitted by mac and dropped by the RS layer because the link is in fault state.";
    }
    leaf counter_slice10_ifg_mac_pool87_tx_drained_pkt_cnt_reg4_tx_drained_pkt_cnt {
      type oc-yang:counter64;
      description
        "Count number of packets that are transmitted by mac and dropped by the RS layer because the link is in fault state.";
    }
    leaf counter_slice10_ifg_mac_pool87_tx_drained_pkt_cnt_reg5_tx_drained_pkt_cnt {
      type oc-yang:counter64;
      description
        "Count number of packets that are transmitted by mac and dropped by the RS layer because the link is in fault state.";
    }
    leaf counter_slice10_ifg_mac_pool87_tx_drained_pkt_cnt_reg6_tx_drained_pkt_cnt {
      type oc-yang:counter64;
      description
        "Count number of packets that are transmitted by mac and dropped by the RS layer because the link is in fault state.";
    }
    leaf counter_slice10_ifg_mac_pool87_tx_drained_pkt_cnt_reg7_tx_drained_pkt_cnt {
      type oc-yang:counter64;
      description
        "Count number of packets that are transmitted by mac and dropped by the RS layer because the link is in fault state.";
    }
    leaf counter_slice11_ifg_mac_pool80_tx_drained_pkt_cnt_reg0_tx_drained_pkt_cnt {
      type oc-yang:counter64;
      description
        "Count number of packets that are transmitted by mac and dropped by the RS layer because the link is in fault state.";
    }
    leaf counter_slice11_ifg_mac_pool80_tx_drained_pkt_cnt_reg1_tx_drained_pkt_cnt {
      type oc-yang:counter64;
      description
        "Count number of packets that are transmitted by mac and dropped by the RS layer because the link is in fault state.";
    }
    leaf counter_slice11_ifg_mac_pool80_tx_drained_pkt_cnt_reg2_tx_drained_pkt_cnt {
      type oc-yang:counter64;
      description
        "Count number of packets that are transmitted by mac and dropped by the RS layer because the link is in fault state.";
    }
    leaf counter_slice11_ifg_mac_pool80_tx_drained_pkt_cnt_reg3_tx_drained_pkt_cnt {
      type oc-yang:counter64;
      description
        "Count number of packets that are transmitted by mac and dropped by the RS layer because the link is in fault state.";
    }
    leaf counter_slice11_ifg_mac_pool80_tx_drained_pkt_cnt_reg4_tx_drained_pkt_cnt {
      type oc-yang:counter64;
      description
        "Count number of packets that are transmitted by mac and dropped by the RS layer because the link is in fault state.";
    }
    leaf counter_slice11_ifg_mac_pool80_tx_drained_pkt_cnt_reg5_tx_drained_pkt_cnt {
      type oc-yang:counter64;
      description
        "Count number of packets that are transmitted by mac and dropped by the RS layer because the link is in fault state.";
    }
    leaf counter_slice11_ifg_mac_pool80_tx_drained_pkt_cnt_reg6_tx_drained_pkt_cnt {
      type oc-yang:counter64;
      description
        "Count number of packets that are transmitted by mac and dropped by the RS layer because the link is in fault state.";
    }
    leaf counter_slice11_ifg_mac_pool80_tx_drained_pkt_cnt_reg7_tx_drained_pkt_cnt {
      type oc-yang:counter64;
      description
        "Count number of packets that are transmitted by mac and dropped by the RS layer because the link is in fault state.";
    }
    leaf counter_slice11_ifg_mac_pool81_tx_drained_pkt_cnt_reg0_tx_drained_pkt_cnt {
      type oc-yang:counter64;
      description
        "Count number of packets that are transmitted by mac and dropped by the RS layer because the link is in fault state.";
    }
    leaf counter_slice11_ifg_mac_pool81_tx_drained_pkt_cnt_reg1_tx_drained_pkt_cnt {
      type oc-yang:counter64;
      description
        "Count number of packets that are transmitted by mac and dropped by the RS layer because the link is in fault state.";
    }
    leaf counter_slice11_ifg_mac_pool81_tx_drained_pkt_cnt_reg2_tx_drained_pkt_cnt {
      type oc-yang:counter64;
      description
        "Count number of packets that are transmitted by mac and dropped by the RS layer because the link is in fault state.";
    }
    leaf counter_slice11_ifg_mac_pool81_tx_drained_pkt_cnt_reg3_tx_drained_pkt_cnt {
      type oc-yang:counter64;
      description
        "Count number of packets that are transmitted by mac and dropped by the RS layer because the link is in fault state.";
    }
    leaf counter_slice11_ifg_mac_pool81_tx_drained_pkt_cnt_reg4_tx_drained_pkt_cnt {
      type oc-yang:counter64;
      description
        "Count number of packets that are transmitted by mac and dropped by the RS layer because the link is in fault state.";
    }
    leaf counter_slice11_ifg_mac_pool81_tx_drained_pkt_cnt_reg5_tx_drained_pkt_cnt {
      type oc-yang:counter64;
      description
        "Count number of packets that are transmitted by mac and dropped by the RS layer because the link is in fault state.";
    }
    leaf counter_slice11_ifg_mac_pool81_tx_drained_pkt_cnt_reg6_tx_drained_pkt_cnt {
      type oc-yang:counter64;
      description
        "Count number of packets that are transmitted by mac and dropped by the RS layer because the link is in fault state.";
    }
    leaf counter_slice11_ifg_mac_pool81_tx_drained_pkt_cnt_reg7_tx_drained_pkt_cnt {
      type oc-yang:counter64;
      description
        "Count number of packets that are transmitted by mac and dropped by the RS layer because the link is in fault state.";
    }
    leaf counter_slice11_ifg_mac_pool82_tx_drained_pkt_cnt_reg0_tx_drained_pkt_cnt {
      type oc-yang:counter64;
      description
        "Count number of packets that are transmitted by mac and dropped by the RS layer because the link is in fault state.";
    }
    leaf counter_slice11_ifg_mac_pool82_tx_drained_pkt_cnt_reg1_tx_drained_pkt_cnt {
      type oc-yang:counter64;
      description
        "Count number of packets that are transmitted by mac and dropped by the RS layer because the link is in fault state.";
    }
    leaf counter_slice11_ifg_mac_pool82_tx_drained_pkt_cnt_reg2_tx_drained_pkt_cnt {
      type oc-yang:counter64;
      description
        "Count number of packets that are transmitted by mac and dropped by the RS layer because the link is in fault state.";
    }
    leaf counter_slice11_ifg_mac_pool82_tx_drained_pkt_cnt_reg3_tx_drained_pkt_cnt {
      type oc-yang:counter64;
      description
        "Count number of packets that are transmitted by mac and dropped by the RS layer because the link is in fault state.";
    }
    leaf counter_slice11_ifg_mac_pool82_tx_drained_pkt_cnt_reg4_tx_drained_pkt_cnt {
      type oc-yang:counter64;
      description
        "Count number of packets that are transmitted by mac and dropped by the RS layer because the link is in fault state.";
    }
    leaf counter_slice11_ifg_mac_pool82_tx_drained_pkt_cnt_reg5_tx_drained_pkt_cnt {
      type oc-yang:counter64;
      description
        "Count number of packets that are transmitted by mac and dropped by the RS layer because the link is in fault state.";
    }
    leaf counter_slice11_ifg_mac_pool82_tx_drained_pkt_cnt_reg6_tx_drained_pkt_cnt {
      type oc-yang:counter64;
      description
        "Count number of packets that are transmitted by mac and dropped by the RS layer because the link is in fault state.";
    }
    leaf counter_slice11_ifg_mac_pool82_tx_drained_pkt_cnt_reg7_tx_drained_pkt_cnt {
      type oc-yang:counter64;
      description
        "Count number of packets that are transmitted by mac and dropped by the RS layer because the link is in fault state.";
    }
    leaf counter_slice11_ifg_mac_pool83_tx_drained_pkt_cnt_reg0_tx_drained_pkt_cnt {
      type oc-yang:counter64;
      description
        "Count number of packets that are transmitted by mac and dropped by the RS layer because the link is in fault state.";
    }
    leaf counter_slice11_ifg_mac_pool83_tx_drained_pkt_cnt_reg1_tx_drained_pkt_cnt {
      type oc-yang:counter64;
      description
        "Count number of packets that are transmitted by mac and dropped by the RS layer because the link is in fault state.";
    }
    leaf counter_slice11_ifg_mac_pool83_tx_drained_pkt_cnt_reg2_tx_drained_pkt_cnt {
      type oc-yang:counter64;
      description
        "Count number of packets that are transmitted by mac and dropped by the RS layer because the link is in fault state.";
    }
    leaf counter_slice11_ifg_mac_pool83_tx_drained_pkt_cnt_reg3_tx_drained_pkt_cnt {
      type oc-yang:counter64;
      description
        "Count number of packets that are transmitted by mac and dropped by the RS layer because the link is in fault state.";
    }
    leaf counter_slice11_ifg_mac_pool83_tx_drained_pkt_cnt_reg4_tx_drained_pkt_cnt {
      type oc-yang:counter64;
      description
        "Count number of packets that are transmitted by mac and dropped by the RS layer because the link is in fault state.";
    }
    leaf counter_slice11_ifg_mac_pool83_tx_drained_pkt_cnt_reg5_tx_drained_pkt_cnt {
      type oc-yang:counter64;
      description
        "Count number of packets that are transmitted by mac and dropped by the RS layer because the link is in fault state.";
    }
    leaf counter_slice11_ifg_mac_pool83_tx_drained_pkt_cnt_reg6_tx_drained_pkt_cnt {
      type oc-yang:counter64;
      description
        "Count number of packets that are transmitted by mac and dropped by the RS layer because the link is in fault state.";
    }
    leaf counter_slice11_ifg_mac_pool83_tx_drained_pkt_cnt_reg7_tx_drained_pkt_cnt {
      type oc-yang:counter64;
      description
        "Count number of packets that are transmitted by mac and dropped by the RS layer because the link is in fault state.";
    }
    leaf counter_slice11_ifg_mac_pool84_tx_drained_pkt_cnt_reg0_tx_drained_pkt_cnt {
      type oc-yang:counter64;
      description
        "Count number of packets that are transmitted by mac and dropped by the RS layer because the link is in fault state.";
    }
    leaf counter_slice11_ifg_mac_pool84_tx_drained_pkt_cnt_reg1_tx_drained_pkt_cnt {
      type oc-yang:counter64;
      description
        "Count number of packets that are transmitted by mac and dropped by the RS layer because the link is in fault state.";
    }
    leaf counter_slice11_ifg_mac_pool84_tx_drained_pkt_cnt_reg2_tx_drained_pkt_cnt {
      type oc-yang:counter64;
      description
        "Count number of packets that are transmitted by mac and dropped by the RS layer because the link is in fault state.";
    }
    leaf counter_slice11_ifg_mac_pool84_tx_drained_pkt_cnt_reg3_tx_drained_pkt_cnt {
      type oc-yang:counter64;
      description
        "Count number of packets that are transmitted by mac and dropped by the RS layer because the link is in fault state.";
    }
    leaf counter_slice11_ifg_mac_pool84_tx_drained_pkt_cnt_reg4_tx_drained_pkt_cnt {
      type oc-yang:counter64;
      description
        "Count number of packets that are transmitted by mac and dropped by the RS layer because the link is in fault state.";
    }
    leaf counter_slice11_ifg_mac_pool84_tx_drained_pkt_cnt_reg5_tx_drained_pkt_cnt {
      type oc-yang:counter64;
      description
        "Count number of packets that are transmitted by mac and dropped by the RS layer because the link is in fault state.";
    }
    leaf counter_slice11_ifg_mac_pool84_tx_drained_pkt_cnt_reg6_tx_drained_pkt_cnt {
      type oc-yang:counter64;
      description
        "Count number of packets that are transmitted by mac and dropped by the RS layer because the link is in fault state.";
    }
    leaf counter_slice11_ifg_mac_pool84_tx_drained_pkt_cnt_reg7_tx_drained_pkt_cnt {
      type oc-yang:counter64;
      description
        "Count number of packets that are transmitted by mac and dropped by the RS layer because the link is in fault state.";
    }
    leaf counter_slice11_ifg_mac_pool85_tx_drained_pkt_cnt_reg0_tx_drained_pkt_cnt {
      type oc-yang:counter64;
      description
        "Count number of packets that are transmitted by mac and dropped by the RS layer because the link is in fault state.";
    }
    leaf counter_slice11_ifg_mac_pool85_tx_drained_pkt_cnt_reg1_tx_drained_pkt_cnt {
      type oc-yang:counter64;
      description
        "Count number of packets that are transmitted by mac and dropped by the RS layer because the link is in fault state.";
    }
    leaf counter_slice11_ifg_mac_pool85_tx_drained_pkt_cnt_reg2_tx_drained_pkt_cnt {
      type oc-yang:counter64;
      description
        "Count number of packets that are transmitted by mac and dropped by the RS layer because the link is in fault state.";
    }
    leaf counter_slice11_ifg_mac_pool85_tx_drained_pkt_cnt_reg3_tx_drained_pkt_cnt {
      type oc-yang:counter64;
      description
        "Count number of packets that are transmitted by mac and dropped by the RS layer because the link is in fault state.";
    }
    leaf counter_slice11_ifg_mac_pool85_tx_drained_pkt_cnt_reg4_tx_drained_pkt_cnt {
      type oc-yang:counter64;
      description
        "Count number of packets that are transmitted by mac and dropped by the RS layer because the link is in fault state.";
    }
    leaf counter_slice11_ifg_mac_pool85_tx_drained_pkt_cnt_reg5_tx_drained_pkt_cnt {
      type oc-yang:counter64;
      description
        "Count number of packets that are transmitted by mac and dropped by the RS layer because the link is in fault state.";
    }
    leaf counter_slice11_ifg_mac_pool85_tx_drained_pkt_cnt_reg6_tx_drained_pkt_cnt {
      type oc-yang:counter64;
      description
        "Count number of packets that are transmitted by mac and dropped by the RS layer because the link is in fault state.";
    }
    leaf counter_slice11_ifg_mac_pool85_tx_drained_pkt_cnt_reg7_tx_drained_pkt_cnt {
      type oc-yang:counter64;
      description
        "Count number of packets that are transmitted by mac and dropped by the RS layer because the link is in fault state.";
    }
    leaf counter_slice11_ifg_mac_pool86_tx_drained_pkt_cnt_reg0_tx_drained_pkt_cnt {
      type oc-yang:counter64;
      description
        "Count number of packets that are transmitted by mac and dropped by the RS layer because the link is in fault state.";
    }
    leaf counter_slice11_ifg_mac_pool86_tx_drained_pkt_cnt_reg1_tx_drained_pkt_cnt {
      type oc-yang:counter64;
      description
        "Count number of packets that are transmitted by mac and dropped by the RS layer because the link is in fault state.";
    }
    leaf counter_slice11_ifg_mac_pool86_tx_drained_pkt_cnt_reg2_tx_drained_pkt_cnt {
      type oc-yang:counter64;
      description
        "Count number of packets that are transmitted by mac and dropped by the RS layer because the link is in fault state.";
    }
    leaf counter_slice11_ifg_mac_pool86_tx_drained_pkt_cnt_reg3_tx_drained_pkt_cnt {
      type oc-yang:counter64;
      description
        "Count number of packets that are transmitted by mac and dropped by the RS layer because the link is in fault state.";
    }
    leaf counter_slice11_ifg_mac_pool86_tx_drained_pkt_cnt_reg4_tx_drained_pkt_cnt {
      type oc-yang:counter64;
      description
        "Count number of packets that are transmitted by mac and dropped by the RS layer because the link is in fault state.";
    }
    leaf counter_slice11_ifg_mac_pool86_tx_drained_pkt_cnt_reg5_tx_drained_pkt_cnt {
      type oc-yang:counter64;
      description
        "Count number of packets that are transmitted by mac and dropped by the RS layer because the link is in fault state.";
    }
    leaf counter_slice11_ifg_mac_pool86_tx_drained_pkt_cnt_reg6_tx_drained_pkt_cnt {
      type oc-yang:counter64;
      description
        "Count number of packets that are transmitted by mac and dropped by the RS layer because the link is in fault state.";
    }
    leaf counter_slice11_ifg_mac_pool86_tx_drained_pkt_cnt_reg7_tx_drained_pkt_cnt {
      type oc-yang:counter64;
      description
        "Count number of packets that are transmitted by mac and dropped by the RS layer because the link is in fault state.";
    }
    leaf counter_slice11_ifg_mac_pool87_tx_drained_pkt_cnt_reg0_tx_drained_pkt_cnt {
      type oc-yang:counter64;
      description
        "Count number of packets that are transmitted by mac and dropped by the RS layer because the link is in fault state.";
    }
    leaf counter_slice11_ifg_mac_pool87_tx_drained_pkt_cnt_reg1_tx_drained_pkt_cnt {
      type oc-yang:counter64;
      description
        "Count number of packets that are transmitted by mac and dropped by the RS layer because the link is in fault state.";
    }
    leaf counter_slice11_ifg_mac_pool87_tx_drained_pkt_cnt_reg2_tx_drained_pkt_cnt {
      type oc-yang:counter64;
      description
        "Count number of packets that are transmitted by mac and dropped by the RS layer because the link is in fault state.";
    }
    leaf counter_slice11_ifg_mac_pool87_tx_drained_pkt_cnt_reg3_tx_drained_pkt_cnt {
      type oc-yang:counter64;
      description
        "Count number of packets that are transmitted by mac and dropped by the RS layer because the link is in fault state.";
    }
    leaf counter_slice11_ifg_mac_pool87_tx_drained_pkt_cnt_reg4_tx_drained_pkt_cnt {
      type oc-yang:counter64;
      description
        "Count number of packets that are transmitted by mac and dropped by the RS layer because the link is in fault state.";
    }
    leaf counter_slice11_ifg_mac_pool87_tx_drained_pkt_cnt_reg5_tx_drained_pkt_cnt {
      type oc-yang:counter64;
      description
        "Count number of packets that are transmitted by mac and dropped by the RS layer because the link is in fault state.";
    }
    leaf counter_slice11_ifg_mac_pool87_tx_drained_pkt_cnt_reg6_tx_drained_pkt_cnt {
      type oc-yang:counter64;
      description
        "Count number of packets that are transmitted by mac and dropped by the RS layer because the link is in fault state.";
    }
    leaf counter_slice11_ifg_mac_pool87_tx_drained_pkt_cnt_reg7_tx_drained_pkt_cnt {
      type oc-yang:counter64;
      description
        "Count number of packets that are transmitted by mac and dropped by the RS layer because the link is in fault state.";
    }
    leaf counter_slice12_ifg_mac_pool80_tx_drained_pkt_cnt_reg0_tx_drained_pkt_cnt {
      type oc-yang:counter64;
      description
        "Count number of packets that are transmitted by mac and dropped by the RS layer because the link is in fault state.";
    }
    leaf counter_slice12_ifg_mac_pool80_tx_drained_pkt_cnt_reg1_tx_drained_pkt_cnt {
      type oc-yang:counter64;
      description
        "Count number of packets that are transmitted by mac and dropped by the RS layer because the link is in fault state.";
    }
    leaf counter_slice12_ifg_mac_pool80_tx_drained_pkt_cnt_reg2_tx_drained_pkt_cnt {
      type oc-yang:counter64;
      description
        "Count number of packets that are transmitted by mac and dropped by the RS layer because the link is in fault state.";
    }
    leaf counter_slice12_ifg_mac_pool80_tx_drained_pkt_cnt_reg3_tx_drained_pkt_cnt {
      type oc-yang:counter64;
      description
        "Count number of packets that are transmitted by mac and dropped by the RS layer because the link is in fault state.";
    }
    leaf counter_slice12_ifg_mac_pool80_tx_drained_pkt_cnt_reg4_tx_drained_pkt_cnt {
      type oc-yang:counter64;
      description
        "Count number of packets that are transmitted by mac and dropped by the RS layer because the link is in fault state.";
    }
    leaf counter_slice12_ifg_mac_pool80_tx_drained_pkt_cnt_reg5_tx_drained_pkt_cnt {
      type oc-yang:counter64;
      description
        "Count number of packets that are transmitted by mac and dropped by the RS layer because the link is in fault state.";
    }
    leaf counter_slice12_ifg_mac_pool80_tx_drained_pkt_cnt_reg6_tx_drained_pkt_cnt {
      type oc-yang:counter64;
      description
        "Count number of packets that are transmitted by mac and dropped by the RS layer because the link is in fault state.";
    }
    leaf counter_slice12_ifg_mac_pool80_tx_drained_pkt_cnt_reg7_tx_drained_pkt_cnt {
      type oc-yang:counter64;
      description
        "Count number of packets that are transmitted by mac and dropped by the RS layer because the link is in fault state.";
    }
    leaf counter_slice12_ifg_mac_pool81_tx_drained_pkt_cnt_reg0_tx_drained_pkt_cnt {
      type oc-yang:counter64;
      description
        "Count number of packets that are transmitted by mac and dropped by the RS layer because the link is in fault state.";
    }
    leaf counter_slice12_ifg_mac_pool81_tx_drained_pkt_cnt_reg1_tx_drained_pkt_cnt {
      type oc-yang:counter64;
      description
        "Count number of packets that are transmitted by mac and dropped by the RS layer because the link is in fault state.";
    }
    leaf counter_slice12_ifg_mac_pool81_tx_drained_pkt_cnt_reg2_tx_drained_pkt_cnt {
      type oc-yang:counter64;
      description
        "Count number of packets that are transmitted by mac and dropped by the RS layer because the link is in fault state.";
    }
    leaf counter_slice12_ifg_mac_pool81_tx_drained_pkt_cnt_reg3_tx_drained_pkt_cnt {
      type oc-yang:counter64;
      description
        "Count number of packets that are transmitted by mac and dropped by the RS layer because the link is in fault state.";
    }
    leaf counter_slice12_ifg_mac_pool81_tx_drained_pkt_cnt_reg4_tx_drained_pkt_cnt {
      type oc-yang:counter64;
      description
        "Count number of packets that are transmitted by mac and dropped by the RS layer because the link is in fault state.";
    }
    leaf counter_slice12_ifg_mac_pool81_tx_drained_pkt_cnt_reg5_tx_drained_pkt_cnt {
      type oc-yang:counter64;
      description
        "Count number of packets that are transmitted by mac and dropped by the RS layer because the link is in fault state.";
    }
    leaf counter_slice12_ifg_mac_pool81_tx_drained_pkt_cnt_reg6_tx_drained_pkt_cnt {
      type oc-yang:counter64;
      description
        "Count number of packets that are transmitted by mac and dropped by the RS layer because the link is in fault state.";
    }
    leaf counter_slice12_ifg_mac_pool81_tx_drained_pkt_cnt_reg7_tx_drained_pkt_cnt {
      type oc-yang:counter64;
      description
        "Count number of packets that are transmitted by mac and dropped by the RS layer because the link is in fault state.";
    }
    leaf counter_slice12_ifg_mac_pool82_tx_drained_pkt_cnt_reg0_tx_drained_pkt_cnt {
      type oc-yang:counter64;
      description
        "Count number of packets that are transmitted by mac and dropped by the RS layer because the link is in fault state.";
    }
    leaf counter_slice12_ifg_mac_pool82_tx_drained_pkt_cnt_reg1_tx_drained_pkt_cnt {
      type oc-yang:counter64;
      description
        "Count number of packets that are transmitted by mac and dropped by the RS layer because the link is in fault state.";
    }
    leaf counter_slice12_ifg_mac_pool82_tx_drained_pkt_cnt_reg2_tx_drained_pkt_cnt {
      type oc-yang:counter64;
      description
        "Count number of packets that are transmitted by mac and dropped by the RS layer because the link is in fault state.";
    }
    leaf counter_slice12_ifg_mac_pool82_tx_drained_pkt_cnt_reg3_tx_drained_pkt_cnt {
      type oc-yang:counter64;
      description
        "Count number of packets that are transmitted by mac and dropped by the RS layer because the link is in fault state.";
    }
    leaf counter_slice12_ifg_mac_pool82_tx_drained_pkt_cnt_reg4_tx_drained_pkt_cnt {
      type oc-yang:counter64;
      description
        "Count number of packets that are transmitted by mac and dropped by the RS layer because the link is in fault state.";
    }
    leaf counter_slice12_ifg_mac_pool82_tx_drained_pkt_cnt_reg5_tx_drained_pkt_cnt {
      type oc-yang:counter64;
      description
        "Count number of packets that are transmitted by mac and dropped by the RS layer because the link is in fault state.";
    }
    leaf counter_slice12_ifg_mac_pool82_tx_drained_pkt_cnt_reg6_tx_drained_pkt_cnt {
      type oc-yang:counter64;
      description
        "Count number of packets that are transmitted by mac and dropped by the RS layer because the link is in fault state.";
    }
    leaf counter_slice12_ifg_mac_pool82_tx_drained_pkt_cnt_reg7_tx_drained_pkt_cnt {
      type oc-yang:counter64;
      description
        "Count number of packets that are transmitted by mac and dropped by the RS layer because the link is in fault state.";
    }
    leaf counter_slice12_ifg_mac_pool83_tx_drained_pkt_cnt_reg0_tx_drained_pkt_cnt {
      type oc-yang:counter64;
      description
        "Count number of packets that are transmitted by mac and dropped by the RS layer because the link is in fault state.";
    }
    leaf counter_slice12_ifg_mac_pool83_tx_drained_pkt_cnt_reg1_tx_drained_pkt_cnt {
      type oc-yang:counter64;
      description
        "Count number of packets that are transmitted by mac and dropped by the RS layer because the link is in fault state.";
    }
    leaf counter_slice12_ifg_mac_pool83_tx_drained_pkt_cnt_reg2_tx_drained_pkt_cnt {
      type oc-yang:counter64;
      description
        "Count number of packets that are transmitted by mac and dropped by the RS layer because the link is in fault state.";
    }
    leaf counter_slice12_ifg_mac_pool83_tx_drained_pkt_cnt_reg3_tx_drained_pkt_cnt {
      type oc-yang:counter64;
      description
        "Count number of packets that are transmitted by mac and dropped by the RS layer because the link is in fault state.";
    }
    leaf counter_slice12_ifg_mac_pool83_tx_drained_pkt_cnt_reg4_tx_drained_pkt_cnt {
      type oc-yang:counter64;
      description
        "Count number of packets that are transmitted by mac and dropped by the RS layer because the link is in fault state.";
    }
    leaf counter_slice12_ifg_mac_pool83_tx_drained_pkt_cnt_reg5_tx_drained_pkt_cnt {
      type oc-yang:counter64;
      description
        "Count number of packets that are transmitted by mac and dropped by the RS layer because the link is in fault state.";
    }
    leaf counter_slice12_ifg_mac_pool83_tx_drained_pkt_cnt_reg6_tx_drained_pkt_cnt {
      type oc-yang:counter64;
      description
        "Count number of packets that are transmitted by mac and dropped by the RS layer because the link is in fault state.";
    }
    leaf counter_slice12_ifg_mac_pool83_tx_drained_pkt_cnt_reg7_tx_drained_pkt_cnt {
      type oc-yang:counter64;
      description
        "Count number of packets that are transmitted by mac and dropped by the RS layer because the link is in fault state.";
    }
    leaf counter_slice12_ifg_mac_pool84_tx_drained_pkt_cnt_reg0_tx_drained_pkt_cnt {
      type oc-yang:counter64;
      description
        "Count number of packets that are transmitted by mac and dropped by the RS layer because the link is in fault state.";
    }
    leaf counter_slice12_ifg_mac_pool84_tx_drained_pkt_cnt_reg1_tx_drained_pkt_cnt {
      type oc-yang:counter64;
      description
        "Count number of packets that are transmitted by mac and dropped by the RS layer because the link is in fault state.";
    }
    leaf counter_slice12_ifg_mac_pool84_tx_drained_pkt_cnt_reg2_tx_drained_pkt_cnt {
      type oc-yang:counter64;
      description
        "Count number of packets that are transmitted by mac and dropped by the RS layer because the link is in fault state.";
    }
    leaf counter_slice12_ifg_mac_pool84_tx_drained_pkt_cnt_reg3_tx_drained_pkt_cnt {
      type oc-yang:counter64;
      description
        "Count number of packets that are transmitted by mac and dropped by the RS layer because the link is in fault state.";
    }
    leaf counter_slice12_ifg_mac_pool84_tx_drained_pkt_cnt_reg4_tx_drained_pkt_cnt {
      type oc-yang:counter64;
      description
        "Count number of packets that are transmitted by mac and dropped by the RS layer because the link is in fault state.";
    }
    leaf counter_slice12_ifg_mac_pool84_tx_drained_pkt_cnt_reg5_tx_drained_pkt_cnt {
      type oc-yang:counter64;
      description
        "Count number of packets that are transmitted by mac and dropped by the RS layer because the link is in fault state.";
    }
    leaf counter_slice12_ifg_mac_pool84_tx_drained_pkt_cnt_reg6_tx_drained_pkt_cnt {
      type oc-yang:counter64;
      description
        "Count number of packets that are transmitted by mac and dropped by the RS layer because the link is in fault state.";
    }
    leaf counter_slice12_ifg_mac_pool84_tx_drained_pkt_cnt_reg7_tx_drained_pkt_cnt {
      type oc-yang:counter64;
      description
        "Count number of packets that are transmitted by mac and dropped by the RS layer because the link is in fault state.";
    }
    leaf counter_slice12_ifg_mac_pool85_tx_drained_pkt_cnt_reg0_tx_drained_pkt_cnt {
      type oc-yang:counter64;
      description
        "Count number of packets that are transmitted by mac and dropped by the RS layer because the link is in fault state.";
    }
    leaf counter_slice12_ifg_mac_pool85_tx_drained_pkt_cnt_reg1_tx_drained_pkt_cnt {
      type oc-yang:counter64;
      description
        "Count number of packets that are transmitted by mac and dropped by the RS layer because the link is in fault state.";
    }
    leaf counter_slice12_ifg_mac_pool85_tx_drained_pkt_cnt_reg2_tx_drained_pkt_cnt {
      type oc-yang:counter64;
      description
        "Count number of packets that are transmitted by mac and dropped by the RS layer because the link is in fault state.";
    }
    leaf counter_slice12_ifg_mac_pool85_tx_drained_pkt_cnt_reg3_tx_drained_pkt_cnt {
      type oc-yang:counter64;
      description
        "Count number of packets that are transmitted by mac and dropped by the RS layer because the link is in fault state.";
    }
    leaf counter_slice12_ifg_mac_pool85_tx_drained_pkt_cnt_reg4_tx_drained_pkt_cnt {
      type oc-yang:counter64;
      description
        "Count number of packets that are transmitted by mac and dropped by the RS layer because the link is in fault state.";
    }
    leaf counter_slice12_ifg_mac_pool85_tx_drained_pkt_cnt_reg5_tx_drained_pkt_cnt {
      type oc-yang:counter64;
      description
        "Count number of packets that are transmitted by mac and dropped by the RS layer because the link is in fault state.";
    }
    leaf counter_slice12_ifg_mac_pool85_tx_drained_pkt_cnt_reg6_tx_drained_pkt_cnt {
      type oc-yang:counter64;
      description
        "Count number of packets that are transmitted by mac and dropped by the RS layer because the link is in fault state.";
    }
    leaf counter_slice12_ifg_mac_pool85_tx_drained_pkt_cnt_reg7_tx_drained_pkt_cnt {
      type oc-yang:counter64;
      description
        "Count number of packets that are transmitted by mac and dropped by the RS layer because the link is in fault state.";
    }
    leaf counter_slice12_ifg_mac_pool86_tx_drained_pkt_cnt_reg0_tx_drained_pkt_cnt {
      type oc-yang:counter64;
      description
        "Count number of packets that are transmitted by mac and dropped by the RS layer because the link is in fault state.";
    }
    leaf counter_slice12_ifg_mac_pool86_tx_drained_pkt_cnt_reg1_tx_drained_pkt_cnt {
      type oc-yang:counter64;
      description
        "Count number of packets that are transmitted by mac and dropped by the RS layer because the link is in fault state.";
    }
    leaf counter_slice12_ifg_mac_pool86_tx_drained_pkt_cnt_reg2_tx_drained_pkt_cnt {
      type oc-yang:counter64;
      description
        "Count number of packets that are transmitted by mac and dropped by the RS layer because the link is in fault state.";
    }
    leaf counter_slice12_ifg_mac_pool86_tx_drained_pkt_cnt_reg3_tx_drained_pkt_cnt {
      type oc-yang:counter64;
      description
        "Count number of packets that are transmitted by mac and dropped by the RS layer because the link is in fault state.";
    }
    leaf counter_slice12_ifg_mac_pool86_tx_drained_pkt_cnt_reg4_tx_drained_pkt_cnt {
      type oc-yang:counter64;
      description
        "Count number of packets that are transmitted by mac and dropped by the RS layer because the link is in fault state.";
    }
    leaf counter_slice12_ifg_mac_pool86_tx_drained_pkt_cnt_reg5_tx_drained_pkt_cnt {
      type oc-yang:counter64;
      description
        "Count number of packets that are transmitted by mac and dropped by the RS layer because the link is in fault state.";
    }
    leaf counter_slice12_ifg_mac_pool86_tx_drained_pkt_cnt_reg6_tx_drained_pkt_cnt {
      type oc-yang:counter64;
      description
        "Count number of packets that are transmitted by mac and dropped by the RS layer because the link is in fault state.";
    }
    leaf counter_slice12_ifg_mac_pool86_tx_drained_pkt_cnt_reg7_tx_drained_pkt_cnt {
      type oc-yang:counter64;
      description
        "Count number of packets that are transmitted by mac and dropped by the RS layer because the link is in fault state.";
    }
    leaf counter_slice12_ifg_mac_pool87_tx_drained_pkt_cnt_reg0_tx_drained_pkt_cnt {
      type oc-yang:counter64;
      description
        "Count number of packets that are transmitted by mac and dropped by the RS layer because the link is in fault state.";
    }
    leaf counter_slice12_ifg_mac_pool87_tx_drained_pkt_cnt_reg1_tx_drained_pkt_cnt {
      type oc-yang:counter64;
      description
        "Count number of packets that are transmitted by mac and dropped by the RS layer because the link is in fault state.";
    }
    leaf counter_slice12_ifg_mac_pool87_tx_drained_pkt_cnt_reg2_tx_drained_pkt_cnt {
      type oc-yang:counter64;
      description
        "Count number of packets that are transmitted by mac and dropped by the RS layer because the link is in fault state.";
    }
    leaf counter_slice12_ifg_mac_pool87_tx_drained_pkt_cnt_reg3_tx_drained_pkt_cnt {
      type oc-yang:counter64;
      description
        "Count number of packets that are transmitted by mac and dropped by the RS layer because the link is in fault state.";
    }
    leaf counter_slice12_ifg_mac_pool87_tx_drained_pkt_cnt_reg4_tx_drained_pkt_cnt {
      type oc-yang:counter64;
      description
        "Count number of packets that are transmitted by mac and dropped by the RS layer because the link is in fault state.";
    }
    leaf counter_slice12_ifg_mac_pool87_tx_drained_pkt_cnt_reg5_tx_drained_pkt_cnt {
      type oc-yang:counter64;
      description
        "Count number of packets that are transmitted by mac and dropped by the RS layer because the link is in fault state.";
    }
    leaf counter_slice12_ifg_mac_pool87_tx_drained_pkt_cnt_reg6_tx_drained_pkt_cnt {
      type oc-yang:counter64;
      description
        "Count number of packets that are transmitted by mac and dropped by the RS layer because the link is in fault state.";
    }
    leaf counter_slice12_ifg_mac_pool87_tx_drained_pkt_cnt_reg7_tx_drained_pkt_cnt {
      type oc-yang:counter64;
      description
        "Count number of packets that are transmitted by mac and dropped by the RS layer because the link is in fault state.";
    }
    leaf counter_slice13_ifg_mac_pool80_tx_drained_pkt_cnt_reg0_tx_drained_pkt_cnt {
      type oc-yang:counter64;
      description
        "Count number of packets that are transmitted by mac and dropped by the RS layer because the link is in fault state.";
    }
    leaf counter_slice13_ifg_mac_pool80_tx_drained_pkt_cnt_reg1_tx_drained_pkt_cnt {
      type oc-yang:counter64;
      description
        "Count number of packets that are transmitted by mac and dropped by the RS layer because the link is in fault state.";
    }
    leaf counter_slice13_ifg_mac_pool80_tx_drained_pkt_cnt_reg2_tx_drained_pkt_cnt {
      type oc-yang:counter64;
      description
        "Count number of packets that are transmitted by mac and dropped by the RS layer because the link is in fault state.";
    }
    leaf counter_slice13_ifg_mac_pool80_tx_drained_pkt_cnt_reg3_tx_drained_pkt_cnt {
      type oc-yang:counter64;
      description
        "Count number of packets that are transmitted by mac and dropped by the RS layer because the link is in fault state.";
    }
    leaf counter_slice13_ifg_mac_pool80_tx_drained_pkt_cnt_reg4_tx_drained_pkt_cnt {
      type oc-yang:counter64;
      description
        "Count number of packets that are transmitted by mac and dropped by the RS layer because the link is in fault state.";
    }
    leaf counter_slice13_ifg_mac_pool80_tx_drained_pkt_cnt_reg5_tx_drained_pkt_cnt {
      type oc-yang:counter64;
      description
        "Count number of packets that are transmitted by mac and dropped by the RS layer because the link is in fault state.";
    }
    leaf counter_slice13_ifg_mac_pool80_tx_drained_pkt_cnt_reg6_tx_drained_pkt_cnt {
      type oc-yang:counter64;
      description
        "Count number of packets that are transmitted by mac and dropped by the RS layer because the link is in fault state.";
    }
    leaf counter_slice13_ifg_mac_pool80_tx_drained_pkt_cnt_reg7_tx_drained_pkt_cnt {
      type oc-yang:counter64;
      description
        "Count number of packets that are transmitted by mac and dropped by the RS layer because the link is in fault state.";
    }
    leaf counter_slice13_ifg_mac_pool81_tx_drained_pkt_cnt_reg0_tx_drained_pkt_cnt {
      type oc-yang:counter64;
      description
        "Count number of packets that are transmitted by mac and dropped by the RS layer because the link is in fault state.";
    }
    leaf counter_slice13_ifg_mac_pool81_tx_drained_pkt_cnt_reg1_tx_drained_pkt_cnt {
      type oc-yang:counter64;
      description
        "Count number of packets that are transmitted by mac and dropped by the RS layer because the link is in fault state.";
    }
    leaf counter_slice13_ifg_mac_pool81_tx_drained_pkt_cnt_reg2_tx_drained_pkt_cnt {
      type oc-yang:counter64;
      description
        "Count number of packets that are transmitted by mac and dropped by the RS layer because the link is in fault state.";
    }
    leaf counter_slice13_ifg_mac_pool81_tx_drained_pkt_cnt_reg3_tx_drained_pkt_cnt {
      type oc-yang:counter64;
      description
        "Count number of packets that are transmitted by mac and dropped by the RS layer because the link is in fault state.";
    }
    leaf counter_slice13_ifg_mac_pool81_tx_drained_pkt_cnt_reg4_tx_drained_pkt_cnt {
      type oc-yang:counter64;
      description
        "Count number of packets that are transmitted by mac and dropped by the RS layer because the link is in fault state.";
    }
    leaf counter_slice13_ifg_mac_pool81_tx_drained_pkt_cnt_reg5_tx_drained_pkt_cnt {
      type oc-yang:counter64;
      description
        "Count number of packets that are transmitted by mac and dropped by the RS layer because the link is in fault state.";
    }
    leaf counter_slice13_ifg_mac_pool81_tx_drained_pkt_cnt_reg6_tx_drained_pkt_cnt {
      type oc-yang:counter64;
      description
        "Count number of packets that are transmitted by mac and dropped by the RS layer because the link is in fault state.";
    }
    leaf counter_slice13_ifg_mac_pool81_tx_drained_pkt_cnt_reg7_tx_drained_pkt_cnt {
      type oc-yang:counter64;
      description
        "Count number of packets that are transmitted by mac and dropped by the RS layer because the link is in fault state.";
    }
    leaf counter_slice13_ifg_mac_pool82_tx_drained_pkt_cnt_reg0_tx_drained_pkt_cnt {
      type oc-yang:counter64;
      description
        "Count number of packets that are transmitted by mac and dropped by the RS layer because the link is in fault state.";
    }
    leaf counter_slice13_ifg_mac_pool82_tx_drained_pkt_cnt_reg1_tx_drained_pkt_cnt {
      type oc-yang:counter64;
      description
        "Count number of packets that are transmitted by mac and dropped by the RS layer because the link is in fault state.";
    }
    leaf counter_slice13_ifg_mac_pool82_tx_drained_pkt_cnt_reg2_tx_drained_pkt_cnt {
      type oc-yang:counter64;
      description
        "Count number of packets that are transmitted by mac and dropped by the RS layer because the link is in fault state.";
    }
    leaf counter_slice13_ifg_mac_pool82_tx_drained_pkt_cnt_reg3_tx_drained_pkt_cnt {
      type oc-yang:counter64;
      description
        "Count number of packets that are transmitted by mac and dropped by the RS layer because the link is in fault state.";
    }
    leaf counter_slice13_ifg_mac_pool82_tx_drained_pkt_cnt_reg4_tx_drained_pkt_cnt {
      type oc-yang:counter64;
      description
        "Count number of packets that are transmitted by mac and dropped by the RS layer because the link is in fault state.";
    }
    leaf counter_slice13_ifg_mac_pool82_tx_drained_pkt_cnt_reg5_tx_drained_pkt_cnt {
      type oc-yang:counter64;
      description
        "Count number of packets that are transmitted by mac and dropped by the RS layer because the link is in fault state.";
    }
    leaf counter_slice13_ifg_mac_pool82_tx_drained_pkt_cnt_reg6_tx_drained_pkt_cnt {
      type oc-yang:counter64;
      description
        "Count number of packets that are transmitted by mac and dropped by the RS layer because the link is in fault state.";
    }
    leaf counter_slice13_ifg_mac_pool82_tx_drained_pkt_cnt_reg7_tx_drained_pkt_cnt {
      type oc-yang:counter64;
      description
        "Count number of packets that are transmitted by mac and dropped by the RS layer because the link is in fault state.";
    }
    leaf counter_slice13_ifg_mac_pool83_tx_drained_pkt_cnt_reg0_tx_drained_pkt_cnt {
      type oc-yang:counter64;
      description
        "Count number of packets that are transmitted by mac and dropped by the RS layer because the link is in fault state.";
    }
    leaf counter_slice13_ifg_mac_pool83_tx_drained_pkt_cnt_reg1_tx_drained_pkt_cnt {
      type oc-yang:counter64;
      description
        "Count number of packets that are transmitted by mac and dropped by the RS layer because the link is in fault state.";
    }
    leaf counter_slice13_ifg_mac_pool83_tx_drained_pkt_cnt_reg2_tx_drained_pkt_cnt {
      type oc-yang:counter64;
      description
        "Count number of packets that are transmitted by mac and dropped by the RS layer because the link is in fault state.";
    }
    leaf counter_slice13_ifg_mac_pool83_tx_drained_pkt_cnt_reg3_tx_drained_pkt_cnt {
      type oc-yang:counter64;
      description
        "Count number of packets that are transmitted by mac and dropped by the RS layer because the link is in fault state.";
    }
    leaf counter_slice13_ifg_mac_pool83_tx_drained_pkt_cnt_reg4_tx_drained_pkt_cnt {
      type oc-yang:counter64;
      description
        "Count number of packets that are transmitted by mac and dropped by the RS layer because the link is in fault state.";
    }
    leaf counter_slice13_ifg_mac_pool83_tx_drained_pkt_cnt_reg5_tx_drained_pkt_cnt {
      type oc-yang:counter64;
      description
        "Count number of packets that are transmitted by mac and dropped by the RS layer because the link is in fault state.";
    }
    leaf counter_slice13_ifg_mac_pool83_tx_drained_pkt_cnt_reg6_tx_drained_pkt_cnt {
      type oc-yang:counter64;
      description
        "Count number of packets that are transmitted by mac and dropped by the RS layer because the link is in fault state.";
    }
    leaf counter_slice13_ifg_mac_pool83_tx_drained_pkt_cnt_reg7_tx_drained_pkt_cnt {
      type oc-yang:counter64;
      description
        "Count number of packets that are transmitted by mac and dropped by the RS layer because the link is in fault state.";
    }
    leaf counter_slice13_ifg_mac_pool84_tx_drained_pkt_cnt_reg0_tx_drained_pkt_cnt {
      type oc-yang:counter64;
      description
        "Count number of packets that are transmitted by mac and dropped by the RS layer because the link is in fault state.";
    }
    leaf counter_slice13_ifg_mac_pool84_tx_drained_pkt_cnt_reg1_tx_drained_pkt_cnt {
      type oc-yang:counter64;
      description
        "Count number of packets that are transmitted by mac and dropped by the RS layer because the link is in fault state.";
    }
    leaf counter_slice13_ifg_mac_pool84_tx_drained_pkt_cnt_reg2_tx_drained_pkt_cnt {
      type oc-yang:counter64;
      description
        "Count number of packets that are transmitted by mac and dropped by the RS layer because the link is in fault state.";
    }
    leaf counter_slice13_ifg_mac_pool84_tx_drained_pkt_cnt_reg3_tx_drained_pkt_cnt {
      type oc-yang:counter64;
      description
        "Count number of packets that are transmitted by mac and dropped by the RS layer because the link is in fault state.";
    }
    leaf counter_slice13_ifg_mac_pool84_tx_drained_pkt_cnt_reg4_tx_drained_pkt_cnt {
      type oc-yang:counter64;
      description
        "Count number of packets that are transmitted by mac and dropped by the RS layer because the link is in fault state.";
    }
    leaf counter_slice13_ifg_mac_pool84_tx_drained_pkt_cnt_reg5_tx_drained_pkt_cnt {
      type oc-yang:counter64;
      description
        "Count number of packets that are transmitted by mac and dropped by the RS layer because the link is in fault state.";
    }
    leaf counter_slice13_ifg_mac_pool84_tx_drained_pkt_cnt_reg6_tx_drained_pkt_cnt {
      type oc-yang:counter64;
      description
        "Count number of packets that are transmitted by mac and dropped by the RS layer because the link is in fault state.";
    }
    leaf counter_slice13_ifg_mac_pool84_tx_drained_pkt_cnt_reg7_tx_drained_pkt_cnt {
      type oc-yang:counter64;
      description
        "Count number of packets that are transmitted by mac and dropped by the RS layer because the link is in fault state.";
    }
    leaf counter_slice13_ifg_mac_pool85_tx_drained_pkt_cnt_reg0_tx_drained_pkt_cnt {
      type oc-yang:counter64;
      description
        "Count number of packets that are transmitted by mac and dropped by the RS layer because the link is in fault state.";
    }
    leaf counter_slice13_ifg_mac_pool85_tx_drained_pkt_cnt_reg1_tx_drained_pkt_cnt {
      type oc-yang:counter64;
      description
        "Count number of packets that are transmitted by mac and dropped by the RS layer because the link is in fault state.";
    }
    leaf counter_slice13_ifg_mac_pool85_tx_drained_pkt_cnt_reg2_tx_drained_pkt_cnt {
      type oc-yang:counter64;
      description
        "Count number of packets that are transmitted by mac and dropped by the RS layer because the link is in fault state.";
    }
    leaf counter_slice13_ifg_mac_pool85_tx_drained_pkt_cnt_reg3_tx_drained_pkt_cnt {
      type oc-yang:counter64;
      description
        "Count number of packets that are transmitted by mac and dropped by the RS layer because the link is in fault state.";
    }
    leaf counter_slice13_ifg_mac_pool85_tx_drained_pkt_cnt_reg4_tx_drained_pkt_cnt {
      type oc-yang:counter64;
      description
        "Count number of packets that are transmitted by mac and dropped by the RS layer because the link is in fault state.";
    }
    leaf counter_slice13_ifg_mac_pool85_tx_drained_pkt_cnt_reg5_tx_drained_pkt_cnt {
      type oc-yang:counter64;
      description
        "Count number of packets that are transmitted by mac and dropped by the RS layer because the link is in fault state.";
    }
    leaf counter_slice13_ifg_mac_pool85_tx_drained_pkt_cnt_reg6_tx_drained_pkt_cnt {
      type oc-yang:counter64;
      description
        "Count number of packets that are transmitted by mac and dropped by the RS layer because the link is in fault state.";
    }
    leaf counter_slice13_ifg_mac_pool85_tx_drained_pkt_cnt_reg7_tx_drained_pkt_cnt {
      type oc-yang:counter64;
      description
        "Count number of packets that are transmitted by mac and dropped by the RS layer because the link is in fault state.";
    }
    leaf counter_slice13_ifg_mac_pool86_tx_drained_pkt_cnt_reg0_tx_drained_pkt_cnt {
      type oc-yang:counter64;
      description
        "Count number of packets that are transmitted by mac and dropped by the RS layer because the link is in fault state.";
    }
    leaf counter_slice13_ifg_mac_pool86_tx_drained_pkt_cnt_reg1_tx_drained_pkt_cnt {
      type oc-yang:counter64;
      description
        "Count number of packets that are transmitted by mac and dropped by the RS layer because the link is in fault state.";
    }
    leaf counter_slice13_ifg_mac_pool86_tx_drained_pkt_cnt_reg2_tx_drained_pkt_cnt {
      type oc-yang:counter64;
      description
        "Count number of packets that are transmitted by mac and dropped by the RS layer because the link is in fault state.";
    }
    leaf counter_slice13_ifg_mac_pool86_tx_drained_pkt_cnt_reg3_tx_drained_pkt_cnt {
      type oc-yang:counter64;
      description
        "Count number of packets that are transmitted by mac and dropped by the RS layer because the link is in fault state.";
    }
    leaf counter_slice13_ifg_mac_pool86_tx_drained_pkt_cnt_reg4_tx_drained_pkt_cnt {
      type oc-yang:counter64;
      description
        "Count number of packets that are transmitted by mac and dropped by the RS layer because the link is in fault state.";
    }
    leaf counter_slice13_ifg_mac_pool86_tx_drained_pkt_cnt_reg5_tx_drained_pkt_cnt {
      type oc-yang:counter64;
      description
        "Count number of packets that are transmitted by mac and dropped by the RS layer because the link is in fault state.";
    }
    leaf counter_slice13_ifg_mac_pool86_tx_drained_pkt_cnt_reg6_tx_drained_pkt_cnt {
      type oc-yang:counter64;
      description
        "Count number of packets that are transmitted by mac and dropped by the RS layer because the link is in fault state.";
    }
    leaf counter_slice13_ifg_mac_pool86_tx_drained_pkt_cnt_reg7_tx_drained_pkt_cnt {
      type oc-yang:counter64;
      description
        "Count number of packets that are transmitted by mac and dropped by the RS layer because the link is in fault state.";
    }
    leaf counter_slice13_ifg_mac_pool87_tx_drained_pkt_cnt_reg0_tx_drained_pkt_cnt {
      type oc-yang:counter64;
      description
        "Count number of packets that are transmitted by mac and dropped by the RS layer because the link is in fault state.";
    }
    leaf counter_slice13_ifg_mac_pool87_tx_drained_pkt_cnt_reg1_tx_drained_pkt_cnt {
      type oc-yang:counter64;
      description
        "Count number of packets that are transmitted by mac and dropped by the RS layer because the link is in fault state.";
    }
    leaf counter_slice13_ifg_mac_pool87_tx_drained_pkt_cnt_reg2_tx_drained_pkt_cnt {
      type oc-yang:counter64;
      description
        "Count number of packets that are transmitted by mac and dropped by the RS layer because the link is in fault state.";
    }
    leaf counter_slice13_ifg_mac_pool87_tx_drained_pkt_cnt_reg3_tx_drained_pkt_cnt {
      type oc-yang:counter64;
      description
        "Count number of packets that are transmitted by mac and dropped by the RS layer because the link is in fault state.";
    }
    leaf counter_slice13_ifg_mac_pool87_tx_drained_pkt_cnt_reg4_tx_drained_pkt_cnt {
      type oc-yang:counter64;
      description
        "Count number of packets that are transmitted by mac and dropped by the RS layer because the link is in fault state.";
    }
    leaf counter_slice13_ifg_mac_pool87_tx_drained_pkt_cnt_reg5_tx_drained_pkt_cnt {
      type oc-yang:counter64;
      description
        "Count number of packets that are transmitted by mac and dropped by the RS layer because the link is in fault state.";
    }
    leaf counter_slice13_ifg_mac_pool87_tx_drained_pkt_cnt_reg6_tx_drained_pkt_cnt {
      type oc-yang:counter64;
      description
        "Count number of packets that are transmitted by mac and dropped by the RS layer because the link is in fault state.";
    }
    leaf counter_slice13_ifg_mac_pool87_tx_drained_pkt_cnt_reg7_tx_drained_pkt_cnt {
      type oc-yang:counter64;
      description
        "Count number of packets that are transmitted by mac and dropped by the RS layer because the link is in fault state.";
    }
    leaf counter_slice14_ifg_mac_pool80_tx_drained_pkt_cnt_reg0_tx_drained_pkt_cnt {
      type oc-yang:counter64;
      description
        "Count number of packets that are transmitted by mac and dropped by the RS layer because the link is in fault state.";
    }
    leaf counter_slice14_ifg_mac_pool80_tx_drained_pkt_cnt_reg1_tx_drained_pkt_cnt {
      type oc-yang:counter64;
      description
        "Count number of packets that are transmitted by mac and dropped by the RS layer because the link is in fault state.";
    }
    leaf counter_slice14_ifg_mac_pool80_tx_drained_pkt_cnt_reg2_tx_drained_pkt_cnt {
      type oc-yang:counter64;
      description
        "Count number of packets that are transmitted by mac and dropped by the RS layer because the link is in fault state.";
    }
    leaf counter_slice14_ifg_mac_pool80_tx_drained_pkt_cnt_reg3_tx_drained_pkt_cnt {
      type oc-yang:counter64;
      description
        "Count number of packets that are transmitted by mac and dropped by the RS layer because the link is in fault state.";
    }
    leaf counter_slice14_ifg_mac_pool80_tx_drained_pkt_cnt_reg4_tx_drained_pkt_cnt {
      type oc-yang:counter64;
      description
        "Count number of packets that are transmitted by mac and dropped by the RS layer because the link is in fault state.";
    }
    leaf counter_slice14_ifg_mac_pool80_tx_drained_pkt_cnt_reg5_tx_drained_pkt_cnt {
      type oc-yang:counter64;
      description
        "Count number of packets that are transmitted by mac and dropped by the RS layer because the link is in fault state.";
    }
    leaf counter_slice14_ifg_mac_pool80_tx_drained_pkt_cnt_reg6_tx_drained_pkt_cnt {
      type oc-yang:counter64;
      description
        "Count number of packets that are transmitted by mac and dropped by the RS layer because the link is in fault state.";
    }
    leaf counter_slice14_ifg_mac_pool80_tx_drained_pkt_cnt_reg7_tx_drained_pkt_cnt {
      type oc-yang:counter64;
      description
        "Count number of packets that are transmitted by mac and dropped by the RS layer because the link is in fault state.";
    }
    leaf counter_slice14_ifg_mac_pool81_tx_drained_pkt_cnt_reg0_tx_drained_pkt_cnt {
      type oc-yang:counter64;
      description
        "Count number of packets that are transmitted by mac and dropped by the RS layer because the link is in fault state.";
    }
    leaf counter_slice14_ifg_mac_pool81_tx_drained_pkt_cnt_reg1_tx_drained_pkt_cnt {
      type oc-yang:counter64;
      description
        "Count number of packets that are transmitted by mac and dropped by the RS layer because the link is in fault state.";
    }
    leaf counter_slice14_ifg_mac_pool81_tx_drained_pkt_cnt_reg2_tx_drained_pkt_cnt {
      type oc-yang:counter64;
      description
        "Count number of packets that are transmitted by mac and dropped by the RS layer because the link is in fault state.";
    }
    leaf counter_slice14_ifg_mac_pool81_tx_drained_pkt_cnt_reg3_tx_drained_pkt_cnt {
      type oc-yang:counter64;
      description
        "Count number of packets that are transmitted by mac and dropped by the RS layer because the link is in fault state.";
    }
    leaf counter_slice14_ifg_mac_pool81_tx_drained_pkt_cnt_reg4_tx_drained_pkt_cnt {
      type oc-yang:counter64;
      description
        "Count number of packets that are transmitted by mac and dropped by the RS layer because the link is in fault state.";
    }
    leaf counter_slice14_ifg_mac_pool81_tx_drained_pkt_cnt_reg5_tx_drained_pkt_cnt {
      type oc-yang:counter64;
      description
        "Count number of packets that are transmitted by mac and dropped by the RS layer because the link is in fault state.";
    }
    leaf counter_slice14_ifg_mac_pool81_tx_drained_pkt_cnt_reg6_tx_drained_pkt_cnt {
      type oc-yang:counter64;
      description
        "Count number of packets that are transmitted by mac and dropped by the RS layer because the link is in fault state.";
    }
    leaf counter_slice14_ifg_mac_pool81_tx_drained_pkt_cnt_reg7_tx_drained_pkt_cnt {
      type oc-yang:counter64;
      description
        "Count number of packets that are transmitted by mac and dropped by the RS layer because the link is in fault state.";
    }
    leaf counter_slice14_ifg_mac_pool82_tx_drained_pkt_cnt_reg0_tx_drained_pkt_cnt {
      type oc-yang:counter64;
      description
        "Count number of packets that are transmitted by mac and dropped by the RS layer because the link is in fault state.";
    }
    leaf counter_slice14_ifg_mac_pool82_tx_drained_pkt_cnt_reg1_tx_drained_pkt_cnt {
      type oc-yang:counter64;
      description
        "Count number of packets that are transmitted by mac and dropped by the RS layer because the link is in fault state.";
    }
    leaf counter_slice14_ifg_mac_pool82_tx_drained_pkt_cnt_reg2_tx_drained_pkt_cnt {
      type oc-yang:counter64;
      description
        "Count number of packets that are transmitted by mac and dropped by the RS layer because the link is in fault state.";
    }
    leaf counter_slice14_ifg_mac_pool82_tx_drained_pkt_cnt_reg3_tx_drained_pkt_cnt {
      type oc-yang:counter64;
      description
        "Count number of packets that are transmitted by mac and dropped by the RS layer because the link is in fault state.";
    }
    leaf counter_slice14_ifg_mac_pool82_tx_drained_pkt_cnt_reg4_tx_drained_pkt_cnt {
      type oc-yang:counter64;
      description
        "Count number of packets that are transmitted by mac and dropped by the RS layer because the link is in fault state.";
    }
    leaf counter_slice14_ifg_mac_pool82_tx_drained_pkt_cnt_reg5_tx_drained_pkt_cnt {
      type oc-yang:counter64;
      description
        "Count number of packets that are transmitted by mac and dropped by the RS layer because the link is in fault state.";
    }
    leaf counter_slice14_ifg_mac_pool82_tx_drained_pkt_cnt_reg6_tx_drained_pkt_cnt {
      type oc-yang:counter64;
      description
        "Count number of packets that are transmitted by mac and dropped by the RS layer because the link is in fault state.";
    }
    leaf counter_slice14_ifg_mac_pool82_tx_drained_pkt_cnt_reg7_tx_drained_pkt_cnt {
      type oc-yang:counter64;
      description
        "Count number of packets that are transmitted by mac and dropped by the RS layer because the link is in fault state.";
    }
    leaf counter_slice14_ifg_mac_pool83_tx_drained_pkt_cnt_reg0_tx_drained_pkt_cnt {
      type oc-yang:counter64;
      description
        "Count number of packets that are transmitted by mac and dropped by the RS layer because the link is in fault state.";
    }
    leaf counter_slice14_ifg_mac_pool83_tx_drained_pkt_cnt_reg1_tx_drained_pkt_cnt {
      type oc-yang:counter64;
      description
        "Count number of packets that are transmitted by mac and dropped by the RS layer because the link is in fault state.";
    }
    leaf counter_slice14_ifg_mac_pool83_tx_drained_pkt_cnt_reg2_tx_drained_pkt_cnt {
      type oc-yang:counter64;
      description
        "Count number of packets that are transmitted by mac and dropped by the RS layer because the link is in fault state.";
    }
    leaf counter_slice14_ifg_mac_pool83_tx_drained_pkt_cnt_reg3_tx_drained_pkt_cnt {
      type oc-yang:counter64;
      description
        "Count number of packets that are transmitted by mac and dropped by the RS layer because the link is in fault state.";
    }
    leaf counter_slice14_ifg_mac_pool83_tx_drained_pkt_cnt_reg4_tx_drained_pkt_cnt {
      type oc-yang:counter64;
      description
        "Count number of packets that are transmitted by mac and dropped by the RS layer because the link is in fault state.";
    }
    leaf counter_slice14_ifg_mac_pool83_tx_drained_pkt_cnt_reg5_tx_drained_pkt_cnt {
      type oc-yang:counter64;
      description
        "Count number of packets that are transmitted by mac and dropped by the RS layer because the link is in fault state.";
    }
    leaf counter_slice14_ifg_mac_pool83_tx_drained_pkt_cnt_reg6_tx_drained_pkt_cnt {
      type oc-yang:counter64;
      description
        "Count number of packets that are transmitted by mac and dropped by the RS layer because the link is in fault state.";
    }
    leaf counter_slice14_ifg_mac_pool83_tx_drained_pkt_cnt_reg7_tx_drained_pkt_cnt {
      type oc-yang:counter64;
      description
        "Count number of packets that are transmitted by mac and dropped by the RS layer because the link is in fault state.";
    }
    leaf counter_slice14_ifg_mac_pool84_tx_drained_pkt_cnt_reg0_tx_drained_pkt_cnt {
      type oc-yang:counter64;
      description
        "Count number of packets that are transmitted by mac and dropped by the RS layer because the link is in fault state.";
    }
    leaf counter_slice14_ifg_mac_pool84_tx_drained_pkt_cnt_reg1_tx_drained_pkt_cnt {
      type oc-yang:counter64;
      description
        "Count number of packets that are transmitted by mac and dropped by the RS layer because the link is in fault state.";
    }
    leaf counter_slice14_ifg_mac_pool84_tx_drained_pkt_cnt_reg2_tx_drained_pkt_cnt {
      type oc-yang:counter64;
      description
        "Count number of packets that are transmitted by mac and dropped by the RS layer because the link is in fault state.";
    }
    leaf counter_slice14_ifg_mac_pool84_tx_drained_pkt_cnt_reg3_tx_drained_pkt_cnt {
      type oc-yang:counter64;
      description
        "Count number of packets that are transmitted by mac and dropped by the RS layer because the link is in fault state.";
    }
    leaf counter_slice14_ifg_mac_pool84_tx_drained_pkt_cnt_reg4_tx_drained_pkt_cnt {
      type oc-yang:counter64;
      description
        "Count number of packets that are transmitted by mac and dropped by the RS layer because the link is in fault state.";
    }
    leaf counter_slice14_ifg_mac_pool84_tx_drained_pkt_cnt_reg5_tx_drained_pkt_cnt {
      type oc-yang:counter64;
      description
        "Count number of packets that are transmitted by mac and dropped by the RS layer because the link is in fault state.";
    }
    leaf counter_slice14_ifg_mac_pool84_tx_drained_pkt_cnt_reg6_tx_drained_pkt_cnt {
      type oc-yang:counter64;
      description
        "Count number of packets that are transmitted by mac and dropped by the RS layer because the link is in fault state.";
    }
    leaf counter_slice14_ifg_mac_pool84_tx_drained_pkt_cnt_reg7_tx_drained_pkt_cnt {
      type oc-yang:counter64;
      description
        "Count number of packets that are transmitted by mac and dropped by the RS layer because the link is in fault state.";
    }
    leaf counter_slice14_ifg_mac_pool85_tx_drained_pkt_cnt_reg0_tx_drained_pkt_cnt {
      type oc-yang:counter64;
      description
        "Count number of packets that are transmitted by mac and dropped by the RS layer because the link is in fault state.";
    }
    leaf counter_slice14_ifg_mac_pool85_tx_drained_pkt_cnt_reg1_tx_drained_pkt_cnt {
      type oc-yang:counter64;
      description
        "Count number of packets that are transmitted by mac and dropped by the RS layer because the link is in fault state.";
    }
    leaf counter_slice14_ifg_mac_pool85_tx_drained_pkt_cnt_reg2_tx_drained_pkt_cnt {
      type oc-yang:counter64;
      description
        "Count number of packets that are transmitted by mac and dropped by the RS layer because the link is in fault state.";
    }
    leaf counter_slice14_ifg_mac_pool85_tx_drained_pkt_cnt_reg3_tx_drained_pkt_cnt {
      type oc-yang:counter64;
      description
        "Count number of packets that are transmitted by mac and dropped by the RS layer because the link is in fault state.";
    }
    leaf counter_slice14_ifg_mac_pool85_tx_drained_pkt_cnt_reg4_tx_drained_pkt_cnt {
      type oc-yang:counter64;
      description
        "Count number of packets that are transmitted by mac and dropped by the RS layer because the link is in fault state.";
    }
    leaf counter_slice14_ifg_mac_pool85_tx_drained_pkt_cnt_reg5_tx_drained_pkt_cnt {
      type oc-yang:counter64;
      description
        "Count number of packets that are transmitted by mac and dropped by the RS layer because the link is in fault state.";
    }
    leaf counter_slice14_ifg_mac_pool85_tx_drained_pkt_cnt_reg6_tx_drained_pkt_cnt {
      type oc-yang:counter64;
      description
        "Count number of packets that are transmitted by mac and dropped by the RS layer because the link is in fault state.";
    }
    leaf counter_slice14_ifg_mac_pool85_tx_drained_pkt_cnt_reg7_tx_drained_pkt_cnt {
      type oc-yang:counter64;
      description
        "Count number of packets that are transmitted by mac and dropped by the RS layer because the link is in fault state.";
    }
    leaf counter_slice14_ifg_mac_pool86_tx_drained_pkt_cnt_reg0_tx_drained_pkt_cnt {
      type oc-yang:counter64;
      description
        "Count number of packets that are transmitted by mac and dropped by the RS layer because the link is in fault state.";
    }
    leaf counter_slice14_ifg_mac_pool86_tx_drained_pkt_cnt_reg1_tx_drained_pkt_cnt {
      type oc-yang:counter64;
      description
        "Count number of packets that are transmitted by mac and dropped by the RS layer because the link is in fault state.";
    }
    leaf counter_slice14_ifg_mac_pool86_tx_drained_pkt_cnt_reg2_tx_drained_pkt_cnt {
      type oc-yang:counter64;
      description
        "Count number of packets that are transmitted by mac and dropped by the RS layer because the link is in fault state.";
    }
    leaf counter_slice14_ifg_mac_pool86_tx_drained_pkt_cnt_reg3_tx_drained_pkt_cnt {
      type oc-yang:counter64;
      description
        "Count number of packets that are transmitted by mac and dropped by the RS layer because the link is in fault state.";
    }
    leaf counter_slice14_ifg_mac_pool86_tx_drained_pkt_cnt_reg4_tx_drained_pkt_cnt {
      type oc-yang:counter64;
      description
        "Count number of packets that are transmitted by mac and dropped by the RS layer because the link is in fault state.";
    }
    leaf counter_slice14_ifg_mac_pool86_tx_drained_pkt_cnt_reg5_tx_drained_pkt_cnt {
      type oc-yang:counter64;
      description
        "Count number of packets that are transmitted by mac and dropped by the RS layer because the link is in fault state.";
    }
    leaf counter_slice14_ifg_mac_pool86_tx_drained_pkt_cnt_reg6_tx_drained_pkt_cnt {
      type oc-yang:counter64;
      description
        "Count number of packets that are transmitted by mac and dropped by the RS layer because the link is in fault state.";
    }
    leaf counter_slice14_ifg_mac_pool86_tx_drained_pkt_cnt_reg7_tx_drained_pkt_cnt {
      type oc-yang:counter64;
      description
        "Count number of packets that are transmitted by mac and dropped by the RS layer because the link is in fault state.";
    }
    leaf counter_slice14_ifg_mac_pool87_tx_drained_pkt_cnt_reg0_tx_drained_pkt_cnt {
      type oc-yang:counter64;
      description
        "Count number of packets that are transmitted by mac and dropped by the RS layer because the link is in fault state.";
    }
    leaf counter_slice14_ifg_mac_pool87_tx_drained_pkt_cnt_reg1_tx_drained_pkt_cnt {
      type oc-yang:counter64;
      description
        "Count number of packets that are transmitted by mac and dropped by the RS layer because the link is in fault state.";
    }
    leaf counter_slice14_ifg_mac_pool87_tx_drained_pkt_cnt_reg2_tx_drained_pkt_cnt {
      type oc-yang:counter64;
      description
        "Count number of packets that are transmitted by mac and dropped by the RS layer because the link is in fault state.";
    }
    leaf counter_slice14_ifg_mac_pool87_tx_drained_pkt_cnt_reg3_tx_drained_pkt_cnt {
      type oc-yang:counter64;
      description
        "Count number of packets that are transmitted by mac and dropped by the RS layer because the link is in fault state.";
    }
    leaf counter_slice14_ifg_mac_pool87_tx_drained_pkt_cnt_reg4_tx_drained_pkt_cnt {
      type oc-yang:counter64;
      description
        "Count number of packets that are transmitted by mac and dropped by the RS layer because the link is in fault state.";
    }
    leaf counter_slice14_ifg_mac_pool87_tx_drained_pkt_cnt_reg5_tx_drained_pkt_cnt {
      type oc-yang:counter64;
      description
        "Count number of packets that are transmitted by mac and dropped by the RS layer because the link is in fault state.";
    }
    leaf counter_slice14_ifg_mac_pool87_tx_drained_pkt_cnt_reg6_tx_drained_pkt_cnt {
      type oc-yang:counter64;
      description
        "Count number of packets that are transmitted by mac and dropped by the RS layer because the link is in fault state.";
    }
    leaf counter_slice14_ifg_mac_pool87_tx_drained_pkt_cnt_reg7_tx_drained_pkt_cnt {
      type oc-yang:counter64;
      description
        "Count number of packets that are transmitted by mac and dropped by the RS layer because the link is in fault state.";
    }
    leaf counter_slice15_ifg_mac_pool80_tx_drained_pkt_cnt_reg0_tx_drained_pkt_cnt {
      type oc-yang:counter64;
      description
        "Count number of packets that are transmitted by mac and dropped by the RS layer because the link is in fault state.";
    }
    leaf counter_slice15_ifg_mac_pool80_tx_drained_pkt_cnt_reg1_tx_drained_pkt_cnt {
      type oc-yang:counter64;
      description
        "Count number of packets that are transmitted by mac and dropped by the RS layer because the link is in fault state.";
    }
    leaf counter_slice15_ifg_mac_pool80_tx_drained_pkt_cnt_reg2_tx_drained_pkt_cnt {
      type oc-yang:counter64;
      description
        "Count number of packets that are transmitted by mac and dropped by the RS layer because the link is in fault state.";
    }
    leaf counter_slice15_ifg_mac_pool80_tx_drained_pkt_cnt_reg3_tx_drained_pkt_cnt {
      type oc-yang:counter64;
      description
        "Count number of packets that are transmitted by mac and dropped by the RS layer because the link is in fault state.";
    }
    leaf counter_slice15_ifg_mac_pool80_tx_drained_pkt_cnt_reg4_tx_drained_pkt_cnt {
      type oc-yang:counter64;
      description
        "Count number of packets that are transmitted by mac and dropped by the RS layer because the link is in fault state.";
    }
    leaf counter_slice15_ifg_mac_pool80_tx_drained_pkt_cnt_reg5_tx_drained_pkt_cnt {
      type oc-yang:counter64;
      description
        "Count number of packets that are transmitted by mac and dropped by the RS layer because the link is in fault state.";
    }
    leaf counter_slice15_ifg_mac_pool80_tx_drained_pkt_cnt_reg6_tx_drained_pkt_cnt {
      type oc-yang:counter64;
      description
        "Count number of packets that are transmitted by mac and dropped by the RS layer because the link is in fault state.";
    }
    leaf counter_slice15_ifg_mac_pool80_tx_drained_pkt_cnt_reg7_tx_drained_pkt_cnt {
      type oc-yang:counter64;
      description
        "Count number of packets that are transmitted by mac and dropped by the RS layer because the link is in fault state.";
    }
    leaf counter_slice15_ifg_mac_pool81_tx_drained_pkt_cnt_reg0_tx_drained_pkt_cnt {
      type oc-yang:counter64;
      description
        "Count number of packets that are transmitted by mac and dropped by the RS layer because the link is in fault state.";
    }
    leaf counter_slice15_ifg_mac_pool81_tx_drained_pkt_cnt_reg1_tx_drained_pkt_cnt {
      type oc-yang:counter64;
      description
        "Count number of packets that are transmitted by mac and dropped by the RS layer because the link is in fault state.";
    }
    leaf counter_slice15_ifg_mac_pool81_tx_drained_pkt_cnt_reg2_tx_drained_pkt_cnt {
      type oc-yang:counter64;
      description
        "Count number of packets that are transmitted by mac and dropped by the RS layer because the link is in fault state.";
    }
    leaf counter_slice15_ifg_mac_pool81_tx_drained_pkt_cnt_reg3_tx_drained_pkt_cnt {
      type oc-yang:counter64;
      description
        "Count number of packets that are transmitted by mac and dropped by the RS layer because the link is in fault state.";
    }
    leaf counter_slice15_ifg_mac_pool81_tx_drained_pkt_cnt_reg4_tx_drained_pkt_cnt {
      type oc-yang:counter64;
      description
        "Count number of packets that are transmitted by mac and dropped by the RS layer because the link is in fault state.";
    }
    leaf counter_slice15_ifg_mac_pool81_tx_drained_pkt_cnt_reg5_tx_drained_pkt_cnt {
      type oc-yang:counter64;
      description
        "Count number of packets that are transmitted by mac and dropped by the RS layer because the link is in fault state.";
    }
    leaf counter_slice15_ifg_mac_pool81_tx_drained_pkt_cnt_reg6_tx_drained_pkt_cnt {
      type oc-yang:counter64;
      description
        "Count number of packets that are transmitted by mac and dropped by the RS layer because the link is in fault state.";
    }
    leaf counter_slice15_ifg_mac_pool81_tx_drained_pkt_cnt_reg7_tx_drained_pkt_cnt {
      type oc-yang:counter64;
      description
        "Count number of packets that are transmitted by mac and dropped by the RS layer because the link is in fault state.";
    }
    leaf counter_slice15_ifg_mac_pool82_tx_drained_pkt_cnt_reg0_tx_drained_pkt_cnt {
      type oc-yang:counter64;
      description
        "Count number of packets that are transmitted by mac and dropped by the RS layer because the link is in fault state.";
    }
    leaf counter_slice15_ifg_mac_pool82_tx_drained_pkt_cnt_reg1_tx_drained_pkt_cnt {
      type oc-yang:counter64;
      description
        "Count number of packets that are transmitted by mac and dropped by the RS layer because the link is in fault state.";
    }
    leaf counter_slice15_ifg_mac_pool82_tx_drained_pkt_cnt_reg2_tx_drained_pkt_cnt {
      type oc-yang:counter64;
      description
        "Count number of packets that are transmitted by mac and dropped by the RS layer because the link is in fault state.";
    }
    leaf counter_slice15_ifg_mac_pool82_tx_drained_pkt_cnt_reg3_tx_drained_pkt_cnt {
      type oc-yang:counter64;
      description
        "Count number of packets that are transmitted by mac and dropped by the RS layer because the link is in fault state.";
    }
    leaf counter_slice15_ifg_mac_pool82_tx_drained_pkt_cnt_reg4_tx_drained_pkt_cnt {
      type oc-yang:counter64;
      description
        "Count number of packets that are transmitted by mac and dropped by the RS layer because the link is in fault state.";
    }
    leaf counter_slice15_ifg_mac_pool82_tx_drained_pkt_cnt_reg5_tx_drained_pkt_cnt {
      type oc-yang:counter64;
      description
        "Count number of packets that are transmitted by mac and dropped by the RS layer because the link is in fault state.";
    }
    leaf counter_slice15_ifg_mac_pool82_tx_drained_pkt_cnt_reg6_tx_drained_pkt_cnt {
      type oc-yang:counter64;
      description
        "Count number of packets that are transmitted by mac and dropped by the RS layer because the link is in fault state.";
    }
    leaf counter_slice15_ifg_mac_pool82_tx_drained_pkt_cnt_reg7_tx_drained_pkt_cnt {
      type oc-yang:counter64;
      description
        "Count number of packets that are transmitted by mac and dropped by the RS layer because the link is in fault state.";
    }
    leaf counter_slice15_ifg_mac_pool83_tx_drained_pkt_cnt_reg0_tx_drained_pkt_cnt {
      type oc-yang:counter64;
      description
        "Count number of packets that are transmitted by mac and dropped by the RS layer because the link is in fault state.";
    }
    leaf counter_slice15_ifg_mac_pool83_tx_drained_pkt_cnt_reg1_tx_drained_pkt_cnt {
      type oc-yang:counter64;
      description
        "Count number of packets that are transmitted by mac and dropped by the RS layer because the link is in fault state.";
    }
    leaf counter_slice15_ifg_mac_pool83_tx_drained_pkt_cnt_reg2_tx_drained_pkt_cnt {
      type oc-yang:counter64;
      description
        "Count number of packets that are transmitted by mac and dropped by the RS layer because the link is in fault state.";
    }
    leaf counter_slice15_ifg_mac_pool83_tx_drained_pkt_cnt_reg3_tx_drained_pkt_cnt {
      type oc-yang:counter64;
      description
        "Count number of packets that are transmitted by mac and dropped by the RS layer because the link is in fault state.";
    }
    leaf counter_slice15_ifg_mac_pool83_tx_drained_pkt_cnt_reg4_tx_drained_pkt_cnt {
      type oc-yang:counter64;
      description
        "Count number of packets that are transmitted by mac and dropped by the RS layer because the link is in fault state.";
    }
    leaf counter_slice15_ifg_mac_pool83_tx_drained_pkt_cnt_reg5_tx_drained_pkt_cnt {
      type oc-yang:counter64;
      description
        "Count number of packets that are transmitted by mac and dropped by the RS layer because the link is in fault state.";
    }
    leaf counter_slice15_ifg_mac_pool83_tx_drained_pkt_cnt_reg6_tx_drained_pkt_cnt {
      type oc-yang:counter64;
      description
        "Count number of packets that are transmitted by mac and dropped by the RS layer because the link is in fault state.";
    }
    leaf counter_slice15_ifg_mac_pool83_tx_drained_pkt_cnt_reg7_tx_drained_pkt_cnt {
      type oc-yang:counter64;
      description
        "Count number of packets that are transmitted by mac and dropped by the RS layer because the link is in fault state.";
    }
    leaf counter_slice15_ifg_mac_pool84_tx_drained_pkt_cnt_reg0_tx_drained_pkt_cnt {
      type oc-yang:counter64;
      description
        "Count number of packets that are transmitted by mac and dropped by the RS layer because the link is in fault state.";
    }
    leaf counter_slice15_ifg_mac_pool84_tx_drained_pkt_cnt_reg1_tx_drained_pkt_cnt {
      type oc-yang:counter64;
      description
        "Count number of packets that are transmitted by mac and dropped by the RS layer because the link is in fault state.";
    }
    leaf counter_slice15_ifg_mac_pool84_tx_drained_pkt_cnt_reg2_tx_drained_pkt_cnt {
      type oc-yang:counter64;
      description
        "Count number of packets that are transmitted by mac and dropped by the RS layer because the link is in fault state.";
    }
    leaf counter_slice15_ifg_mac_pool84_tx_drained_pkt_cnt_reg3_tx_drained_pkt_cnt {
      type oc-yang:counter64;
      description
        "Count number of packets that are transmitted by mac and dropped by the RS layer because the link is in fault state.";
    }
    leaf counter_slice15_ifg_mac_pool84_tx_drained_pkt_cnt_reg4_tx_drained_pkt_cnt {
      type oc-yang:counter64;
      description
        "Count number of packets that are transmitted by mac and dropped by the RS layer because the link is in fault state.";
    }
    leaf counter_slice15_ifg_mac_pool84_tx_drained_pkt_cnt_reg5_tx_drained_pkt_cnt {
      type oc-yang:counter64;
      description
        "Count number of packets that are transmitted by mac and dropped by the RS layer because the link is in fault state.";
    }
    leaf counter_slice15_ifg_mac_pool84_tx_drained_pkt_cnt_reg6_tx_drained_pkt_cnt {
      type oc-yang:counter64;
      description
        "Count number of packets that are transmitted by mac and dropped by the RS layer because the link is in fault state.";
    }
    leaf counter_slice15_ifg_mac_pool84_tx_drained_pkt_cnt_reg7_tx_drained_pkt_cnt {
      type oc-yang:counter64;
      description
        "Count number of packets that are transmitted by mac and dropped by the RS layer because the link is in fault state.";
    }
    leaf counter_slice15_ifg_mac_pool85_tx_drained_pkt_cnt_reg0_tx_drained_pkt_cnt {
      type oc-yang:counter64;
      description
        "Count number of packets that are transmitted by mac and dropped by the RS layer because the link is in fault state.";
    }
    leaf counter_slice15_ifg_mac_pool85_tx_drained_pkt_cnt_reg1_tx_drained_pkt_cnt {
      type oc-yang:counter64;
      description
        "Count number of packets that are transmitted by mac and dropped by the RS layer because the link is in fault state.";
    }
    leaf counter_slice15_ifg_mac_pool85_tx_drained_pkt_cnt_reg2_tx_drained_pkt_cnt {
      type oc-yang:counter64;
      description
        "Count number of packets that are transmitted by mac and dropped by the RS layer because the link is in fault state.";
    }
    leaf counter_slice15_ifg_mac_pool85_tx_drained_pkt_cnt_reg3_tx_drained_pkt_cnt {
      type oc-yang:counter64;
      description
        "Count number of packets that are transmitted by mac and dropped by the RS layer because the link is in fault state.";
    }
    leaf counter_slice15_ifg_mac_pool85_tx_drained_pkt_cnt_reg4_tx_drained_pkt_cnt {
      type oc-yang:counter64;
      description
        "Count number of packets that are transmitted by mac and dropped by the RS layer because the link is in fault state.";
    }
    leaf counter_slice15_ifg_mac_pool85_tx_drained_pkt_cnt_reg5_tx_drained_pkt_cnt {
      type oc-yang:counter64;
      description
        "Count number of packets that are transmitted by mac and dropped by the RS layer because the link is in fault state.";
    }
    leaf counter_slice15_ifg_mac_pool85_tx_drained_pkt_cnt_reg6_tx_drained_pkt_cnt {
      type oc-yang:counter64;
      description
        "Count number of packets that are transmitted by mac and dropped by the RS layer because the link is in fault state.";
    }
    leaf counter_slice15_ifg_mac_pool85_tx_drained_pkt_cnt_reg7_tx_drained_pkt_cnt {
      type oc-yang:counter64;
      description
        "Count number of packets that are transmitted by mac and dropped by the RS layer because the link is in fault state.";
    }
    leaf counter_slice15_ifg_mac_pool86_tx_drained_pkt_cnt_reg0_tx_drained_pkt_cnt {
      type oc-yang:counter64;
      description
        "Count number of packets that are transmitted by mac and dropped by the RS layer because the link is in fault state.";
    }
    leaf counter_slice15_ifg_mac_pool86_tx_drained_pkt_cnt_reg1_tx_drained_pkt_cnt {
      type oc-yang:counter64;
      description
        "Count number of packets that are transmitted by mac and dropped by the RS layer because the link is in fault state.";
    }
    leaf counter_slice15_ifg_mac_pool86_tx_drained_pkt_cnt_reg2_tx_drained_pkt_cnt {
      type oc-yang:counter64;
      description
        "Count number of packets that are transmitted by mac and dropped by the RS layer because the link is in fault state.";
    }
    leaf counter_slice15_ifg_mac_pool86_tx_drained_pkt_cnt_reg3_tx_drained_pkt_cnt {
      type oc-yang:counter64;
      description
        "Count number of packets that are transmitted by mac and dropped by the RS layer because the link is in fault state.";
    }
    leaf counter_slice15_ifg_mac_pool86_tx_drained_pkt_cnt_reg4_tx_drained_pkt_cnt {
      type oc-yang:counter64;
      description
        "Count number of packets that are transmitted by mac and dropped by the RS layer because the link is in fault state.";
    }
    leaf counter_slice15_ifg_mac_pool86_tx_drained_pkt_cnt_reg5_tx_drained_pkt_cnt {
      type oc-yang:counter64;
      description
        "Count number of packets that are transmitted by mac and dropped by the RS layer because the link is in fault state.";
    }
    leaf counter_slice15_ifg_mac_pool86_tx_drained_pkt_cnt_reg6_tx_drained_pkt_cnt {
      type oc-yang:counter64;
      description
        "Count number of packets that are transmitted by mac and dropped by the RS layer because the link is in fault state.";
    }
    leaf counter_slice15_ifg_mac_pool86_tx_drained_pkt_cnt_reg7_tx_drained_pkt_cnt {
      type oc-yang:counter64;
      description
        "Count number of packets that are transmitted by mac and dropped by the RS layer because the link is in fault state.";
    }
    leaf counter_slice15_ifg_mac_pool87_tx_drained_pkt_cnt_reg0_tx_drained_pkt_cnt {
      type oc-yang:counter64;
      description
        "Count number of packets that are transmitted by mac and dropped by the RS layer because the link is in fault state.";
    }
    leaf counter_slice15_ifg_mac_pool87_tx_drained_pkt_cnt_reg1_tx_drained_pkt_cnt {
      type oc-yang:counter64;
      description
        "Count number of packets that are transmitted by mac and dropped by the RS layer because the link is in fault state.";
    }
    leaf counter_slice15_ifg_mac_pool87_tx_drained_pkt_cnt_reg2_tx_drained_pkt_cnt {
      type oc-yang:counter64;
      description
        "Count number of packets that are transmitted by mac and dropped by the RS layer because the link is in fault state.";
    }
    leaf counter_slice15_ifg_mac_pool87_tx_drained_pkt_cnt_reg3_tx_drained_pkt_cnt {
      type oc-yang:counter64;
      description
        "Count number of packets that are transmitted by mac and dropped by the RS layer because the link is in fault state.";
    }
    leaf counter_slice15_ifg_mac_pool87_tx_drained_pkt_cnt_reg4_tx_drained_pkt_cnt {
      type oc-yang:counter64;
      description
        "Count number of packets that are transmitted by mac and dropped by the RS layer because the link is in fault state.";
    }
    leaf counter_slice15_ifg_mac_pool87_tx_drained_pkt_cnt_reg5_tx_drained_pkt_cnt {
      type oc-yang:counter64;
      description
        "Count number of packets that are transmitted by mac and dropped by the RS layer because the link is in fault state.";
    }
    leaf counter_slice15_ifg_mac_pool87_tx_drained_pkt_cnt_reg6_tx_drained_pkt_cnt {
      type oc-yang:counter64;
      description
        "Count number of packets that are transmitted by mac and dropped by the RS layer because the link is in fault state.";
    }
    leaf counter_slice15_ifg_mac_pool87_tx_drained_pkt_cnt_reg7_tx_drained_pkt_cnt {
      type oc-yang:counter64;
      description
        "Count number of packets that are transmitted by mac and dropped by the RS layer because the link is in fault state.";
    }
    leaf counter_slice0_ifg_mac_pool80_tx_mac_partial1_invert_crc_cnt_reg0_tx_mac_partial1_invert_crc_cnt {
      type oc-yang:counter64;
      description
        "Counts the number of transmitted packets with partial CRC type 1.";
    }
    leaf counter_slice0_ifg_mac_pool80_tx_mac_partial1_invert_crc_cnt_reg1_tx_mac_partial1_invert_crc_cnt {
      type oc-yang:counter64;
      description
        "Counts the number of transmitted packets with partial CRC type 1.";
    }
    leaf counter_slice0_ifg_mac_pool80_tx_mac_partial1_invert_crc_cnt_reg2_tx_mac_partial1_invert_crc_cnt {
      type oc-yang:counter64;
      description
        "Counts the number of transmitted packets with partial CRC type 1.";
    }
    leaf counter_slice0_ifg_mac_pool80_tx_mac_partial1_invert_crc_cnt_reg3_tx_mac_partial1_invert_crc_cnt {
      type oc-yang:counter64;
      description
        "Counts the number of transmitted packets with partial CRC type 1.";
    }
    leaf counter_slice0_ifg_mac_pool80_tx_mac_partial1_invert_crc_cnt_reg4_tx_mac_partial1_invert_crc_cnt {
      type oc-yang:counter64;
      description
        "Counts the number of transmitted packets with partial CRC type 1.";
    }
    leaf counter_slice0_ifg_mac_pool80_tx_mac_partial1_invert_crc_cnt_reg5_tx_mac_partial1_invert_crc_cnt {
      type oc-yang:counter64;
      description
        "Counts the number of transmitted packets with partial CRC type 1.";
    }
    leaf counter_slice0_ifg_mac_pool80_tx_mac_partial1_invert_crc_cnt_reg6_tx_mac_partial1_invert_crc_cnt {
      type oc-yang:counter64;
      description
        "Counts the number of transmitted packets with partial CRC type 1.";
    }
    leaf counter_slice0_ifg_mac_pool80_tx_mac_partial1_invert_crc_cnt_reg7_tx_mac_partial1_invert_crc_cnt {
      type oc-yang:counter64;
      description
        "Counts the number of transmitted packets with partial CRC type 1.";
    }
    leaf counter_slice0_ifg_mac_pool81_tx_mac_partial1_invert_crc_cnt_reg0_tx_mac_partial1_invert_crc_cnt {
      type oc-yang:counter64;
      description
        "Counts the number of transmitted packets with partial CRC type 1.";
    }
    leaf counter_slice0_ifg_mac_pool81_tx_mac_partial1_invert_crc_cnt_reg1_tx_mac_partial1_invert_crc_cnt {
      type oc-yang:counter64;
      description
        "Counts the number of transmitted packets with partial CRC type 1.";
    }
    leaf counter_slice0_ifg_mac_pool81_tx_mac_partial1_invert_crc_cnt_reg2_tx_mac_partial1_invert_crc_cnt {
      type oc-yang:counter64;
      description
        "Counts the number of transmitted packets with partial CRC type 1.";
    }
    leaf counter_slice0_ifg_mac_pool81_tx_mac_partial1_invert_crc_cnt_reg3_tx_mac_partial1_invert_crc_cnt {
      type oc-yang:counter64;
      description
        "Counts the number of transmitted packets with partial CRC type 1.";
    }
    leaf counter_slice0_ifg_mac_pool81_tx_mac_partial1_invert_crc_cnt_reg4_tx_mac_partial1_invert_crc_cnt {
      type oc-yang:counter64;
      description
        "Counts the number of transmitted packets with partial CRC type 1.";
    }
    leaf counter_slice0_ifg_mac_pool81_tx_mac_partial1_invert_crc_cnt_reg5_tx_mac_partial1_invert_crc_cnt {
      type oc-yang:counter64;
      description
        "Counts the number of transmitted packets with partial CRC type 1.";
    }
    leaf counter_slice0_ifg_mac_pool81_tx_mac_partial1_invert_crc_cnt_reg6_tx_mac_partial1_invert_crc_cnt {
      type oc-yang:counter64;
      description
        "Counts the number of transmitted packets with partial CRC type 1.";
    }
    leaf counter_slice0_ifg_mac_pool81_tx_mac_partial1_invert_crc_cnt_reg7_tx_mac_partial1_invert_crc_cnt {
      type oc-yang:counter64;
      description
        "Counts the number of transmitted packets with partial CRC type 1.";
    }
    leaf counter_slice0_ifg_mac_pool82_tx_mac_partial1_invert_crc_cnt_reg0_tx_mac_partial1_invert_crc_cnt {
      type oc-yang:counter64;
      description
        "Counts the number of transmitted packets with partial CRC type 1.";
    }
    leaf counter_slice0_ifg_mac_pool82_tx_mac_partial1_invert_crc_cnt_reg1_tx_mac_partial1_invert_crc_cnt {
      type oc-yang:counter64;
      description
        "Counts the number of transmitted packets with partial CRC type 1.";
    }
    leaf counter_slice0_ifg_mac_pool82_tx_mac_partial1_invert_crc_cnt_reg2_tx_mac_partial1_invert_crc_cnt {
      type oc-yang:counter64;
      description
        "Counts the number of transmitted packets with partial CRC type 1.";
    }
    leaf counter_slice0_ifg_mac_pool82_tx_mac_partial1_invert_crc_cnt_reg3_tx_mac_partial1_invert_crc_cnt {
      type oc-yang:counter64;
      description
        "Counts the number of transmitted packets with partial CRC type 1.";
    }
    leaf counter_slice0_ifg_mac_pool82_tx_mac_partial1_invert_crc_cnt_reg4_tx_mac_partial1_invert_crc_cnt {
      type oc-yang:counter64;
      description
        "Counts the number of transmitted packets with partial CRC type 1.";
    }
    leaf counter_slice0_ifg_mac_pool82_tx_mac_partial1_invert_crc_cnt_reg5_tx_mac_partial1_invert_crc_cnt {
      type oc-yang:counter64;
      description
        "Counts the number of transmitted packets with partial CRC type 1.";
    }
    leaf counter_slice0_ifg_mac_pool82_tx_mac_partial1_invert_crc_cnt_reg6_tx_mac_partial1_invert_crc_cnt {
      type oc-yang:counter64;
      description
        "Counts the number of transmitted packets with partial CRC type 1.";
    }
    leaf counter_slice0_ifg_mac_pool82_tx_mac_partial1_invert_crc_cnt_reg7_tx_mac_partial1_invert_crc_cnt {
      type oc-yang:counter64;
      description
        "Counts the number of transmitted packets with partial CRC type 1.";
    }
    leaf counter_slice0_ifg_mac_pool83_tx_mac_partial1_invert_crc_cnt_reg0_tx_mac_partial1_invert_crc_cnt {
      type oc-yang:counter64;
      description
        "Counts the number of transmitted packets with partial CRC type 1.";
    }
    leaf counter_slice0_ifg_mac_pool83_tx_mac_partial1_invert_crc_cnt_reg1_tx_mac_partial1_invert_crc_cnt {
      type oc-yang:counter64;
      description
        "Counts the number of transmitted packets with partial CRC type 1.";
    }
    leaf counter_slice0_ifg_mac_pool83_tx_mac_partial1_invert_crc_cnt_reg2_tx_mac_partial1_invert_crc_cnt {
      type oc-yang:counter64;
      description
        "Counts the number of transmitted packets with partial CRC type 1.";
    }
    leaf counter_slice0_ifg_mac_pool83_tx_mac_partial1_invert_crc_cnt_reg3_tx_mac_partial1_invert_crc_cnt {
      type oc-yang:counter64;
      description
        "Counts the number of transmitted packets with partial CRC type 1.";
    }
    leaf counter_slice0_ifg_mac_pool83_tx_mac_partial1_invert_crc_cnt_reg4_tx_mac_partial1_invert_crc_cnt {
      type oc-yang:counter64;
      description
        "Counts the number of transmitted packets with partial CRC type 1.";
    }
    leaf counter_slice0_ifg_mac_pool83_tx_mac_partial1_invert_crc_cnt_reg5_tx_mac_partial1_invert_crc_cnt {
      type oc-yang:counter64;
      description
        "Counts the number of transmitted packets with partial CRC type 1.";
    }
    leaf counter_slice0_ifg_mac_pool83_tx_mac_partial1_invert_crc_cnt_reg6_tx_mac_partial1_invert_crc_cnt {
      type oc-yang:counter64;
      description
        "Counts the number of transmitted packets with partial CRC type 1.";
    }
    leaf counter_slice0_ifg_mac_pool83_tx_mac_partial1_invert_crc_cnt_reg7_tx_mac_partial1_invert_crc_cnt {
      type oc-yang:counter64;
      description
        "Counts the number of transmitted packets with partial CRC type 1.";
    }
    leaf counter_slice0_ifg_mac_pool84_tx_mac_partial1_invert_crc_cnt_reg0_tx_mac_partial1_invert_crc_cnt {
      type oc-yang:counter64;
      description
        "Counts the number of transmitted packets with partial CRC type 1.";
    }
    leaf counter_slice0_ifg_mac_pool84_tx_mac_partial1_invert_crc_cnt_reg1_tx_mac_partial1_invert_crc_cnt {
      type oc-yang:counter64;
      description
        "Counts the number of transmitted packets with partial CRC type 1.";
    }
    leaf counter_slice0_ifg_mac_pool84_tx_mac_partial1_invert_crc_cnt_reg2_tx_mac_partial1_invert_crc_cnt {
      type oc-yang:counter64;
      description
        "Counts the number of transmitted packets with partial CRC type 1.";
    }
    leaf counter_slice0_ifg_mac_pool84_tx_mac_partial1_invert_crc_cnt_reg3_tx_mac_partial1_invert_crc_cnt {
      type oc-yang:counter64;
      description
        "Counts the number of transmitted packets with partial CRC type 1.";
    }
    leaf counter_slice0_ifg_mac_pool84_tx_mac_partial1_invert_crc_cnt_reg4_tx_mac_partial1_invert_crc_cnt {
      type oc-yang:counter64;
      description
        "Counts the number of transmitted packets with partial CRC type 1.";
    }
    leaf counter_slice0_ifg_mac_pool84_tx_mac_partial1_invert_crc_cnt_reg5_tx_mac_partial1_invert_crc_cnt {
      type oc-yang:counter64;
      description
        "Counts the number of transmitted packets with partial CRC type 1.";
    }
    leaf counter_slice0_ifg_mac_pool84_tx_mac_partial1_invert_crc_cnt_reg6_tx_mac_partial1_invert_crc_cnt {
      type oc-yang:counter64;
      description
        "Counts the number of transmitted packets with partial CRC type 1.";
    }
    leaf counter_slice0_ifg_mac_pool84_tx_mac_partial1_invert_crc_cnt_reg7_tx_mac_partial1_invert_crc_cnt {
      type oc-yang:counter64;
      description
        "Counts the number of transmitted packets with partial CRC type 1.";
    }
    leaf counter_slice0_ifg_mac_pool85_tx_mac_partial1_invert_crc_cnt_reg0_tx_mac_partial1_invert_crc_cnt {
      type oc-yang:counter64;
      description
        "Counts the number of transmitted packets with partial CRC type 1.";
    }
    leaf counter_slice0_ifg_mac_pool85_tx_mac_partial1_invert_crc_cnt_reg1_tx_mac_partial1_invert_crc_cnt {
      type oc-yang:counter64;
      description
        "Counts the number of transmitted packets with partial CRC type 1.";
    }
    leaf counter_slice0_ifg_mac_pool85_tx_mac_partial1_invert_crc_cnt_reg2_tx_mac_partial1_invert_crc_cnt {
      type oc-yang:counter64;
      description
        "Counts the number of transmitted packets with partial CRC type 1.";
    }
    leaf counter_slice0_ifg_mac_pool85_tx_mac_partial1_invert_crc_cnt_reg3_tx_mac_partial1_invert_crc_cnt {
      type oc-yang:counter64;
      description
        "Counts the number of transmitted packets with partial CRC type 1.";
    }
    leaf counter_slice0_ifg_mac_pool85_tx_mac_partial1_invert_crc_cnt_reg4_tx_mac_partial1_invert_crc_cnt {
      type oc-yang:counter64;
      description
        "Counts the number of transmitted packets with partial CRC type 1.";
    }
    leaf counter_slice0_ifg_mac_pool85_tx_mac_partial1_invert_crc_cnt_reg5_tx_mac_partial1_invert_crc_cnt {
      type oc-yang:counter64;
      description
        "Counts the number of transmitted packets with partial CRC type 1.";
    }
    leaf counter_slice0_ifg_mac_pool85_tx_mac_partial1_invert_crc_cnt_reg6_tx_mac_partial1_invert_crc_cnt {
      type oc-yang:counter64;
      description
        "Counts the number of transmitted packets with partial CRC type 1.";
    }
    leaf counter_slice0_ifg_mac_pool85_tx_mac_partial1_invert_crc_cnt_reg7_tx_mac_partial1_invert_crc_cnt {
      type oc-yang:counter64;
      description
        "Counts the number of transmitted packets with partial CRC type 1.";
    }
    leaf counter_slice0_ifg_mac_pool86_tx_mac_partial1_invert_crc_cnt_reg0_tx_mac_partial1_invert_crc_cnt {
      type oc-yang:counter64;
      description
        "Counts the number of transmitted packets with partial CRC type 1.";
    }
    leaf counter_slice0_ifg_mac_pool86_tx_mac_partial1_invert_crc_cnt_reg1_tx_mac_partial1_invert_crc_cnt {
      type oc-yang:counter64;
      description
        "Counts the number of transmitted packets with partial CRC type 1.";
    }
    leaf counter_slice0_ifg_mac_pool86_tx_mac_partial1_invert_crc_cnt_reg2_tx_mac_partial1_invert_crc_cnt {
      type oc-yang:counter64;
      description
        "Counts the number of transmitted packets with partial CRC type 1.";
    }
    leaf counter_slice0_ifg_mac_pool86_tx_mac_partial1_invert_crc_cnt_reg3_tx_mac_partial1_invert_crc_cnt {
      type oc-yang:counter64;
      description
        "Counts the number of transmitted packets with partial CRC type 1.";
    }
    leaf counter_slice0_ifg_mac_pool86_tx_mac_partial1_invert_crc_cnt_reg4_tx_mac_partial1_invert_crc_cnt {
      type oc-yang:counter64;
      description
        "Counts the number of transmitted packets with partial CRC type 1.";
    }
    leaf counter_slice0_ifg_mac_pool86_tx_mac_partial1_invert_crc_cnt_reg5_tx_mac_partial1_invert_crc_cnt {
      type oc-yang:counter64;
      description
        "Counts the number of transmitted packets with partial CRC type 1.";
    }
    leaf counter_slice0_ifg_mac_pool86_tx_mac_partial1_invert_crc_cnt_reg6_tx_mac_partial1_invert_crc_cnt {
      type oc-yang:counter64;
      description
        "Counts the number of transmitted packets with partial CRC type 1.";
    }
    leaf counter_slice0_ifg_mac_pool86_tx_mac_partial1_invert_crc_cnt_reg7_tx_mac_partial1_invert_crc_cnt {
      type oc-yang:counter64;
      description
        "Counts the number of transmitted packets with partial CRC type 1.";
    }
    leaf counter_slice0_ifg_mac_pool87_tx_mac_partial1_invert_crc_cnt_reg0_tx_mac_partial1_invert_crc_cnt {
      type oc-yang:counter64;
      description
        "Counts the number of transmitted packets with partial CRC type 1.";
    }
    leaf counter_slice0_ifg_mac_pool87_tx_mac_partial1_invert_crc_cnt_reg1_tx_mac_partial1_invert_crc_cnt {
      type oc-yang:counter64;
      description
        "Counts the number of transmitted packets with partial CRC type 1.";
    }
    leaf counter_slice0_ifg_mac_pool87_tx_mac_partial1_invert_crc_cnt_reg2_tx_mac_partial1_invert_crc_cnt {
      type oc-yang:counter64;
      description
        "Counts the number of transmitted packets with partial CRC type 1.";
    }
    leaf counter_slice0_ifg_mac_pool87_tx_mac_partial1_invert_crc_cnt_reg3_tx_mac_partial1_invert_crc_cnt {
      type oc-yang:counter64;
      description
        "Counts the number of transmitted packets with partial CRC type 1.";
    }
    leaf counter_slice0_ifg_mac_pool87_tx_mac_partial1_invert_crc_cnt_reg4_tx_mac_partial1_invert_crc_cnt {
      type oc-yang:counter64;
      description
        "Counts the number of transmitted packets with partial CRC type 1.";
    }
    leaf counter_slice0_ifg_mac_pool87_tx_mac_partial1_invert_crc_cnt_reg5_tx_mac_partial1_invert_crc_cnt {
      type oc-yang:counter64;
      description
        "Counts the number of transmitted packets with partial CRC type 1.";
    }
    leaf counter_slice0_ifg_mac_pool87_tx_mac_partial1_invert_crc_cnt_reg6_tx_mac_partial1_invert_crc_cnt {
      type oc-yang:counter64;
      description
        "Counts the number of transmitted packets with partial CRC type 1.";
    }
    leaf counter_slice0_ifg_mac_pool87_tx_mac_partial1_invert_crc_cnt_reg7_tx_mac_partial1_invert_crc_cnt {
      type oc-yang:counter64;
      description
        "Counts the number of transmitted packets with partial CRC type 1.";
    }
    leaf counter_slice1_ifg_mac_pool80_tx_mac_partial1_invert_crc_cnt_reg0_tx_mac_partial1_invert_crc_cnt {
      type oc-yang:counter64;
      description
        "Counts the number of transmitted packets with partial CRC type 1.";
    }
    leaf counter_slice1_ifg_mac_pool80_tx_mac_partial1_invert_crc_cnt_reg1_tx_mac_partial1_invert_crc_cnt {
      type oc-yang:counter64;
      description
        "Counts the number of transmitted packets with partial CRC type 1.";
    }
    leaf counter_slice1_ifg_mac_pool80_tx_mac_partial1_invert_crc_cnt_reg2_tx_mac_partial1_invert_crc_cnt {
      type oc-yang:counter64;
      description
        "Counts the number of transmitted packets with partial CRC type 1.";
    }
    leaf counter_slice1_ifg_mac_pool80_tx_mac_partial1_invert_crc_cnt_reg3_tx_mac_partial1_invert_crc_cnt {
      type oc-yang:counter64;
      description
        "Counts the number of transmitted packets with partial CRC type 1.";
    }
    leaf counter_slice1_ifg_mac_pool80_tx_mac_partial1_invert_crc_cnt_reg4_tx_mac_partial1_invert_crc_cnt {
      type oc-yang:counter64;
      description
        "Counts the number of transmitted packets with partial CRC type 1.";
    }
    leaf counter_slice1_ifg_mac_pool80_tx_mac_partial1_invert_crc_cnt_reg5_tx_mac_partial1_invert_crc_cnt {
      type oc-yang:counter64;
      description
        "Counts the number of transmitted packets with partial CRC type 1.";
    }
    leaf counter_slice1_ifg_mac_pool80_tx_mac_partial1_invert_crc_cnt_reg6_tx_mac_partial1_invert_crc_cnt {
      type oc-yang:counter64;
      description
        "Counts the number of transmitted packets with partial CRC type 1.";
    }
    leaf counter_slice1_ifg_mac_pool80_tx_mac_partial1_invert_crc_cnt_reg7_tx_mac_partial1_invert_crc_cnt {
      type oc-yang:counter64;
      description
        "Counts the number of transmitted packets with partial CRC type 1.";
    }
    leaf counter_slice1_ifg_mac_pool81_tx_mac_partial1_invert_crc_cnt_reg0_tx_mac_partial1_invert_crc_cnt {
      type oc-yang:counter64;
      description
        "Counts the number of transmitted packets with partial CRC type 1.";
    }
    leaf counter_slice1_ifg_mac_pool81_tx_mac_partial1_invert_crc_cnt_reg1_tx_mac_partial1_invert_crc_cnt {
      type oc-yang:counter64;
      description
        "Counts the number of transmitted packets with partial CRC type 1.";
    }
    leaf counter_slice1_ifg_mac_pool81_tx_mac_partial1_invert_crc_cnt_reg2_tx_mac_partial1_invert_crc_cnt {
      type oc-yang:counter64;
      description
        "Counts the number of transmitted packets with partial CRC type 1.";
    }
    leaf counter_slice1_ifg_mac_pool81_tx_mac_partial1_invert_crc_cnt_reg3_tx_mac_partial1_invert_crc_cnt {
      type oc-yang:counter64;
      description
        "Counts the number of transmitted packets with partial CRC type 1.";
    }
    leaf counter_slice1_ifg_mac_pool81_tx_mac_partial1_invert_crc_cnt_reg4_tx_mac_partial1_invert_crc_cnt {
      type oc-yang:counter64;
      description
        "Counts the number of transmitted packets with partial CRC type 1.";
    }
    leaf counter_slice1_ifg_mac_pool81_tx_mac_partial1_invert_crc_cnt_reg5_tx_mac_partial1_invert_crc_cnt {
      type oc-yang:counter64;
      description
        "Counts the number of transmitted packets with partial CRC type 1.";
    }
    leaf counter_slice1_ifg_mac_pool81_tx_mac_partial1_invert_crc_cnt_reg6_tx_mac_partial1_invert_crc_cnt {
      type oc-yang:counter64;
      description
        "Counts the number of transmitted packets with partial CRC type 1.";
    }
    leaf counter_slice1_ifg_mac_pool81_tx_mac_partial1_invert_crc_cnt_reg7_tx_mac_partial1_invert_crc_cnt {
      type oc-yang:counter64;
      description
        "Counts the number of transmitted packets with partial CRC type 1.";
    }
    leaf counter_slice1_ifg_mac_pool82_tx_mac_partial1_invert_crc_cnt_reg0_tx_mac_partial1_invert_crc_cnt {
      type oc-yang:counter64;
      description
        "Counts the number of transmitted packets with partial CRC type 1.";
    }
    leaf counter_slice1_ifg_mac_pool82_tx_mac_partial1_invert_crc_cnt_reg1_tx_mac_partial1_invert_crc_cnt {
      type oc-yang:counter64;
      description
        "Counts the number of transmitted packets with partial CRC type 1.";
    }
    leaf counter_slice1_ifg_mac_pool82_tx_mac_partial1_invert_crc_cnt_reg2_tx_mac_partial1_invert_crc_cnt {
      type oc-yang:counter64;
      description
        "Counts the number of transmitted packets with partial CRC type 1.";
    }
    leaf counter_slice1_ifg_mac_pool82_tx_mac_partial1_invert_crc_cnt_reg3_tx_mac_partial1_invert_crc_cnt {
      type oc-yang:counter64;
      description
        "Counts the number of transmitted packets with partial CRC type 1.";
    }
    leaf counter_slice1_ifg_mac_pool82_tx_mac_partial1_invert_crc_cnt_reg4_tx_mac_partial1_invert_crc_cnt {
      type oc-yang:counter64;
      description
        "Counts the number of transmitted packets with partial CRC type 1.";
    }
    leaf counter_slice1_ifg_mac_pool82_tx_mac_partial1_invert_crc_cnt_reg5_tx_mac_partial1_invert_crc_cnt {
      type oc-yang:counter64;
      description
        "Counts the number of transmitted packets with partial CRC type 1.";
    }
    leaf counter_slice1_ifg_mac_pool82_tx_mac_partial1_invert_crc_cnt_reg6_tx_mac_partial1_invert_crc_cnt {
      type oc-yang:counter64;
      description
        "Counts the number of transmitted packets with partial CRC type 1.";
    }
    leaf counter_slice1_ifg_mac_pool82_tx_mac_partial1_invert_crc_cnt_reg7_tx_mac_partial1_invert_crc_cnt {
      type oc-yang:counter64;
      description
        "Counts the number of transmitted packets with partial CRC type 1.";
    }
    leaf counter_slice1_ifg_mac_pool83_tx_mac_partial1_invert_crc_cnt_reg0_tx_mac_partial1_invert_crc_cnt {
      type oc-yang:counter64;
      description
        "Counts the number of transmitted packets with partial CRC type 1.";
    }
    leaf counter_slice1_ifg_mac_pool83_tx_mac_partial1_invert_crc_cnt_reg1_tx_mac_partial1_invert_crc_cnt {
      type oc-yang:counter64;
      description
        "Counts the number of transmitted packets with partial CRC type 1.";
    }
    leaf counter_slice1_ifg_mac_pool83_tx_mac_partial1_invert_crc_cnt_reg2_tx_mac_partial1_invert_crc_cnt {
      type oc-yang:counter64;
      description
        "Counts the number of transmitted packets with partial CRC type 1.";
    }
    leaf counter_slice1_ifg_mac_pool83_tx_mac_partial1_invert_crc_cnt_reg3_tx_mac_partial1_invert_crc_cnt {
      type oc-yang:counter64;
      description
        "Counts the number of transmitted packets with partial CRC type 1.";
    }
    leaf counter_slice1_ifg_mac_pool83_tx_mac_partial1_invert_crc_cnt_reg4_tx_mac_partial1_invert_crc_cnt {
      type oc-yang:counter64;
      description
        "Counts the number of transmitted packets with partial CRC type 1.";
    }
    leaf counter_slice1_ifg_mac_pool83_tx_mac_partial1_invert_crc_cnt_reg5_tx_mac_partial1_invert_crc_cnt {
      type oc-yang:counter64;
      description
        "Counts the number of transmitted packets with partial CRC type 1.";
    }
    leaf counter_slice1_ifg_mac_pool83_tx_mac_partial1_invert_crc_cnt_reg6_tx_mac_partial1_invert_crc_cnt {
      type oc-yang:counter64;
      description
        "Counts the number of transmitted packets with partial CRC type 1.";
    }
    leaf counter_slice1_ifg_mac_pool83_tx_mac_partial1_invert_crc_cnt_reg7_tx_mac_partial1_invert_crc_cnt {
      type oc-yang:counter64;
      description
        "Counts the number of transmitted packets with partial CRC type 1.";
    }
    leaf counter_slice1_ifg_mac_pool84_tx_mac_partial1_invert_crc_cnt_reg0_tx_mac_partial1_invert_crc_cnt {
      type oc-yang:counter64;
      description
        "Counts the number of transmitted packets with partial CRC type 1.";
    }
    leaf counter_slice1_ifg_mac_pool84_tx_mac_partial1_invert_crc_cnt_reg1_tx_mac_partial1_invert_crc_cnt {
      type oc-yang:counter64;
      description
        "Counts the number of transmitted packets with partial CRC type 1.";
    }
    leaf counter_slice1_ifg_mac_pool84_tx_mac_partial1_invert_crc_cnt_reg2_tx_mac_partial1_invert_crc_cnt {
      type oc-yang:counter64;
      description
        "Counts the number of transmitted packets with partial CRC type 1.";
    }
    leaf counter_slice1_ifg_mac_pool84_tx_mac_partial1_invert_crc_cnt_reg3_tx_mac_partial1_invert_crc_cnt {
      type oc-yang:counter64;
      description
        "Counts the number of transmitted packets with partial CRC type 1.";
    }
    leaf counter_slice1_ifg_mac_pool84_tx_mac_partial1_invert_crc_cnt_reg4_tx_mac_partial1_invert_crc_cnt {
      type oc-yang:counter64;
      description
        "Counts the number of transmitted packets with partial CRC type 1.";
    }
    leaf counter_slice1_ifg_mac_pool84_tx_mac_partial1_invert_crc_cnt_reg5_tx_mac_partial1_invert_crc_cnt {
      type oc-yang:counter64;
      description
        "Counts the number of transmitted packets with partial CRC type 1.";
    }
    leaf counter_slice1_ifg_mac_pool84_tx_mac_partial1_invert_crc_cnt_reg6_tx_mac_partial1_invert_crc_cnt {
      type oc-yang:counter64;
      description
        "Counts the number of transmitted packets with partial CRC type 1.";
    }
    leaf counter_slice1_ifg_mac_pool84_tx_mac_partial1_invert_crc_cnt_reg7_tx_mac_partial1_invert_crc_cnt {
      type oc-yang:counter64;
      description
        "Counts the number of transmitted packets with partial CRC type 1.";
    }
    leaf counter_slice1_ifg_mac_pool85_tx_mac_partial1_invert_crc_cnt_reg0_tx_mac_partial1_invert_crc_cnt {
      type oc-yang:counter64;
      description
        "Counts the number of transmitted packets with partial CRC type 1.";
    }
    leaf counter_slice1_ifg_mac_pool85_tx_mac_partial1_invert_crc_cnt_reg1_tx_mac_partial1_invert_crc_cnt {
      type oc-yang:counter64;
      description
        "Counts the number of transmitted packets with partial CRC type 1.";
    }
    leaf counter_slice1_ifg_mac_pool85_tx_mac_partial1_invert_crc_cnt_reg2_tx_mac_partial1_invert_crc_cnt {
      type oc-yang:counter64;
      description
        "Counts the number of transmitted packets with partial CRC type 1.";
    }
    leaf counter_slice1_ifg_mac_pool85_tx_mac_partial1_invert_crc_cnt_reg3_tx_mac_partial1_invert_crc_cnt {
      type oc-yang:counter64;
      description
        "Counts the number of transmitted packets with partial CRC type 1.";
    }
    leaf counter_slice1_ifg_mac_pool85_tx_mac_partial1_invert_crc_cnt_reg4_tx_mac_partial1_invert_crc_cnt {
      type oc-yang:counter64;
      description
        "Counts the number of transmitted packets with partial CRC type 1.";
    }
    leaf counter_slice1_ifg_mac_pool85_tx_mac_partial1_invert_crc_cnt_reg5_tx_mac_partial1_invert_crc_cnt {
      type oc-yang:counter64;
      description
        "Counts the number of transmitted packets with partial CRC type 1.";
    }
    leaf counter_slice1_ifg_mac_pool85_tx_mac_partial1_invert_crc_cnt_reg6_tx_mac_partial1_invert_crc_cnt {
      type oc-yang:counter64;
      description
        "Counts the number of transmitted packets with partial CRC type 1.";
    }
    leaf counter_slice1_ifg_mac_pool85_tx_mac_partial1_invert_crc_cnt_reg7_tx_mac_partial1_invert_crc_cnt {
      type oc-yang:counter64;
      description
        "Counts the number of transmitted packets with partial CRC type 1.";
    }
    leaf counter_slice1_ifg_mac_pool86_tx_mac_partial1_invert_crc_cnt_reg0_tx_mac_partial1_invert_crc_cnt {
      type oc-yang:counter64;
      description
        "Counts the number of transmitted packets with partial CRC type 1.";
    }
    leaf counter_slice1_ifg_mac_pool86_tx_mac_partial1_invert_crc_cnt_reg1_tx_mac_partial1_invert_crc_cnt {
      type oc-yang:counter64;
      description
        "Counts the number of transmitted packets with partial CRC type 1.";
    }
    leaf counter_slice1_ifg_mac_pool86_tx_mac_partial1_invert_crc_cnt_reg2_tx_mac_partial1_invert_crc_cnt {
      type oc-yang:counter64;
      description
        "Counts the number of transmitted packets with partial CRC type 1.";
    }
    leaf counter_slice1_ifg_mac_pool86_tx_mac_partial1_invert_crc_cnt_reg3_tx_mac_partial1_invert_crc_cnt {
      type oc-yang:counter64;
      description
        "Counts the number of transmitted packets with partial CRC type 1.";
    }
    leaf counter_slice1_ifg_mac_pool86_tx_mac_partial1_invert_crc_cnt_reg4_tx_mac_partial1_invert_crc_cnt {
      type oc-yang:counter64;
      description
        "Counts the number of transmitted packets with partial CRC type 1.";
    }
    leaf counter_slice1_ifg_mac_pool86_tx_mac_partial1_invert_crc_cnt_reg5_tx_mac_partial1_invert_crc_cnt {
      type oc-yang:counter64;
      description
        "Counts the number of transmitted packets with partial CRC type 1.";
    }
    leaf counter_slice1_ifg_mac_pool86_tx_mac_partial1_invert_crc_cnt_reg6_tx_mac_partial1_invert_crc_cnt {
      type oc-yang:counter64;
      description
        "Counts the number of transmitted packets with partial CRC type 1.";
    }
    leaf counter_slice1_ifg_mac_pool86_tx_mac_partial1_invert_crc_cnt_reg7_tx_mac_partial1_invert_crc_cnt {
      type oc-yang:counter64;
      description
        "Counts the number of transmitted packets with partial CRC type 1.";
    }
    leaf counter_slice1_ifg_mac_pool87_tx_mac_partial1_invert_crc_cnt_reg0_tx_mac_partial1_invert_crc_cnt {
      type oc-yang:counter64;
      description
        "Counts the number of transmitted packets with partial CRC type 1.";
    }
    leaf counter_slice1_ifg_mac_pool87_tx_mac_partial1_invert_crc_cnt_reg1_tx_mac_partial1_invert_crc_cnt {
      type oc-yang:counter64;
      description
        "Counts the number of transmitted packets with partial CRC type 1.";
    }
    leaf counter_slice1_ifg_mac_pool87_tx_mac_partial1_invert_crc_cnt_reg2_tx_mac_partial1_invert_crc_cnt {
      type oc-yang:counter64;
      description
        "Counts the number of transmitted packets with partial CRC type 1.";
    }
    leaf counter_slice1_ifg_mac_pool87_tx_mac_partial1_invert_crc_cnt_reg3_tx_mac_partial1_invert_crc_cnt {
      type oc-yang:counter64;
      description
        "Counts the number of transmitted packets with partial CRC type 1.";
    }
    leaf counter_slice1_ifg_mac_pool87_tx_mac_partial1_invert_crc_cnt_reg4_tx_mac_partial1_invert_crc_cnt {
      type oc-yang:counter64;
      description
        "Counts the number of transmitted packets with partial CRC type 1.";
    }
    leaf counter_slice1_ifg_mac_pool87_tx_mac_partial1_invert_crc_cnt_reg5_tx_mac_partial1_invert_crc_cnt {
      type oc-yang:counter64;
      description
        "Counts the number of transmitted packets with partial CRC type 1.";
    }
    leaf counter_slice1_ifg_mac_pool87_tx_mac_partial1_invert_crc_cnt_reg6_tx_mac_partial1_invert_crc_cnt {
      type oc-yang:counter64;
      description
        "Counts the number of transmitted packets with partial CRC type 1.";
    }
    leaf counter_slice1_ifg_mac_pool87_tx_mac_partial1_invert_crc_cnt_reg7_tx_mac_partial1_invert_crc_cnt {
      type oc-yang:counter64;
      description
        "Counts the number of transmitted packets with partial CRC type 1.";
    }
    leaf counter_slice2_ifg_mac_pool80_tx_mac_partial1_invert_crc_cnt_reg0_tx_mac_partial1_invert_crc_cnt {
      type oc-yang:counter64;
      description
        "Counts the number of transmitted packets with partial CRC type 1.";
    }
    leaf counter_slice2_ifg_mac_pool80_tx_mac_partial1_invert_crc_cnt_reg1_tx_mac_partial1_invert_crc_cnt {
      type oc-yang:counter64;
      description
        "Counts the number of transmitted packets with partial CRC type 1.";
    }
    leaf counter_slice2_ifg_mac_pool80_tx_mac_partial1_invert_crc_cnt_reg2_tx_mac_partial1_invert_crc_cnt {
      type oc-yang:counter64;
      description
        "Counts the number of transmitted packets with partial CRC type 1.";
    }
    leaf counter_slice2_ifg_mac_pool80_tx_mac_partial1_invert_crc_cnt_reg3_tx_mac_partial1_invert_crc_cnt {
      type oc-yang:counter64;
      description
        "Counts the number of transmitted packets with partial CRC type 1.";
    }
    leaf counter_slice2_ifg_mac_pool80_tx_mac_partial1_invert_crc_cnt_reg4_tx_mac_partial1_invert_crc_cnt {
      type oc-yang:counter64;
      description
        "Counts the number of transmitted packets with partial CRC type 1.";
    }
    leaf counter_slice2_ifg_mac_pool80_tx_mac_partial1_invert_crc_cnt_reg5_tx_mac_partial1_invert_crc_cnt {
      type oc-yang:counter64;
      description
        "Counts the number of transmitted packets with partial CRC type 1.";
    }
    leaf counter_slice2_ifg_mac_pool80_tx_mac_partial1_invert_crc_cnt_reg6_tx_mac_partial1_invert_crc_cnt {
      type oc-yang:counter64;
      description
        "Counts the number of transmitted packets with partial CRC type 1.";
    }
    leaf counter_slice2_ifg_mac_pool80_tx_mac_partial1_invert_crc_cnt_reg7_tx_mac_partial1_invert_crc_cnt {
      type oc-yang:counter64;
      description
        "Counts the number of transmitted packets with partial CRC type 1.";
    }
    leaf counter_slice2_ifg_mac_pool81_tx_mac_partial1_invert_crc_cnt_reg0_tx_mac_partial1_invert_crc_cnt {
      type oc-yang:counter64;
      description
        "Counts the number of transmitted packets with partial CRC type 1.";
    }
    leaf counter_slice2_ifg_mac_pool81_tx_mac_partial1_invert_crc_cnt_reg1_tx_mac_partial1_invert_crc_cnt {
      type oc-yang:counter64;
      description
        "Counts the number of transmitted packets with partial CRC type 1.";
    }
    leaf counter_slice2_ifg_mac_pool81_tx_mac_partial1_invert_crc_cnt_reg2_tx_mac_partial1_invert_crc_cnt {
      type oc-yang:counter64;
      description
        "Counts the number of transmitted packets with partial CRC type 1.";
    }
    leaf counter_slice2_ifg_mac_pool81_tx_mac_partial1_invert_crc_cnt_reg3_tx_mac_partial1_invert_crc_cnt {
      type oc-yang:counter64;
      description
        "Counts the number of transmitted packets with partial CRC type 1.";
    }
    leaf counter_slice2_ifg_mac_pool81_tx_mac_partial1_invert_crc_cnt_reg4_tx_mac_partial1_invert_crc_cnt {
      type oc-yang:counter64;
      description
        "Counts the number of transmitted packets with partial CRC type 1.";
    }
    leaf counter_slice2_ifg_mac_pool81_tx_mac_partial1_invert_crc_cnt_reg5_tx_mac_partial1_invert_crc_cnt {
      type oc-yang:counter64;
      description
        "Counts the number of transmitted packets with partial CRC type 1.";
    }
    leaf counter_slice2_ifg_mac_pool81_tx_mac_partial1_invert_crc_cnt_reg6_tx_mac_partial1_invert_crc_cnt {
      type oc-yang:counter64;
      description
        "Counts the number of transmitted packets with partial CRC type 1.";
    }
    leaf counter_slice2_ifg_mac_pool81_tx_mac_partial1_invert_crc_cnt_reg7_tx_mac_partial1_invert_crc_cnt {
      type oc-yang:counter64;
      description
        "Counts the number of transmitted packets with partial CRC type 1.";
    }
    leaf counter_slice2_ifg_mac_pool82_tx_mac_partial1_invert_crc_cnt_reg0_tx_mac_partial1_invert_crc_cnt {
      type oc-yang:counter64;
      description
        "Counts the number of transmitted packets with partial CRC type 1.";
    }
    leaf counter_slice2_ifg_mac_pool82_tx_mac_partial1_invert_crc_cnt_reg1_tx_mac_partial1_invert_crc_cnt {
      type oc-yang:counter64;
      description
        "Counts the number of transmitted packets with partial CRC type 1.";
    }
    leaf counter_slice2_ifg_mac_pool82_tx_mac_partial1_invert_crc_cnt_reg2_tx_mac_partial1_invert_crc_cnt {
      type oc-yang:counter64;
      description
        "Counts the number of transmitted packets with partial CRC type 1.";
    }
    leaf counter_slice2_ifg_mac_pool82_tx_mac_partial1_invert_crc_cnt_reg3_tx_mac_partial1_invert_crc_cnt {
      type oc-yang:counter64;
      description
        "Counts the number of transmitted packets with partial CRC type 1.";
    }
    leaf counter_slice2_ifg_mac_pool82_tx_mac_partial1_invert_crc_cnt_reg4_tx_mac_partial1_invert_crc_cnt {
      type oc-yang:counter64;
      description
        "Counts the number of transmitted packets with partial CRC type 1.";
    }
    leaf counter_slice2_ifg_mac_pool82_tx_mac_partial1_invert_crc_cnt_reg5_tx_mac_partial1_invert_crc_cnt {
      type oc-yang:counter64;
      description
        "Counts the number of transmitted packets with partial CRC type 1.";
    }
    leaf counter_slice2_ifg_mac_pool82_tx_mac_partial1_invert_crc_cnt_reg6_tx_mac_partial1_invert_crc_cnt {
      type oc-yang:counter64;
      description
        "Counts the number of transmitted packets with partial CRC type 1.";
    }
    leaf counter_slice2_ifg_mac_pool82_tx_mac_partial1_invert_crc_cnt_reg7_tx_mac_partial1_invert_crc_cnt {
      type oc-yang:counter64;
      description
        "Counts the number of transmitted packets with partial CRC type 1.";
    }
    leaf counter_slice2_ifg_mac_pool83_tx_mac_partial1_invert_crc_cnt_reg0_tx_mac_partial1_invert_crc_cnt {
      type oc-yang:counter64;
      description
        "Counts the number of transmitted packets with partial CRC type 1.";
    }
    leaf counter_slice2_ifg_mac_pool83_tx_mac_partial1_invert_crc_cnt_reg1_tx_mac_partial1_invert_crc_cnt {
      type oc-yang:counter64;
      description
        "Counts the number of transmitted packets with partial CRC type 1.";
    }
    leaf counter_slice2_ifg_mac_pool83_tx_mac_partial1_invert_crc_cnt_reg2_tx_mac_partial1_invert_crc_cnt {
      type oc-yang:counter64;
      description
        "Counts the number of transmitted packets with partial CRC type 1.";
    }
    leaf counter_slice2_ifg_mac_pool83_tx_mac_partial1_invert_crc_cnt_reg3_tx_mac_partial1_invert_crc_cnt {
      type oc-yang:counter64;
      description
        "Counts the number of transmitted packets with partial CRC type 1.";
    }
    leaf counter_slice2_ifg_mac_pool83_tx_mac_partial1_invert_crc_cnt_reg4_tx_mac_partial1_invert_crc_cnt {
      type oc-yang:counter64;
      description
        "Counts the number of transmitted packets with partial CRC type 1.";
    }
    leaf counter_slice2_ifg_mac_pool83_tx_mac_partial1_invert_crc_cnt_reg5_tx_mac_partial1_invert_crc_cnt {
      type oc-yang:counter64;
      description
        "Counts the number of transmitted packets with partial CRC type 1.";
    }
    leaf counter_slice2_ifg_mac_pool83_tx_mac_partial1_invert_crc_cnt_reg6_tx_mac_partial1_invert_crc_cnt {
      type oc-yang:counter64;
      description
        "Counts the number of transmitted packets with partial CRC type 1.";
    }
    leaf counter_slice2_ifg_mac_pool83_tx_mac_partial1_invert_crc_cnt_reg7_tx_mac_partial1_invert_crc_cnt {
      type oc-yang:counter64;
      description
        "Counts the number of transmitted packets with partial CRC type 1.";
    }
    leaf counter_slice2_ifg_mac_pool84_tx_mac_partial1_invert_crc_cnt_reg0_tx_mac_partial1_invert_crc_cnt {
      type oc-yang:counter64;
      description
        "Counts the number of transmitted packets with partial CRC type 1.";
    }
    leaf counter_slice2_ifg_mac_pool84_tx_mac_partial1_invert_crc_cnt_reg1_tx_mac_partial1_invert_crc_cnt {
      type oc-yang:counter64;
      description
        "Counts the number of transmitted packets with partial CRC type 1.";
    }
    leaf counter_slice2_ifg_mac_pool84_tx_mac_partial1_invert_crc_cnt_reg2_tx_mac_partial1_invert_crc_cnt {
      type oc-yang:counter64;
      description
        "Counts the number of transmitted packets with partial CRC type 1.";
    }
    leaf counter_slice2_ifg_mac_pool84_tx_mac_partial1_invert_crc_cnt_reg3_tx_mac_partial1_invert_crc_cnt {
      type oc-yang:counter64;
      description
        "Counts the number of transmitted packets with partial CRC type 1.";
    }
    leaf counter_slice2_ifg_mac_pool84_tx_mac_partial1_invert_crc_cnt_reg4_tx_mac_partial1_invert_crc_cnt {
      type oc-yang:counter64;
      description
        "Counts the number of transmitted packets with partial CRC type 1.";
    }
    leaf counter_slice2_ifg_mac_pool84_tx_mac_partial1_invert_crc_cnt_reg5_tx_mac_partial1_invert_crc_cnt {
      type oc-yang:counter64;
      description
        "Counts the number of transmitted packets with partial CRC type 1.";
    }
    leaf counter_slice2_ifg_mac_pool84_tx_mac_partial1_invert_crc_cnt_reg6_tx_mac_partial1_invert_crc_cnt {
      type oc-yang:counter64;
      description
        "Counts the number of transmitted packets with partial CRC type 1.";
    }
    leaf counter_slice2_ifg_mac_pool84_tx_mac_partial1_invert_crc_cnt_reg7_tx_mac_partial1_invert_crc_cnt {
      type oc-yang:counter64;
      description
        "Counts the number of transmitted packets with partial CRC type 1.";
    }
    leaf counter_slice2_ifg_mac_pool85_tx_mac_partial1_invert_crc_cnt_reg0_tx_mac_partial1_invert_crc_cnt {
      type oc-yang:counter64;
      description
        "Counts the number of transmitted packets with partial CRC type 1.";
    }
    leaf counter_slice2_ifg_mac_pool85_tx_mac_partial1_invert_crc_cnt_reg1_tx_mac_partial1_invert_crc_cnt {
      type oc-yang:counter64;
      description
        "Counts the number of transmitted packets with partial CRC type 1.";
    }
    leaf counter_slice2_ifg_mac_pool85_tx_mac_partial1_invert_crc_cnt_reg2_tx_mac_partial1_invert_crc_cnt {
      type oc-yang:counter64;
      description
        "Counts the number of transmitted packets with partial CRC type 1.";
    }
    leaf counter_slice2_ifg_mac_pool85_tx_mac_partial1_invert_crc_cnt_reg3_tx_mac_partial1_invert_crc_cnt {
      type oc-yang:counter64;
      description
        "Counts the number of transmitted packets with partial CRC type 1.";
    }
    leaf counter_slice2_ifg_mac_pool85_tx_mac_partial1_invert_crc_cnt_reg4_tx_mac_partial1_invert_crc_cnt {
      type oc-yang:counter64;
      description
        "Counts the number of transmitted packets with partial CRC type 1.";
    }
    leaf counter_slice2_ifg_mac_pool85_tx_mac_partial1_invert_crc_cnt_reg5_tx_mac_partial1_invert_crc_cnt {
      type oc-yang:counter64;
      description
        "Counts the number of transmitted packets with partial CRC type 1.";
    }
    leaf counter_slice2_ifg_mac_pool85_tx_mac_partial1_invert_crc_cnt_reg6_tx_mac_partial1_invert_crc_cnt {
      type oc-yang:counter64;
      description
        "Counts the number of transmitted packets with partial CRC type 1.";
    }
    leaf counter_slice2_ifg_mac_pool85_tx_mac_partial1_invert_crc_cnt_reg7_tx_mac_partial1_invert_crc_cnt {
      type oc-yang:counter64;
      description
        "Counts the number of transmitted packets with partial CRC type 1.";
    }
    leaf counter_slice2_ifg_mac_pool86_tx_mac_partial1_invert_crc_cnt_reg0_tx_mac_partial1_invert_crc_cnt {
      type oc-yang:counter64;
      description
        "Counts the number of transmitted packets with partial CRC type 1.";
    }
    leaf counter_slice2_ifg_mac_pool86_tx_mac_partial1_invert_crc_cnt_reg1_tx_mac_partial1_invert_crc_cnt {
      type oc-yang:counter64;
      description
        "Counts the number of transmitted packets with partial CRC type 1.";
    }
    leaf counter_slice2_ifg_mac_pool86_tx_mac_partial1_invert_crc_cnt_reg2_tx_mac_partial1_invert_crc_cnt {
      type oc-yang:counter64;
      description
        "Counts the number of transmitted packets with partial CRC type 1.";
    }
    leaf counter_slice2_ifg_mac_pool86_tx_mac_partial1_invert_crc_cnt_reg3_tx_mac_partial1_invert_crc_cnt {
      type oc-yang:counter64;
      description
        "Counts the number of transmitted packets with partial CRC type 1.";
    }
    leaf counter_slice2_ifg_mac_pool86_tx_mac_partial1_invert_crc_cnt_reg4_tx_mac_partial1_invert_crc_cnt {
      type oc-yang:counter64;
      description
        "Counts the number of transmitted packets with partial CRC type 1.";
    }
    leaf counter_slice2_ifg_mac_pool86_tx_mac_partial1_invert_crc_cnt_reg5_tx_mac_partial1_invert_crc_cnt {
      type oc-yang:counter64;
      description
        "Counts the number of transmitted packets with partial CRC type 1.";
    }
    leaf counter_slice2_ifg_mac_pool86_tx_mac_partial1_invert_crc_cnt_reg6_tx_mac_partial1_invert_crc_cnt {
      type oc-yang:counter64;
      description
        "Counts the number of transmitted packets with partial CRC type 1.";
    }
    leaf counter_slice2_ifg_mac_pool86_tx_mac_partial1_invert_crc_cnt_reg7_tx_mac_partial1_invert_crc_cnt {
      type oc-yang:counter64;
      description
        "Counts the number of transmitted packets with partial CRC type 1.";
    }
    leaf counter_slice2_ifg_mac_pool87_tx_mac_partial1_invert_crc_cnt_reg0_tx_mac_partial1_invert_crc_cnt {
      type oc-yang:counter64;
      description
        "Counts the number of transmitted packets with partial CRC type 1.";
    }
    leaf counter_slice2_ifg_mac_pool87_tx_mac_partial1_invert_crc_cnt_reg1_tx_mac_partial1_invert_crc_cnt {
      type oc-yang:counter64;
      description
        "Counts the number of transmitted packets with partial CRC type 1.";
    }
    leaf counter_slice2_ifg_mac_pool87_tx_mac_partial1_invert_crc_cnt_reg2_tx_mac_partial1_invert_crc_cnt {
      type oc-yang:counter64;
      description
        "Counts the number of transmitted packets with partial CRC type 1.";
    }
    leaf counter_slice2_ifg_mac_pool87_tx_mac_partial1_invert_crc_cnt_reg3_tx_mac_partial1_invert_crc_cnt {
      type oc-yang:counter64;
      description
        "Counts the number of transmitted packets with partial CRC type 1.";
    }
    leaf counter_slice2_ifg_mac_pool87_tx_mac_partial1_invert_crc_cnt_reg4_tx_mac_partial1_invert_crc_cnt {
      type oc-yang:counter64;
      description
        "Counts the number of transmitted packets with partial CRC type 1.";
    }
    leaf counter_slice2_ifg_mac_pool87_tx_mac_partial1_invert_crc_cnt_reg5_tx_mac_partial1_invert_crc_cnt {
      type oc-yang:counter64;
      description
        "Counts the number of transmitted packets with partial CRC type 1.";
    }
    leaf counter_slice2_ifg_mac_pool87_tx_mac_partial1_invert_crc_cnt_reg6_tx_mac_partial1_invert_crc_cnt {
      type oc-yang:counter64;
      description
        "Counts the number of transmitted packets with partial CRC type 1.";
    }
    leaf counter_slice2_ifg_mac_pool87_tx_mac_partial1_invert_crc_cnt_reg7_tx_mac_partial1_invert_crc_cnt {
      type oc-yang:counter64;
      description
        "Counts the number of transmitted packets with partial CRC type 1.";
    }
    leaf counter_slice3_ifg_mac_pool80_tx_mac_partial1_invert_crc_cnt_reg0_tx_mac_partial1_invert_crc_cnt {
      type oc-yang:counter64;
      description
        "Counts the number of transmitted packets with partial CRC type 1.";
    }
    leaf counter_slice3_ifg_mac_pool80_tx_mac_partial1_invert_crc_cnt_reg1_tx_mac_partial1_invert_crc_cnt {
      type oc-yang:counter64;
      description
        "Counts the number of transmitted packets with partial CRC type 1.";
    }
    leaf counter_slice3_ifg_mac_pool80_tx_mac_partial1_invert_crc_cnt_reg2_tx_mac_partial1_invert_crc_cnt {
      type oc-yang:counter64;
      description
        "Counts the number of transmitted packets with partial CRC type 1.";
    }
    leaf counter_slice3_ifg_mac_pool80_tx_mac_partial1_invert_crc_cnt_reg3_tx_mac_partial1_invert_crc_cnt {
      type oc-yang:counter64;
      description
        "Counts the number of transmitted packets with partial CRC type 1.";
    }
    leaf counter_slice3_ifg_mac_pool80_tx_mac_partial1_invert_crc_cnt_reg4_tx_mac_partial1_invert_crc_cnt {
      type oc-yang:counter64;
      description
        "Counts the number of transmitted packets with partial CRC type 1.";
    }
    leaf counter_slice3_ifg_mac_pool80_tx_mac_partial1_invert_crc_cnt_reg5_tx_mac_partial1_invert_crc_cnt {
      type oc-yang:counter64;
      description
        "Counts the number of transmitted packets with partial CRC type 1.";
    }
    leaf counter_slice3_ifg_mac_pool80_tx_mac_partial1_invert_crc_cnt_reg6_tx_mac_partial1_invert_crc_cnt {
      type oc-yang:counter64;
      description
        "Counts the number of transmitted packets with partial CRC type 1.";
    }
    leaf counter_slice3_ifg_mac_pool80_tx_mac_partial1_invert_crc_cnt_reg7_tx_mac_partial1_invert_crc_cnt {
      type oc-yang:counter64;
      description
        "Counts the number of transmitted packets with partial CRC type 1.";
    }
    leaf counter_slice3_ifg_mac_pool81_tx_mac_partial1_invert_crc_cnt_reg0_tx_mac_partial1_invert_crc_cnt {
      type oc-yang:counter64;
      description
        "Counts the number of transmitted packets with partial CRC type 1.";
    }
    leaf counter_slice3_ifg_mac_pool81_tx_mac_partial1_invert_crc_cnt_reg1_tx_mac_partial1_invert_crc_cnt {
      type oc-yang:counter64;
      description
        "Counts the number of transmitted packets with partial CRC type 1.";
    }
    leaf counter_slice3_ifg_mac_pool81_tx_mac_partial1_invert_crc_cnt_reg2_tx_mac_partial1_invert_crc_cnt {
      type oc-yang:counter64;
      description
        "Counts the number of transmitted packets with partial CRC type 1.";
    }
    leaf counter_slice3_ifg_mac_pool81_tx_mac_partial1_invert_crc_cnt_reg3_tx_mac_partial1_invert_crc_cnt {
      type oc-yang:counter64;
      description
        "Counts the number of transmitted packets with partial CRC type 1.";
    }
    leaf counter_slice3_ifg_mac_pool81_tx_mac_partial1_invert_crc_cnt_reg4_tx_mac_partial1_invert_crc_cnt {
      type oc-yang:counter64;
      description
        "Counts the number of transmitted packets with partial CRC type 1.";
    }
    leaf counter_slice3_ifg_mac_pool81_tx_mac_partial1_invert_crc_cnt_reg5_tx_mac_partial1_invert_crc_cnt {
      type oc-yang:counter64;
      description
        "Counts the number of transmitted packets with partial CRC type 1.";
    }
    leaf counter_slice3_ifg_mac_pool81_tx_mac_partial1_invert_crc_cnt_reg6_tx_mac_partial1_invert_crc_cnt {
      type oc-yang:counter64;
      description
        "Counts the number of transmitted packets with partial CRC type 1.";
    }
    leaf counter_slice3_ifg_mac_pool81_tx_mac_partial1_invert_crc_cnt_reg7_tx_mac_partial1_invert_crc_cnt {
      type oc-yang:counter64;
      description
        "Counts the number of transmitted packets with partial CRC type 1.";
    }
    leaf counter_slice3_ifg_mac_pool82_tx_mac_partial1_invert_crc_cnt_reg0_tx_mac_partial1_invert_crc_cnt {
      type oc-yang:counter64;
      description
        "Counts the number of transmitted packets with partial CRC type 1.";
    }
    leaf counter_slice3_ifg_mac_pool82_tx_mac_partial1_invert_crc_cnt_reg1_tx_mac_partial1_invert_crc_cnt {
      type oc-yang:counter64;
      description
        "Counts the number of transmitted packets with partial CRC type 1.";
    }
    leaf counter_slice3_ifg_mac_pool82_tx_mac_partial1_invert_crc_cnt_reg2_tx_mac_partial1_invert_crc_cnt {
      type oc-yang:counter64;
      description
        "Counts the number of transmitted packets with partial CRC type 1.";
    }
    leaf counter_slice3_ifg_mac_pool82_tx_mac_partial1_invert_crc_cnt_reg3_tx_mac_partial1_invert_crc_cnt {
      type oc-yang:counter64;
      description
        "Counts the number of transmitted packets with partial CRC type 1.";
    }
    leaf counter_slice3_ifg_mac_pool82_tx_mac_partial1_invert_crc_cnt_reg4_tx_mac_partial1_invert_crc_cnt {
      type oc-yang:counter64;
      description
        "Counts the number of transmitted packets with partial CRC type 1.";
    }
    leaf counter_slice3_ifg_mac_pool82_tx_mac_partial1_invert_crc_cnt_reg5_tx_mac_partial1_invert_crc_cnt {
      type oc-yang:counter64;
      description
        "Counts the number of transmitted packets with partial CRC type 1.";
    }
    leaf counter_slice3_ifg_mac_pool82_tx_mac_partial1_invert_crc_cnt_reg6_tx_mac_partial1_invert_crc_cnt {
      type oc-yang:counter64;
      description
        "Counts the number of transmitted packets with partial CRC type 1.";
    }
    leaf counter_slice3_ifg_mac_pool82_tx_mac_partial1_invert_crc_cnt_reg7_tx_mac_partial1_invert_crc_cnt {
      type oc-yang:counter64;
      description
        "Counts the number of transmitted packets with partial CRC type 1.";
    }
    leaf counter_slice3_ifg_mac_pool83_tx_mac_partial1_invert_crc_cnt_reg0_tx_mac_partial1_invert_crc_cnt {
      type oc-yang:counter64;
      description
        "Counts the number of transmitted packets with partial CRC type 1.";
    }
    leaf counter_slice3_ifg_mac_pool83_tx_mac_partial1_invert_crc_cnt_reg1_tx_mac_partial1_invert_crc_cnt {
      type oc-yang:counter64;
      description
        "Counts the number of transmitted packets with partial CRC type 1.";
    }
    leaf counter_slice3_ifg_mac_pool83_tx_mac_partial1_invert_crc_cnt_reg2_tx_mac_partial1_invert_crc_cnt {
      type oc-yang:counter64;
      description
        "Counts the number of transmitted packets with partial CRC type 1.";
    }
    leaf counter_slice3_ifg_mac_pool83_tx_mac_partial1_invert_crc_cnt_reg3_tx_mac_partial1_invert_crc_cnt {
      type oc-yang:counter64;
      description
        "Counts the number of transmitted packets with partial CRC type 1.";
    }
    leaf counter_slice3_ifg_mac_pool83_tx_mac_partial1_invert_crc_cnt_reg4_tx_mac_partial1_invert_crc_cnt {
      type oc-yang:counter64;
      description
        "Counts the number of transmitted packets with partial CRC type 1.";
    }
    leaf counter_slice3_ifg_mac_pool83_tx_mac_partial1_invert_crc_cnt_reg5_tx_mac_partial1_invert_crc_cnt {
      type oc-yang:counter64;
      description
        "Counts the number of transmitted packets with partial CRC type 1.";
    }
    leaf counter_slice3_ifg_mac_pool83_tx_mac_partial1_invert_crc_cnt_reg6_tx_mac_partial1_invert_crc_cnt {
      type oc-yang:counter64;
      description
        "Counts the number of transmitted packets with partial CRC type 1.";
    }
    leaf counter_slice3_ifg_mac_pool83_tx_mac_partial1_invert_crc_cnt_reg7_tx_mac_partial1_invert_crc_cnt {
      type oc-yang:counter64;
      description
        "Counts the number of transmitted packets with partial CRC type 1.";
    }
    leaf counter_slice3_ifg_mac_pool84_tx_mac_partial1_invert_crc_cnt_reg0_tx_mac_partial1_invert_crc_cnt {
      type oc-yang:counter64;
      description
        "Counts the number of transmitted packets with partial CRC type 1.";
    }
    leaf counter_slice3_ifg_mac_pool84_tx_mac_partial1_invert_crc_cnt_reg1_tx_mac_partial1_invert_crc_cnt {
      type oc-yang:counter64;
      description
        "Counts the number of transmitted packets with partial CRC type 1.";
    }
    leaf counter_slice3_ifg_mac_pool84_tx_mac_partial1_invert_crc_cnt_reg2_tx_mac_partial1_invert_crc_cnt {
      type oc-yang:counter64;
      description
        "Counts the number of transmitted packets with partial CRC type 1.";
    }
    leaf counter_slice3_ifg_mac_pool84_tx_mac_partial1_invert_crc_cnt_reg3_tx_mac_partial1_invert_crc_cnt {
      type oc-yang:counter64;
      description
        "Counts the number of transmitted packets with partial CRC type 1.";
    }
    leaf counter_slice3_ifg_mac_pool84_tx_mac_partial1_invert_crc_cnt_reg4_tx_mac_partial1_invert_crc_cnt {
      type oc-yang:counter64;
      description
        "Counts the number of transmitted packets with partial CRC type 1.";
    }
    leaf counter_slice3_ifg_mac_pool84_tx_mac_partial1_invert_crc_cnt_reg5_tx_mac_partial1_invert_crc_cnt {
      type oc-yang:counter64;
      description
        "Counts the number of transmitted packets with partial CRC type 1.";
    }
    leaf counter_slice3_ifg_mac_pool84_tx_mac_partial1_invert_crc_cnt_reg6_tx_mac_partial1_invert_crc_cnt {
      type oc-yang:counter64;
      description
        "Counts the number of transmitted packets with partial CRC type 1.";
    }
    leaf counter_slice3_ifg_mac_pool84_tx_mac_partial1_invert_crc_cnt_reg7_tx_mac_partial1_invert_crc_cnt {
      type oc-yang:counter64;
      description
        "Counts the number of transmitted packets with partial CRC type 1.";
    }
    leaf counter_slice3_ifg_mac_pool85_tx_mac_partial1_invert_crc_cnt_reg0_tx_mac_partial1_invert_crc_cnt {
      type oc-yang:counter64;
      description
        "Counts the number of transmitted packets with partial CRC type 1.";
    }
    leaf counter_slice3_ifg_mac_pool85_tx_mac_partial1_invert_crc_cnt_reg1_tx_mac_partial1_invert_crc_cnt {
      type oc-yang:counter64;
      description
        "Counts the number of transmitted packets with partial CRC type 1.";
    }
    leaf counter_slice3_ifg_mac_pool85_tx_mac_partial1_invert_crc_cnt_reg2_tx_mac_partial1_invert_crc_cnt {
      type oc-yang:counter64;
      description
        "Counts the number of transmitted packets with partial CRC type 1.";
    }
    leaf counter_slice3_ifg_mac_pool85_tx_mac_partial1_invert_crc_cnt_reg3_tx_mac_partial1_invert_crc_cnt {
      type oc-yang:counter64;
      description
        "Counts the number of transmitted packets with partial CRC type 1.";
    }
    leaf counter_slice3_ifg_mac_pool85_tx_mac_partial1_invert_crc_cnt_reg4_tx_mac_partial1_invert_crc_cnt {
      type oc-yang:counter64;
      description
        "Counts the number of transmitted packets with partial CRC type 1.";
    }
    leaf counter_slice3_ifg_mac_pool85_tx_mac_partial1_invert_crc_cnt_reg5_tx_mac_partial1_invert_crc_cnt {
      type oc-yang:counter64;
      description
        "Counts the number of transmitted packets with partial CRC type 1.";
    }
    leaf counter_slice3_ifg_mac_pool85_tx_mac_partial1_invert_crc_cnt_reg6_tx_mac_partial1_invert_crc_cnt {
      type oc-yang:counter64;
      description
        "Counts the number of transmitted packets with partial CRC type 1.";
    }
    leaf counter_slice3_ifg_mac_pool85_tx_mac_partial1_invert_crc_cnt_reg7_tx_mac_partial1_invert_crc_cnt {
      type oc-yang:counter64;
      description
        "Counts the number of transmitted packets with partial CRC type 1.";
    }
    leaf counter_slice3_ifg_mac_pool86_tx_mac_partial1_invert_crc_cnt_reg0_tx_mac_partial1_invert_crc_cnt {
      type oc-yang:counter64;
      description
        "Counts the number of transmitted packets with partial CRC type 1.";
    }
    leaf counter_slice3_ifg_mac_pool86_tx_mac_partial1_invert_crc_cnt_reg1_tx_mac_partial1_invert_crc_cnt {
      type oc-yang:counter64;
      description
        "Counts the number of transmitted packets with partial CRC type 1.";
    }
    leaf counter_slice3_ifg_mac_pool86_tx_mac_partial1_invert_crc_cnt_reg2_tx_mac_partial1_invert_crc_cnt {
      type oc-yang:counter64;
      description
        "Counts the number of transmitted packets with partial CRC type 1.";
    }
    leaf counter_slice3_ifg_mac_pool86_tx_mac_partial1_invert_crc_cnt_reg3_tx_mac_partial1_invert_crc_cnt {
      type oc-yang:counter64;
      description
        "Counts the number of transmitted packets with partial CRC type 1.";
    }
    leaf counter_slice3_ifg_mac_pool86_tx_mac_partial1_invert_crc_cnt_reg4_tx_mac_partial1_invert_crc_cnt {
      type oc-yang:counter64;
      description
        "Counts the number of transmitted packets with partial CRC type 1.";
    }
    leaf counter_slice3_ifg_mac_pool86_tx_mac_partial1_invert_crc_cnt_reg5_tx_mac_partial1_invert_crc_cnt {
      type oc-yang:counter64;
      description
        "Counts the number of transmitted packets with partial CRC type 1.";
    }
    leaf counter_slice3_ifg_mac_pool86_tx_mac_partial1_invert_crc_cnt_reg6_tx_mac_partial1_invert_crc_cnt {
      type oc-yang:counter64;
      description
        "Counts the number of transmitted packets with partial CRC type 1.";
    }
    leaf counter_slice3_ifg_mac_pool86_tx_mac_partial1_invert_crc_cnt_reg7_tx_mac_partial1_invert_crc_cnt {
      type oc-yang:counter64;
      description
        "Counts the number of transmitted packets with partial CRC type 1.";
    }
    leaf counter_slice3_ifg_mac_pool87_tx_mac_partial1_invert_crc_cnt_reg0_tx_mac_partial1_invert_crc_cnt {
      type oc-yang:counter64;
      description
        "Counts the number of transmitted packets with partial CRC type 1.";
    }
    leaf counter_slice3_ifg_mac_pool87_tx_mac_partial1_invert_crc_cnt_reg1_tx_mac_partial1_invert_crc_cnt {
      type oc-yang:counter64;
      description
        "Counts the number of transmitted packets with partial CRC type 1.";
    }
    leaf counter_slice3_ifg_mac_pool87_tx_mac_partial1_invert_crc_cnt_reg2_tx_mac_partial1_invert_crc_cnt {
      type oc-yang:counter64;
      description
        "Counts the number of transmitted packets with partial CRC type 1.";
    }
    leaf counter_slice3_ifg_mac_pool87_tx_mac_partial1_invert_crc_cnt_reg3_tx_mac_partial1_invert_crc_cnt {
      type oc-yang:counter64;
      description
        "Counts the number of transmitted packets with partial CRC type 1.";
    }
    leaf counter_slice3_ifg_mac_pool87_tx_mac_partial1_invert_crc_cnt_reg4_tx_mac_partial1_invert_crc_cnt {
      type oc-yang:counter64;
      description
        "Counts the number of transmitted packets with partial CRC type 1.";
    }
    leaf counter_slice3_ifg_mac_pool87_tx_mac_partial1_invert_crc_cnt_reg5_tx_mac_partial1_invert_crc_cnt {
      type oc-yang:counter64;
      description
        "Counts the number of transmitted packets with partial CRC type 1.";
    }
    leaf counter_slice3_ifg_mac_pool87_tx_mac_partial1_invert_crc_cnt_reg6_tx_mac_partial1_invert_crc_cnt {
      type oc-yang:counter64;
      description
        "Counts the number of transmitted packets with partial CRC type 1.";
    }
    leaf counter_slice3_ifg_mac_pool87_tx_mac_partial1_invert_crc_cnt_reg7_tx_mac_partial1_invert_crc_cnt {
      type oc-yang:counter64;
      description
        "Counts the number of transmitted packets with partial CRC type 1.";
    }
    leaf counter_slice4_ifg_mac_pool80_tx_mac_partial1_invert_crc_cnt_reg0_tx_mac_partial1_invert_crc_cnt {
      type oc-yang:counter64;
      description
        "Counts the number of transmitted packets with partial CRC type 1.";
    }
    leaf counter_slice4_ifg_mac_pool80_tx_mac_partial1_invert_crc_cnt_reg1_tx_mac_partial1_invert_crc_cnt {
      type oc-yang:counter64;
      description
        "Counts the number of transmitted packets with partial CRC type 1.";
    }
    leaf counter_slice4_ifg_mac_pool80_tx_mac_partial1_invert_crc_cnt_reg2_tx_mac_partial1_invert_crc_cnt {
      type oc-yang:counter64;
      description
        "Counts the number of transmitted packets with partial CRC type 1.";
    }
    leaf counter_slice4_ifg_mac_pool80_tx_mac_partial1_invert_crc_cnt_reg3_tx_mac_partial1_invert_crc_cnt {
      type oc-yang:counter64;
      description
        "Counts the number of transmitted packets with partial CRC type 1.";
    }
    leaf counter_slice4_ifg_mac_pool80_tx_mac_partial1_invert_crc_cnt_reg4_tx_mac_partial1_invert_crc_cnt {
      type oc-yang:counter64;
      description
        "Counts the number of transmitted packets with partial CRC type 1.";
    }
    leaf counter_slice4_ifg_mac_pool80_tx_mac_partial1_invert_crc_cnt_reg5_tx_mac_partial1_invert_crc_cnt {
      type oc-yang:counter64;
      description
        "Counts the number of transmitted packets with partial CRC type 1.";
    }
    leaf counter_slice4_ifg_mac_pool80_tx_mac_partial1_invert_crc_cnt_reg6_tx_mac_partial1_invert_crc_cnt {
      type oc-yang:counter64;
      description
        "Counts the number of transmitted packets with partial CRC type 1.";
    }
    leaf counter_slice4_ifg_mac_pool80_tx_mac_partial1_invert_crc_cnt_reg7_tx_mac_partial1_invert_crc_cnt {
      type oc-yang:counter64;
      description
        "Counts the number of transmitted packets with partial CRC type 1.";
    }
    leaf counter_slice4_ifg_mac_pool81_tx_mac_partial1_invert_crc_cnt_reg0_tx_mac_partial1_invert_crc_cnt {
      type oc-yang:counter64;
      description
        "Counts the number of transmitted packets with partial CRC type 1.";
    }
    leaf counter_slice4_ifg_mac_pool81_tx_mac_partial1_invert_crc_cnt_reg1_tx_mac_partial1_invert_crc_cnt {
      type oc-yang:counter64;
      description
        "Counts the number of transmitted packets with partial CRC type 1.";
    }
    leaf counter_slice4_ifg_mac_pool81_tx_mac_partial1_invert_crc_cnt_reg2_tx_mac_partial1_invert_crc_cnt {
      type oc-yang:counter64;
      description
        "Counts the number of transmitted packets with partial CRC type 1.";
    }
    leaf counter_slice4_ifg_mac_pool81_tx_mac_partial1_invert_crc_cnt_reg3_tx_mac_partial1_invert_crc_cnt {
      type oc-yang:counter64;
      description
        "Counts the number of transmitted packets with partial CRC type 1.";
    }
    leaf counter_slice4_ifg_mac_pool81_tx_mac_partial1_invert_crc_cnt_reg4_tx_mac_partial1_invert_crc_cnt {
      type oc-yang:counter64;
      description
        "Counts the number of transmitted packets with partial CRC type 1.";
    }
    leaf counter_slice4_ifg_mac_pool81_tx_mac_partial1_invert_crc_cnt_reg5_tx_mac_partial1_invert_crc_cnt {
      type oc-yang:counter64;
      description
        "Counts the number of transmitted packets with partial CRC type 1.";
    }
    leaf counter_slice4_ifg_mac_pool81_tx_mac_partial1_invert_crc_cnt_reg6_tx_mac_partial1_invert_crc_cnt {
      type oc-yang:counter64;
      description
        "Counts the number of transmitted packets with partial CRC type 1.";
    }
    leaf counter_slice4_ifg_mac_pool81_tx_mac_partial1_invert_crc_cnt_reg7_tx_mac_partial1_invert_crc_cnt {
      type oc-yang:counter64;
      description
        "Counts the number of transmitted packets with partial CRC type 1.";
    }
    leaf counter_slice4_ifg_mac_pool82_tx_mac_partial1_invert_crc_cnt_reg0_tx_mac_partial1_invert_crc_cnt {
      type oc-yang:counter64;
      description
        "Counts the number of transmitted packets with partial CRC type 1.";
    }
    leaf counter_slice4_ifg_mac_pool82_tx_mac_partial1_invert_crc_cnt_reg1_tx_mac_partial1_invert_crc_cnt {
      type oc-yang:counter64;
      description
        "Counts the number of transmitted packets with partial CRC type 1.";
    }
    leaf counter_slice4_ifg_mac_pool82_tx_mac_partial1_invert_crc_cnt_reg2_tx_mac_partial1_invert_crc_cnt {
      type oc-yang:counter64;
      description
        "Counts the number of transmitted packets with partial CRC type 1.";
    }
    leaf counter_slice4_ifg_mac_pool82_tx_mac_partial1_invert_crc_cnt_reg3_tx_mac_partial1_invert_crc_cnt {
      type oc-yang:counter64;
      description
        "Counts the number of transmitted packets with partial CRC type 1.";
    }
    leaf counter_slice4_ifg_mac_pool82_tx_mac_partial1_invert_crc_cnt_reg4_tx_mac_partial1_invert_crc_cnt {
      type oc-yang:counter64;
      description
        "Counts the number of transmitted packets with partial CRC type 1.";
    }
    leaf counter_slice4_ifg_mac_pool82_tx_mac_partial1_invert_crc_cnt_reg5_tx_mac_partial1_invert_crc_cnt {
      type oc-yang:counter64;
      description
        "Counts the number of transmitted packets with partial CRC type 1.";
    }
    leaf counter_slice4_ifg_mac_pool82_tx_mac_partial1_invert_crc_cnt_reg6_tx_mac_partial1_invert_crc_cnt {
      type oc-yang:counter64;
      description
        "Counts the number of transmitted packets with partial CRC type 1.";
    }
    leaf counter_slice4_ifg_mac_pool82_tx_mac_partial1_invert_crc_cnt_reg7_tx_mac_partial1_invert_crc_cnt {
      type oc-yang:counter64;
      description
        "Counts the number of transmitted packets with partial CRC type 1.";
    }
    leaf counter_slice4_ifg_mac_pool83_tx_mac_partial1_invert_crc_cnt_reg0_tx_mac_partial1_invert_crc_cnt {
      type oc-yang:counter64;
      description
        "Counts the number of transmitted packets with partial CRC type 1.";
    }
    leaf counter_slice4_ifg_mac_pool83_tx_mac_partial1_invert_crc_cnt_reg1_tx_mac_partial1_invert_crc_cnt {
      type oc-yang:counter64;
      description
        "Counts the number of transmitted packets with partial CRC type 1.";
    }
    leaf counter_slice4_ifg_mac_pool83_tx_mac_partial1_invert_crc_cnt_reg2_tx_mac_partial1_invert_crc_cnt {
      type oc-yang:counter64;
      description
        "Counts the number of transmitted packets with partial CRC type 1.";
    }
    leaf counter_slice4_ifg_mac_pool83_tx_mac_partial1_invert_crc_cnt_reg3_tx_mac_partial1_invert_crc_cnt {
      type oc-yang:counter64;
      description
        "Counts the number of transmitted packets with partial CRC type 1.";
    }
    leaf counter_slice4_ifg_mac_pool83_tx_mac_partial1_invert_crc_cnt_reg4_tx_mac_partial1_invert_crc_cnt {
      type oc-yang:counter64;
      description
        "Counts the number of transmitted packets with partial CRC type 1.";
    }
    leaf counter_slice4_ifg_mac_pool83_tx_mac_partial1_invert_crc_cnt_reg5_tx_mac_partial1_invert_crc_cnt {
      type oc-yang:counter64;
      description
        "Counts the number of transmitted packets with partial CRC type 1.";
    }
    leaf counter_slice4_ifg_mac_pool83_tx_mac_partial1_invert_crc_cnt_reg6_tx_mac_partial1_invert_crc_cnt {
      type oc-yang:counter64;
      description
        "Counts the number of transmitted packets with partial CRC type 1.";
    }
    leaf counter_slice4_ifg_mac_pool83_tx_mac_partial1_invert_crc_cnt_reg7_tx_mac_partial1_invert_crc_cnt {
      type oc-yang:counter64;
      description
        "Counts the number of transmitted packets with partial CRC type 1.";
    }
    leaf counter_slice4_ifg_mac_pool84_tx_mac_partial1_invert_crc_cnt_reg0_tx_mac_partial1_invert_crc_cnt {
      type oc-yang:counter64;
      description
        "Counts the number of transmitted packets with partial CRC type 1.";
    }
    leaf counter_slice4_ifg_mac_pool84_tx_mac_partial1_invert_crc_cnt_reg1_tx_mac_partial1_invert_crc_cnt {
      type oc-yang:counter64;
      description
        "Counts the number of transmitted packets with partial CRC type 1.";
    }
    leaf counter_slice4_ifg_mac_pool84_tx_mac_partial1_invert_crc_cnt_reg2_tx_mac_partial1_invert_crc_cnt {
      type oc-yang:counter64;
      description
        "Counts the number of transmitted packets with partial CRC type 1.";
    }
    leaf counter_slice4_ifg_mac_pool84_tx_mac_partial1_invert_crc_cnt_reg3_tx_mac_partial1_invert_crc_cnt {
      type oc-yang:counter64;
      description
        "Counts the number of transmitted packets with partial CRC type 1.";
    }
    leaf counter_slice4_ifg_mac_pool84_tx_mac_partial1_invert_crc_cnt_reg4_tx_mac_partial1_invert_crc_cnt {
      type oc-yang:counter64;
      description
        "Counts the number of transmitted packets with partial CRC type 1.";
    }
    leaf counter_slice4_ifg_mac_pool84_tx_mac_partial1_invert_crc_cnt_reg5_tx_mac_partial1_invert_crc_cnt {
      type oc-yang:counter64;
      description
        "Counts the number of transmitted packets with partial CRC type 1.";
    }
    leaf counter_slice4_ifg_mac_pool84_tx_mac_partial1_invert_crc_cnt_reg6_tx_mac_partial1_invert_crc_cnt {
      type oc-yang:counter64;
      description
        "Counts the number of transmitted packets with partial CRC type 1.";
    }
    leaf counter_slice4_ifg_mac_pool84_tx_mac_partial1_invert_crc_cnt_reg7_tx_mac_partial1_invert_crc_cnt {
      type oc-yang:counter64;
      description
        "Counts the number of transmitted packets with partial CRC type 1.";
    }
    leaf counter_slice4_ifg_mac_pool85_tx_mac_partial1_invert_crc_cnt_reg0_tx_mac_partial1_invert_crc_cnt {
      type oc-yang:counter64;
      description
        "Counts the number of transmitted packets with partial CRC type 1.";
    }
    leaf counter_slice4_ifg_mac_pool85_tx_mac_partial1_invert_crc_cnt_reg1_tx_mac_partial1_invert_crc_cnt {
      type oc-yang:counter64;
      description
        "Counts the number of transmitted packets with partial CRC type 1.";
    }
    leaf counter_slice4_ifg_mac_pool85_tx_mac_partial1_invert_crc_cnt_reg2_tx_mac_partial1_invert_crc_cnt {
      type oc-yang:counter64;
      description
        "Counts the number of transmitted packets with partial CRC type 1.";
    }
    leaf counter_slice4_ifg_mac_pool85_tx_mac_partial1_invert_crc_cnt_reg3_tx_mac_partial1_invert_crc_cnt {
      type oc-yang:counter64;
      description
        "Counts the number of transmitted packets with partial CRC type 1.";
    }
    leaf counter_slice4_ifg_mac_pool85_tx_mac_partial1_invert_crc_cnt_reg4_tx_mac_partial1_invert_crc_cnt {
      type oc-yang:counter64;
      description
        "Counts the number of transmitted packets with partial CRC type 1.";
    }
    leaf counter_slice4_ifg_mac_pool85_tx_mac_partial1_invert_crc_cnt_reg5_tx_mac_partial1_invert_crc_cnt {
      type oc-yang:counter64;
      description
        "Counts the number of transmitted packets with partial CRC type 1.";
    }
    leaf counter_slice4_ifg_mac_pool85_tx_mac_partial1_invert_crc_cnt_reg6_tx_mac_partial1_invert_crc_cnt {
      type oc-yang:counter64;
      description
        "Counts the number of transmitted packets with partial CRC type 1.";
    }
    leaf counter_slice4_ifg_mac_pool85_tx_mac_partial1_invert_crc_cnt_reg7_tx_mac_partial1_invert_crc_cnt {
      type oc-yang:counter64;
      description
        "Counts the number of transmitted packets with partial CRC type 1.";
    }
    leaf counter_slice4_ifg_mac_pool86_tx_mac_partial1_invert_crc_cnt_reg0_tx_mac_partial1_invert_crc_cnt {
      type oc-yang:counter64;
      description
        "Counts the number of transmitted packets with partial CRC type 1.";
    }
    leaf counter_slice4_ifg_mac_pool86_tx_mac_partial1_invert_crc_cnt_reg1_tx_mac_partial1_invert_crc_cnt {
      type oc-yang:counter64;
      description
        "Counts the number of transmitted packets with partial CRC type 1.";
    }
    leaf counter_slice4_ifg_mac_pool86_tx_mac_partial1_invert_crc_cnt_reg2_tx_mac_partial1_invert_crc_cnt {
      type oc-yang:counter64;
      description
        "Counts the number of transmitted packets with partial CRC type 1.";
    }
    leaf counter_slice4_ifg_mac_pool86_tx_mac_partial1_invert_crc_cnt_reg3_tx_mac_partial1_invert_crc_cnt {
      type oc-yang:counter64;
      description
        "Counts the number of transmitted packets with partial CRC type 1.";
    }
    leaf counter_slice4_ifg_mac_pool86_tx_mac_partial1_invert_crc_cnt_reg4_tx_mac_partial1_invert_crc_cnt {
      type oc-yang:counter64;
      description
        "Counts the number of transmitted packets with partial CRC type 1.";
    }
    leaf counter_slice4_ifg_mac_pool86_tx_mac_partial1_invert_crc_cnt_reg5_tx_mac_partial1_invert_crc_cnt {
      type oc-yang:counter64;
      description
        "Counts the number of transmitted packets with partial CRC type 1.";
    }
    leaf counter_slice4_ifg_mac_pool86_tx_mac_partial1_invert_crc_cnt_reg6_tx_mac_partial1_invert_crc_cnt {
      type oc-yang:counter64;
      description
        "Counts the number of transmitted packets with partial CRC type 1.";
    }
    leaf counter_slice4_ifg_mac_pool86_tx_mac_partial1_invert_crc_cnt_reg7_tx_mac_partial1_invert_crc_cnt {
      type oc-yang:counter64;
      description
        "Counts the number of transmitted packets with partial CRC type 1.";
    }
    leaf counter_slice4_ifg_mac_pool87_tx_mac_partial1_invert_crc_cnt_reg0_tx_mac_partial1_invert_crc_cnt {
      type oc-yang:counter64;
      description
        "Counts the number of transmitted packets with partial CRC type 1.";
    }
    leaf counter_slice4_ifg_mac_pool87_tx_mac_partial1_invert_crc_cnt_reg1_tx_mac_partial1_invert_crc_cnt {
      type oc-yang:counter64;
      description
        "Counts the number of transmitted packets with partial CRC type 1.";
    }
    leaf counter_slice4_ifg_mac_pool87_tx_mac_partial1_invert_crc_cnt_reg2_tx_mac_partial1_invert_crc_cnt {
      type oc-yang:counter64;
      description
        "Counts the number of transmitted packets with partial CRC type 1.";
    }
    leaf counter_slice4_ifg_mac_pool87_tx_mac_partial1_invert_crc_cnt_reg3_tx_mac_partial1_invert_crc_cnt {
      type oc-yang:counter64;
      description
        "Counts the number of transmitted packets with partial CRC type 1.";
    }
    leaf counter_slice4_ifg_mac_pool87_tx_mac_partial1_invert_crc_cnt_reg4_tx_mac_partial1_invert_crc_cnt {
      type oc-yang:counter64;
      description
        "Counts the number of transmitted packets with partial CRC type 1.";
    }
    leaf counter_slice4_ifg_mac_pool87_tx_mac_partial1_invert_crc_cnt_reg5_tx_mac_partial1_invert_crc_cnt {
      type oc-yang:counter64;
      description
        "Counts the number of transmitted packets with partial CRC type 1.";
    }
    leaf counter_slice4_ifg_mac_pool87_tx_mac_partial1_invert_crc_cnt_reg6_tx_mac_partial1_invert_crc_cnt {
      type oc-yang:counter64;
      description
        "Counts the number of transmitted packets with partial CRC type 1.";
    }
    leaf counter_slice4_ifg_mac_pool87_tx_mac_partial1_invert_crc_cnt_reg7_tx_mac_partial1_invert_crc_cnt {
      type oc-yang:counter64;
      description
        "Counts the number of transmitted packets with partial CRC type 1.";
    }
    leaf counter_slice5_ifg_mac_pool80_tx_mac_partial1_invert_crc_cnt_reg0_tx_mac_partial1_invert_crc_cnt {
      type oc-yang:counter64;
      description
        "Counts the number of transmitted packets with partial CRC type 1.";
    }
    leaf counter_slice5_ifg_mac_pool80_tx_mac_partial1_invert_crc_cnt_reg1_tx_mac_partial1_invert_crc_cnt {
      type oc-yang:counter64;
      description
        "Counts the number of transmitted packets with partial CRC type 1.";
    }
    leaf counter_slice5_ifg_mac_pool80_tx_mac_partial1_invert_crc_cnt_reg2_tx_mac_partial1_invert_crc_cnt {
      type oc-yang:counter64;
      description
        "Counts the number of transmitted packets with partial CRC type 1.";
    }
    leaf counter_slice5_ifg_mac_pool80_tx_mac_partial1_invert_crc_cnt_reg3_tx_mac_partial1_invert_crc_cnt {
      type oc-yang:counter64;
      description
        "Counts the number of transmitted packets with partial CRC type 1.";
    }
    leaf counter_slice5_ifg_mac_pool80_tx_mac_partial1_invert_crc_cnt_reg4_tx_mac_partial1_invert_crc_cnt {
      type oc-yang:counter64;
      description
        "Counts the number of transmitted packets with partial CRC type 1.";
    }
    leaf counter_slice5_ifg_mac_pool80_tx_mac_partial1_invert_crc_cnt_reg5_tx_mac_partial1_invert_crc_cnt {
      type oc-yang:counter64;
      description
        "Counts the number of transmitted packets with partial CRC type 1.";
    }
    leaf counter_slice5_ifg_mac_pool80_tx_mac_partial1_invert_crc_cnt_reg6_tx_mac_partial1_invert_crc_cnt {
      type oc-yang:counter64;
      description
        "Counts the number of transmitted packets with partial CRC type 1.";
    }
    leaf counter_slice5_ifg_mac_pool80_tx_mac_partial1_invert_crc_cnt_reg7_tx_mac_partial1_invert_crc_cnt {
      type oc-yang:counter64;
      description
        "Counts the number of transmitted packets with partial CRC type 1.";
    }
    leaf counter_slice5_ifg_mac_pool81_tx_mac_partial1_invert_crc_cnt_reg0_tx_mac_partial1_invert_crc_cnt {
      type oc-yang:counter64;
      description
        "Counts the number of transmitted packets with partial CRC type 1.";
    }
    leaf counter_slice5_ifg_mac_pool81_tx_mac_partial1_invert_crc_cnt_reg1_tx_mac_partial1_invert_crc_cnt {
      type oc-yang:counter64;
      description
        "Counts the number of transmitted packets with partial CRC type 1.";
    }
    leaf counter_slice5_ifg_mac_pool81_tx_mac_partial1_invert_crc_cnt_reg2_tx_mac_partial1_invert_crc_cnt {
      type oc-yang:counter64;
      description
        "Counts the number of transmitted packets with partial CRC type 1.";
    }
    leaf counter_slice5_ifg_mac_pool81_tx_mac_partial1_invert_crc_cnt_reg3_tx_mac_partial1_invert_crc_cnt {
      type oc-yang:counter64;
      description
        "Counts the number of transmitted packets with partial CRC type 1.";
    }
    leaf counter_slice5_ifg_mac_pool81_tx_mac_partial1_invert_crc_cnt_reg4_tx_mac_partial1_invert_crc_cnt {
      type oc-yang:counter64;
      description
        "Counts the number of transmitted packets with partial CRC type 1.";
    }
    leaf counter_slice5_ifg_mac_pool81_tx_mac_partial1_invert_crc_cnt_reg5_tx_mac_partial1_invert_crc_cnt {
      type oc-yang:counter64;
      description
        "Counts the number of transmitted packets with partial CRC type 1.";
    }
    leaf counter_slice5_ifg_mac_pool81_tx_mac_partial1_invert_crc_cnt_reg6_tx_mac_partial1_invert_crc_cnt {
      type oc-yang:counter64;
      description
        "Counts the number of transmitted packets with partial CRC type 1.";
    }
    leaf counter_slice5_ifg_mac_pool81_tx_mac_partial1_invert_crc_cnt_reg7_tx_mac_partial1_invert_crc_cnt {
      type oc-yang:counter64;
      description
        "Counts the number of transmitted packets with partial CRC type 1.";
    }
    leaf counter_slice5_ifg_mac_pool82_tx_mac_partial1_invert_crc_cnt_reg0_tx_mac_partial1_invert_crc_cnt {
      type oc-yang:counter64;
      description
        "Counts the number of transmitted packets with partial CRC type 1.";
    }
    leaf counter_slice5_ifg_mac_pool82_tx_mac_partial1_invert_crc_cnt_reg1_tx_mac_partial1_invert_crc_cnt {
      type oc-yang:counter64;
      description
        "Counts the number of transmitted packets with partial CRC type 1.";
    }
    leaf counter_slice5_ifg_mac_pool82_tx_mac_partial1_invert_crc_cnt_reg2_tx_mac_partial1_invert_crc_cnt {
      type oc-yang:counter64;
      description
        "Counts the number of transmitted packets with partial CRC type 1.";
    }
    leaf counter_slice5_ifg_mac_pool82_tx_mac_partial1_invert_crc_cnt_reg3_tx_mac_partial1_invert_crc_cnt {
      type oc-yang:counter64;
      description
        "Counts the number of transmitted packets with partial CRC type 1.";
    }
    leaf counter_slice5_ifg_mac_pool82_tx_mac_partial1_invert_crc_cnt_reg4_tx_mac_partial1_invert_crc_cnt {
      type oc-yang:counter64;
      description
        "Counts the number of transmitted packets with partial CRC type 1.";
    }
    leaf counter_slice5_ifg_mac_pool82_tx_mac_partial1_invert_crc_cnt_reg5_tx_mac_partial1_invert_crc_cnt {
      type oc-yang:counter64;
      description
        "Counts the number of transmitted packets with partial CRC type 1.";
    }
    leaf counter_slice5_ifg_mac_pool82_tx_mac_partial1_invert_crc_cnt_reg6_tx_mac_partial1_invert_crc_cnt {
      type oc-yang:counter64;
      description
        "Counts the number of transmitted packets with partial CRC type 1.";
    }
    leaf counter_slice5_ifg_mac_pool82_tx_mac_partial1_invert_crc_cnt_reg7_tx_mac_partial1_invert_crc_cnt {
      type oc-yang:counter64;
      description
        "Counts the number of transmitted packets with partial CRC type 1.";
    }
    leaf counter_slice5_ifg_mac_pool83_tx_mac_partial1_invert_crc_cnt_reg0_tx_mac_partial1_invert_crc_cnt {
      type oc-yang:counter64;
      description
        "Counts the number of transmitted packets with partial CRC type 1.";
    }
    leaf counter_slice5_ifg_mac_pool83_tx_mac_partial1_invert_crc_cnt_reg1_tx_mac_partial1_invert_crc_cnt {
      type oc-yang:counter64;
      description
        "Counts the number of transmitted packets with partial CRC type 1.";
    }
    leaf counter_slice5_ifg_mac_pool83_tx_mac_partial1_invert_crc_cnt_reg2_tx_mac_partial1_invert_crc_cnt {
      type oc-yang:counter64;
      description
        "Counts the number of transmitted packets with partial CRC type 1.";
    }
    leaf counter_slice5_ifg_mac_pool83_tx_mac_partial1_invert_crc_cnt_reg3_tx_mac_partial1_invert_crc_cnt {
      type oc-yang:counter64;
      description
        "Counts the number of transmitted packets with partial CRC type 1.";
    }
    leaf counter_slice5_ifg_mac_pool83_tx_mac_partial1_invert_crc_cnt_reg4_tx_mac_partial1_invert_crc_cnt {
      type oc-yang:counter64;
      description
        "Counts the number of transmitted packets with partial CRC type 1.";
    }
    leaf counter_slice5_ifg_mac_pool83_tx_mac_partial1_invert_crc_cnt_reg5_tx_mac_partial1_invert_crc_cnt {
      type oc-yang:counter64;
      description
        "Counts the number of transmitted packets with partial CRC type 1.";
    }
    leaf counter_slice5_ifg_mac_pool83_tx_mac_partial1_invert_crc_cnt_reg6_tx_mac_partial1_invert_crc_cnt {
      type oc-yang:counter64;
      description
        "Counts the number of transmitted packets with partial CRC type 1.";
    }
    leaf counter_slice5_ifg_mac_pool83_tx_mac_partial1_invert_crc_cnt_reg7_tx_mac_partial1_invert_crc_cnt {
      type oc-yang:counter64;
      description
        "Counts the number of transmitted packets with partial CRC type 1.";
    }
    leaf counter_slice5_ifg_mac_pool84_tx_mac_partial1_invert_crc_cnt_reg0_tx_mac_partial1_invert_crc_cnt {
      type oc-yang:counter64;
      description
        "Counts the number of transmitted packets with partial CRC type 1.";
    }
    leaf counter_slice5_ifg_mac_pool84_tx_mac_partial1_invert_crc_cnt_reg1_tx_mac_partial1_invert_crc_cnt {
      type oc-yang:counter64;
      description
        "Counts the number of transmitted packets with partial CRC type 1.";
    }
    leaf counter_slice5_ifg_mac_pool84_tx_mac_partial1_invert_crc_cnt_reg2_tx_mac_partial1_invert_crc_cnt {
      type oc-yang:counter64;
      description
        "Counts the number of transmitted packets with partial CRC type 1.";
    }
    leaf counter_slice5_ifg_mac_pool84_tx_mac_partial1_invert_crc_cnt_reg3_tx_mac_partial1_invert_crc_cnt {
      type oc-yang:counter64;
      description
        "Counts the number of transmitted packets with partial CRC type 1.";
    }
    leaf counter_slice5_ifg_mac_pool84_tx_mac_partial1_invert_crc_cnt_reg4_tx_mac_partial1_invert_crc_cnt {
      type oc-yang:counter64;
      description
        "Counts the number of transmitted packets with partial CRC type 1.";
    }
    leaf counter_slice5_ifg_mac_pool84_tx_mac_partial1_invert_crc_cnt_reg5_tx_mac_partial1_invert_crc_cnt {
      type oc-yang:counter64;
      description
        "Counts the number of transmitted packets with partial CRC type 1.";
    }
    leaf counter_slice5_ifg_mac_pool84_tx_mac_partial1_invert_crc_cnt_reg6_tx_mac_partial1_invert_crc_cnt {
      type oc-yang:counter64;
      description
        "Counts the number of transmitted packets with partial CRC type 1.";
    }
    leaf counter_slice5_ifg_mac_pool84_tx_mac_partial1_invert_crc_cnt_reg7_tx_mac_partial1_invert_crc_cnt {
      type oc-yang:counter64;
      description
        "Counts the number of transmitted packets with partial CRC type 1.";
    }
    leaf counter_slice5_ifg_mac_pool85_tx_mac_partial1_invert_crc_cnt_reg0_tx_mac_partial1_invert_crc_cnt {
      type oc-yang:counter64;
      description
        "Counts the number of transmitted packets with partial CRC type 1.";
    }
    leaf counter_slice5_ifg_mac_pool85_tx_mac_partial1_invert_crc_cnt_reg1_tx_mac_partial1_invert_crc_cnt {
      type oc-yang:counter64;
      description
        "Counts the number of transmitted packets with partial CRC type 1.";
    }
    leaf counter_slice5_ifg_mac_pool85_tx_mac_partial1_invert_crc_cnt_reg2_tx_mac_partial1_invert_crc_cnt {
      type oc-yang:counter64;
      description
        "Counts the number of transmitted packets with partial CRC type 1.";
    }
    leaf counter_slice5_ifg_mac_pool85_tx_mac_partial1_invert_crc_cnt_reg3_tx_mac_partial1_invert_crc_cnt {
      type oc-yang:counter64;
      description
        "Counts the number of transmitted packets with partial CRC type 1.";
    }
    leaf counter_slice5_ifg_mac_pool85_tx_mac_partial1_invert_crc_cnt_reg4_tx_mac_partial1_invert_crc_cnt {
      type oc-yang:counter64;
      description
        "Counts the number of transmitted packets with partial CRC type 1.";
    }
    leaf counter_slice5_ifg_mac_pool85_tx_mac_partial1_invert_crc_cnt_reg5_tx_mac_partial1_invert_crc_cnt {
      type oc-yang:counter64;
      description
        "Counts the number of transmitted packets with partial CRC type 1.";
    }
    leaf counter_slice5_ifg_mac_pool85_tx_mac_partial1_invert_crc_cnt_reg6_tx_mac_partial1_invert_crc_cnt {
      type oc-yang:counter64;
      description
        "Counts the number of transmitted packets with partial CRC type 1.";
    }
    leaf counter_slice5_ifg_mac_pool85_tx_mac_partial1_invert_crc_cnt_reg7_tx_mac_partial1_invert_crc_cnt {
      type oc-yang:counter64;
      description
        "Counts the number of transmitted packets with partial CRC type 1.";
    }
    leaf counter_slice5_ifg_mac_pool86_tx_mac_partial1_invert_crc_cnt_reg0_tx_mac_partial1_invert_crc_cnt {
      type oc-yang:counter64;
      description
        "Counts the number of transmitted packets with partial CRC type 1.";
    }
    leaf counter_slice5_ifg_mac_pool86_tx_mac_partial1_invert_crc_cnt_reg1_tx_mac_partial1_invert_crc_cnt {
      type oc-yang:counter64;
      description
        "Counts the number of transmitted packets with partial CRC type 1.";
    }
    leaf counter_slice5_ifg_mac_pool86_tx_mac_partial1_invert_crc_cnt_reg2_tx_mac_partial1_invert_crc_cnt {
      type oc-yang:counter64;
      description
        "Counts the number of transmitted packets with partial CRC type 1.";
    }
    leaf counter_slice5_ifg_mac_pool86_tx_mac_partial1_invert_crc_cnt_reg3_tx_mac_partial1_invert_crc_cnt {
      type oc-yang:counter64;
      description
        "Counts the number of transmitted packets with partial CRC type 1.";
    }
    leaf counter_slice5_ifg_mac_pool86_tx_mac_partial1_invert_crc_cnt_reg4_tx_mac_partial1_invert_crc_cnt {
      type oc-yang:counter64;
      description
        "Counts the number of transmitted packets with partial CRC type 1.";
    }
    leaf counter_slice5_ifg_mac_pool86_tx_mac_partial1_invert_crc_cnt_reg5_tx_mac_partial1_invert_crc_cnt {
      type oc-yang:counter64;
      description
        "Counts the number of transmitted packets with partial CRC type 1.";
    }
    leaf counter_slice5_ifg_mac_pool86_tx_mac_partial1_invert_crc_cnt_reg6_tx_mac_partial1_invert_crc_cnt {
      type oc-yang:counter64;
      description
        "Counts the number of transmitted packets with partial CRC type 1.";
    }
    leaf counter_slice5_ifg_mac_pool86_tx_mac_partial1_invert_crc_cnt_reg7_tx_mac_partial1_invert_crc_cnt {
      type oc-yang:counter64;
      description
        "Counts the number of transmitted packets with partial CRC type 1.";
    }
    leaf counter_slice5_ifg_mac_pool87_tx_mac_partial1_invert_crc_cnt_reg0_tx_mac_partial1_invert_crc_cnt {
      type oc-yang:counter64;
      description
        "Counts the number of transmitted packets with partial CRC type 1.";
    }
    leaf counter_slice5_ifg_mac_pool87_tx_mac_partial1_invert_crc_cnt_reg1_tx_mac_partial1_invert_crc_cnt {
      type oc-yang:counter64;
      description
        "Counts the number of transmitted packets with partial CRC type 1.";
    }
    leaf counter_slice5_ifg_mac_pool87_tx_mac_partial1_invert_crc_cnt_reg2_tx_mac_partial1_invert_crc_cnt {
      type oc-yang:counter64;
      description
        "Counts the number of transmitted packets with partial CRC type 1.";
    }
    leaf counter_slice5_ifg_mac_pool87_tx_mac_partial1_invert_crc_cnt_reg3_tx_mac_partial1_invert_crc_cnt {
      type oc-yang:counter64;
      description
        "Counts the number of transmitted packets with partial CRC type 1.";
    }
    leaf counter_slice5_ifg_mac_pool87_tx_mac_partial1_invert_crc_cnt_reg4_tx_mac_partial1_invert_crc_cnt {
      type oc-yang:counter64;
      description
        "Counts the number of transmitted packets with partial CRC type 1.";
    }
    leaf counter_slice5_ifg_mac_pool87_tx_mac_partial1_invert_crc_cnt_reg5_tx_mac_partial1_invert_crc_cnt {
      type oc-yang:counter64;
      description
        "Counts the number of transmitted packets with partial CRC type 1.";
    }
    leaf counter_slice5_ifg_mac_pool87_tx_mac_partial1_invert_crc_cnt_reg6_tx_mac_partial1_invert_crc_cnt {
      type oc-yang:counter64;
      description
        "Counts the number of transmitted packets with partial CRC type 1.";
    }
    leaf counter_slice5_ifg_mac_pool87_tx_mac_partial1_invert_crc_cnt_reg7_tx_mac_partial1_invert_crc_cnt {
      type oc-yang:counter64;
      description
        "Counts the number of transmitted packets with partial CRC type 1.";
    }
    leaf counter_slice6_ifg_mac_pool80_tx_mac_partial1_invert_crc_cnt_reg0_tx_mac_partial1_invert_crc_cnt {
      type oc-yang:counter64;
      description
        "Counts the number of transmitted packets with partial CRC type 1.";
    }
    leaf counter_slice6_ifg_mac_pool80_tx_mac_partial1_invert_crc_cnt_reg1_tx_mac_partial1_invert_crc_cnt {
      type oc-yang:counter64;
      description
        "Counts the number of transmitted packets with partial CRC type 1.";
    }
    leaf counter_slice6_ifg_mac_pool80_tx_mac_partial1_invert_crc_cnt_reg2_tx_mac_partial1_invert_crc_cnt {
      type oc-yang:counter64;
      description
        "Counts the number of transmitted packets with partial CRC type 1.";
    }
    leaf counter_slice6_ifg_mac_pool80_tx_mac_partial1_invert_crc_cnt_reg3_tx_mac_partial1_invert_crc_cnt {
      type oc-yang:counter64;
      description
        "Counts the number of transmitted packets with partial CRC type 1.";
    }
    leaf counter_slice6_ifg_mac_pool80_tx_mac_partial1_invert_crc_cnt_reg4_tx_mac_partial1_invert_crc_cnt {
      type oc-yang:counter64;
      description
        "Counts the number of transmitted packets with partial CRC type 1.";
    }
    leaf counter_slice6_ifg_mac_pool80_tx_mac_partial1_invert_crc_cnt_reg5_tx_mac_partial1_invert_crc_cnt {
      type oc-yang:counter64;
      description
        "Counts the number of transmitted packets with partial CRC type 1.";
    }
    leaf counter_slice6_ifg_mac_pool80_tx_mac_partial1_invert_crc_cnt_reg6_tx_mac_partial1_invert_crc_cnt {
      type oc-yang:counter64;
      description
        "Counts the number of transmitted packets with partial CRC type 1.";
    }
    leaf counter_slice6_ifg_mac_pool80_tx_mac_partial1_invert_crc_cnt_reg7_tx_mac_partial1_invert_crc_cnt {
      type oc-yang:counter64;
      description
        "Counts the number of transmitted packets with partial CRC type 1.";
    }
    leaf counter_slice6_ifg_mac_pool81_tx_mac_partial1_invert_crc_cnt_reg0_tx_mac_partial1_invert_crc_cnt {
      type oc-yang:counter64;
      description
        "Counts the number of transmitted packets with partial CRC type 1.";
    }
    leaf counter_slice6_ifg_mac_pool81_tx_mac_partial1_invert_crc_cnt_reg1_tx_mac_partial1_invert_crc_cnt {
      type oc-yang:counter64;
      description
        "Counts the number of transmitted packets with partial CRC type 1.";
    }
    leaf counter_slice6_ifg_mac_pool81_tx_mac_partial1_invert_crc_cnt_reg2_tx_mac_partial1_invert_crc_cnt {
      type oc-yang:counter64;
      description
        "Counts the number of transmitted packets with partial CRC type 1.";
    }
    leaf counter_slice6_ifg_mac_pool81_tx_mac_partial1_invert_crc_cnt_reg3_tx_mac_partial1_invert_crc_cnt {
      type oc-yang:counter64;
      description
        "Counts the number of transmitted packets with partial CRC type 1.";
    }
    leaf counter_slice6_ifg_mac_pool81_tx_mac_partial1_invert_crc_cnt_reg4_tx_mac_partial1_invert_crc_cnt {
      type oc-yang:counter64;
      description
        "Counts the number of transmitted packets with partial CRC type 1.";
    }
    leaf counter_slice6_ifg_mac_pool81_tx_mac_partial1_invert_crc_cnt_reg5_tx_mac_partial1_invert_crc_cnt {
      type oc-yang:counter64;
      description
        "Counts the number of transmitted packets with partial CRC type 1.";
    }
    leaf counter_slice6_ifg_mac_pool81_tx_mac_partial1_invert_crc_cnt_reg6_tx_mac_partial1_invert_crc_cnt {
      type oc-yang:counter64;
      description
        "Counts the number of transmitted packets with partial CRC type 1.";
    }
    leaf counter_slice6_ifg_mac_pool81_tx_mac_partial1_invert_crc_cnt_reg7_tx_mac_partial1_invert_crc_cnt {
      type oc-yang:counter64;
      description
        "Counts the number of transmitted packets with partial CRC type 1.";
    }
    leaf counter_slice6_ifg_mac_pool82_tx_mac_partial1_invert_crc_cnt_reg0_tx_mac_partial1_invert_crc_cnt {
      type oc-yang:counter64;
      description
        "Counts the number of transmitted packets with partial CRC type 1.";
    }
    leaf counter_slice6_ifg_mac_pool82_tx_mac_partial1_invert_crc_cnt_reg1_tx_mac_partial1_invert_crc_cnt {
      type oc-yang:counter64;
      description
        "Counts the number of transmitted packets with partial CRC type 1.";
    }
    leaf counter_slice6_ifg_mac_pool82_tx_mac_partial1_invert_crc_cnt_reg2_tx_mac_partial1_invert_crc_cnt {
      type oc-yang:counter64;
      description
        "Counts the number of transmitted packets with partial CRC type 1.";
    }
    leaf counter_slice6_ifg_mac_pool82_tx_mac_partial1_invert_crc_cnt_reg3_tx_mac_partial1_invert_crc_cnt {
      type oc-yang:counter64;
      description
        "Counts the number of transmitted packets with partial CRC type 1.";
    }
    leaf counter_slice6_ifg_mac_pool82_tx_mac_partial1_invert_crc_cnt_reg4_tx_mac_partial1_invert_crc_cnt {
      type oc-yang:counter64;
      description
        "Counts the number of transmitted packets with partial CRC type 1.";
    }
    leaf counter_slice6_ifg_mac_pool82_tx_mac_partial1_invert_crc_cnt_reg5_tx_mac_partial1_invert_crc_cnt {
      type oc-yang:counter64;
      description
        "Counts the number of transmitted packets with partial CRC type 1.";
    }
    leaf counter_slice6_ifg_mac_pool82_tx_mac_partial1_invert_crc_cnt_reg6_tx_mac_partial1_invert_crc_cnt {
      type oc-yang:counter64;
      description
        "Counts the number of transmitted packets with partial CRC type 1.";
    }
    leaf counter_slice6_ifg_mac_pool82_tx_mac_partial1_invert_crc_cnt_reg7_tx_mac_partial1_invert_crc_cnt {
      type oc-yang:counter64;
      description
        "Counts the number of transmitted packets with partial CRC type 1.";
    }
    leaf counter_slice6_ifg_mac_pool83_tx_mac_partial1_invert_crc_cnt_reg0_tx_mac_partial1_invert_crc_cnt {
      type oc-yang:counter64;
      description
        "Counts the number of transmitted packets with partial CRC type 1.";
    }
    leaf counter_slice6_ifg_mac_pool83_tx_mac_partial1_invert_crc_cnt_reg1_tx_mac_partial1_invert_crc_cnt {
      type oc-yang:counter64;
      description
        "Counts the number of transmitted packets with partial CRC type 1.";
    }
    leaf counter_slice6_ifg_mac_pool83_tx_mac_partial1_invert_crc_cnt_reg2_tx_mac_partial1_invert_crc_cnt {
      type oc-yang:counter64;
      description
        "Counts the number of transmitted packets with partial CRC type 1.";
    }
    leaf counter_slice6_ifg_mac_pool83_tx_mac_partial1_invert_crc_cnt_reg3_tx_mac_partial1_invert_crc_cnt {
      type oc-yang:counter64;
      description
        "Counts the number of transmitted packets with partial CRC type 1.";
    }
    leaf counter_slice6_ifg_mac_pool83_tx_mac_partial1_invert_crc_cnt_reg4_tx_mac_partial1_invert_crc_cnt {
      type oc-yang:counter64;
      description
        "Counts the number of transmitted packets with partial CRC type 1.";
    }
    leaf counter_slice6_ifg_mac_pool83_tx_mac_partial1_invert_crc_cnt_reg5_tx_mac_partial1_invert_crc_cnt {
      type oc-yang:counter64;
      description
        "Counts the number of transmitted packets with partial CRC type 1.";
    }
    leaf counter_slice6_ifg_mac_pool83_tx_mac_partial1_invert_crc_cnt_reg6_tx_mac_partial1_invert_crc_cnt {
      type oc-yang:counter64;
      description
        "Counts the number of transmitted packets with partial CRC type 1.";
    }
    leaf counter_slice6_ifg_mac_pool83_tx_mac_partial1_invert_crc_cnt_reg7_tx_mac_partial1_invert_crc_cnt {
      type oc-yang:counter64;
      description
        "Counts the number of transmitted packets with partial CRC type 1.";
    }
    leaf counter_slice6_ifg_mac_pool84_tx_mac_partial1_invert_crc_cnt_reg0_tx_mac_partial1_invert_crc_cnt {
      type oc-yang:counter64;
      description
        "Counts the number of transmitted packets with partial CRC type 1.";
    }
    leaf counter_slice6_ifg_mac_pool84_tx_mac_partial1_invert_crc_cnt_reg1_tx_mac_partial1_invert_crc_cnt {
      type oc-yang:counter64;
      description
        "Counts the number of transmitted packets with partial CRC type 1.";
    }
    leaf counter_slice6_ifg_mac_pool84_tx_mac_partial1_invert_crc_cnt_reg2_tx_mac_partial1_invert_crc_cnt {
      type oc-yang:counter64;
      description
        "Counts the number of transmitted packets with partial CRC type 1.";
    }
    leaf counter_slice6_ifg_mac_pool84_tx_mac_partial1_invert_crc_cnt_reg3_tx_mac_partial1_invert_crc_cnt {
      type oc-yang:counter64;
      description
        "Counts the number of transmitted packets with partial CRC type 1.";
    }
    leaf counter_slice6_ifg_mac_pool84_tx_mac_partial1_invert_crc_cnt_reg4_tx_mac_partial1_invert_crc_cnt {
      type oc-yang:counter64;
      description
        "Counts the number of transmitted packets with partial CRC type 1.";
    }
    leaf counter_slice6_ifg_mac_pool84_tx_mac_partial1_invert_crc_cnt_reg5_tx_mac_partial1_invert_crc_cnt {
      type oc-yang:counter64;
      description
        "Counts the number of transmitted packets with partial CRC type 1.";
    }
    leaf counter_slice6_ifg_mac_pool84_tx_mac_partial1_invert_crc_cnt_reg6_tx_mac_partial1_invert_crc_cnt {
      type oc-yang:counter64;
      description
        "Counts the number of transmitted packets with partial CRC type 1.";
    }
    leaf counter_slice6_ifg_mac_pool84_tx_mac_partial1_invert_crc_cnt_reg7_tx_mac_partial1_invert_crc_cnt {
      type oc-yang:counter64;
      description
        "Counts the number of transmitted packets with partial CRC type 1.";
    }
    leaf counter_slice6_ifg_mac_pool85_tx_mac_partial1_invert_crc_cnt_reg0_tx_mac_partial1_invert_crc_cnt {
      type oc-yang:counter64;
      description
        "Counts the number of transmitted packets with partial CRC type 1.";
    }
    leaf counter_slice6_ifg_mac_pool85_tx_mac_partial1_invert_crc_cnt_reg1_tx_mac_partial1_invert_crc_cnt {
      type oc-yang:counter64;
      description
        "Counts the number of transmitted packets with partial CRC type 1.";
    }
    leaf counter_slice6_ifg_mac_pool85_tx_mac_partial1_invert_crc_cnt_reg2_tx_mac_partial1_invert_crc_cnt {
      type oc-yang:counter64;
      description
        "Counts the number of transmitted packets with partial CRC type 1.";
    }
    leaf counter_slice6_ifg_mac_pool85_tx_mac_partial1_invert_crc_cnt_reg3_tx_mac_partial1_invert_crc_cnt {
      type oc-yang:counter64;
      description
        "Counts the number of transmitted packets with partial CRC type 1.";
    }
    leaf counter_slice6_ifg_mac_pool85_tx_mac_partial1_invert_crc_cnt_reg4_tx_mac_partial1_invert_crc_cnt {
      type oc-yang:counter64;
      description
        "Counts the number of transmitted packets with partial CRC type 1.";
    }
    leaf counter_slice6_ifg_mac_pool85_tx_mac_partial1_invert_crc_cnt_reg5_tx_mac_partial1_invert_crc_cnt {
      type oc-yang:counter64;
      description
        "Counts the number of transmitted packets with partial CRC type 1.";
    }
    leaf counter_slice6_ifg_mac_pool85_tx_mac_partial1_invert_crc_cnt_reg6_tx_mac_partial1_invert_crc_cnt {
      type oc-yang:counter64;
      description
        "Counts the number of transmitted packets with partial CRC type 1.";
    }
    leaf counter_slice6_ifg_mac_pool85_tx_mac_partial1_invert_crc_cnt_reg7_tx_mac_partial1_invert_crc_cnt {
      type oc-yang:counter64;
      description
        "Counts the number of transmitted packets with partial CRC type 1.";
    }
    leaf counter_slice6_ifg_mac_pool86_tx_mac_partial1_invert_crc_cnt_reg0_tx_mac_partial1_invert_crc_cnt {
      type oc-yang:counter64;
      description
        "Counts the number of transmitted packets with partial CRC type 1.";
    }
    leaf counter_slice6_ifg_mac_pool86_tx_mac_partial1_invert_crc_cnt_reg1_tx_mac_partial1_invert_crc_cnt {
      type oc-yang:counter64;
      description
        "Counts the number of transmitted packets with partial CRC type 1.";
    }
    leaf counter_slice6_ifg_mac_pool86_tx_mac_partial1_invert_crc_cnt_reg2_tx_mac_partial1_invert_crc_cnt {
      type oc-yang:counter64;
      description
        "Counts the number of transmitted packets with partial CRC type 1.";
    }
    leaf counter_slice6_ifg_mac_pool86_tx_mac_partial1_invert_crc_cnt_reg3_tx_mac_partial1_invert_crc_cnt {
      type oc-yang:counter64;
      description
        "Counts the number of transmitted packets with partial CRC type 1.";
    }
    leaf counter_slice6_ifg_mac_pool86_tx_mac_partial1_invert_crc_cnt_reg4_tx_mac_partial1_invert_crc_cnt {
      type oc-yang:counter64;
      description
        "Counts the number of transmitted packets with partial CRC type 1.";
    }
    leaf counter_slice6_ifg_mac_pool86_tx_mac_partial1_invert_crc_cnt_reg5_tx_mac_partial1_invert_crc_cnt {
      type oc-yang:counter64;
      description
        "Counts the number of transmitted packets with partial CRC type 1.";
    }
    leaf counter_slice6_ifg_mac_pool86_tx_mac_partial1_invert_crc_cnt_reg6_tx_mac_partial1_invert_crc_cnt {
      type oc-yang:counter64;
      description
        "Counts the number of transmitted packets with partial CRC type 1.";
    }
    leaf counter_slice6_ifg_mac_pool86_tx_mac_partial1_invert_crc_cnt_reg7_tx_mac_partial1_invert_crc_cnt {
      type oc-yang:counter64;
      description
        "Counts the number of transmitted packets with partial CRC type 1.";
    }
    leaf counter_slice6_ifg_mac_pool87_tx_mac_partial1_invert_crc_cnt_reg0_tx_mac_partial1_invert_crc_cnt {
      type oc-yang:counter64;
      description
        "Counts the number of transmitted packets with partial CRC type 1.";
    }
    leaf counter_slice6_ifg_mac_pool87_tx_mac_partial1_invert_crc_cnt_reg1_tx_mac_partial1_invert_crc_cnt {
      type oc-yang:counter64;
      description
        "Counts the number of transmitted packets with partial CRC type 1.";
    }
    leaf counter_slice6_ifg_mac_pool87_tx_mac_partial1_invert_crc_cnt_reg2_tx_mac_partial1_invert_crc_cnt {
      type oc-yang:counter64;
      description
        "Counts the number of transmitted packets with partial CRC type 1.";
    }
    leaf counter_slice6_ifg_mac_pool87_tx_mac_partial1_invert_crc_cnt_reg3_tx_mac_partial1_invert_crc_cnt {
      type oc-yang:counter64;
      description
        "Counts the number of transmitted packets with partial CRC type 1.";
    }
    leaf counter_slice6_ifg_mac_pool87_tx_mac_partial1_invert_crc_cnt_reg4_tx_mac_partial1_invert_crc_cnt {
      type oc-yang:counter64;
      description
        "Counts the number of transmitted packets with partial CRC type 1.";
    }
    leaf counter_slice6_ifg_mac_pool87_tx_mac_partial1_invert_crc_cnt_reg5_tx_mac_partial1_invert_crc_cnt {
      type oc-yang:counter64;
      description
        "Counts the number of transmitted packets with partial CRC type 1.";
    }
    leaf counter_slice6_ifg_mac_pool87_tx_mac_partial1_invert_crc_cnt_reg6_tx_mac_partial1_invert_crc_cnt {
      type oc-yang:counter64;
      description
        "Counts the number of transmitted packets with partial CRC type 1.";
    }
    leaf counter_slice6_ifg_mac_pool87_tx_mac_partial1_invert_crc_cnt_reg7_tx_mac_partial1_invert_crc_cnt {
      type oc-yang:counter64;
      description
        "Counts the number of transmitted packets with partial CRC type 1.";
    }
    leaf counter_slice7_ifg_mac_pool80_tx_mac_partial1_invert_crc_cnt_reg0_tx_mac_partial1_invert_crc_cnt {
      type oc-yang:counter64;
      description
        "Counts the number of transmitted packets with partial CRC type 1.";
    }
    leaf counter_slice7_ifg_mac_pool80_tx_mac_partial1_invert_crc_cnt_reg1_tx_mac_partial1_invert_crc_cnt {
      type oc-yang:counter64;
      description
        "Counts the number of transmitted packets with partial CRC type 1.";
    }
    leaf counter_slice7_ifg_mac_pool80_tx_mac_partial1_invert_crc_cnt_reg2_tx_mac_partial1_invert_crc_cnt {
      type oc-yang:counter64;
      description
        "Counts the number of transmitted packets with partial CRC type 1.";
    }
    leaf counter_slice7_ifg_mac_pool80_tx_mac_partial1_invert_crc_cnt_reg3_tx_mac_partial1_invert_crc_cnt {
      type oc-yang:counter64;
      description
        "Counts the number of transmitted packets with partial CRC type 1.";
    }
    leaf counter_slice7_ifg_mac_pool80_tx_mac_partial1_invert_crc_cnt_reg4_tx_mac_partial1_invert_crc_cnt {
      type oc-yang:counter64;
      description
        "Counts the number of transmitted packets with partial CRC type 1.";
    }
    leaf counter_slice7_ifg_mac_pool80_tx_mac_partial1_invert_crc_cnt_reg5_tx_mac_partial1_invert_crc_cnt {
      type oc-yang:counter64;
      description
        "Counts the number of transmitted packets with partial CRC type 1.";
    }
    leaf counter_slice7_ifg_mac_pool80_tx_mac_partial1_invert_crc_cnt_reg6_tx_mac_partial1_invert_crc_cnt {
      type oc-yang:counter64;
      description
        "Counts the number of transmitted packets with partial CRC type 1.";
    }
    leaf counter_slice7_ifg_mac_pool80_tx_mac_partial1_invert_crc_cnt_reg7_tx_mac_partial1_invert_crc_cnt {
      type oc-yang:counter64;
      description
        "Counts the number of transmitted packets with partial CRC type 1.";
    }
    leaf counter_slice7_ifg_mac_pool81_tx_mac_partial1_invert_crc_cnt_reg0_tx_mac_partial1_invert_crc_cnt {
      type oc-yang:counter64;
      description
        "Counts the number of transmitted packets with partial CRC type 1.";
    }
    leaf counter_slice7_ifg_mac_pool81_tx_mac_partial1_invert_crc_cnt_reg1_tx_mac_partial1_invert_crc_cnt {
      type oc-yang:counter64;
      description
        "Counts the number of transmitted packets with partial CRC type 1.";
    }
    leaf counter_slice7_ifg_mac_pool81_tx_mac_partial1_invert_crc_cnt_reg2_tx_mac_partial1_invert_crc_cnt {
      type oc-yang:counter64;
      description
        "Counts the number of transmitted packets with partial CRC type 1.";
    }
    leaf counter_slice7_ifg_mac_pool81_tx_mac_partial1_invert_crc_cnt_reg3_tx_mac_partial1_invert_crc_cnt {
      type oc-yang:counter64;
      description
        "Counts the number of transmitted packets with partial CRC type 1.";
    }
    leaf counter_slice7_ifg_mac_pool81_tx_mac_partial1_invert_crc_cnt_reg4_tx_mac_partial1_invert_crc_cnt {
      type oc-yang:counter64;
      description
        "Counts the number of transmitted packets with partial CRC type 1.";
    }
    leaf counter_slice7_ifg_mac_pool81_tx_mac_partial1_invert_crc_cnt_reg5_tx_mac_partial1_invert_crc_cnt {
      type oc-yang:counter64;
      description
        "Counts the number of transmitted packets with partial CRC type 1.";
    }
    leaf counter_slice7_ifg_mac_pool81_tx_mac_partial1_invert_crc_cnt_reg6_tx_mac_partial1_invert_crc_cnt {
      type oc-yang:counter64;
      description
        "Counts the number of transmitted packets with partial CRC type 1.";
    }
    leaf counter_slice7_ifg_mac_pool81_tx_mac_partial1_invert_crc_cnt_reg7_tx_mac_partial1_invert_crc_cnt {
      type oc-yang:counter64;
      description
        "Counts the number of transmitted packets with partial CRC type 1.";
    }
    leaf counter_slice7_ifg_mac_pool82_tx_mac_partial1_invert_crc_cnt_reg0_tx_mac_partial1_invert_crc_cnt {
      type oc-yang:counter64;
      description
        "Counts the number of transmitted packets with partial CRC type 1.";
    }
    leaf counter_slice7_ifg_mac_pool82_tx_mac_partial1_invert_crc_cnt_reg1_tx_mac_partial1_invert_crc_cnt {
      type oc-yang:counter64;
      description
        "Counts the number of transmitted packets with partial CRC type 1.";
    }
    leaf counter_slice7_ifg_mac_pool82_tx_mac_partial1_invert_crc_cnt_reg2_tx_mac_partial1_invert_crc_cnt {
      type oc-yang:counter64;
      description
        "Counts the number of transmitted packets with partial CRC type 1.";
    }
    leaf counter_slice7_ifg_mac_pool82_tx_mac_partial1_invert_crc_cnt_reg3_tx_mac_partial1_invert_crc_cnt {
      type oc-yang:counter64;
      description
        "Counts the number of transmitted packets with partial CRC type 1.";
    }
    leaf counter_slice7_ifg_mac_pool82_tx_mac_partial1_invert_crc_cnt_reg4_tx_mac_partial1_invert_crc_cnt {
      type oc-yang:counter64;
      description
        "Counts the number of transmitted packets with partial CRC type 1.";
    }
    leaf counter_slice7_ifg_mac_pool82_tx_mac_partial1_invert_crc_cnt_reg5_tx_mac_partial1_invert_crc_cnt {
      type oc-yang:counter64;
      description
        "Counts the number of transmitted packets with partial CRC type 1.";
    }
    leaf counter_slice7_ifg_mac_pool82_tx_mac_partial1_invert_crc_cnt_reg6_tx_mac_partial1_invert_crc_cnt {
      type oc-yang:counter64;
      description
        "Counts the number of transmitted packets with partial CRC type 1.";
    }
    leaf counter_slice7_ifg_mac_pool82_tx_mac_partial1_invert_crc_cnt_reg7_tx_mac_partial1_invert_crc_cnt {
      type oc-yang:counter64;
      description
        "Counts the number of transmitted packets with partial CRC type 1.";
    }
    leaf counter_slice7_ifg_mac_pool83_tx_mac_partial1_invert_crc_cnt_reg0_tx_mac_partial1_invert_crc_cnt {
      type oc-yang:counter64;
      description
        "Counts the number of transmitted packets with partial CRC type 1.";
    }
    leaf counter_slice7_ifg_mac_pool83_tx_mac_partial1_invert_crc_cnt_reg1_tx_mac_partial1_invert_crc_cnt {
      type oc-yang:counter64;
      description
        "Counts the number of transmitted packets with partial CRC type 1.";
    }
    leaf counter_slice7_ifg_mac_pool83_tx_mac_partial1_invert_crc_cnt_reg2_tx_mac_partial1_invert_crc_cnt {
      type oc-yang:counter64;
      description
        "Counts the number of transmitted packets with partial CRC type 1.";
    }
    leaf counter_slice7_ifg_mac_pool83_tx_mac_partial1_invert_crc_cnt_reg3_tx_mac_partial1_invert_crc_cnt {
      type oc-yang:counter64;
      description
        "Counts the number of transmitted packets with partial CRC type 1.";
    }
    leaf counter_slice7_ifg_mac_pool83_tx_mac_partial1_invert_crc_cnt_reg4_tx_mac_partial1_invert_crc_cnt {
      type oc-yang:counter64;
      description
        "Counts the number of transmitted packets with partial CRC type 1.";
    }
    leaf counter_slice7_ifg_mac_pool83_tx_mac_partial1_invert_crc_cnt_reg5_tx_mac_partial1_invert_crc_cnt {
      type oc-yang:counter64;
      description
        "Counts the number of transmitted packets with partial CRC type 1.";
    }
    leaf counter_slice7_ifg_mac_pool83_tx_mac_partial1_invert_crc_cnt_reg6_tx_mac_partial1_invert_crc_cnt {
      type oc-yang:counter64;
      description
        "Counts the number of transmitted packets with partial CRC type 1.";
    }
    leaf counter_slice7_ifg_mac_pool83_tx_mac_partial1_invert_crc_cnt_reg7_tx_mac_partial1_invert_crc_cnt {
      type oc-yang:counter64;
      description
        "Counts the number of transmitted packets with partial CRC type 1.";
    }
    leaf counter_slice7_ifg_mac_pool84_tx_mac_partial1_invert_crc_cnt_reg0_tx_mac_partial1_invert_crc_cnt {
      type oc-yang:counter64;
      description
        "Counts the number of transmitted packets with partial CRC type 1.";
    }
    leaf counter_slice7_ifg_mac_pool84_tx_mac_partial1_invert_crc_cnt_reg1_tx_mac_partial1_invert_crc_cnt {
      type oc-yang:counter64;
      description
        "Counts the number of transmitted packets with partial CRC type 1.";
    }
    leaf counter_slice7_ifg_mac_pool84_tx_mac_partial1_invert_crc_cnt_reg2_tx_mac_partial1_invert_crc_cnt {
      type oc-yang:counter64;
      description
        "Counts the number of transmitted packets with partial CRC type 1.";
    }
    leaf counter_slice7_ifg_mac_pool84_tx_mac_partial1_invert_crc_cnt_reg3_tx_mac_partial1_invert_crc_cnt {
      type oc-yang:counter64;
      description
        "Counts the number of transmitted packets with partial CRC type 1.";
    }
    leaf counter_slice7_ifg_mac_pool84_tx_mac_partial1_invert_crc_cnt_reg4_tx_mac_partial1_invert_crc_cnt {
      type oc-yang:counter64;
      description
        "Counts the number of transmitted packets with partial CRC type 1.";
    }
    leaf counter_slice7_ifg_mac_pool84_tx_mac_partial1_invert_crc_cnt_reg5_tx_mac_partial1_invert_crc_cnt {
      type oc-yang:counter64;
      description
        "Counts the number of transmitted packets with partial CRC type 1.";
    }
    leaf counter_slice7_ifg_mac_pool84_tx_mac_partial1_invert_crc_cnt_reg6_tx_mac_partial1_invert_crc_cnt {
      type oc-yang:counter64;
      description
        "Counts the number of transmitted packets with partial CRC type 1.";
    }
    leaf counter_slice7_ifg_mac_pool84_tx_mac_partial1_invert_crc_cnt_reg7_tx_mac_partial1_invert_crc_cnt {
      type oc-yang:counter64;
      description
        "Counts the number of transmitted packets with partial CRC type 1.";
    }
    leaf counter_slice7_ifg_mac_pool85_tx_mac_partial1_invert_crc_cnt_reg0_tx_mac_partial1_invert_crc_cnt {
      type oc-yang:counter64;
      description
        "Counts the number of transmitted packets with partial CRC type 1.";
    }
    leaf counter_slice7_ifg_mac_pool85_tx_mac_partial1_invert_crc_cnt_reg1_tx_mac_partial1_invert_crc_cnt {
      type oc-yang:counter64;
      description
        "Counts the number of transmitted packets with partial CRC type 1.";
    }
    leaf counter_slice7_ifg_mac_pool85_tx_mac_partial1_invert_crc_cnt_reg2_tx_mac_partial1_invert_crc_cnt {
      type oc-yang:counter64;
      description
        "Counts the number of transmitted packets with partial CRC type 1.";
    }
    leaf counter_slice7_ifg_mac_pool85_tx_mac_partial1_invert_crc_cnt_reg3_tx_mac_partial1_invert_crc_cnt {
      type oc-yang:counter64;
      description
        "Counts the number of transmitted packets with partial CRC type 1.";
    }
    leaf counter_slice7_ifg_mac_pool85_tx_mac_partial1_invert_crc_cnt_reg4_tx_mac_partial1_invert_crc_cnt {
      type oc-yang:counter64;
      description
        "Counts the number of transmitted packets with partial CRC type 1.";
    }
    leaf counter_slice7_ifg_mac_pool85_tx_mac_partial1_invert_crc_cnt_reg5_tx_mac_partial1_invert_crc_cnt {
      type oc-yang:counter64;
      description
        "Counts the number of transmitted packets with partial CRC type 1.";
    }
    leaf counter_slice7_ifg_mac_pool85_tx_mac_partial1_invert_crc_cnt_reg6_tx_mac_partial1_invert_crc_cnt {
      type oc-yang:counter64;
      description
        "Counts the number of transmitted packets with partial CRC type 1.";
    }
    leaf counter_slice7_ifg_mac_pool85_tx_mac_partial1_invert_crc_cnt_reg7_tx_mac_partial1_invert_crc_cnt {
      type oc-yang:counter64;
      description
        "Counts the number of transmitted packets with partial CRC type 1.";
    }
    leaf counter_slice7_ifg_mac_pool86_tx_mac_partial1_invert_crc_cnt_reg0_tx_mac_partial1_invert_crc_cnt {
      type oc-yang:counter64;
      description
        "Counts the number of transmitted packets with partial CRC type 1.";
    }
    leaf counter_slice7_ifg_mac_pool86_tx_mac_partial1_invert_crc_cnt_reg1_tx_mac_partial1_invert_crc_cnt {
      type oc-yang:counter64;
      description
        "Counts the number of transmitted packets with partial CRC type 1.";
    }
    leaf counter_slice7_ifg_mac_pool86_tx_mac_partial1_invert_crc_cnt_reg2_tx_mac_partial1_invert_crc_cnt {
      type oc-yang:counter64;
      description
        "Counts the number of transmitted packets with partial CRC type 1.";
    }
    leaf counter_slice7_ifg_mac_pool86_tx_mac_partial1_invert_crc_cnt_reg3_tx_mac_partial1_invert_crc_cnt {
      type oc-yang:counter64;
      description
        "Counts the number of transmitted packets with partial CRC type 1.";
    }
    leaf counter_slice7_ifg_mac_pool86_tx_mac_partial1_invert_crc_cnt_reg4_tx_mac_partial1_invert_crc_cnt {
      type oc-yang:counter64;
      description
        "Counts the number of transmitted packets with partial CRC type 1.";
    }
    leaf counter_slice7_ifg_mac_pool86_tx_mac_partial1_invert_crc_cnt_reg5_tx_mac_partial1_invert_crc_cnt {
      type oc-yang:counter64;
      description
        "Counts the number of transmitted packets with partial CRC type 1.";
    }
    leaf counter_slice7_ifg_mac_pool86_tx_mac_partial1_invert_crc_cnt_reg6_tx_mac_partial1_invert_crc_cnt {
      type oc-yang:counter64;
      description
        "Counts the number of transmitted packets with partial CRC type 1.";
    }
    leaf counter_slice7_ifg_mac_pool86_tx_mac_partial1_invert_crc_cnt_reg7_tx_mac_partial1_invert_crc_cnt {
      type oc-yang:counter64;
      description
        "Counts the number of transmitted packets with partial CRC type 1.";
    }
    leaf counter_slice7_ifg_mac_pool87_tx_mac_partial1_invert_crc_cnt_reg0_tx_mac_partial1_invert_crc_cnt {
      type oc-yang:counter64;
      description
        "Counts the number of transmitted packets with partial CRC type 1.";
    }
    leaf counter_slice7_ifg_mac_pool87_tx_mac_partial1_invert_crc_cnt_reg1_tx_mac_partial1_invert_crc_cnt {
      type oc-yang:counter64;
      description
        "Counts the number of transmitted packets with partial CRC type 1.";
    }
    leaf counter_slice7_ifg_mac_pool87_tx_mac_partial1_invert_crc_cnt_reg2_tx_mac_partial1_invert_crc_cnt {
      type oc-yang:counter64;
      description
        "Counts the number of transmitted packets with partial CRC type 1.";
    }
    leaf counter_slice7_ifg_mac_pool87_tx_mac_partial1_invert_crc_cnt_reg3_tx_mac_partial1_invert_crc_cnt {
      type oc-yang:counter64;
      description
        "Counts the number of transmitted packets with partial CRC type 1.";
    }
    leaf counter_slice7_ifg_mac_pool87_tx_mac_partial1_invert_crc_cnt_reg4_tx_mac_partial1_invert_crc_cnt {
      type oc-yang:counter64;
      description
        "Counts the number of transmitted packets with partial CRC type 1.";
    }
    leaf counter_slice7_ifg_mac_pool87_tx_mac_partial1_invert_crc_cnt_reg5_tx_mac_partial1_invert_crc_cnt {
      type oc-yang:counter64;
      description
        "Counts the number of transmitted packets with partial CRC type 1.";
    }
    leaf counter_slice7_ifg_mac_pool87_tx_mac_partial1_invert_crc_cnt_reg6_tx_mac_partial1_invert_crc_cnt {
      type oc-yang:counter64;
      description
        "Counts the number of transmitted packets with partial CRC type 1.";
    }
    leaf counter_slice7_ifg_mac_pool87_tx_mac_partial1_invert_crc_cnt_reg7_tx_mac_partial1_invert_crc_cnt {
      type oc-yang:counter64;
      description
        "Counts the number of transmitted packets with partial CRC type 1.";
    }
    leaf counter_slice8_ifg_mac_pool80_tx_mac_partial1_invert_crc_cnt_reg0_tx_mac_partial1_invert_crc_cnt {
      type oc-yang:counter64;
      description
        "Counts the number of transmitted packets with partial CRC type 1.";
    }
    leaf counter_slice8_ifg_mac_pool80_tx_mac_partial1_invert_crc_cnt_reg1_tx_mac_partial1_invert_crc_cnt {
      type oc-yang:counter64;
      description
        "Counts the number of transmitted packets with partial CRC type 1.";
    }
    leaf counter_slice8_ifg_mac_pool80_tx_mac_partial1_invert_crc_cnt_reg2_tx_mac_partial1_invert_crc_cnt {
      type oc-yang:counter64;
      description
        "Counts the number of transmitted packets with partial CRC type 1.";
    }
    leaf counter_slice8_ifg_mac_pool80_tx_mac_partial1_invert_crc_cnt_reg3_tx_mac_partial1_invert_crc_cnt {
      type oc-yang:counter64;
      description
        "Counts the number of transmitted packets with partial CRC type 1.";
    }
    leaf counter_slice8_ifg_mac_pool80_tx_mac_partial1_invert_crc_cnt_reg4_tx_mac_partial1_invert_crc_cnt {
      type oc-yang:counter64;
      description
        "Counts the number of transmitted packets with partial CRC type 1.";
    }
    leaf counter_slice8_ifg_mac_pool80_tx_mac_partial1_invert_crc_cnt_reg5_tx_mac_partial1_invert_crc_cnt {
      type oc-yang:counter64;
      description
        "Counts the number of transmitted packets with partial CRC type 1.";
    }
    leaf counter_slice8_ifg_mac_pool80_tx_mac_partial1_invert_crc_cnt_reg6_tx_mac_partial1_invert_crc_cnt {
      type oc-yang:counter64;
      description
        "Counts the number of transmitted packets with partial CRC type 1.";
    }
    leaf counter_slice8_ifg_mac_pool80_tx_mac_partial1_invert_crc_cnt_reg7_tx_mac_partial1_invert_crc_cnt {
      type oc-yang:counter64;
      description
        "Counts the number of transmitted packets with partial CRC type 1.";
    }
    leaf counter_slice8_ifg_mac_pool81_tx_mac_partial1_invert_crc_cnt_reg0_tx_mac_partial1_invert_crc_cnt {
      type oc-yang:counter64;
      description
        "Counts the number of transmitted packets with partial CRC type 1.";
    }
    leaf counter_slice8_ifg_mac_pool81_tx_mac_partial1_invert_crc_cnt_reg1_tx_mac_partial1_invert_crc_cnt {
      type oc-yang:counter64;
      description
        "Counts the number of transmitted packets with partial CRC type 1.";
    }
    leaf counter_slice8_ifg_mac_pool81_tx_mac_partial1_invert_crc_cnt_reg2_tx_mac_partial1_invert_crc_cnt {
      type oc-yang:counter64;
      description
        "Counts the number of transmitted packets with partial CRC type 1.";
    }
    leaf counter_slice8_ifg_mac_pool81_tx_mac_partial1_invert_crc_cnt_reg3_tx_mac_partial1_invert_crc_cnt {
      type oc-yang:counter64;
      description
        "Counts the number of transmitted packets with partial CRC type 1.";
    }
    leaf counter_slice8_ifg_mac_pool81_tx_mac_partial1_invert_crc_cnt_reg4_tx_mac_partial1_invert_crc_cnt {
      type oc-yang:counter64;
      description
        "Counts the number of transmitted packets with partial CRC type 1.";
    }
    leaf counter_slice8_ifg_mac_pool81_tx_mac_partial1_invert_crc_cnt_reg5_tx_mac_partial1_invert_crc_cnt {
      type oc-yang:counter64;
      description
        "Counts the number of transmitted packets with partial CRC type 1.";
    }
    leaf counter_slice8_ifg_mac_pool81_tx_mac_partial1_invert_crc_cnt_reg6_tx_mac_partial1_invert_crc_cnt {
      type oc-yang:counter64;
      description
        "Counts the number of transmitted packets with partial CRC type 1.";
    }
    leaf counter_slice8_ifg_mac_pool81_tx_mac_partial1_invert_crc_cnt_reg7_tx_mac_partial1_invert_crc_cnt {
      type oc-yang:counter64;
      description
        "Counts the number of transmitted packets with partial CRC type 1.";
    }
    leaf counter_slice8_ifg_mac_pool82_tx_mac_partial1_invert_crc_cnt_reg0_tx_mac_partial1_invert_crc_cnt {
      type oc-yang:counter64;
      description
        "Counts the number of transmitted packets with partial CRC type 1.";
    }
    leaf counter_slice8_ifg_mac_pool82_tx_mac_partial1_invert_crc_cnt_reg1_tx_mac_partial1_invert_crc_cnt {
      type oc-yang:counter64;
      description
        "Counts the number of transmitted packets with partial CRC type 1.";
    }
    leaf counter_slice8_ifg_mac_pool82_tx_mac_partial1_invert_crc_cnt_reg2_tx_mac_partial1_invert_crc_cnt {
      type oc-yang:counter64;
      description
        "Counts the number of transmitted packets with partial CRC type 1.";
    }
    leaf counter_slice8_ifg_mac_pool82_tx_mac_partial1_invert_crc_cnt_reg3_tx_mac_partial1_invert_crc_cnt {
      type oc-yang:counter64;
      description
        "Counts the number of transmitted packets with partial CRC type 1.";
    }
    leaf counter_slice8_ifg_mac_pool82_tx_mac_partial1_invert_crc_cnt_reg4_tx_mac_partial1_invert_crc_cnt {
      type oc-yang:counter64;
      description
        "Counts the number of transmitted packets with partial CRC type 1.";
    }
    leaf counter_slice8_ifg_mac_pool82_tx_mac_partial1_invert_crc_cnt_reg5_tx_mac_partial1_invert_crc_cnt {
      type oc-yang:counter64;
      description
        "Counts the number of transmitted packets with partial CRC type 1.";
    }
    leaf counter_slice8_ifg_mac_pool82_tx_mac_partial1_invert_crc_cnt_reg6_tx_mac_partial1_invert_crc_cnt {
      type oc-yang:counter64;
      description
        "Counts the number of transmitted packets with partial CRC type 1.";
    }
    leaf counter_slice8_ifg_mac_pool82_tx_mac_partial1_invert_crc_cnt_reg7_tx_mac_partial1_invert_crc_cnt {
      type oc-yang:counter64;
      description
        "Counts the number of transmitted packets with partial CRC type 1.";
    }
    leaf counter_slice8_ifg_mac_pool83_tx_mac_partial1_invert_crc_cnt_reg0_tx_mac_partial1_invert_crc_cnt {
      type oc-yang:counter64;
      description
        "Counts the number of transmitted packets with partial CRC type 1.";
    }
    leaf counter_slice8_ifg_mac_pool83_tx_mac_partial1_invert_crc_cnt_reg1_tx_mac_partial1_invert_crc_cnt {
      type oc-yang:counter64;
      description
        "Counts the number of transmitted packets with partial CRC type 1.";
    }
    leaf counter_slice8_ifg_mac_pool83_tx_mac_partial1_invert_crc_cnt_reg2_tx_mac_partial1_invert_crc_cnt {
      type oc-yang:counter64;
      description
        "Counts the number of transmitted packets with partial CRC type 1.";
    }
    leaf counter_slice8_ifg_mac_pool83_tx_mac_partial1_invert_crc_cnt_reg3_tx_mac_partial1_invert_crc_cnt {
      type oc-yang:counter64;
      description
        "Counts the number of transmitted packets with partial CRC type 1.";
    }
    leaf counter_slice8_ifg_mac_pool83_tx_mac_partial1_invert_crc_cnt_reg4_tx_mac_partial1_invert_crc_cnt {
      type oc-yang:counter64;
      description
        "Counts the number of transmitted packets with partial CRC type 1.";
    }
    leaf counter_slice8_ifg_mac_pool83_tx_mac_partial1_invert_crc_cnt_reg5_tx_mac_partial1_invert_crc_cnt {
      type oc-yang:counter64;
      description
        "Counts the number of transmitted packets with partial CRC type 1.";
    }
    leaf counter_slice8_ifg_mac_pool83_tx_mac_partial1_invert_crc_cnt_reg6_tx_mac_partial1_invert_crc_cnt {
      type oc-yang:counter64;
      description
        "Counts the number of transmitted packets with partial CRC type 1.";
    }
    leaf counter_slice8_ifg_mac_pool83_tx_mac_partial1_invert_crc_cnt_reg7_tx_mac_partial1_invert_crc_cnt {
      type oc-yang:counter64;
      description
        "Counts the number of transmitted packets with partial CRC type 1.";
    }
    leaf counter_slice8_ifg_mac_pool84_tx_mac_partial1_invert_crc_cnt_reg0_tx_mac_partial1_invert_crc_cnt {
      type oc-yang:counter64;
      description
        "Counts the number of transmitted packets with partial CRC type 1.";
    }
    leaf counter_slice8_ifg_mac_pool84_tx_mac_partial1_invert_crc_cnt_reg1_tx_mac_partial1_invert_crc_cnt {
      type oc-yang:counter64;
      description
        "Counts the number of transmitted packets with partial CRC type 1.";
    }
    leaf counter_slice8_ifg_mac_pool84_tx_mac_partial1_invert_crc_cnt_reg2_tx_mac_partial1_invert_crc_cnt {
      type oc-yang:counter64;
      description
        "Counts the number of transmitted packets with partial CRC type 1.";
    }
    leaf counter_slice8_ifg_mac_pool84_tx_mac_partial1_invert_crc_cnt_reg3_tx_mac_partial1_invert_crc_cnt {
      type oc-yang:counter64;
      description
        "Counts the number of transmitted packets with partial CRC type 1.";
    }
    leaf counter_slice8_ifg_mac_pool84_tx_mac_partial1_invert_crc_cnt_reg4_tx_mac_partial1_invert_crc_cnt {
      type oc-yang:counter64;
      description
        "Counts the number of transmitted packets with partial CRC type 1.";
    }
    leaf counter_slice8_ifg_mac_pool84_tx_mac_partial1_invert_crc_cnt_reg5_tx_mac_partial1_invert_crc_cnt {
      type oc-yang:counter64;
      description
        "Counts the number of transmitted packets with partial CRC type 1.";
    }
    leaf counter_slice8_ifg_mac_pool84_tx_mac_partial1_invert_crc_cnt_reg6_tx_mac_partial1_invert_crc_cnt {
      type oc-yang:counter64;
      description
        "Counts the number of transmitted packets with partial CRC type 1.";
    }
    leaf counter_slice8_ifg_mac_pool84_tx_mac_partial1_invert_crc_cnt_reg7_tx_mac_partial1_invert_crc_cnt {
      type oc-yang:counter64;
      description
        "Counts the number of transmitted packets with partial CRC type 1.";
    }
    leaf counter_slice8_ifg_mac_pool85_tx_mac_partial1_invert_crc_cnt_reg0_tx_mac_partial1_invert_crc_cnt {
      type oc-yang:counter64;
      description
        "Counts the number of transmitted packets with partial CRC type 1.";
    }
    leaf counter_slice8_ifg_mac_pool85_tx_mac_partial1_invert_crc_cnt_reg1_tx_mac_partial1_invert_crc_cnt {
      type oc-yang:counter64;
      description
        "Counts the number of transmitted packets with partial CRC type 1.";
    }
    leaf counter_slice8_ifg_mac_pool85_tx_mac_partial1_invert_crc_cnt_reg2_tx_mac_partial1_invert_crc_cnt {
      type oc-yang:counter64;
      description
        "Counts the number of transmitted packets with partial CRC type 1.";
    }
    leaf counter_slice8_ifg_mac_pool85_tx_mac_partial1_invert_crc_cnt_reg3_tx_mac_partial1_invert_crc_cnt {
      type oc-yang:counter64;
      description
        "Counts the number of transmitted packets with partial CRC type 1.";
    }
    leaf counter_slice8_ifg_mac_pool85_tx_mac_partial1_invert_crc_cnt_reg4_tx_mac_partial1_invert_crc_cnt {
      type oc-yang:counter64;
      description
        "Counts the number of transmitted packets with partial CRC type 1.";
    }
    leaf counter_slice8_ifg_mac_pool85_tx_mac_partial1_invert_crc_cnt_reg5_tx_mac_partial1_invert_crc_cnt {
      type oc-yang:counter64;
      description
        "Counts the number of transmitted packets with partial CRC type 1.";
    }
    leaf counter_slice8_ifg_mac_pool85_tx_mac_partial1_invert_crc_cnt_reg6_tx_mac_partial1_invert_crc_cnt {
      type oc-yang:counter64;
      description
        "Counts the number of transmitted packets with partial CRC type 1.";
    }
    leaf counter_slice8_ifg_mac_pool85_tx_mac_partial1_invert_crc_cnt_reg7_tx_mac_partial1_invert_crc_cnt {
      type oc-yang:counter64;
      description
        "Counts the number of transmitted packets with partial CRC type 1.";
    }
    leaf counter_slice8_ifg_mac_pool86_tx_mac_partial1_invert_crc_cnt_reg0_tx_mac_partial1_invert_crc_cnt {
      type oc-yang:counter64;
      description
        "Counts the number of transmitted packets with partial CRC type 1.";
    }
    leaf counter_slice8_ifg_mac_pool86_tx_mac_partial1_invert_crc_cnt_reg1_tx_mac_partial1_invert_crc_cnt {
      type oc-yang:counter64;
      description
        "Counts the number of transmitted packets with partial CRC type 1.";
    }
    leaf counter_slice8_ifg_mac_pool86_tx_mac_partial1_invert_crc_cnt_reg2_tx_mac_partial1_invert_crc_cnt {
      type oc-yang:counter64;
      description
        "Counts the number of transmitted packets with partial CRC type 1.";
    }
    leaf counter_slice8_ifg_mac_pool86_tx_mac_partial1_invert_crc_cnt_reg3_tx_mac_partial1_invert_crc_cnt {
      type oc-yang:counter64;
      description
        "Counts the number of transmitted packets with partial CRC type 1.";
    }
    leaf counter_slice8_ifg_mac_pool86_tx_mac_partial1_invert_crc_cnt_reg4_tx_mac_partial1_invert_crc_cnt {
      type oc-yang:counter64;
      description
        "Counts the number of transmitted packets with partial CRC type 1.";
    }
    leaf counter_slice8_ifg_mac_pool86_tx_mac_partial1_invert_crc_cnt_reg5_tx_mac_partial1_invert_crc_cnt {
      type oc-yang:counter64;
      description
        "Counts the number of transmitted packets with partial CRC type 1.";
    }
    leaf counter_slice8_ifg_mac_pool86_tx_mac_partial1_invert_crc_cnt_reg6_tx_mac_partial1_invert_crc_cnt {
      type oc-yang:counter64;
      description
        "Counts the number of transmitted packets with partial CRC type 1.";
    }
    leaf counter_slice8_ifg_mac_pool86_tx_mac_partial1_invert_crc_cnt_reg7_tx_mac_partial1_invert_crc_cnt {
      type oc-yang:counter64;
      description
        "Counts the number of transmitted packets with partial CRC type 1.";
    }
    leaf counter_slice8_ifg_mac_pool87_tx_mac_partial1_invert_crc_cnt_reg0_tx_mac_partial1_invert_crc_cnt {
      type oc-yang:counter64;
      description
        "Counts the number of transmitted packets with partial CRC type 1.";
    }
    leaf counter_slice8_ifg_mac_pool87_tx_mac_partial1_invert_crc_cnt_reg1_tx_mac_partial1_invert_crc_cnt {
      type oc-yang:counter64;
      description
        "Counts the number of transmitted packets with partial CRC type 1.";
    }
    leaf counter_slice8_ifg_mac_pool87_tx_mac_partial1_invert_crc_cnt_reg2_tx_mac_partial1_invert_crc_cnt {
      type oc-yang:counter64;
      description
        "Counts the number of transmitted packets with partial CRC type 1.";
    }
    leaf counter_slice8_ifg_mac_pool87_tx_mac_partial1_invert_crc_cnt_reg3_tx_mac_partial1_invert_crc_cnt {
      type oc-yang:counter64;
      description
        "Counts the number of transmitted packets with partial CRC type 1.";
    }
    leaf counter_slice8_ifg_mac_pool87_tx_mac_partial1_invert_crc_cnt_reg4_tx_mac_partial1_invert_crc_cnt {
      type oc-yang:counter64;
      description
        "Counts the number of transmitted packets with partial CRC type 1.";
    }
    leaf counter_slice8_ifg_mac_pool87_tx_mac_partial1_invert_crc_cnt_reg5_tx_mac_partial1_invert_crc_cnt {
      type oc-yang:counter64;
      description
        "Counts the number of transmitted packets with partial CRC type 1.";
    }
    leaf counter_slice8_ifg_mac_pool87_tx_mac_partial1_invert_crc_cnt_reg6_tx_mac_partial1_invert_crc_cnt {
      type oc-yang:counter64;
      description
        "Counts the number of transmitted packets with partial CRC type 1.";
    }
    leaf counter_slice8_ifg_mac_pool87_tx_mac_partial1_invert_crc_cnt_reg7_tx_mac_partial1_invert_crc_cnt {
      type oc-yang:counter64;
      description
        "Counts the number of transmitted packets with partial CRC type 1.";
    }
    leaf counter_slice9_ifg_mac_pool80_tx_mac_partial1_invert_crc_cnt_reg0_tx_mac_partial1_invert_crc_cnt {
      type oc-yang:counter64;
      description
        "Counts the number of transmitted packets with partial CRC type 1.";
    }
    leaf counter_slice9_ifg_mac_pool80_tx_mac_partial1_invert_crc_cnt_reg1_tx_mac_partial1_invert_crc_cnt {
      type oc-yang:counter64;
      description
        "Counts the number of transmitted packets with partial CRC type 1.";
    }
    leaf counter_slice9_ifg_mac_pool80_tx_mac_partial1_invert_crc_cnt_reg2_tx_mac_partial1_invert_crc_cnt {
      type oc-yang:counter64;
      description
        "Counts the number of transmitted packets with partial CRC type 1.";
    }
    leaf counter_slice9_ifg_mac_pool80_tx_mac_partial1_invert_crc_cnt_reg3_tx_mac_partial1_invert_crc_cnt {
      type oc-yang:counter64;
      description
        "Counts the number of transmitted packets with partial CRC type 1.";
    }
    leaf counter_slice9_ifg_mac_pool80_tx_mac_partial1_invert_crc_cnt_reg4_tx_mac_partial1_invert_crc_cnt {
      type oc-yang:counter64;
      description
        "Counts the number of transmitted packets with partial CRC type 1.";
    }
    leaf counter_slice9_ifg_mac_pool80_tx_mac_partial1_invert_crc_cnt_reg5_tx_mac_partial1_invert_crc_cnt {
      type oc-yang:counter64;
      description
        "Counts the number of transmitted packets with partial CRC type 1.";
    }
    leaf counter_slice9_ifg_mac_pool80_tx_mac_partial1_invert_crc_cnt_reg6_tx_mac_partial1_invert_crc_cnt {
      type oc-yang:counter64;
      description
        "Counts the number of transmitted packets with partial CRC type 1.";
    }
    leaf counter_slice9_ifg_mac_pool80_tx_mac_partial1_invert_crc_cnt_reg7_tx_mac_partial1_invert_crc_cnt {
      type oc-yang:counter64;
      description
        "Counts the number of transmitted packets with partial CRC type 1.";
    }
    leaf counter_slice9_ifg_mac_pool81_tx_mac_partial1_invert_crc_cnt_reg0_tx_mac_partial1_invert_crc_cnt {
      type oc-yang:counter64;
      description
        "Counts the number of transmitted packets with partial CRC type 1.";
    }
    leaf counter_slice9_ifg_mac_pool81_tx_mac_partial1_invert_crc_cnt_reg1_tx_mac_partial1_invert_crc_cnt {
      type oc-yang:counter64;
      description
        "Counts the number of transmitted packets with partial CRC type 1.";
    }
    leaf counter_slice9_ifg_mac_pool81_tx_mac_partial1_invert_crc_cnt_reg2_tx_mac_partial1_invert_crc_cnt {
      type oc-yang:counter64;
      description
        "Counts the number of transmitted packets with partial CRC type 1.";
    }
    leaf counter_slice9_ifg_mac_pool81_tx_mac_partial1_invert_crc_cnt_reg3_tx_mac_partial1_invert_crc_cnt {
      type oc-yang:counter64;
      description
        "Counts the number of transmitted packets with partial CRC type 1.";
    }
    leaf counter_slice9_ifg_mac_pool81_tx_mac_partial1_invert_crc_cnt_reg4_tx_mac_partial1_invert_crc_cnt {
      type oc-yang:counter64;
      description
        "Counts the number of transmitted packets with partial CRC type 1.";
    }
    leaf counter_slice9_ifg_mac_pool81_tx_mac_partial1_invert_crc_cnt_reg5_tx_mac_partial1_invert_crc_cnt {
      type oc-yang:counter64;
      description
        "Counts the number of transmitted packets with partial CRC type 1.";
    }
    leaf counter_slice9_ifg_mac_pool81_tx_mac_partial1_invert_crc_cnt_reg6_tx_mac_partial1_invert_crc_cnt {
      type oc-yang:counter64;
      description
        "Counts the number of transmitted packets with partial CRC type 1.";
    }
    leaf counter_slice9_ifg_mac_pool81_tx_mac_partial1_invert_crc_cnt_reg7_tx_mac_partial1_invert_crc_cnt {
      type oc-yang:counter64;
      description
        "Counts the number of transmitted packets with partial CRC type 1.";
    }
    leaf counter_slice9_ifg_mac_pool82_tx_mac_partial1_invert_crc_cnt_reg0_tx_mac_partial1_invert_crc_cnt {
      type oc-yang:counter64;
      description
        "Counts the number of transmitted packets with partial CRC type 1.";
    }
    leaf counter_slice9_ifg_mac_pool82_tx_mac_partial1_invert_crc_cnt_reg1_tx_mac_partial1_invert_crc_cnt {
      type oc-yang:counter64;
      description
        "Counts the number of transmitted packets with partial CRC type 1.";
    }
    leaf counter_slice9_ifg_mac_pool82_tx_mac_partial1_invert_crc_cnt_reg2_tx_mac_partial1_invert_crc_cnt {
      type oc-yang:counter64;
      description
        "Counts the number of transmitted packets with partial CRC type 1.";
    }
    leaf counter_slice9_ifg_mac_pool82_tx_mac_partial1_invert_crc_cnt_reg3_tx_mac_partial1_invert_crc_cnt {
      type oc-yang:counter64;
      description
        "Counts the number of transmitted packets with partial CRC type 1.";
    }
    leaf counter_slice9_ifg_mac_pool82_tx_mac_partial1_invert_crc_cnt_reg4_tx_mac_partial1_invert_crc_cnt {
      type oc-yang:counter64;
      description
        "Counts the number of transmitted packets with partial CRC type 1.";
    }
    leaf counter_slice9_ifg_mac_pool82_tx_mac_partial1_invert_crc_cnt_reg5_tx_mac_partial1_invert_crc_cnt {
      type oc-yang:counter64;
      description
        "Counts the number of transmitted packets with partial CRC type 1.";
    }
    leaf counter_slice9_ifg_mac_pool82_tx_mac_partial1_invert_crc_cnt_reg6_tx_mac_partial1_invert_crc_cnt {
      type oc-yang:counter64;
      description
        "Counts the number of transmitted packets with partial CRC type 1.";
    }
    leaf counter_slice9_ifg_mac_pool82_tx_mac_partial1_invert_crc_cnt_reg7_tx_mac_partial1_invert_crc_cnt {
      type oc-yang:counter64;
      description
        "Counts the number of transmitted packets with partial CRC type 1.";
    }
    leaf counter_slice9_ifg_mac_pool83_tx_mac_partial1_invert_crc_cnt_reg0_tx_mac_partial1_invert_crc_cnt {
      type oc-yang:counter64;
      description
        "Counts the number of transmitted packets with partial CRC type 1.";
    }
    leaf counter_slice9_ifg_mac_pool83_tx_mac_partial1_invert_crc_cnt_reg1_tx_mac_partial1_invert_crc_cnt {
      type oc-yang:counter64;
      description
        "Counts the number of transmitted packets with partial CRC type 1.";
    }
    leaf counter_slice9_ifg_mac_pool83_tx_mac_partial1_invert_crc_cnt_reg2_tx_mac_partial1_invert_crc_cnt {
      type oc-yang:counter64;
      description
        "Counts the number of transmitted packets with partial CRC type 1.";
    }
    leaf counter_slice9_ifg_mac_pool83_tx_mac_partial1_invert_crc_cnt_reg3_tx_mac_partial1_invert_crc_cnt {
      type oc-yang:counter64;
      description
        "Counts the number of transmitted packets with partial CRC type 1.";
    }
    leaf counter_slice9_ifg_mac_pool83_tx_mac_partial1_invert_crc_cnt_reg4_tx_mac_partial1_invert_crc_cnt {
      type oc-yang:counter64;
      description
        "Counts the number of transmitted packets with partial CRC type 1.";
    }
    leaf counter_slice9_ifg_mac_pool83_tx_mac_partial1_invert_crc_cnt_reg5_tx_mac_partial1_invert_crc_cnt {
      type oc-yang:counter64;
      description
        "Counts the number of transmitted packets with partial CRC type 1.";
    }
    leaf counter_slice9_ifg_mac_pool83_tx_mac_partial1_invert_crc_cnt_reg6_tx_mac_partial1_invert_crc_cnt {
      type oc-yang:counter64;
      description
        "Counts the number of transmitted packets with partial CRC type 1.";
    }
    leaf counter_slice9_ifg_mac_pool83_tx_mac_partial1_invert_crc_cnt_reg7_tx_mac_partial1_invert_crc_cnt {
      type oc-yang:counter64;
      description
        "Counts the number of transmitted packets with partial CRC type 1.";
    }
    leaf counter_slice9_ifg_mac_pool84_tx_mac_partial1_invert_crc_cnt_reg0_tx_mac_partial1_invert_crc_cnt {
      type oc-yang:counter64;
      description
        "Counts the number of transmitted packets with partial CRC type 1.";
    }
    leaf counter_slice9_ifg_mac_pool84_tx_mac_partial1_invert_crc_cnt_reg1_tx_mac_partial1_invert_crc_cnt {
      type oc-yang:counter64;
      description
        "Counts the number of transmitted packets with partial CRC type 1.";
    }
    leaf counter_slice9_ifg_mac_pool84_tx_mac_partial1_invert_crc_cnt_reg2_tx_mac_partial1_invert_crc_cnt {
      type oc-yang:counter64;
      description
        "Counts the number of transmitted packets with partial CRC type 1.";
    }
    leaf counter_slice9_ifg_mac_pool84_tx_mac_partial1_invert_crc_cnt_reg3_tx_mac_partial1_invert_crc_cnt {
      type oc-yang:counter64;
      description
        "Counts the number of transmitted packets with partial CRC type 1.";
    }
    leaf counter_slice9_ifg_mac_pool84_tx_mac_partial1_invert_crc_cnt_reg4_tx_mac_partial1_invert_crc_cnt {
      type oc-yang:counter64;
      description
        "Counts the number of transmitted packets with partial CRC type 1.";
    }
    leaf counter_slice9_ifg_mac_pool84_tx_mac_partial1_invert_crc_cnt_reg5_tx_mac_partial1_invert_crc_cnt {
      type oc-yang:counter64;
      description
        "Counts the number of transmitted packets with partial CRC type 1.";
    }
    leaf counter_slice9_ifg_mac_pool84_tx_mac_partial1_invert_crc_cnt_reg6_tx_mac_partial1_invert_crc_cnt {
      type oc-yang:counter64;
      description
        "Counts the number of transmitted packets with partial CRC type 1.";
    }
    leaf counter_slice9_ifg_mac_pool84_tx_mac_partial1_invert_crc_cnt_reg7_tx_mac_partial1_invert_crc_cnt {
      type oc-yang:counter64;
      description
        "Counts the number of transmitted packets with partial CRC type 1.";
    }
    leaf counter_slice9_ifg_mac_pool85_tx_mac_partial1_invert_crc_cnt_reg0_tx_mac_partial1_invert_crc_cnt {
      type oc-yang:counter64;
      description
        "Counts the number of transmitted packets with partial CRC type 1.";
    }
    leaf counter_slice9_ifg_mac_pool85_tx_mac_partial1_invert_crc_cnt_reg1_tx_mac_partial1_invert_crc_cnt {
      type oc-yang:counter64;
      description
        "Counts the number of transmitted packets with partial CRC type 1.";
    }
    leaf counter_slice9_ifg_mac_pool85_tx_mac_partial1_invert_crc_cnt_reg2_tx_mac_partial1_invert_crc_cnt {
      type oc-yang:counter64;
      description
        "Counts the number of transmitted packets with partial CRC type 1.";
    }
    leaf counter_slice9_ifg_mac_pool85_tx_mac_partial1_invert_crc_cnt_reg3_tx_mac_partial1_invert_crc_cnt {
      type oc-yang:counter64;
      description
        "Counts the number of transmitted packets with partial CRC type 1.";
    }
    leaf counter_slice9_ifg_mac_pool85_tx_mac_partial1_invert_crc_cnt_reg4_tx_mac_partial1_invert_crc_cnt {
      type oc-yang:counter64;
      description
        "Counts the number of transmitted packets with partial CRC type 1.";
    }
    leaf counter_slice9_ifg_mac_pool85_tx_mac_partial1_invert_crc_cnt_reg5_tx_mac_partial1_invert_crc_cnt {
      type oc-yang:counter64;
      description
        "Counts the number of transmitted packets with partial CRC type 1.";
    }
    leaf counter_slice9_ifg_mac_pool85_tx_mac_partial1_invert_crc_cnt_reg6_tx_mac_partial1_invert_crc_cnt {
      type oc-yang:counter64;
      description
        "Counts the number of transmitted packets with partial CRC type 1.";
    }
    leaf counter_slice9_ifg_mac_pool85_tx_mac_partial1_invert_crc_cnt_reg7_tx_mac_partial1_invert_crc_cnt {
      type oc-yang:counter64;
      description
        "Counts the number of transmitted packets with partial CRC type 1.";
    }
    leaf counter_slice9_ifg_mac_pool86_tx_mac_partial1_invert_crc_cnt_reg0_tx_mac_partial1_invert_crc_cnt {
      type oc-yang:counter64;
      description
        "Counts the number of transmitted packets with partial CRC type 1.";
    }
    leaf counter_slice9_ifg_mac_pool86_tx_mac_partial1_invert_crc_cnt_reg1_tx_mac_partial1_invert_crc_cnt {
      type oc-yang:counter64;
      description
        "Counts the number of transmitted packets with partial CRC type 1.";
    }
    leaf counter_slice9_ifg_mac_pool86_tx_mac_partial1_invert_crc_cnt_reg2_tx_mac_partial1_invert_crc_cnt {
      type oc-yang:counter64;
      description
        "Counts the number of transmitted packets with partial CRC type 1.";
    }
    leaf counter_slice9_ifg_mac_pool86_tx_mac_partial1_invert_crc_cnt_reg3_tx_mac_partial1_invert_crc_cnt {
      type oc-yang:counter64;
      description
        "Counts the number of transmitted packets with partial CRC type 1.";
    }
    leaf counter_slice9_ifg_mac_pool86_tx_mac_partial1_invert_crc_cnt_reg4_tx_mac_partial1_invert_crc_cnt {
      type oc-yang:counter64;
      description
        "Counts the number of transmitted packets with partial CRC type 1.";
    }
    leaf counter_slice9_ifg_mac_pool86_tx_mac_partial1_invert_crc_cnt_reg5_tx_mac_partial1_invert_crc_cnt {
      type oc-yang:counter64;
      description
        "Counts the number of transmitted packets with partial CRC type 1.";
    }
    leaf counter_slice9_ifg_mac_pool86_tx_mac_partial1_invert_crc_cnt_reg6_tx_mac_partial1_invert_crc_cnt {
      type oc-yang:counter64;
      description
        "Counts the number of transmitted packets with partial CRC type 1.";
    }
    leaf counter_slice9_ifg_mac_pool86_tx_mac_partial1_invert_crc_cnt_reg7_tx_mac_partial1_invert_crc_cnt {
      type oc-yang:counter64;
      description
        "Counts the number of transmitted packets with partial CRC type 1.";
    }
    leaf counter_slice9_ifg_mac_pool87_tx_mac_partial1_invert_crc_cnt_reg0_tx_mac_partial1_invert_crc_cnt {
      type oc-yang:counter64;
      description
        "Counts the number of transmitted packets with partial CRC type 1.";
    }
    leaf counter_slice9_ifg_mac_pool87_tx_mac_partial1_invert_crc_cnt_reg1_tx_mac_partial1_invert_crc_cnt {
      type oc-yang:counter64;
      description
        "Counts the number of transmitted packets with partial CRC type 1.";
    }
    leaf counter_slice9_ifg_mac_pool87_tx_mac_partial1_invert_crc_cnt_reg2_tx_mac_partial1_invert_crc_cnt {
      type oc-yang:counter64;
      description
        "Counts the number of transmitted packets with partial CRC type 1.";
    }
    leaf counter_slice9_ifg_mac_pool87_tx_mac_partial1_invert_crc_cnt_reg3_tx_mac_partial1_invert_crc_cnt {
      type oc-yang:counter64;
      description
        "Counts the number of transmitted packets with partial CRC type 1.";
    }
    leaf counter_slice9_ifg_mac_pool87_tx_mac_partial1_invert_crc_cnt_reg4_tx_mac_partial1_invert_crc_cnt {
      type oc-yang:counter64;
      description
        "Counts the number of transmitted packets with partial CRC type 1.";
    }
    leaf counter_slice9_ifg_mac_pool87_tx_mac_partial1_invert_crc_cnt_reg5_tx_mac_partial1_invert_crc_cnt {
      type oc-yang:counter64;
      description
        "Counts the number of transmitted packets with partial CRC type 1.";
    }
    leaf counter_slice9_ifg_mac_pool87_tx_mac_partial1_invert_crc_cnt_reg6_tx_mac_partial1_invert_crc_cnt {
      type oc-yang:counter64;
      description
        "Counts the number of transmitted packets with partial CRC type 1.";
    }
    leaf counter_slice9_ifg_mac_pool87_tx_mac_partial1_invert_crc_cnt_reg7_tx_mac_partial1_invert_crc_cnt {
      type oc-yang:counter64;
      description
        "Counts the number of transmitted packets with partial CRC type 1.";
    }
    leaf counter_slice10_ifg_mac_pool80_tx_mac_partial1_invert_crc_cnt_reg0_tx_mac_partial1_invert_crc_cnt {
      type oc-yang:counter64;
      description
        "Counts the number of transmitted packets with partial CRC type 1.";
    }
    leaf counter_slice10_ifg_mac_pool80_tx_mac_partial1_invert_crc_cnt_reg1_tx_mac_partial1_invert_crc_cnt {
      type oc-yang:counter64;
      description
        "Counts the number of transmitted packets with partial CRC type 1.";
    }
    leaf counter_slice10_ifg_mac_pool80_tx_mac_partial1_invert_crc_cnt_reg2_tx_mac_partial1_invert_crc_cnt {
      type oc-yang:counter64;
      description
        "Counts the number of transmitted packets with partial CRC type 1.";
    }
    leaf counter_slice10_ifg_mac_pool80_tx_mac_partial1_invert_crc_cnt_reg3_tx_mac_partial1_invert_crc_cnt {
      type oc-yang:counter64;
      description
        "Counts the number of transmitted packets with partial CRC type 1.";
    }
    leaf counter_slice10_ifg_mac_pool80_tx_mac_partial1_invert_crc_cnt_reg4_tx_mac_partial1_invert_crc_cnt {
      type oc-yang:counter64;
      description
        "Counts the number of transmitted packets with partial CRC type 1.";
    }
    leaf counter_slice10_ifg_mac_pool80_tx_mac_partial1_invert_crc_cnt_reg5_tx_mac_partial1_invert_crc_cnt {
      type oc-yang:counter64;
      description
        "Counts the number of transmitted packets with partial CRC type 1.";
    }
    leaf counter_slice10_ifg_mac_pool80_tx_mac_partial1_invert_crc_cnt_reg6_tx_mac_partial1_invert_crc_cnt {
      type oc-yang:counter64;
      description
        "Counts the number of transmitted packets with partial CRC type 1.";
    }
    leaf counter_slice10_ifg_mac_pool80_tx_mac_partial1_invert_crc_cnt_reg7_tx_mac_partial1_invert_crc_cnt {
      type oc-yang:counter64;
      description
        "Counts the number of transmitted packets with partial CRC type 1.";
    }
    leaf counter_slice10_ifg_mac_pool81_tx_mac_partial1_invert_crc_cnt_reg0_tx_mac_partial1_invert_crc_cnt {
      type oc-yang:counter64;
      description
        "Counts the number of transmitted packets with partial CRC type 1.";
    }
    leaf counter_slice10_ifg_mac_pool81_tx_mac_partial1_invert_crc_cnt_reg1_tx_mac_partial1_invert_crc_cnt {
      type oc-yang:counter64;
      description
        "Counts the number of transmitted packets with partial CRC type 1.";
    }
    leaf counter_slice10_ifg_mac_pool81_tx_mac_partial1_invert_crc_cnt_reg2_tx_mac_partial1_invert_crc_cnt {
      type oc-yang:counter64;
      description
        "Counts the number of transmitted packets with partial CRC type 1.";
    }
    leaf counter_slice10_ifg_mac_pool81_tx_mac_partial1_invert_crc_cnt_reg3_tx_mac_partial1_invert_crc_cnt {
      type oc-yang:counter64;
      description
        "Counts the number of transmitted packets with partial CRC type 1.";
    }
    leaf counter_slice10_ifg_mac_pool81_tx_mac_partial1_invert_crc_cnt_reg4_tx_mac_partial1_invert_crc_cnt {
      type oc-yang:counter64;
      description
        "Counts the number of transmitted packets with partial CRC type 1.";
    }
    leaf counter_slice10_ifg_mac_pool81_tx_mac_partial1_invert_crc_cnt_reg5_tx_mac_partial1_invert_crc_cnt {
      type oc-yang:counter64;
      description
        "Counts the number of transmitted packets with partial CRC type 1.";
    }
    leaf counter_slice10_ifg_mac_pool81_tx_mac_partial1_invert_crc_cnt_reg6_tx_mac_partial1_invert_crc_cnt {
      type oc-yang:counter64;
      description
        "Counts the number of transmitted packets with partial CRC type 1.";
    }
    leaf counter_slice10_ifg_mac_pool81_tx_mac_partial1_invert_crc_cnt_reg7_tx_mac_partial1_invert_crc_cnt {
      type oc-yang:counter64;
      description
        "Counts the number of transmitted packets with partial CRC type 1.";
    }
    leaf counter_slice10_ifg_mac_pool82_tx_mac_partial1_invert_crc_cnt_reg0_tx_mac_partial1_invert_crc_cnt {
      type oc-yang:counter64;
      description
        "Counts the number of transmitted packets with partial CRC type 1.";
    }
    leaf counter_slice10_ifg_mac_pool82_tx_mac_partial1_invert_crc_cnt_reg1_tx_mac_partial1_invert_crc_cnt {
      type oc-yang:counter64;
      description
        "Counts the number of transmitted packets with partial CRC type 1.";
    }
    leaf counter_slice10_ifg_mac_pool82_tx_mac_partial1_invert_crc_cnt_reg2_tx_mac_partial1_invert_crc_cnt {
      type oc-yang:counter64;
      description
        "Counts the number of transmitted packets with partial CRC type 1.";
    }
    leaf counter_slice10_ifg_mac_pool82_tx_mac_partial1_invert_crc_cnt_reg3_tx_mac_partial1_invert_crc_cnt {
      type oc-yang:counter64;
      description
        "Counts the number of transmitted packets with partial CRC type 1.";
    }
    leaf counter_slice10_ifg_mac_pool82_tx_mac_partial1_invert_crc_cnt_reg4_tx_mac_partial1_invert_crc_cnt {
      type oc-yang:counter64;
      description
        "Counts the number of transmitted packets with partial CRC type 1.";
    }
    leaf counter_slice10_ifg_mac_pool82_tx_mac_partial1_invert_crc_cnt_reg5_tx_mac_partial1_invert_crc_cnt {
      type oc-yang:counter64;
      description
        "Counts the number of transmitted packets with partial CRC type 1.";
    }
    leaf counter_slice10_ifg_mac_pool82_tx_mac_partial1_invert_crc_cnt_reg6_tx_mac_partial1_invert_crc_cnt {
      type oc-yang:counter64;
      description
        "Counts the number of transmitted packets with partial CRC type 1.";
    }
    leaf counter_slice10_ifg_mac_pool82_tx_mac_partial1_invert_crc_cnt_reg7_tx_mac_partial1_invert_crc_cnt {
      type oc-yang:counter64;
      description
        "Counts the number of transmitted packets with partial CRC type 1.";
    }
    leaf counter_slice10_ifg_mac_pool83_tx_mac_partial1_invert_crc_cnt_reg0_tx_mac_partial1_invert_crc_cnt {
      type oc-yang:counter64;
      description
        "Counts the number of transmitted packets with partial CRC type 1.";
    }
    leaf counter_slice10_ifg_mac_pool83_tx_mac_partial1_invert_crc_cnt_reg1_tx_mac_partial1_invert_crc_cnt {
      type oc-yang:counter64;
      description
        "Counts the number of transmitted packets with partial CRC type 1.";
    }
    leaf counter_slice10_ifg_mac_pool83_tx_mac_partial1_invert_crc_cnt_reg2_tx_mac_partial1_invert_crc_cnt {
      type oc-yang:counter64;
      description
        "Counts the number of transmitted packets with partial CRC type 1.";
    }
    leaf counter_slice10_ifg_mac_pool83_tx_mac_partial1_invert_crc_cnt_reg3_tx_mac_partial1_invert_crc_cnt {
      type oc-yang:counter64;
      description
        "Counts the number of transmitted packets with partial CRC type 1.";
    }
    leaf counter_slice10_ifg_mac_pool83_tx_mac_partial1_invert_crc_cnt_reg4_tx_mac_partial1_invert_crc_cnt {
      type oc-yang:counter64;
      description
        "Counts the number of transmitted packets with partial CRC type 1.";
    }
    leaf counter_slice10_ifg_mac_pool83_tx_mac_partial1_invert_crc_cnt_reg5_tx_mac_partial1_invert_crc_cnt {
      type oc-yang:counter64;
      description
        "Counts the number of transmitted packets with partial CRC type 1.";
    }
    leaf counter_slice10_ifg_mac_pool83_tx_mac_partial1_invert_crc_cnt_reg6_tx_mac_partial1_invert_crc_cnt {
      type oc-yang:counter64;
      description
        "Counts the number of transmitted packets with partial CRC type 1.";
    }
    leaf counter_slice10_ifg_mac_pool83_tx_mac_partial1_invert_crc_cnt_reg7_tx_mac_partial1_invert_crc_cnt {
      type oc-yang:counter64;
      description
        "Counts the number of transmitted packets with partial CRC type 1.";
    }
    leaf counter_slice10_ifg_mac_pool84_tx_mac_partial1_invert_crc_cnt_reg0_tx_mac_partial1_invert_crc_cnt {
      type oc-yang:counter64;
      description
        "Counts the number of transmitted packets with partial CRC type 1.";
    }
    leaf counter_slice10_ifg_mac_pool84_tx_mac_partial1_invert_crc_cnt_reg1_tx_mac_partial1_invert_crc_cnt {
      type oc-yang:counter64;
      description
        "Counts the number of transmitted packets with partial CRC type 1.";
    }
    leaf counter_slice10_ifg_mac_pool84_tx_mac_partial1_invert_crc_cnt_reg2_tx_mac_partial1_invert_crc_cnt {
      type oc-yang:counter64;
      description
        "Counts the number of transmitted packets with partial CRC type 1.";
    }
    leaf counter_slice10_ifg_mac_pool84_tx_mac_partial1_invert_crc_cnt_reg3_tx_mac_partial1_invert_crc_cnt {
      type oc-yang:counter64;
      description
        "Counts the number of transmitted packets with partial CRC type 1.";
    }
    leaf counter_slice10_ifg_mac_pool84_tx_mac_partial1_invert_crc_cnt_reg4_tx_mac_partial1_invert_crc_cnt {
      type oc-yang:counter64;
      description
        "Counts the number of transmitted packets with partial CRC type 1.";
    }
    leaf counter_slice10_ifg_mac_pool84_tx_mac_partial1_invert_crc_cnt_reg5_tx_mac_partial1_invert_crc_cnt {
      type oc-yang:counter64;
      description
        "Counts the number of transmitted packets with partial CRC type 1.";
    }
    leaf counter_slice10_ifg_mac_pool84_tx_mac_partial1_invert_crc_cnt_reg6_tx_mac_partial1_invert_crc_cnt {
      type oc-yang:counter64;
      description
        "Counts the number of transmitted packets with partial CRC type 1.";
    }
    leaf counter_slice10_ifg_mac_pool84_tx_mac_partial1_invert_crc_cnt_reg7_tx_mac_partial1_invert_crc_cnt {
      type oc-yang:counter64;
      description
        "Counts the number of transmitted packets with partial CRC type 1.";
    }
    leaf counter_slice10_ifg_mac_pool85_tx_mac_partial1_invert_crc_cnt_reg0_tx_mac_partial1_invert_crc_cnt {
      type oc-yang:counter64;
      description
        "Counts the number of transmitted packets with partial CRC type 1.";
    }
    leaf counter_slice10_ifg_mac_pool85_tx_mac_partial1_invert_crc_cnt_reg1_tx_mac_partial1_invert_crc_cnt {
      type oc-yang:counter64;
      description
        "Counts the number of transmitted packets with partial CRC type 1.";
    }
    leaf counter_slice10_ifg_mac_pool85_tx_mac_partial1_invert_crc_cnt_reg2_tx_mac_partial1_invert_crc_cnt {
      type oc-yang:counter64;
      description
        "Counts the number of transmitted packets with partial CRC type 1.";
    }
    leaf counter_slice10_ifg_mac_pool85_tx_mac_partial1_invert_crc_cnt_reg3_tx_mac_partial1_invert_crc_cnt {
      type oc-yang:counter64;
      description
        "Counts the number of transmitted packets with partial CRC type 1.";
    }
    leaf counter_slice10_ifg_mac_pool85_tx_mac_partial1_invert_crc_cnt_reg4_tx_mac_partial1_invert_crc_cnt {
      type oc-yang:counter64;
      description
        "Counts the number of transmitted packets with partial CRC type 1.";
    }
    leaf counter_slice10_ifg_mac_pool85_tx_mac_partial1_invert_crc_cnt_reg5_tx_mac_partial1_invert_crc_cnt {
      type oc-yang:counter64;
      description
        "Counts the number of transmitted packets with partial CRC type 1.";
    }
    leaf counter_slice10_ifg_mac_pool85_tx_mac_partial1_invert_crc_cnt_reg6_tx_mac_partial1_invert_crc_cnt {
      type oc-yang:counter64;
      description
        "Counts the number of transmitted packets with partial CRC type 1.";
    }
    leaf counter_slice10_ifg_mac_pool85_tx_mac_partial1_invert_crc_cnt_reg7_tx_mac_partial1_invert_crc_cnt {
      type oc-yang:counter64;
      description
        "Counts the number of transmitted packets with partial CRC type 1.";
    }
    leaf counter_slice10_ifg_mac_pool86_tx_mac_partial1_invert_crc_cnt_reg0_tx_mac_partial1_invert_crc_cnt {
      type oc-yang:counter64;
      description
        "Counts the number of transmitted packets with partial CRC type 1.";
    }
    leaf counter_slice10_ifg_mac_pool86_tx_mac_partial1_invert_crc_cnt_reg1_tx_mac_partial1_invert_crc_cnt {
      type oc-yang:counter64;
      description
        "Counts the number of transmitted packets with partial CRC type 1.";
    }
    leaf counter_slice10_ifg_mac_pool86_tx_mac_partial1_invert_crc_cnt_reg2_tx_mac_partial1_invert_crc_cnt {
      type oc-yang:counter64;
      description
        "Counts the number of transmitted packets with partial CRC type 1.";
    }
    leaf counter_slice10_ifg_mac_pool86_tx_mac_partial1_invert_crc_cnt_reg3_tx_mac_partial1_invert_crc_cnt {
      type oc-yang:counter64;
      description
        "Counts the number of transmitted packets with partial CRC type 1.";
    }
    leaf counter_slice10_ifg_mac_pool86_tx_mac_partial1_invert_crc_cnt_reg4_tx_mac_partial1_invert_crc_cnt {
      type oc-yang:counter64;
      description
        "Counts the number of transmitted packets with partial CRC type 1.";
    }
    leaf counter_slice10_ifg_mac_pool86_tx_mac_partial1_invert_crc_cnt_reg5_tx_mac_partial1_invert_crc_cnt {
      type oc-yang:counter64;
      description
        "Counts the number of transmitted packets with partial CRC type 1.";
    }
    leaf counter_slice10_ifg_mac_pool86_tx_mac_partial1_invert_crc_cnt_reg6_tx_mac_partial1_invert_crc_cnt {
      type oc-yang:counter64;
      description
        "Counts the number of transmitted packets with partial CRC type 1.";
    }
    leaf counter_slice10_ifg_mac_pool86_tx_mac_partial1_invert_crc_cnt_reg7_tx_mac_partial1_invert_crc_cnt {
      type oc-yang:counter64;
      description
        "Counts the number of transmitted packets with partial CRC type 1.";
    }
    leaf counter_slice10_ifg_mac_pool87_tx_mac_partial1_invert_crc_cnt_reg0_tx_mac_partial1_invert_crc_cnt {
      type oc-yang:counter64;
      description
        "Counts the number of transmitted packets with partial CRC type 1.";
    }
    leaf counter_slice10_ifg_mac_pool87_tx_mac_partial1_invert_crc_cnt_reg1_tx_mac_partial1_invert_crc_cnt {
      type oc-yang:counter64;
      description
        "Counts the number of transmitted packets with partial CRC type 1.";
    }
    leaf counter_slice10_ifg_mac_pool87_tx_mac_partial1_invert_crc_cnt_reg2_tx_mac_partial1_invert_crc_cnt {
      type oc-yang:counter64;
      description
        "Counts the number of transmitted packets with partial CRC type 1.";
    }
    leaf counter_slice10_ifg_mac_pool87_tx_mac_partial1_invert_crc_cnt_reg3_tx_mac_partial1_invert_crc_cnt {
      type oc-yang:counter64;
      description
        "Counts the number of transmitted packets with partial CRC type 1.";
    }
    leaf counter_slice10_ifg_mac_pool87_tx_mac_partial1_invert_crc_cnt_reg4_tx_mac_partial1_invert_crc_cnt {
      type oc-yang:counter64;
      description
        "Counts the number of transmitted packets with partial CRC type 1.";
    }
    leaf counter_slice10_ifg_mac_pool87_tx_mac_partial1_invert_crc_cnt_reg5_tx_mac_partial1_invert_crc_cnt {
      type oc-yang:counter64;
      description
        "Counts the number of transmitted packets with partial CRC type 1.";
    }
    leaf counter_slice10_ifg_mac_pool87_tx_mac_partial1_invert_crc_cnt_reg6_tx_mac_partial1_invert_crc_cnt {
      type oc-yang:counter64;
      description
        "Counts the number of transmitted packets with partial CRC type 1.";
    }
    leaf counter_slice10_ifg_mac_pool87_tx_mac_partial1_invert_crc_cnt_reg7_tx_mac_partial1_invert_crc_cnt {
      type oc-yang:counter64;
      description
        "Counts the number of transmitted packets with partial CRC type 1.";
    }
    leaf counter_slice11_ifg_mac_pool80_tx_mac_partial1_invert_crc_cnt_reg0_tx_mac_partial1_invert_crc_cnt {
      type oc-yang:counter64;
      description
        "Counts the number of transmitted packets with partial CRC type 1.";
    }
    leaf counter_slice11_ifg_mac_pool80_tx_mac_partial1_invert_crc_cnt_reg1_tx_mac_partial1_invert_crc_cnt {
      type oc-yang:counter64;
      description
        "Counts the number of transmitted packets with partial CRC type 1.";
    }
    leaf counter_slice11_ifg_mac_pool80_tx_mac_partial1_invert_crc_cnt_reg2_tx_mac_partial1_invert_crc_cnt {
      type oc-yang:counter64;
      description
        "Counts the number of transmitted packets with partial CRC type 1.";
    }
    leaf counter_slice11_ifg_mac_pool80_tx_mac_partial1_invert_crc_cnt_reg3_tx_mac_partial1_invert_crc_cnt {
      type oc-yang:counter64;
      description
        "Counts the number of transmitted packets with partial CRC type 1.";
    }
    leaf counter_slice11_ifg_mac_pool80_tx_mac_partial1_invert_crc_cnt_reg4_tx_mac_partial1_invert_crc_cnt {
      type oc-yang:counter64;
      description
        "Counts the number of transmitted packets with partial CRC type 1.";
    }
    leaf counter_slice11_ifg_mac_pool80_tx_mac_partial1_invert_crc_cnt_reg5_tx_mac_partial1_invert_crc_cnt {
      type oc-yang:counter64;
      description
        "Counts the number of transmitted packets with partial CRC type 1.";
    }
    leaf counter_slice11_ifg_mac_pool80_tx_mac_partial1_invert_crc_cnt_reg6_tx_mac_partial1_invert_crc_cnt {
      type oc-yang:counter64;
      description
        "Counts the number of transmitted packets with partial CRC type 1.";
    }
    leaf counter_slice11_ifg_mac_pool80_tx_mac_partial1_invert_crc_cnt_reg7_tx_mac_partial1_invert_crc_cnt {
      type oc-yang:counter64;
      description
        "Counts the number of transmitted packets with partial CRC type 1.";
    }
    leaf counter_slice11_ifg_mac_pool81_tx_mac_partial1_invert_crc_cnt_reg0_tx_mac_partial1_invert_crc_cnt {
      type oc-yang:counter64;
      description
        "Counts the number of transmitted packets with partial CRC type 1.";
    }
    leaf counter_slice11_ifg_mac_pool81_tx_mac_partial1_invert_crc_cnt_reg1_tx_mac_partial1_invert_crc_cnt {
      type oc-yang:counter64;
      description
        "Counts the number of transmitted packets with partial CRC type 1.";
    }
    leaf counter_slice11_ifg_mac_pool81_tx_mac_partial1_invert_crc_cnt_reg2_tx_mac_partial1_invert_crc_cnt {
      type oc-yang:counter64;
      description
        "Counts the number of transmitted packets with partial CRC type 1.";
    }
    leaf counter_slice11_ifg_mac_pool81_tx_mac_partial1_invert_crc_cnt_reg3_tx_mac_partial1_invert_crc_cnt {
      type oc-yang:counter64;
      description
        "Counts the number of transmitted packets with partial CRC type 1.";
    }
    leaf counter_slice11_ifg_mac_pool81_tx_mac_partial1_invert_crc_cnt_reg4_tx_mac_partial1_invert_crc_cnt {
      type oc-yang:counter64;
      description
        "Counts the number of transmitted packets with partial CRC type 1.";
    }
    leaf counter_slice11_ifg_mac_pool81_tx_mac_partial1_invert_crc_cnt_reg5_tx_mac_partial1_invert_crc_cnt {
      type oc-yang:counter64;
      description
        "Counts the number of transmitted packets with partial CRC type 1.";
    }
    leaf counter_slice11_ifg_mac_pool81_tx_mac_partial1_invert_crc_cnt_reg6_tx_mac_partial1_invert_crc_cnt {
      type oc-yang:counter64;
      description
        "Counts the number of transmitted packets with partial CRC type 1.";
    }
    leaf counter_slice11_ifg_mac_pool81_tx_mac_partial1_invert_crc_cnt_reg7_tx_mac_partial1_invert_crc_cnt {
      type oc-yang:counter64;
      description
        "Counts the number of transmitted packets with partial CRC type 1.";
    }
    leaf counter_slice11_ifg_mac_pool82_tx_mac_partial1_invert_crc_cnt_reg0_tx_mac_partial1_invert_crc_cnt {
      type oc-yang:counter64;
      description
        "Counts the number of transmitted packets with partial CRC type 1.";
    }
    leaf counter_slice11_ifg_mac_pool82_tx_mac_partial1_invert_crc_cnt_reg1_tx_mac_partial1_invert_crc_cnt {
      type oc-yang:counter64;
      description
        "Counts the number of transmitted packets with partial CRC type 1.";
    }
    leaf counter_slice11_ifg_mac_pool82_tx_mac_partial1_invert_crc_cnt_reg2_tx_mac_partial1_invert_crc_cnt {
      type oc-yang:counter64;
      description
        "Counts the number of transmitted packets with partial CRC type 1.";
    }
    leaf counter_slice11_ifg_mac_pool82_tx_mac_partial1_invert_crc_cnt_reg3_tx_mac_partial1_invert_crc_cnt {
      type oc-yang:counter64;
      description
        "Counts the number of transmitted packets with partial CRC type 1.";
    }
    leaf counter_slice11_ifg_mac_pool82_tx_mac_partial1_invert_crc_cnt_reg4_tx_mac_partial1_invert_crc_cnt {
      type oc-yang:counter64;
      description
        "Counts the number of transmitted packets with partial CRC type 1.";
    }
    leaf counter_slice11_ifg_mac_pool82_tx_mac_partial1_invert_crc_cnt_reg5_tx_mac_partial1_invert_crc_cnt {
      type oc-yang:counter64;
      description
        "Counts the number of transmitted packets with partial CRC type 1.";
    }
    leaf counter_slice11_ifg_mac_pool82_tx_mac_partial1_invert_crc_cnt_reg6_tx_mac_partial1_invert_crc_cnt {
      type oc-yang:counter64;
      description
        "Counts the number of transmitted packets with partial CRC type 1.";
    }
    leaf counter_slice11_ifg_mac_pool82_tx_mac_partial1_invert_crc_cnt_reg7_tx_mac_partial1_invert_crc_cnt {
      type oc-yang:counter64;
      description
        "Counts the number of transmitted packets with partial CRC type 1.";
    }
    leaf counter_slice11_ifg_mac_pool83_tx_mac_partial1_invert_crc_cnt_reg0_tx_mac_partial1_invert_crc_cnt {
      type oc-yang:counter64;
      description
        "Counts the number of transmitted packets with partial CRC type 1.";
    }
    leaf counter_slice11_ifg_mac_pool83_tx_mac_partial1_invert_crc_cnt_reg1_tx_mac_partial1_invert_crc_cnt {
      type oc-yang:counter64;
      description
        "Counts the number of transmitted packets with partial CRC type 1.";
    }
    leaf counter_slice11_ifg_mac_pool83_tx_mac_partial1_invert_crc_cnt_reg2_tx_mac_partial1_invert_crc_cnt {
      type oc-yang:counter64;
      description
        "Counts the number of transmitted packets with partial CRC type 1.";
    }
    leaf counter_slice11_ifg_mac_pool83_tx_mac_partial1_invert_crc_cnt_reg3_tx_mac_partial1_invert_crc_cnt {
      type oc-yang:counter64;
      description
        "Counts the number of transmitted packets with partial CRC type 1.";
    }
    leaf counter_slice11_ifg_mac_pool83_tx_mac_partial1_invert_crc_cnt_reg4_tx_mac_partial1_invert_crc_cnt {
      type oc-yang:counter64;
      description
        "Counts the number of transmitted packets with partial CRC type 1.";
    }
    leaf counter_slice11_ifg_mac_pool83_tx_mac_partial1_invert_crc_cnt_reg5_tx_mac_partial1_invert_crc_cnt {
      type oc-yang:counter64;
      description
        "Counts the number of transmitted packets with partial CRC type 1.";
    }
    leaf counter_slice11_ifg_mac_pool83_tx_mac_partial1_invert_crc_cnt_reg6_tx_mac_partial1_invert_crc_cnt {
      type oc-yang:counter64;
      description
        "Counts the number of transmitted packets with partial CRC type 1.";
    }
    leaf counter_slice11_ifg_mac_pool83_tx_mac_partial1_invert_crc_cnt_reg7_tx_mac_partial1_invert_crc_cnt {
      type oc-yang:counter64;
      description
        "Counts the number of transmitted packets with partial CRC type 1.";
    }
    leaf counter_slice11_ifg_mac_pool84_tx_mac_partial1_invert_crc_cnt_reg0_tx_mac_partial1_invert_crc_cnt {
      type oc-yang:counter64;
      description
        "Counts the number of transmitted packets with partial CRC type 1.";
    }
    leaf counter_slice11_ifg_mac_pool84_tx_mac_partial1_invert_crc_cnt_reg1_tx_mac_partial1_invert_crc_cnt {
      type oc-yang:counter64;
      description
        "Counts the number of transmitted packets with partial CRC type 1.";
    }
    leaf counter_slice11_ifg_mac_pool84_tx_mac_partial1_invert_crc_cnt_reg2_tx_mac_partial1_invert_crc_cnt {
      type oc-yang:counter64;
      description
        "Counts the number of transmitted packets with partial CRC type 1.";
    }
    leaf counter_slice11_ifg_mac_pool84_tx_mac_partial1_invert_crc_cnt_reg3_tx_mac_partial1_invert_crc_cnt {
      type oc-yang:counter64;
      description
        "Counts the number of transmitted packets with partial CRC type 1.";
    }
    leaf counter_slice11_ifg_mac_pool84_tx_mac_partial1_invert_crc_cnt_reg4_tx_mac_partial1_invert_crc_cnt {
      type oc-yang:counter64;
      description
        "Counts the number of transmitted packets with partial CRC type 1.";
    }
    leaf counter_slice11_ifg_mac_pool84_tx_mac_partial1_invert_crc_cnt_reg5_tx_mac_partial1_invert_crc_cnt {
      type oc-yang:counter64;
      description
        "Counts the number of transmitted packets with partial CRC type 1.";
    }
    leaf counter_slice11_ifg_mac_pool84_tx_mac_partial1_invert_crc_cnt_reg6_tx_mac_partial1_invert_crc_cnt {
      type oc-yang:counter64;
      description
        "Counts the number of transmitted packets with partial CRC type 1.";
    }
    leaf counter_slice11_ifg_mac_pool84_tx_mac_partial1_invert_crc_cnt_reg7_tx_mac_partial1_invert_crc_cnt {
      type oc-yang:counter64;
      description
        "Counts the number of transmitted packets with partial CRC type 1.";
    }
    leaf counter_slice11_ifg_mac_pool85_tx_mac_partial1_invert_crc_cnt_reg0_tx_mac_partial1_invert_crc_cnt {
      type oc-yang:counter64;
      description
        "Counts the number of transmitted packets with partial CRC type 1.";
    }
    leaf counter_slice11_ifg_mac_pool85_tx_mac_partial1_invert_crc_cnt_reg1_tx_mac_partial1_invert_crc_cnt {
      type oc-yang:counter64;
      description
        "Counts the number of transmitted packets with partial CRC type 1.";
    }
    leaf counter_slice11_ifg_mac_pool85_tx_mac_partial1_invert_crc_cnt_reg2_tx_mac_partial1_invert_crc_cnt {
      type oc-yang:counter64;
      description
        "Counts the number of transmitted packets with partial CRC type 1.";
    }
    leaf counter_slice11_ifg_mac_pool85_tx_mac_partial1_invert_crc_cnt_reg3_tx_mac_partial1_invert_crc_cnt {
      type oc-yang:counter64;
      description
        "Counts the number of transmitted packets with partial CRC type 1.";
    }
    leaf counter_slice11_ifg_mac_pool85_tx_mac_partial1_invert_crc_cnt_reg4_tx_mac_partial1_invert_crc_cnt {
      type oc-yang:counter64;
      description
        "Counts the number of transmitted packets with partial CRC type 1.";
    }
    leaf counter_slice11_ifg_mac_pool85_tx_mac_partial1_invert_crc_cnt_reg5_tx_mac_partial1_invert_crc_cnt {
      type oc-yang:counter64;
      description
        "Counts the number of transmitted packets with partial CRC type 1.";
    }
    leaf counter_slice11_ifg_mac_pool85_tx_mac_partial1_invert_crc_cnt_reg6_tx_mac_partial1_invert_crc_cnt {
      type oc-yang:counter64;
      description
        "Counts the number of transmitted packets with partial CRC type 1.";
    }
    leaf counter_slice11_ifg_mac_pool85_tx_mac_partial1_invert_crc_cnt_reg7_tx_mac_partial1_invert_crc_cnt {
      type oc-yang:counter64;
      description
        "Counts the number of transmitted packets with partial CRC type 1.";
    }
    leaf counter_slice11_ifg_mac_pool86_tx_mac_partial1_invert_crc_cnt_reg0_tx_mac_partial1_invert_crc_cnt {
      type oc-yang:counter64;
      description
        "Counts the number of transmitted packets with partial CRC type 1.";
    }
    leaf counter_slice11_ifg_mac_pool86_tx_mac_partial1_invert_crc_cnt_reg1_tx_mac_partial1_invert_crc_cnt {
      type oc-yang:counter64;
      description
        "Counts the number of transmitted packets with partial CRC type 1.";
    }
    leaf counter_slice11_ifg_mac_pool86_tx_mac_partial1_invert_crc_cnt_reg2_tx_mac_partial1_invert_crc_cnt {
      type oc-yang:counter64;
      description
        "Counts the number of transmitted packets with partial CRC type 1.";
    }
    leaf counter_slice11_ifg_mac_pool86_tx_mac_partial1_invert_crc_cnt_reg3_tx_mac_partial1_invert_crc_cnt {
      type oc-yang:counter64;
      description
        "Counts the number of transmitted packets with partial CRC type 1.";
    }
    leaf counter_slice11_ifg_mac_pool86_tx_mac_partial1_invert_crc_cnt_reg4_tx_mac_partial1_invert_crc_cnt {
      type oc-yang:counter64;
      description
        "Counts the number of transmitted packets with partial CRC type 1.";
    }
    leaf counter_slice11_ifg_mac_pool86_tx_mac_partial1_invert_crc_cnt_reg5_tx_mac_partial1_invert_crc_cnt {
      type oc-yang:counter64;
      description
        "Counts the number of transmitted packets with partial CRC type 1.";
    }
    leaf counter_slice11_ifg_mac_pool86_tx_mac_partial1_invert_crc_cnt_reg6_tx_mac_partial1_invert_crc_cnt {
      type oc-yang:counter64;
      description
        "Counts the number of transmitted packets with partial CRC type 1.";
    }
    leaf counter_slice11_ifg_mac_pool86_tx_mac_partial1_invert_crc_cnt_reg7_tx_mac_partial1_invert_crc_cnt {
      type oc-yang:counter64;
      description
        "Counts the number of transmitted packets with partial CRC type 1.";
    }
    leaf counter_slice11_ifg_mac_pool87_tx_mac_partial1_invert_crc_cnt_reg0_tx_mac_partial1_invert_crc_cnt {
      type oc-yang:counter64;
      description
        "Counts the number of transmitted packets with partial CRC type 1.";
    }
    leaf counter_slice11_ifg_mac_pool87_tx_mac_partial1_invert_crc_cnt_reg1_tx_mac_partial1_invert_crc_cnt {
      type oc-yang:counter64;
      description
        "Counts the number of transmitted packets with partial CRC type 1.";
    }
    leaf counter_slice11_ifg_mac_pool87_tx_mac_partial1_invert_crc_cnt_reg2_tx_mac_partial1_invert_crc_cnt {
      type oc-yang:counter64;
      description
        "Counts the number of transmitted packets with partial CRC type 1.";
    }
    leaf counter_slice11_ifg_mac_pool87_tx_mac_partial1_invert_crc_cnt_reg3_tx_mac_partial1_invert_crc_cnt {
      type oc-yang:counter64;
      description
        "Counts the number of transmitted packets with partial CRC type 1.";
    }
    leaf counter_slice11_ifg_mac_pool87_tx_mac_partial1_invert_crc_cnt_reg4_tx_mac_partial1_invert_crc_cnt {
      type oc-yang:counter64;
      description
        "Counts the number of transmitted packets with partial CRC type 1.";
    }
    leaf counter_slice11_ifg_mac_pool87_tx_mac_partial1_invert_crc_cnt_reg5_tx_mac_partial1_invert_crc_cnt {
      type oc-yang:counter64;
      description
        "Counts the number of transmitted packets with partial CRC type 1.";
    }
    leaf counter_slice11_ifg_mac_pool87_tx_mac_partial1_invert_crc_cnt_reg6_tx_mac_partial1_invert_crc_cnt {
      type oc-yang:counter64;
      description
        "Counts the number of transmitted packets with partial CRC type 1.";
    }
    leaf counter_slice11_ifg_mac_pool87_tx_mac_partial1_invert_crc_cnt_reg7_tx_mac_partial1_invert_crc_cnt {
      type oc-yang:counter64;
      description
        "Counts the number of transmitted packets with partial CRC type 1.";
    }
    leaf counter_slice12_ifg_mac_pool80_tx_mac_partial1_invert_crc_cnt_reg0_tx_mac_partial1_invert_crc_cnt {
      type oc-yang:counter64;
      description
        "Counts the number of transmitted packets with partial CRC type 1.";
    }
    leaf counter_slice12_ifg_mac_pool80_tx_mac_partial1_invert_crc_cnt_reg1_tx_mac_partial1_invert_crc_cnt {
      type oc-yang:counter64;
      description
        "Counts the number of transmitted packets with partial CRC type 1.";
    }
    leaf counter_slice12_ifg_mac_pool80_tx_mac_partial1_invert_crc_cnt_reg2_tx_mac_partial1_invert_crc_cnt {
      type oc-yang:counter64;
      description
        "Counts the number of transmitted packets with partial CRC type 1.";
    }
    leaf counter_slice12_ifg_mac_pool80_tx_mac_partial1_invert_crc_cnt_reg3_tx_mac_partial1_invert_crc_cnt {
      type oc-yang:counter64;
      description
        "Counts the number of transmitted packets with partial CRC type 1.";
    }
    leaf counter_slice12_ifg_mac_pool80_tx_mac_partial1_invert_crc_cnt_reg4_tx_mac_partial1_invert_crc_cnt {
      type oc-yang:counter64;
      description
        "Counts the number of transmitted packets with partial CRC type 1.";
    }
    leaf counter_slice12_ifg_mac_pool80_tx_mac_partial1_invert_crc_cnt_reg5_tx_mac_partial1_invert_crc_cnt {
      type oc-yang:counter64;
      description
        "Counts the number of transmitted packets with partial CRC type 1.";
    }
    leaf counter_slice12_ifg_mac_pool80_tx_mac_partial1_invert_crc_cnt_reg6_tx_mac_partial1_invert_crc_cnt {
      type oc-yang:counter64;
      description
        "Counts the number of transmitted packets with partial CRC type 1.";
    }
    leaf counter_slice12_ifg_mac_pool80_tx_mac_partial1_invert_crc_cnt_reg7_tx_mac_partial1_invert_crc_cnt {
      type oc-yang:counter64;
      description
        "Counts the number of transmitted packets with partial CRC type 1.";
    }
    leaf counter_slice12_ifg_mac_pool81_tx_mac_partial1_invert_crc_cnt_reg0_tx_mac_partial1_invert_crc_cnt {
      type oc-yang:counter64;
      description
        "Counts the number of transmitted packets with partial CRC type 1.";
    }
    leaf counter_slice12_ifg_mac_pool81_tx_mac_partial1_invert_crc_cnt_reg1_tx_mac_partial1_invert_crc_cnt {
      type oc-yang:counter64;
      description
        "Counts the number of transmitted packets with partial CRC type 1.";
    }
    leaf counter_slice12_ifg_mac_pool81_tx_mac_partial1_invert_crc_cnt_reg2_tx_mac_partial1_invert_crc_cnt {
      type oc-yang:counter64;
      description
        "Counts the number of transmitted packets with partial CRC type 1.";
    }
    leaf counter_slice12_ifg_mac_pool81_tx_mac_partial1_invert_crc_cnt_reg3_tx_mac_partial1_invert_crc_cnt {
      type oc-yang:counter64;
      description
        "Counts the number of transmitted packets with partial CRC type 1.";
    }
    leaf counter_slice12_ifg_mac_pool81_tx_mac_partial1_invert_crc_cnt_reg4_tx_mac_partial1_invert_crc_cnt {
      type oc-yang:counter64;
      description
        "Counts the number of transmitted packets with partial CRC type 1.";
    }
    leaf counter_slice12_ifg_mac_pool81_tx_mac_partial1_invert_crc_cnt_reg5_tx_mac_partial1_invert_crc_cnt {
      type oc-yang:counter64;
      description
        "Counts the number of transmitted packets with partial CRC type 1.";
    }
    leaf counter_slice12_ifg_mac_pool81_tx_mac_partial1_invert_crc_cnt_reg6_tx_mac_partial1_invert_crc_cnt {
      type oc-yang:counter64;
      description
        "Counts the number of transmitted packets with partial CRC type 1.";
    }
    leaf counter_slice12_ifg_mac_pool81_tx_mac_partial1_invert_crc_cnt_reg7_tx_mac_partial1_invert_crc_cnt {
      type oc-yang:counter64;
      description
        "Counts the number of transmitted packets with partial CRC type 1.";
    }
    leaf counter_slice12_ifg_mac_pool82_tx_mac_partial1_invert_crc_cnt_reg0_tx_mac_partial1_invert_crc_cnt {
      type oc-yang:counter64;
      description
        "Counts the number of transmitted packets with partial CRC type 1.";
    }
    leaf counter_slice12_ifg_mac_pool82_tx_mac_partial1_invert_crc_cnt_reg1_tx_mac_partial1_invert_crc_cnt {
      type oc-yang:counter64;
      description
        "Counts the number of transmitted packets with partial CRC type 1.";
    }
    leaf counter_slice12_ifg_mac_pool82_tx_mac_partial1_invert_crc_cnt_reg2_tx_mac_partial1_invert_crc_cnt {
      type oc-yang:counter64;
      description
        "Counts the number of transmitted packets with partial CRC type 1.";
    }
    leaf counter_slice12_ifg_mac_pool82_tx_mac_partial1_invert_crc_cnt_reg3_tx_mac_partial1_invert_crc_cnt {
      type oc-yang:counter64;
      description
        "Counts the number of transmitted packets with partial CRC type 1.";
    }
    leaf counter_slice12_ifg_mac_pool82_tx_mac_partial1_invert_crc_cnt_reg4_tx_mac_partial1_invert_crc_cnt {
      type oc-yang:counter64;
      description
        "Counts the number of transmitted packets with partial CRC type 1.";
    }
    leaf counter_slice12_ifg_mac_pool82_tx_mac_partial1_invert_crc_cnt_reg5_tx_mac_partial1_invert_crc_cnt {
      type oc-yang:counter64;
      description
        "Counts the number of transmitted packets with partial CRC type 1.";
    }
    leaf counter_slice12_ifg_mac_pool82_tx_mac_partial1_invert_crc_cnt_reg6_tx_mac_partial1_invert_crc_cnt {
      type oc-yang:counter64;
      description
        "Counts the number of transmitted packets with partial CRC type 1.";
    }
    leaf counter_slice12_ifg_mac_pool82_tx_mac_partial1_invert_crc_cnt_reg7_tx_mac_partial1_invert_crc_cnt {
      type oc-yang:counter64;
      description
        "Counts the number of transmitted packets with partial CRC type 1.";
    }
    leaf counter_slice12_ifg_mac_pool83_tx_mac_partial1_invert_crc_cnt_reg0_tx_mac_partial1_invert_crc_cnt {
      type oc-yang:counter64;
      description
        "Counts the number of transmitted packets with partial CRC type 1.";
    }
    leaf counter_slice12_ifg_mac_pool83_tx_mac_partial1_invert_crc_cnt_reg1_tx_mac_partial1_invert_crc_cnt {
      type oc-yang:counter64;
      description
        "Counts the number of transmitted packets with partial CRC type 1.";
    }
    leaf counter_slice12_ifg_mac_pool83_tx_mac_partial1_invert_crc_cnt_reg2_tx_mac_partial1_invert_crc_cnt {
      type oc-yang:counter64;
      description
        "Counts the number of transmitted packets with partial CRC type 1.";
    }
    leaf counter_slice12_ifg_mac_pool83_tx_mac_partial1_invert_crc_cnt_reg3_tx_mac_partial1_invert_crc_cnt {
      type oc-yang:counter64;
      description
        "Counts the number of transmitted packets with partial CRC type 1.";
    }
    leaf counter_slice12_ifg_mac_pool83_tx_mac_partial1_invert_crc_cnt_reg4_tx_mac_partial1_invert_crc_cnt {
      type oc-yang:counter64;
      description
        "Counts the number of transmitted packets with partial CRC type 1.";
    }
    leaf counter_slice12_ifg_mac_pool83_tx_mac_partial1_invert_crc_cnt_reg5_tx_mac_partial1_invert_crc_cnt {
      type oc-yang:counter64;
      description
        "Counts the number of transmitted packets with partial CRC type 1.";
    }
    leaf counter_slice12_ifg_mac_pool83_tx_mac_partial1_invert_crc_cnt_reg6_tx_mac_partial1_invert_crc_cnt {
      type oc-yang:counter64;
      description
        "Counts the number of transmitted packets with partial CRC type 1.";
    }
    leaf counter_slice12_ifg_mac_pool83_tx_mac_partial1_invert_crc_cnt_reg7_tx_mac_partial1_invert_crc_cnt {
      type oc-yang:counter64;
      description
        "Counts the number of transmitted packets with partial CRC type 1.";
    }
    leaf counter_slice12_ifg_mac_pool84_tx_mac_partial1_invert_crc_cnt_reg0_tx_mac_partial1_invert_crc_cnt {
      type oc-yang:counter64;
      description
        "Counts the number of transmitted packets with partial CRC type 1.";
    }
    leaf counter_slice12_ifg_mac_pool84_tx_mac_partial1_invert_crc_cnt_reg1_tx_mac_partial1_invert_crc_cnt {
      type oc-yang:counter64;
      description
        "Counts the number of transmitted packets with partial CRC type 1.";
    }
    leaf counter_slice12_ifg_mac_pool84_tx_mac_partial1_invert_crc_cnt_reg2_tx_mac_partial1_invert_crc_cnt {
      type oc-yang:counter64;
      description
        "Counts the number of transmitted packets with partial CRC type 1.";
    }
    leaf counter_slice12_ifg_mac_pool84_tx_mac_partial1_invert_crc_cnt_reg3_tx_mac_partial1_invert_crc_cnt {
      type oc-yang:counter64;
      description
        "Counts the number of transmitted packets with partial CRC type 1.";
    }
    leaf counter_slice12_ifg_mac_pool84_tx_mac_partial1_invert_crc_cnt_reg4_tx_mac_partial1_invert_crc_cnt {
      type oc-yang:counter64;
      description
        "Counts the number of transmitted packets with partial CRC type 1.";
    }
    leaf counter_slice12_ifg_mac_pool84_tx_mac_partial1_invert_crc_cnt_reg5_tx_mac_partial1_invert_crc_cnt {
      type oc-yang:counter64;
      description
        "Counts the number of transmitted packets with partial CRC type 1.";
    }
    leaf counter_slice12_ifg_mac_pool84_tx_mac_partial1_invert_crc_cnt_reg6_tx_mac_partial1_invert_crc_cnt {
      type oc-yang:counter64;
      description
        "Counts the number of transmitted packets with partial CRC type 1.";
    }
    leaf counter_slice12_ifg_mac_pool84_tx_mac_partial1_invert_crc_cnt_reg7_tx_mac_partial1_invert_crc_cnt {
      type oc-yang:counter64;
      description
        "Counts the number of transmitted packets with partial CRC type 1.";
    }
    leaf counter_slice12_ifg_mac_pool85_tx_mac_partial1_invert_crc_cnt_reg0_tx_mac_partial1_invert_crc_cnt {
      type oc-yang:counter64;
      description
        "Counts the number of transmitted packets with partial CRC type 1.";
    }
    leaf counter_slice12_ifg_mac_pool85_tx_mac_partial1_invert_crc_cnt_reg1_tx_mac_partial1_invert_crc_cnt {
      type oc-yang:counter64;
      description
        "Counts the number of transmitted packets with partial CRC type 1.";
    }
    leaf counter_slice12_ifg_mac_pool85_tx_mac_partial1_invert_crc_cnt_reg2_tx_mac_partial1_invert_crc_cnt {
      type oc-yang:counter64;
      description
        "Counts the number of transmitted packets with partial CRC type 1.";
    }
    leaf counter_slice12_ifg_mac_pool85_tx_mac_partial1_invert_crc_cnt_reg3_tx_mac_partial1_invert_crc_cnt {
      type oc-yang:counter64;
      description
        "Counts the number of transmitted packets with partial CRC type 1.";
    }
    leaf counter_slice12_ifg_mac_pool85_tx_mac_partial1_invert_crc_cnt_reg4_tx_mac_partial1_invert_crc_cnt {
      type oc-yang:counter64;
      description
        "Counts the number of transmitted packets with partial CRC type 1.";
    }
    leaf counter_slice12_ifg_mac_pool85_tx_mac_partial1_invert_crc_cnt_reg5_tx_mac_partial1_invert_crc_cnt {
      type oc-yang:counter64;
      description
        "Counts the number of transmitted packets with partial CRC type 1.";
    }
    leaf counter_slice12_ifg_mac_pool85_tx_mac_partial1_invert_crc_cnt_reg6_tx_mac_partial1_invert_crc_cnt {
      type oc-yang:counter64;
      description
        "Counts the number of transmitted packets with partial CRC type 1.";
    }
    leaf counter_slice12_ifg_mac_pool85_tx_mac_partial1_invert_crc_cnt_reg7_tx_mac_partial1_invert_crc_cnt {
      type oc-yang:counter64;
      description
        "Counts the number of transmitted packets with partial CRC type 1.";
    }
    leaf counter_slice12_ifg_mac_pool86_tx_mac_partial1_invert_crc_cnt_reg0_tx_mac_partial1_invert_crc_cnt {
      type oc-yang:counter64;
      description
        "Counts the number of transmitted packets with partial CRC type 1.";
    }
    leaf counter_slice12_ifg_mac_pool86_tx_mac_partial1_invert_crc_cnt_reg1_tx_mac_partial1_invert_crc_cnt {
      type oc-yang:counter64;
      description
        "Counts the number of transmitted packets with partial CRC type 1.";
    }
    leaf counter_slice12_ifg_mac_pool86_tx_mac_partial1_invert_crc_cnt_reg2_tx_mac_partial1_invert_crc_cnt {
      type oc-yang:counter64;
      description
        "Counts the number of transmitted packets with partial CRC type 1.";
    }
    leaf counter_slice12_ifg_mac_pool86_tx_mac_partial1_invert_crc_cnt_reg3_tx_mac_partial1_invert_crc_cnt {
      type oc-yang:counter64;
      description
        "Counts the number of transmitted packets with partial CRC type 1.";
    }
    leaf counter_slice12_ifg_mac_pool86_tx_mac_partial1_invert_crc_cnt_reg4_tx_mac_partial1_invert_crc_cnt {
      type oc-yang:counter64;
      description
        "Counts the number of transmitted packets with partial CRC type 1.";
    }
    leaf counter_slice12_ifg_mac_pool86_tx_mac_partial1_invert_crc_cnt_reg5_tx_mac_partial1_invert_crc_cnt {
      type oc-yang:counter64;
      description
        "Counts the number of transmitted packets with partial CRC type 1.";
    }
    leaf counter_slice12_ifg_mac_pool86_tx_mac_partial1_invert_crc_cnt_reg6_tx_mac_partial1_invert_crc_cnt {
      type oc-yang:counter64;
      description
        "Counts the number of transmitted packets with partial CRC type 1.";
    }
    leaf counter_slice12_ifg_mac_pool86_tx_mac_partial1_invert_crc_cnt_reg7_tx_mac_partial1_invert_crc_cnt {
      type oc-yang:counter64;
      description
        "Counts the number of transmitted packets with partial CRC type 1.";
    }
    leaf counter_slice12_ifg_mac_pool87_tx_mac_partial1_invert_crc_cnt_reg0_tx_mac_partial1_invert_crc_cnt {
      type oc-yang:counter64;
      description
        "Counts the number of transmitted packets with partial CRC type 1.";
    }
    leaf counter_slice12_ifg_mac_pool87_tx_mac_partial1_invert_crc_cnt_reg1_tx_mac_partial1_invert_crc_cnt {
      type oc-yang:counter64;
      description
        "Counts the number of transmitted packets with partial CRC type 1.";
    }
    leaf counter_slice12_ifg_mac_pool87_tx_mac_partial1_invert_crc_cnt_reg2_tx_mac_partial1_invert_crc_cnt {
      type oc-yang:counter64;
      description
        "Counts the number of transmitted packets with partial CRC type 1.";
    }
    leaf counter_slice12_ifg_mac_pool87_tx_mac_partial1_invert_crc_cnt_reg3_tx_mac_partial1_invert_crc_cnt {
      type oc-yang:counter64;
      description
        "Counts the number of transmitted packets with partial CRC type 1.";
    }
    leaf counter_slice12_ifg_mac_pool87_tx_mac_partial1_invert_crc_cnt_reg4_tx_mac_partial1_invert_crc_cnt {
      type oc-yang:counter64;
      description
        "Counts the number of transmitted packets with partial CRC type 1.";
    }
    leaf counter_slice12_ifg_mac_pool87_tx_mac_partial1_invert_crc_cnt_reg5_tx_mac_partial1_invert_crc_cnt {
      type oc-yang:counter64;
      description
        "Counts the number of transmitted packets with partial CRC type 1.";
    }
    leaf counter_slice12_ifg_mac_pool87_tx_mac_partial1_invert_crc_cnt_reg6_tx_mac_partial1_invert_crc_cnt {
      type oc-yang:counter64;
      description
        "Counts the number of transmitted packets with partial CRC type 1.";
    }
    leaf counter_slice12_ifg_mac_pool87_tx_mac_partial1_invert_crc_cnt_reg7_tx_mac_partial1_invert_crc_cnt {
      type oc-yang:counter64;
      description
        "Counts the number of transmitted packets with partial CRC type 1.";
    }
    leaf counter_slice13_ifg_mac_pool80_tx_mac_partial1_invert_crc_cnt_reg0_tx_mac_partial1_invert_crc_cnt {
      type oc-yang:counter64;
      description
        "Counts the number of transmitted packets with partial CRC type 1.";
    }
    leaf counter_slice13_ifg_mac_pool80_tx_mac_partial1_invert_crc_cnt_reg1_tx_mac_partial1_invert_crc_cnt {
      type oc-yang:counter64;
      description
        "Counts the number of transmitted packets with partial CRC type 1.";
    }
    leaf counter_slice13_ifg_mac_pool80_tx_mac_partial1_invert_crc_cnt_reg2_tx_mac_partial1_invert_crc_cnt {
      type oc-yang:counter64;
      description
        "Counts the number of transmitted packets with partial CRC type 1.";
    }
    leaf counter_slice13_ifg_mac_pool80_tx_mac_partial1_invert_crc_cnt_reg3_tx_mac_partial1_invert_crc_cnt {
      type oc-yang:counter64;
      description
        "Counts the number of transmitted packets with partial CRC type 1.";
    }
    leaf counter_slice13_ifg_mac_pool80_tx_mac_partial1_invert_crc_cnt_reg4_tx_mac_partial1_invert_crc_cnt {
      type oc-yang:counter64;
      description
        "Counts the number of transmitted packets with partial CRC type 1.";
    }
    leaf counter_slice13_ifg_mac_pool80_tx_mac_partial1_invert_crc_cnt_reg5_tx_mac_partial1_invert_crc_cnt {
      type oc-yang:counter64;
      description
        "Counts the number of transmitted packets with partial CRC type 1.";
    }
    leaf counter_slice13_ifg_mac_pool80_tx_mac_partial1_invert_crc_cnt_reg6_tx_mac_partial1_invert_crc_cnt {
      type oc-yang:counter64;
      description
        "Counts the number of transmitted packets with partial CRC type 1.";
    }
    leaf counter_slice13_ifg_mac_pool80_tx_mac_partial1_invert_crc_cnt_reg7_tx_mac_partial1_invert_crc_cnt {
      type oc-yang:counter64;
      description
        "Counts the number of transmitted packets with partial CRC type 1.";
    }
    leaf counter_slice13_ifg_mac_pool81_tx_mac_partial1_invert_crc_cnt_reg0_tx_mac_partial1_invert_crc_cnt {
      type oc-yang:counter64;
      description
        "Counts the number of transmitted packets with partial CRC type 1.";
    }
    leaf counter_slice13_ifg_mac_pool81_tx_mac_partial1_invert_crc_cnt_reg1_tx_mac_partial1_invert_crc_cnt {
      type oc-yang:counter64;
      description
        "Counts the number of transmitted packets with partial CRC type 1.";
    }
    leaf counter_slice13_ifg_mac_pool81_tx_mac_partial1_invert_crc_cnt_reg2_tx_mac_partial1_invert_crc_cnt {
      type oc-yang:counter64;
      description
        "Counts the number of transmitted packets with partial CRC type 1.";
    }
    leaf counter_slice13_ifg_mac_pool81_tx_mac_partial1_invert_crc_cnt_reg3_tx_mac_partial1_invert_crc_cnt {
      type oc-yang:counter64;
      description
        "Counts the number of transmitted packets with partial CRC type 1.";
    }
    leaf counter_slice13_ifg_mac_pool81_tx_mac_partial1_invert_crc_cnt_reg4_tx_mac_partial1_invert_crc_cnt {
      type oc-yang:counter64;
      description
        "Counts the number of transmitted packets with partial CRC type 1.";
    }
    leaf counter_slice13_ifg_mac_pool81_tx_mac_partial1_invert_crc_cnt_reg5_tx_mac_partial1_invert_crc_cnt {
      type oc-yang:counter64;
      description
        "Counts the number of transmitted packets with partial CRC type 1.";
    }
    leaf counter_slice13_ifg_mac_pool81_tx_mac_partial1_invert_crc_cnt_reg6_tx_mac_partial1_invert_crc_cnt {
      type oc-yang:counter64;
      description
        "Counts the number of transmitted packets with partial CRC type 1.";
    }
    leaf counter_slice13_ifg_mac_pool81_tx_mac_partial1_invert_crc_cnt_reg7_tx_mac_partial1_invert_crc_cnt {
      type oc-yang:counter64;
      description
        "Counts the number of transmitted packets with partial CRC type 1.";
    }
    leaf counter_slice13_ifg_mac_pool82_tx_mac_partial1_invert_crc_cnt_reg0_tx_mac_partial1_invert_crc_cnt {
      type oc-yang:counter64;
      description
        "Counts the number of transmitted packets with partial CRC type 1.";
    }
    leaf counter_slice13_ifg_mac_pool82_tx_mac_partial1_invert_crc_cnt_reg1_tx_mac_partial1_invert_crc_cnt {
      type oc-yang:counter64;
      description
        "Counts the number of transmitted packets with partial CRC type 1.";
    }
    leaf counter_slice13_ifg_mac_pool82_tx_mac_partial1_invert_crc_cnt_reg2_tx_mac_partial1_invert_crc_cnt {
      type oc-yang:counter64;
      description
        "Counts the number of transmitted packets with partial CRC type 1.";
    }
    leaf counter_slice13_ifg_mac_pool82_tx_mac_partial1_invert_crc_cnt_reg3_tx_mac_partial1_invert_crc_cnt {
      type oc-yang:counter64;
      description
        "Counts the number of transmitted packets with partial CRC type 1.";
    }
    leaf counter_slice13_ifg_mac_pool82_tx_mac_partial1_invert_crc_cnt_reg4_tx_mac_partial1_invert_crc_cnt {
      type oc-yang:counter64;
      description
        "Counts the number of transmitted packets with partial CRC type 1.";
    }
    leaf counter_slice13_ifg_mac_pool82_tx_mac_partial1_invert_crc_cnt_reg5_tx_mac_partial1_invert_crc_cnt {
      type oc-yang:counter64;
      description
        "Counts the number of transmitted packets with partial CRC type 1.";
    }
    leaf counter_slice13_ifg_mac_pool82_tx_mac_partial1_invert_crc_cnt_reg6_tx_mac_partial1_invert_crc_cnt {
      type oc-yang:counter64;
      description
        "Counts the number of transmitted packets with partial CRC type 1.";
    }
    leaf counter_slice13_ifg_mac_pool82_tx_mac_partial1_invert_crc_cnt_reg7_tx_mac_partial1_invert_crc_cnt {
      type oc-yang:counter64;
      description
        "Counts the number of transmitted packets with partial CRC type 1.";
    }
    leaf counter_slice13_ifg_mac_pool83_tx_mac_partial1_invert_crc_cnt_reg0_tx_mac_partial1_invert_crc_cnt {
      type oc-yang:counter64;
      description
        "Counts the number of transmitted packets with partial CRC type 1.";
    }
    leaf counter_slice13_ifg_mac_pool83_tx_mac_partial1_invert_crc_cnt_reg1_tx_mac_partial1_invert_crc_cnt {
      type oc-yang:counter64;
      description
        "Counts the number of transmitted packets with partial CRC type 1.";
    }
    leaf counter_slice13_ifg_mac_pool83_tx_mac_partial1_invert_crc_cnt_reg2_tx_mac_partial1_invert_crc_cnt {
      type oc-yang:counter64;
      description
        "Counts the number of transmitted packets with partial CRC type 1.";
    }
    leaf counter_slice13_ifg_mac_pool83_tx_mac_partial1_invert_crc_cnt_reg3_tx_mac_partial1_invert_crc_cnt {
      type oc-yang:counter64;
      description
        "Counts the number of transmitted packets with partial CRC type 1.";
    }
    leaf counter_slice13_ifg_mac_pool83_tx_mac_partial1_invert_crc_cnt_reg4_tx_mac_partial1_invert_crc_cnt {
      type oc-yang:counter64;
      description
        "Counts the number of transmitted packets with partial CRC type 1.";
    }
    leaf counter_slice13_ifg_mac_pool83_tx_mac_partial1_invert_crc_cnt_reg5_tx_mac_partial1_invert_crc_cnt {
      type oc-yang:counter64;
      description
        "Counts the number of transmitted packets with partial CRC type 1.";
    }
    leaf counter_slice13_ifg_mac_pool83_tx_mac_partial1_invert_crc_cnt_reg6_tx_mac_partial1_invert_crc_cnt {
      type oc-yang:counter64;
      description
        "Counts the number of transmitted packets with partial CRC type 1.";
    }
    leaf counter_slice13_ifg_mac_pool83_tx_mac_partial1_invert_crc_cnt_reg7_tx_mac_partial1_invert_crc_cnt {
      type oc-yang:counter64;
      description
        "Counts the number of transmitted packets with partial CRC type 1.";
    }
    leaf counter_slice13_ifg_mac_pool84_tx_mac_partial1_invert_crc_cnt_reg0_tx_mac_partial1_invert_crc_cnt {
      type oc-yang:counter64;
      description
        "Counts the number of transmitted packets with partial CRC type 1.";
    }
    leaf counter_slice13_ifg_mac_pool84_tx_mac_partial1_invert_crc_cnt_reg1_tx_mac_partial1_invert_crc_cnt {
      type oc-yang:counter64;
      description
        "Counts the number of transmitted packets with partial CRC type 1.";
    }
    leaf counter_slice13_ifg_mac_pool84_tx_mac_partial1_invert_crc_cnt_reg2_tx_mac_partial1_invert_crc_cnt {
      type oc-yang:counter64;
      description
        "Counts the number of transmitted packets with partial CRC type 1.";
    }
    leaf counter_slice13_ifg_mac_pool84_tx_mac_partial1_invert_crc_cnt_reg3_tx_mac_partial1_invert_crc_cnt {
      type oc-yang:counter64;
      description
        "Counts the number of transmitted packets with partial CRC type 1.";
    }
    leaf counter_slice13_ifg_mac_pool84_tx_mac_partial1_invert_crc_cnt_reg4_tx_mac_partial1_invert_crc_cnt {
      type oc-yang:counter64;
      description
        "Counts the number of transmitted packets with partial CRC type 1.";
    }
    leaf counter_slice13_ifg_mac_pool84_tx_mac_partial1_invert_crc_cnt_reg5_tx_mac_partial1_invert_crc_cnt {
      type oc-yang:counter64;
      description
        "Counts the number of transmitted packets with partial CRC type 1.";
    }
    leaf counter_slice13_ifg_mac_pool84_tx_mac_partial1_invert_crc_cnt_reg6_tx_mac_partial1_invert_crc_cnt {
      type oc-yang:counter64;
      description
        "Counts the number of transmitted packets with partial CRC type 1.";
    }
    leaf counter_slice13_ifg_mac_pool84_tx_mac_partial1_invert_crc_cnt_reg7_tx_mac_partial1_invert_crc_cnt {
      type oc-yang:counter64;
      description
        "Counts the number of transmitted packets with partial CRC type 1.";
    }
    leaf counter_slice13_ifg_mac_pool85_tx_mac_partial1_invert_crc_cnt_reg0_tx_mac_partial1_invert_crc_cnt {
      type oc-yang:counter64;
      description
        "Counts the number of transmitted packets with partial CRC type 1.";
    }
    leaf counter_slice13_ifg_mac_pool85_tx_mac_partial1_invert_crc_cnt_reg1_tx_mac_partial1_invert_crc_cnt {
      type oc-yang:counter64;
      description
        "Counts the number of transmitted packets with partial CRC type 1.";
    }
    leaf counter_slice13_ifg_mac_pool85_tx_mac_partial1_invert_crc_cnt_reg2_tx_mac_partial1_invert_crc_cnt {
      type oc-yang:counter64;
      description
        "Counts the number of transmitted packets with partial CRC type 1.";
    }
    leaf counter_slice13_ifg_mac_pool85_tx_mac_partial1_invert_crc_cnt_reg3_tx_mac_partial1_invert_crc_cnt {
      type oc-yang:counter64;
      description
        "Counts the number of transmitted packets with partial CRC type 1.";
    }
    leaf counter_slice13_ifg_mac_pool85_tx_mac_partial1_invert_crc_cnt_reg4_tx_mac_partial1_invert_crc_cnt {
      type oc-yang:counter64;
      description
        "Counts the number of transmitted packets with partial CRC type 1.";
    }
    leaf counter_slice13_ifg_mac_pool85_tx_mac_partial1_invert_crc_cnt_reg5_tx_mac_partial1_invert_crc_cnt {
      type oc-yang:counter64;
      description
        "Counts the number of transmitted packets with partial CRC type 1.";
    }
    leaf counter_slice13_ifg_mac_pool85_tx_mac_partial1_invert_crc_cnt_reg6_tx_mac_partial1_invert_crc_cnt {
      type oc-yang:counter64;
      description
        "Counts the number of transmitted packets with partial CRC type 1.";
    }
    leaf counter_slice13_ifg_mac_pool85_tx_mac_partial1_invert_crc_cnt_reg7_tx_mac_partial1_invert_crc_cnt {
      type oc-yang:counter64;
      description
        "Counts the number of transmitted packets with partial CRC type 1.";
    }
    leaf counter_slice13_ifg_mac_pool86_tx_mac_partial1_invert_crc_cnt_reg0_tx_mac_partial1_invert_crc_cnt {
      type oc-yang:counter64;
      description
        "Counts the number of transmitted packets with partial CRC type 1.";
    }
    leaf counter_slice13_ifg_mac_pool86_tx_mac_partial1_invert_crc_cnt_reg1_tx_mac_partial1_invert_crc_cnt {
      type oc-yang:counter64;
      description
        "Counts the number of transmitted packets with partial CRC type 1.";
    }
    leaf counter_slice13_ifg_mac_pool86_tx_mac_partial1_invert_crc_cnt_reg2_tx_mac_partial1_invert_crc_cnt {
      type oc-yang:counter64;
      description
        "Counts the number of transmitted packets with partial CRC type 1.";
    }
    leaf counter_slice13_ifg_mac_pool86_tx_mac_partial1_invert_crc_cnt_reg3_tx_mac_partial1_invert_crc_cnt {
      type oc-yang:counter64;
      description
        "Counts the number of transmitted packets with partial CRC type 1.";
    }
    leaf counter_slice13_ifg_mac_pool86_tx_mac_partial1_invert_crc_cnt_reg4_tx_mac_partial1_invert_crc_cnt {
      type oc-yang:counter64;
      description
        "Counts the number of transmitted packets with partial CRC type 1.";
    }
    leaf counter_slice13_ifg_mac_pool86_tx_mac_partial1_invert_crc_cnt_reg5_tx_mac_partial1_invert_crc_cnt {
      type oc-yang:counter64;
      description
        "Counts the number of transmitted packets with partial CRC type 1.";
    }
    leaf counter_slice13_ifg_mac_pool86_tx_mac_partial1_invert_crc_cnt_reg6_tx_mac_partial1_invert_crc_cnt {
      type oc-yang:counter64;
      description
        "Counts the number of transmitted packets with partial CRC type 1.";
    }
    leaf counter_slice13_ifg_mac_pool86_tx_mac_partial1_invert_crc_cnt_reg7_tx_mac_partial1_invert_crc_cnt {
      type oc-yang:counter64;
      description
        "Counts the number of transmitted packets with partial CRC type 1.";
    }
    leaf counter_slice13_ifg_mac_pool87_tx_mac_partial1_invert_crc_cnt_reg0_tx_mac_partial1_invert_crc_cnt {
      type oc-yang:counter64;
      description
        "Counts the number of transmitted packets with partial CRC type 1.";
    }
    leaf counter_slice13_ifg_mac_pool87_tx_mac_partial1_invert_crc_cnt_reg1_tx_mac_partial1_invert_crc_cnt {
      type oc-yang:counter64;
      description
        "Counts the number of transmitted packets with partial CRC type 1.";
    }
    leaf counter_slice13_ifg_mac_pool87_tx_mac_partial1_invert_crc_cnt_reg2_tx_mac_partial1_invert_crc_cnt {
      type oc-yang:counter64;
      description
        "Counts the number of transmitted packets with partial CRC type 1.";
    }
    leaf counter_slice13_ifg_mac_pool87_tx_mac_partial1_invert_crc_cnt_reg3_tx_mac_partial1_invert_crc_cnt {
      type oc-yang:counter64;
      description
        "Counts the number of transmitted packets with partial CRC type 1.";
    }
    leaf counter_slice13_ifg_mac_pool87_tx_mac_partial1_invert_crc_cnt_reg4_tx_mac_partial1_invert_crc_cnt {
      type oc-yang:counter64;
      description
        "Counts the number of transmitted packets with partial CRC type 1.";
    }
    leaf counter_slice13_ifg_mac_pool87_tx_mac_partial1_invert_crc_cnt_reg5_tx_mac_partial1_invert_crc_cnt {
      type oc-yang:counter64;
      description
        "Counts the number of transmitted packets with partial CRC type 1.";
    }
    leaf counter_slice13_ifg_mac_pool87_tx_mac_partial1_invert_crc_cnt_reg6_tx_mac_partial1_invert_crc_cnt {
      type oc-yang:counter64;
      description
        "Counts the number of transmitted packets with partial CRC type 1.";
    }
    leaf counter_slice13_ifg_mac_pool87_tx_mac_partial1_invert_crc_cnt_reg7_tx_mac_partial1_invert_crc_cnt {
      type oc-yang:counter64;
      description
        "Counts the number of transmitted packets with partial CRC type 1.";
    }
    leaf counter_slice14_ifg_mac_pool80_tx_mac_partial1_invert_crc_cnt_reg0_tx_mac_partial1_invert_crc_cnt {
      type oc-yang:counter64;
      description
        "Counts the number of transmitted packets with partial CRC type 1.";
    }
    leaf counter_slice14_ifg_mac_pool80_tx_mac_partial1_invert_crc_cnt_reg1_tx_mac_partial1_invert_crc_cnt {
      type oc-yang:counter64;
      description
        "Counts the number of transmitted packets with partial CRC type 1.";
    }
    leaf counter_slice14_ifg_mac_pool80_tx_mac_partial1_invert_crc_cnt_reg2_tx_mac_partial1_invert_crc_cnt {
      type oc-yang:counter64;
      description
        "Counts the number of transmitted packets with partial CRC type 1.";
    }
    leaf counter_slice14_ifg_mac_pool80_tx_mac_partial1_invert_crc_cnt_reg3_tx_mac_partial1_invert_crc_cnt {
      type oc-yang:counter64;
      description
        "Counts the number of transmitted packets with partial CRC type 1.";
    }
    leaf counter_slice14_ifg_mac_pool80_tx_mac_partial1_invert_crc_cnt_reg4_tx_mac_partial1_invert_crc_cnt {
      type oc-yang:counter64;
      description
        "Counts the number of transmitted packets with partial CRC type 1.";
    }
    leaf counter_slice14_ifg_mac_pool80_tx_mac_partial1_invert_crc_cnt_reg5_tx_mac_partial1_invert_crc_cnt {
      type oc-yang:counter64;
      description
        "Counts the number of transmitted packets with partial CRC type 1.";
    }
    leaf counter_slice14_ifg_mac_pool80_tx_mac_partial1_invert_crc_cnt_reg6_tx_mac_partial1_invert_crc_cnt {
      type oc-yang:counter64;
      description
        "Counts the number of transmitted packets with partial CRC type 1.";
    }
    leaf counter_slice14_ifg_mac_pool80_tx_mac_partial1_invert_crc_cnt_reg7_tx_mac_partial1_invert_crc_cnt {
      type oc-yang:counter64;
      description
        "Counts the number of transmitted packets with partial CRC type 1.";
    }
    leaf counter_slice14_ifg_mac_pool81_tx_mac_partial1_invert_crc_cnt_reg0_tx_mac_partial1_invert_crc_cnt {
      type oc-yang:counter64;
      description
        "Counts the number of transmitted packets with partial CRC type 1.";
    }
    leaf counter_slice14_ifg_mac_pool81_tx_mac_partial1_invert_crc_cnt_reg1_tx_mac_partial1_invert_crc_cnt {
      type oc-yang:counter64;
      description
        "Counts the number of transmitted packets with partial CRC type 1.";
    }
    leaf counter_slice14_ifg_mac_pool81_tx_mac_partial1_invert_crc_cnt_reg2_tx_mac_partial1_invert_crc_cnt {
      type oc-yang:counter64;
      description
        "Counts the number of transmitted packets with partial CRC type 1.";
    }
    leaf counter_slice14_ifg_mac_pool81_tx_mac_partial1_invert_crc_cnt_reg3_tx_mac_partial1_invert_crc_cnt {
      type oc-yang:counter64;
      description
        "Counts the number of transmitted packets with partial CRC type 1.";
    }
    leaf counter_slice14_ifg_mac_pool81_tx_mac_partial1_invert_crc_cnt_reg4_tx_mac_partial1_invert_crc_cnt {
      type oc-yang:counter64;
      description
        "Counts the number of transmitted packets with partial CRC type 1.";
    }
    leaf counter_slice14_ifg_mac_pool81_tx_mac_partial1_invert_crc_cnt_reg5_tx_mac_partial1_invert_crc_cnt {
      type oc-yang:counter64;
      description
        "Counts the number of transmitted packets with partial CRC type 1.";
    }
    leaf counter_slice14_ifg_mac_pool81_tx_mac_partial1_invert_crc_cnt_reg6_tx_mac_partial1_invert_crc_cnt {
      type oc-yang:counter64;
      description
        "Counts the number of transmitted packets with partial CRC type 1.";
    }
    leaf counter_slice14_ifg_mac_pool81_tx_mac_partial1_invert_crc_cnt_reg7_tx_mac_partial1_invert_crc_cnt {
      type oc-yang:counter64;
      description
        "Counts the number of transmitted packets with partial CRC type 1.";
    }
    leaf counter_slice14_ifg_mac_pool82_tx_mac_partial1_invert_crc_cnt_reg0_tx_mac_partial1_invert_crc_cnt {
      type oc-yang:counter64;
      description
        "Counts the number of transmitted packets with partial CRC type 1.";
    }
    leaf counter_slice14_ifg_mac_pool82_tx_mac_partial1_invert_crc_cnt_reg1_tx_mac_partial1_invert_crc_cnt {
      type oc-yang:counter64;
      description
        "Counts the number of transmitted packets with partial CRC type 1.";
    }
    leaf counter_slice14_ifg_mac_pool82_tx_mac_partial1_invert_crc_cnt_reg2_tx_mac_partial1_invert_crc_cnt {
      type oc-yang:counter64;
      description
        "Counts the number of transmitted packets with partial CRC type 1.";
    }
    leaf counter_slice14_ifg_mac_pool82_tx_mac_partial1_invert_crc_cnt_reg3_tx_mac_partial1_invert_crc_cnt {
      type oc-yang:counter64;
      description
        "Counts the number of transmitted packets with partial CRC type 1.";
    }
    leaf counter_slice14_ifg_mac_pool82_tx_mac_partial1_invert_crc_cnt_reg4_tx_mac_partial1_invert_crc_cnt {
      type oc-yang:counter64;
      description
        "Counts the number of transmitted packets with partial CRC type 1.";
    }
    leaf counter_slice14_ifg_mac_pool82_tx_mac_partial1_invert_crc_cnt_reg5_tx_mac_partial1_invert_crc_cnt {
      type oc-yang:counter64;
      description
        "Counts the number of transmitted packets with partial CRC type 1.";
    }
    leaf counter_slice14_ifg_mac_pool82_tx_mac_partial1_invert_crc_cnt_reg6_tx_mac_partial1_invert_crc_cnt {
      type oc-yang:counter64;
      description
        "Counts the number of transmitted packets with partial CRC type 1.";
    }
    leaf counter_slice14_ifg_mac_pool82_tx_mac_partial1_invert_crc_cnt_reg7_tx_mac_partial1_invert_crc_cnt {
      type oc-yang:counter64;
      description
        "Counts the number of transmitted packets with partial CRC type 1.";
    }
    leaf counter_slice14_ifg_mac_pool83_tx_mac_partial1_invert_crc_cnt_reg0_tx_mac_partial1_invert_crc_cnt {
      type oc-yang:counter64;
      description
        "Counts the number of transmitted packets with partial CRC type 1.";
    }
    leaf counter_slice14_ifg_mac_pool83_tx_mac_partial1_invert_crc_cnt_reg1_tx_mac_partial1_invert_crc_cnt {
      type oc-yang:counter64;
      description
        "Counts the number of transmitted packets with partial CRC type 1.";
    }
    leaf counter_slice14_ifg_mac_pool83_tx_mac_partial1_invert_crc_cnt_reg2_tx_mac_partial1_invert_crc_cnt {
      type oc-yang:counter64;
      description
        "Counts the number of transmitted packets with partial CRC type 1.";
    }
    leaf counter_slice14_ifg_mac_pool83_tx_mac_partial1_invert_crc_cnt_reg3_tx_mac_partial1_invert_crc_cnt {
      type oc-yang:counter64;
      description
        "Counts the number of transmitted packets with partial CRC type 1.";
    }
    leaf counter_slice14_ifg_mac_pool83_tx_mac_partial1_invert_crc_cnt_reg4_tx_mac_partial1_invert_crc_cnt {
      type oc-yang:counter64;
      description
        "Counts the number of transmitted packets with partial CRC type 1.";
    }
    leaf counter_slice14_ifg_mac_pool83_tx_mac_partial1_invert_crc_cnt_reg5_tx_mac_partial1_invert_crc_cnt {
      type oc-yang:counter64;
      description
        "Counts the number of transmitted packets with partial CRC type 1.";
    }
    leaf counter_slice14_ifg_mac_pool83_tx_mac_partial1_invert_crc_cnt_reg6_tx_mac_partial1_invert_crc_cnt {
      type oc-yang:counter64;
      description
        "Counts the number of transmitted packets with partial CRC type 1.";
    }
    leaf counter_slice14_ifg_mac_pool83_tx_mac_partial1_invert_crc_cnt_reg7_tx_mac_partial1_invert_crc_cnt {
      type oc-yang:counter64;
      description
        "Counts the number of transmitted packets with partial CRC type 1.";
    }
    leaf counter_slice14_ifg_mac_pool84_tx_mac_partial1_invert_crc_cnt_reg0_tx_mac_partial1_invert_crc_cnt {
      type oc-yang:counter64;
      description
        "Counts the number of transmitted packets with partial CRC type 1.";
    }
    leaf counter_slice14_ifg_mac_pool84_tx_mac_partial1_invert_crc_cnt_reg1_tx_mac_partial1_invert_crc_cnt {
      type oc-yang:counter64;
      description
        "Counts the number of transmitted packets with partial CRC type 1.";
    }
    leaf counter_slice14_ifg_mac_pool84_tx_mac_partial1_invert_crc_cnt_reg2_tx_mac_partial1_invert_crc_cnt {
      type oc-yang:counter64;
      description
        "Counts the number of transmitted packets with partial CRC type 1.";
    }
    leaf counter_slice14_ifg_mac_pool84_tx_mac_partial1_invert_crc_cnt_reg3_tx_mac_partial1_invert_crc_cnt {
      type oc-yang:counter64;
      description
        "Counts the number of transmitted packets with partial CRC type 1.";
    }
    leaf counter_slice14_ifg_mac_pool84_tx_mac_partial1_invert_crc_cnt_reg4_tx_mac_partial1_invert_crc_cnt {
      type oc-yang:counter64;
      description
        "Counts the number of transmitted packets with partial CRC type 1.";
    }
    leaf counter_slice14_ifg_mac_pool84_tx_mac_partial1_invert_crc_cnt_reg5_tx_mac_partial1_invert_crc_cnt {
      type oc-yang:counter64;
      description
        "Counts the number of transmitted packets with partial CRC type 1.";
    }
    leaf counter_slice14_ifg_mac_pool84_tx_mac_partial1_invert_crc_cnt_reg6_tx_mac_partial1_invert_crc_cnt {
      type oc-yang:counter64;
      description
        "Counts the number of transmitted packets with partial CRC type 1.";
    }
    leaf counter_slice14_ifg_mac_pool84_tx_mac_partial1_invert_crc_cnt_reg7_tx_mac_partial1_invert_crc_cnt {
      type oc-yang:counter64;
      description
        "Counts the number of transmitted packets with partial CRC type 1.";
    }
    leaf counter_slice14_ifg_mac_pool85_tx_mac_partial1_invert_crc_cnt_reg0_tx_mac_partial1_invert_crc_cnt {
      type oc-yang:counter64;
      description
        "Counts the number of transmitted packets with partial CRC type 1.";
    }
    leaf counter_slice14_ifg_mac_pool85_tx_mac_partial1_invert_crc_cnt_reg1_tx_mac_partial1_invert_crc_cnt {
      type oc-yang:counter64;
      description
        "Counts the number of transmitted packets with partial CRC type 1.";
    }
    leaf counter_slice14_ifg_mac_pool85_tx_mac_partial1_invert_crc_cnt_reg2_tx_mac_partial1_invert_crc_cnt {
      type oc-yang:counter64;
      description
        "Counts the number of transmitted packets with partial CRC type 1.";
    }
    leaf counter_slice14_ifg_mac_pool85_tx_mac_partial1_invert_crc_cnt_reg3_tx_mac_partial1_invert_crc_cnt {
      type oc-yang:counter64;
      description
        "Counts the number of transmitted packets with partial CRC type 1.";
    }
    leaf counter_slice14_ifg_mac_pool85_tx_mac_partial1_invert_crc_cnt_reg4_tx_mac_partial1_invert_crc_cnt {
      type oc-yang:counter64;
      description
        "Counts the number of transmitted packets with partial CRC type 1.";
    }
    leaf counter_slice14_ifg_mac_pool85_tx_mac_partial1_invert_crc_cnt_reg5_tx_mac_partial1_invert_crc_cnt {
      type oc-yang:counter64;
      description
        "Counts the number of transmitted packets with partial CRC type 1.";
    }
    leaf counter_slice14_ifg_mac_pool85_tx_mac_partial1_invert_crc_cnt_reg6_tx_mac_partial1_invert_crc_cnt {
      type oc-yang:counter64;
      description
        "Counts the number of transmitted packets with partial CRC type 1.";
    }
    leaf counter_slice14_ifg_mac_pool85_tx_mac_partial1_invert_crc_cnt_reg7_tx_mac_partial1_invert_crc_cnt {
      type oc-yang:counter64;
      description
        "Counts the number of transmitted packets with partial CRC type 1.";
    }
    leaf counter_slice14_ifg_mac_pool86_tx_mac_partial1_invert_crc_cnt_reg0_tx_mac_partial1_invert_crc_cnt {
      type oc-yang:counter64;
      description
        "Counts the number of transmitted packets with partial CRC type 1.";
    }
    leaf counter_slice14_ifg_mac_pool86_tx_mac_partial1_invert_crc_cnt_reg1_tx_mac_partial1_invert_crc_cnt {
      type oc-yang:counter64;
      description
        "Counts the number of transmitted packets with partial CRC type 1.";
    }
    leaf counter_slice14_ifg_mac_pool86_tx_mac_partial1_invert_crc_cnt_reg2_tx_mac_partial1_invert_crc_cnt {
      type oc-yang:counter64;
      description
        "Counts the number of transmitted packets with partial CRC type 1.";
    }
    leaf counter_slice14_ifg_mac_pool86_tx_mac_partial1_invert_crc_cnt_reg3_tx_mac_partial1_invert_crc_cnt {
      type oc-yang:counter64;
      description
        "Counts the number of transmitted packets with partial CRC type 1.";
    }
    leaf counter_slice14_ifg_mac_pool86_tx_mac_partial1_invert_crc_cnt_reg4_tx_mac_partial1_invert_crc_cnt {
      type oc-yang:counter64;
      description
        "Counts the number of transmitted packets with partial CRC type 1.";
    }
    leaf counter_slice14_ifg_mac_pool86_tx_mac_partial1_invert_crc_cnt_reg5_tx_mac_partial1_invert_crc_cnt {
      type oc-yang:counter64;
      description
        "Counts the number of transmitted packets with partial CRC type 1.";
    }
    leaf counter_slice14_ifg_mac_pool86_tx_mac_partial1_invert_crc_cnt_reg6_tx_mac_partial1_invert_crc_cnt {
      type oc-yang:counter64;
      description
        "Counts the number of transmitted packets with partial CRC type 1.";
    }
    leaf counter_slice14_ifg_mac_pool86_tx_mac_partial1_invert_crc_cnt_reg7_tx_mac_partial1_invert_crc_cnt {
      type oc-yang:counter64;
      description
        "Counts the number of transmitted packets with partial CRC type 1.";
    }
    leaf counter_slice14_ifg_mac_pool87_tx_mac_partial1_invert_crc_cnt_reg0_tx_mac_partial1_invert_crc_cnt {
      type oc-yang:counter64;
      description
        "Counts the number of transmitted packets with partial CRC type 1.";
    }
    leaf counter_slice14_ifg_mac_pool87_tx_mac_partial1_invert_crc_cnt_reg1_tx_mac_partial1_invert_crc_cnt {
      type oc-yang:counter64;
      description
        "Counts the number of transmitted packets with partial CRC type 1.";
    }
    leaf counter_slice14_ifg_mac_pool87_tx_mac_partial1_invert_crc_cnt_reg2_tx_mac_partial1_invert_crc_cnt {
      type oc-yang:counter64;
      description
        "Counts the number of transmitted packets with partial CRC type 1.";
    }
    leaf counter_slice14_ifg_mac_pool87_tx_mac_partial1_invert_crc_cnt_reg3_tx_mac_partial1_invert_crc_cnt {
      type oc-yang:counter64;
      description
        "Counts the number of transmitted packets with partial CRC type 1.";
    }
    leaf counter_slice14_ifg_mac_pool87_tx_mac_partial1_invert_crc_cnt_reg4_tx_mac_partial1_invert_crc_cnt {
      type oc-yang:counter64;
      description
        "Counts the number of transmitted packets with partial CRC type 1.";
    }
    leaf counter_slice14_ifg_mac_pool87_tx_mac_partial1_invert_crc_cnt_reg5_tx_mac_partial1_invert_crc_cnt {
      type oc-yang:counter64;
      description
        "Counts the number of transmitted packets with partial CRC type 1.";
    }
    leaf counter_slice14_ifg_mac_pool87_tx_mac_partial1_invert_crc_cnt_reg6_tx_mac_partial1_invert_crc_cnt {
      type oc-yang:counter64;
      description
        "Counts the number of transmitted packets with partial CRC type 1.";
    }
    leaf counter_slice14_ifg_mac_pool87_tx_mac_partial1_invert_crc_cnt_reg7_tx_mac_partial1_invert_crc_cnt {
      type oc-yang:counter64;
      description
        "Counts the number of transmitted packets with partial CRC type 1.";
    }
    leaf counter_slice15_ifg_mac_pool80_tx_mac_partial1_invert_crc_cnt_reg0_tx_mac_partial1_invert_crc_cnt {
      type oc-yang:counter64;
      description
        "Counts the number of transmitted packets with partial CRC type 1.";
    }
    leaf counter_slice15_ifg_mac_pool80_tx_mac_partial1_invert_crc_cnt_reg1_tx_mac_partial1_invert_crc_cnt {
      type oc-yang:counter64;
      description
        "Counts the number of transmitted packets with partial CRC type 1.";
    }
    leaf counter_slice15_ifg_mac_pool80_tx_mac_partial1_invert_crc_cnt_reg2_tx_mac_partial1_invert_crc_cnt {
      type oc-yang:counter64;
      description
        "Counts the number of transmitted packets with partial CRC type 1.";
    }
    leaf counter_slice15_ifg_mac_pool80_tx_mac_partial1_invert_crc_cnt_reg3_tx_mac_partial1_invert_crc_cnt {
      type oc-yang:counter64;
      description
        "Counts the number of transmitted packets with partial CRC type 1.";
    }
    leaf counter_slice15_ifg_mac_pool80_tx_mac_partial1_invert_crc_cnt_reg4_tx_mac_partial1_invert_crc_cnt {
      type oc-yang:counter64;
      description
        "Counts the number of transmitted packets with partial CRC type 1.";
    }
    leaf counter_slice15_ifg_mac_pool80_tx_mac_partial1_invert_crc_cnt_reg5_tx_mac_partial1_invert_crc_cnt {
      type oc-yang:counter64;
      description
        "Counts the number of transmitted packets with partial CRC type 1.";
    }
    leaf counter_slice15_ifg_mac_pool80_tx_mac_partial1_invert_crc_cnt_reg6_tx_mac_partial1_invert_crc_cnt {
      type oc-yang:counter64;
      description
        "Counts the number of transmitted packets with partial CRC type 1.";
    }
    leaf counter_slice15_ifg_mac_pool80_tx_mac_partial1_invert_crc_cnt_reg7_tx_mac_partial1_invert_crc_cnt {
      type oc-yang:counter64;
      description
        "Counts the number of transmitted packets with partial CRC type 1.";
    }
    leaf counter_slice15_ifg_mac_pool81_tx_mac_partial1_invert_crc_cnt_reg0_tx_mac_partial1_invert_crc_cnt {
      type oc-yang:counter64;
      description
        "Counts the number of transmitted packets with partial CRC type 1.";
    }
    leaf counter_slice15_ifg_mac_pool81_tx_mac_partial1_invert_crc_cnt_reg1_tx_mac_partial1_invert_crc_cnt {
      type oc-yang:counter64;
      description
        "Counts the number of transmitted packets with partial CRC type 1.";
    }
    leaf counter_slice15_ifg_mac_pool81_tx_mac_partial1_invert_crc_cnt_reg2_tx_mac_partial1_invert_crc_cnt {
      type oc-yang:counter64;
      description
        "Counts the number of transmitted packets with partial CRC type 1.";
    }
    leaf counter_slice15_ifg_mac_pool81_tx_mac_partial1_invert_crc_cnt_reg3_tx_mac_partial1_invert_crc_cnt {
      type oc-yang:counter64;
      description
        "Counts the number of transmitted packets with partial CRC type 1.";
    }
    leaf counter_slice15_ifg_mac_pool81_tx_mac_partial1_invert_crc_cnt_reg4_tx_mac_partial1_invert_crc_cnt {
      type oc-yang:counter64;
      description
        "Counts the number of transmitted packets with partial CRC type 1.";
    }
    leaf counter_slice15_ifg_mac_pool81_tx_mac_partial1_invert_crc_cnt_reg5_tx_mac_partial1_invert_crc_cnt {
      type oc-yang:counter64;
      description
        "Counts the number of transmitted packets with partial CRC type 1.";
    }
    leaf counter_slice15_ifg_mac_pool81_tx_mac_partial1_invert_crc_cnt_reg6_tx_mac_partial1_invert_crc_cnt {
      type oc-yang:counter64;
      description
        "Counts the number of transmitted packets with partial CRC type 1.";
    }
    leaf counter_slice15_ifg_mac_pool81_tx_mac_partial1_invert_crc_cnt_reg7_tx_mac_partial1_invert_crc_cnt {
      type oc-yang:counter64;
      description
        "Counts the number of transmitted packets with partial CRC type 1.";
    }
    leaf counter_slice15_ifg_mac_pool82_tx_mac_partial1_invert_crc_cnt_reg0_tx_mac_partial1_invert_crc_cnt {
      type oc-yang:counter64;
      description
        "Counts the number of transmitted packets with partial CRC type 1.";
    }
    leaf counter_slice15_ifg_mac_pool82_tx_mac_partial1_invert_crc_cnt_reg1_tx_mac_partial1_invert_crc_cnt {
      type oc-yang:counter64;
      description
        "Counts the number of transmitted packets with partial CRC type 1.";
    }
    leaf counter_slice15_ifg_mac_pool82_tx_mac_partial1_invert_crc_cnt_reg2_tx_mac_partial1_invert_crc_cnt {
      type oc-yang:counter64;
      description
        "Counts the number of transmitted packets with partial CRC type 1.";
    }
    leaf counter_slice15_ifg_mac_pool82_tx_mac_partial1_invert_crc_cnt_reg3_tx_mac_partial1_invert_crc_cnt {
      type oc-yang:counter64;
      description
        "Counts the number of transmitted packets with partial CRC type 1.";
    }
    leaf counter_slice15_ifg_mac_pool82_tx_mac_partial1_invert_crc_cnt_reg4_tx_mac_partial1_invert_crc_cnt {
      type oc-yang:counter64;
      description
        "Counts the number of transmitted packets with partial CRC type 1.";
    }
    leaf counter_slice15_ifg_mac_pool82_tx_mac_partial1_invert_crc_cnt_reg5_tx_mac_partial1_invert_crc_cnt {
      type oc-yang:counter64;
      description
        "Counts the number of transmitted packets with partial CRC type 1.";
    }
    leaf counter_slice15_ifg_mac_pool82_tx_mac_partial1_invert_crc_cnt_reg6_tx_mac_partial1_invert_crc_cnt {
      type oc-yang:counter64;
      description
        "Counts the number of transmitted packets with partial CRC type 1.";
    }
    leaf counter_slice15_ifg_mac_pool82_tx_mac_partial1_invert_crc_cnt_reg7_tx_mac_partial1_invert_crc_cnt {
      type oc-yang:counter64;
      description
        "Counts the number of transmitted packets with partial CRC type 1.";
    }
    leaf counter_slice15_ifg_mac_pool83_tx_mac_partial1_invert_crc_cnt_reg0_tx_mac_partial1_invert_crc_cnt {
      type oc-yang:counter64;
      description
        "Counts the number of transmitted packets with partial CRC type 1.";
    }
    leaf counter_slice15_ifg_mac_pool83_tx_mac_partial1_invert_crc_cnt_reg1_tx_mac_partial1_invert_crc_cnt {
      type oc-yang:counter64;
      description
        "Counts the number of transmitted packets with partial CRC type 1.";
    }
    leaf counter_slice15_ifg_mac_pool83_tx_mac_partial1_invert_crc_cnt_reg2_tx_mac_partial1_invert_crc_cnt {
      type oc-yang:counter64;
      description
        "Counts the number of transmitted packets with partial CRC type 1.";
    }
    leaf counter_slice15_ifg_mac_pool83_tx_mac_partial1_invert_crc_cnt_reg3_tx_mac_partial1_invert_crc_cnt {
      type oc-yang:counter64;
      description
        "Counts the number of transmitted packets with partial CRC type 1.";
    }
    leaf counter_slice15_ifg_mac_pool83_tx_mac_partial1_invert_crc_cnt_reg4_tx_mac_partial1_invert_crc_cnt {
      type oc-yang:counter64;
      description
        "Counts the number of transmitted packets with partial CRC type 1.";
    }
    leaf counter_slice15_ifg_mac_pool83_tx_mac_partial1_invert_crc_cnt_reg5_tx_mac_partial1_invert_crc_cnt {
      type oc-yang:counter64;
      description
        "Counts the number of transmitted packets with partial CRC type 1.";
    }
    leaf counter_slice15_ifg_mac_pool83_tx_mac_partial1_invert_crc_cnt_reg6_tx_mac_partial1_invert_crc_cnt {
      type oc-yang:counter64;
      description
        "Counts the number of transmitted packets with partial CRC type 1.";
    }
    leaf counter_slice15_ifg_mac_pool83_tx_mac_partial1_invert_crc_cnt_reg7_tx_mac_partial1_invert_crc_cnt {
      type oc-yang:counter64;
      description
        "Counts the number of transmitted packets with partial CRC type 1.";
    }
    leaf counter_slice15_ifg_mac_pool84_tx_mac_partial1_invert_crc_cnt_reg0_tx_mac_partial1_invert_crc_cnt {
      type oc-yang:counter64;
      description
        "Counts the number of transmitted packets with partial CRC type 1.";
    }
    leaf counter_slice15_ifg_mac_pool84_tx_mac_partial1_invert_crc_cnt_reg1_tx_mac_partial1_invert_crc_cnt {
      type oc-yang:counter64;
      description
        "Counts the number of transmitted packets with partial CRC type 1.";
    }
    leaf counter_slice15_ifg_mac_pool84_tx_mac_partial1_invert_crc_cnt_reg2_tx_mac_partial1_invert_crc_cnt {
      type oc-yang:counter64;
      description
        "Counts the number of transmitted packets with partial CRC type 1.";
    }
    leaf counter_slice15_ifg_mac_pool84_tx_mac_partial1_invert_crc_cnt_reg3_tx_mac_partial1_invert_crc_cnt {
      type oc-yang:counter64;
      description
        "Counts the number of transmitted packets with partial CRC type 1.";
    }
    leaf counter_slice15_ifg_mac_pool84_tx_mac_partial1_invert_crc_cnt_reg4_tx_mac_partial1_invert_crc_cnt {
      type oc-yang:counter64;
      description
        "Counts the number of transmitted packets with partial CRC type 1.";
    }
    leaf counter_slice15_ifg_mac_pool84_tx_mac_partial1_invert_crc_cnt_reg5_tx_mac_partial1_invert_crc_cnt {
      type oc-yang:counter64;
      description
        "Counts the number of transmitted packets with partial CRC type 1.";
    }
    leaf counter_slice15_ifg_mac_pool84_tx_mac_partial1_invert_crc_cnt_reg6_tx_mac_partial1_invert_crc_cnt {
      type oc-yang:counter64;
      description
        "Counts the number of transmitted packets with partial CRC type 1.";
    }
    leaf counter_slice15_ifg_mac_pool84_tx_mac_partial1_invert_crc_cnt_reg7_tx_mac_partial1_invert_crc_cnt {
      type oc-yang:counter64;
      description
        "Counts the number of transmitted packets with partial CRC type 1.";
    }
    leaf counter_slice15_ifg_mac_pool85_tx_mac_partial1_invert_crc_cnt_reg0_tx_mac_partial1_invert_crc_cnt {
      type oc-yang:counter64;
      description
        "Counts the number of transmitted packets with partial CRC type 1.";
    }
    leaf counter_slice15_ifg_mac_pool85_tx_mac_partial1_invert_crc_cnt_reg1_tx_mac_partial1_invert_crc_cnt {
      type oc-yang:counter64;
      description
        "Counts the number of transmitted packets with partial CRC type 1.";
    }
    leaf counter_slice15_ifg_mac_pool85_tx_mac_partial1_invert_crc_cnt_reg2_tx_mac_partial1_invert_crc_cnt {
      type oc-yang:counter64;
      description
        "Counts the number of transmitted packets with partial CRC type 1.";
    }
    leaf counter_slice15_ifg_mac_pool85_tx_mac_partial1_invert_crc_cnt_reg3_tx_mac_partial1_invert_crc_cnt {
      type oc-yang:counter64;
      description
        "Counts the number of transmitted packets with partial CRC type 1.";
    }
    leaf counter_slice15_ifg_mac_pool85_tx_mac_partial1_invert_crc_cnt_reg4_tx_mac_partial1_invert_crc_cnt {
      type oc-yang:counter64;
      description
        "Counts the number of transmitted packets with partial CRC type 1.";
    }
    leaf counter_slice15_ifg_mac_pool85_tx_mac_partial1_invert_crc_cnt_reg5_tx_mac_partial1_invert_crc_cnt {
      type oc-yang:counter64;
      description
        "Counts the number of transmitted packets with partial CRC type 1.";
    }
    leaf counter_slice15_ifg_mac_pool85_tx_mac_partial1_invert_crc_cnt_reg6_tx_mac_partial1_invert_crc_cnt {
      type oc-yang:counter64;
      description
        "Counts the number of transmitted packets with partial CRC type 1.";
    }
    leaf counter_slice15_ifg_mac_pool85_tx_mac_partial1_invert_crc_cnt_reg7_tx_mac_partial1_invert_crc_cnt {
      type oc-yang:counter64;
      description
        "Counts the number of transmitted packets with partial CRC type 1.";
    }
    leaf counter_slice15_ifg_mac_pool86_tx_mac_partial1_invert_crc_cnt_reg0_tx_mac_partial1_invert_crc_cnt {
      type oc-yang:counter64;
      description
        "Counts the number of transmitted packets with partial CRC type 1.";
    }
    leaf counter_slice15_ifg_mac_pool86_tx_mac_partial1_invert_crc_cnt_reg1_tx_mac_partial1_invert_crc_cnt {
      type oc-yang:counter64;
      description
        "Counts the number of transmitted packets with partial CRC type 1.";
    }
    leaf counter_slice15_ifg_mac_pool86_tx_mac_partial1_invert_crc_cnt_reg2_tx_mac_partial1_invert_crc_cnt {
      type oc-yang:counter64;
      description
        "Counts the number of transmitted packets with partial CRC type 1.";
    }
    leaf counter_slice15_ifg_mac_pool86_tx_mac_partial1_invert_crc_cnt_reg3_tx_mac_partial1_invert_crc_cnt {
      type oc-yang:counter64;
      description
        "Counts the number of transmitted packets with partial CRC type 1.";
    }
    leaf counter_slice15_ifg_mac_pool86_tx_mac_partial1_invert_crc_cnt_reg4_tx_mac_partial1_invert_crc_cnt {
      type oc-yang:counter64;
      description
        "Counts the number of transmitted packets with partial CRC type 1.";
    }
    leaf counter_slice15_ifg_mac_pool86_tx_mac_partial1_invert_crc_cnt_reg5_tx_mac_partial1_invert_crc_cnt {
      type oc-yang:counter64;
      description
        "Counts the number of transmitted packets with partial CRC type 1.";
    }
    leaf counter_slice15_ifg_mac_pool86_tx_mac_partial1_invert_crc_cnt_reg6_tx_mac_partial1_invert_crc_cnt {
      type oc-yang:counter64;
      description
        "Counts the number of transmitted packets with partial CRC type 1.";
    }
    leaf counter_slice15_ifg_mac_pool86_tx_mac_partial1_invert_crc_cnt_reg7_tx_mac_partial1_invert_crc_cnt {
      type oc-yang:counter64;
      description
        "Counts the number of transmitted packets with partial CRC type 1.";
    }
    leaf counter_slice15_ifg_mac_pool87_tx_mac_partial1_invert_crc_cnt_reg0_tx_mac_partial1_invert_crc_cnt {
      type oc-yang:counter64;
      description
        "Counts the number of transmitted packets with partial CRC type 1.";
    }
    leaf counter_slice15_ifg_mac_pool87_tx_mac_partial1_invert_crc_cnt_reg1_tx_mac_partial1_invert_crc_cnt {
      type oc-yang:counter64;
      description
        "Counts the number of transmitted packets with partial CRC type 1.";
    }
    leaf counter_slice15_ifg_mac_pool87_tx_mac_partial1_invert_crc_cnt_reg2_tx_mac_partial1_invert_crc_cnt {
      type oc-yang:counter64;
      description
        "Counts the number of transmitted packets with partial CRC type 1.";
    }
    leaf counter_slice15_ifg_mac_pool87_tx_mac_partial1_invert_crc_cnt_reg3_tx_mac_partial1_invert_crc_cnt {
      type oc-yang:counter64;
      description
        "Counts the number of transmitted packets with partial CRC type 1.";
    }
    leaf counter_slice15_ifg_mac_pool87_tx_mac_partial1_invert_crc_cnt_reg4_tx_mac_partial1_invert_crc_cnt {
      type oc-yang:counter64;
      description
        "Counts the number of transmitted packets with partial CRC type 1.";
    }
    leaf counter_slice15_ifg_mac_pool87_tx_mac_partial1_invert_crc_cnt_reg5_tx_mac_partial1_invert_crc_cnt {
      type oc-yang:counter64;
      description
        "Counts the number of transmitted packets with partial CRC type 1.";
    }
    leaf counter_slice15_ifg_mac_pool87_tx_mac_partial1_invert_crc_cnt_reg6_tx_mac_partial1_invert_crc_cnt {
      type oc-yang:counter64;
      description
        "Counts the number of transmitted packets with partial CRC type 1.";
    }
    leaf counter_slice15_ifg_mac_pool87_tx_mac_partial1_invert_crc_cnt_reg7_tx_mac_partial1_invert_crc_cnt {
      type oc-yang:counter64;
      description
        "Counts the number of transmitted packets with partial CRC type 1.";
    }
    leaf counter_slice0_ifg_mac_pool80_tx_mac_partial2_invert_crc_cnt_reg0_tx_mac_partial2_invert_crc_cnt {
      type oc-yang:counter64;
      description
        "Counts the number of transmitted packets with partial CRC type 2.";
    }
    leaf counter_slice0_ifg_mac_pool80_tx_mac_partial2_invert_crc_cnt_reg1_tx_mac_partial2_invert_crc_cnt {
      type oc-yang:counter64;
      description
        "Counts the number of transmitted packets with partial CRC type 2.";
    }
    leaf counter_slice0_ifg_mac_pool80_tx_mac_partial2_invert_crc_cnt_reg2_tx_mac_partial2_invert_crc_cnt {
      type oc-yang:counter64;
      description
        "Counts the number of transmitted packets with partial CRC type 2.";
    }
    leaf counter_slice0_ifg_mac_pool80_tx_mac_partial2_invert_crc_cnt_reg3_tx_mac_partial2_invert_crc_cnt {
      type oc-yang:counter64;
      description
        "Counts the number of transmitted packets with partial CRC type 2.";
    }
    leaf counter_slice0_ifg_mac_pool80_tx_mac_partial2_invert_crc_cnt_reg4_tx_mac_partial2_invert_crc_cnt {
      type oc-yang:counter64;
      description
        "Counts the number of transmitted packets with partial CRC type 2.";
    }
    leaf counter_slice0_ifg_mac_pool80_tx_mac_partial2_invert_crc_cnt_reg5_tx_mac_partial2_invert_crc_cnt {
      type oc-yang:counter64;
      description
        "Counts the number of transmitted packets with partial CRC type 2.";
    }
    leaf counter_slice0_ifg_mac_pool80_tx_mac_partial2_invert_crc_cnt_reg6_tx_mac_partial2_invert_crc_cnt {
      type oc-yang:counter64;
      description
        "Counts the number of transmitted packets with partial CRC type 2.";
    }
    leaf counter_slice0_ifg_mac_pool80_tx_mac_partial2_invert_crc_cnt_reg7_tx_mac_partial2_invert_crc_cnt {
      type oc-yang:counter64;
      description
        "Counts the number of transmitted packets with partial CRC type 2.";
    }
    leaf counter_slice0_ifg_mac_pool81_tx_mac_partial2_invert_crc_cnt_reg0_tx_mac_partial2_invert_crc_cnt {
      type oc-yang:counter64;
      description
        "Counts the number of transmitted packets with partial CRC type 2.";
    }
    leaf counter_slice0_ifg_mac_pool81_tx_mac_partial2_invert_crc_cnt_reg1_tx_mac_partial2_invert_crc_cnt {
      type oc-yang:counter64;
      description
        "Counts the number of transmitted packets with partial CRC type 2.";
    }
    leaf counter_slice0_ifg_mac_pool81_tx_mac_partial2_invert_crc_cnt_reg2_tx_mac_partial2_invert_crc_cnt {
      type oc-yang:counter64;
      description
        "Counts the number of transmitted packets with partial CRC type 2.";
    }
    leaf counter_slice0_ifg_mac_pool81_tx_mac_partial2_invert_crc_cnt_reg3_tx_mac_partial2_invert_crc_cnt {
      type oc-yang:counter64;
      description
        "Counts the number of transmitted packets with partial CRC type 2.";
    }
    leaf counter_slice0_ifg_mac_pool81_tx_mac_partial2_invert_crc_cnt_reg4_tx_mac_partial2_invert_crc_cnt {
      type oc-yang:counter64;
      description
        "Counts the number of transmitted packets with partial CRC type 2.";
    }
    leaf counter_slice0_ifg_mac_pool81_tx_mac_partial2_invert_crc_cnt_reg5_tx_mac_partial2_invert_crc_cnt {
      type oc-yang:counter64;
      description
        "Counts the number of transmitted packets with partial CRC type 2.";
    }
    leaf counter_slice0_ifg_mac_pool81_tx_mac_partial2_invert_crc_cnt_reg6_tx_mac_partial2_invert_crc_cnt {
      type oc-yang:counter64;
      description
        "Counts the number of transmitted packets with partial CRC type 2.";
    }
    leaf counter_slice0_ifg_mac_pool81_tx_mac_partial2_invert_crc_cnt_reg7_tx_mac_partial2_invert_crc_cnt {
      type oc-yang:counter64;
      description
        "Counts the number of transmitted packets with partial CRC type 2.";
    }
    leaf counter_slice0_ifg_mac_pool82_tx_mac_partial2_invert_crc_cnt_reg0_tx_mac_partial2_invert_crc_cnt {
      type oc-yang:counter64;
      description
        "Counts the number of transmitted packets with partial CRC type 2.";
    }
    leaf counter_slice0_ifg_mac_pool82_tx_mac_partial2_invert_crc_cnt_reg1_tx_mac_partial2_invert_crc_cnt {
      type oc-yang:counter64;
      description
        "Counts the number of transmitted packets with partial CRC type 2.";
    }
    leaf counter_slice0_ifg_mac_pool82_tx_mac_partial2_invert_crc_cnt_reg2_tx_mac_partial2_invert_crc_cnt {
      type oc-yang:counter64;
      description
        "Counts the number of transmitted packets with partial CRC type 2.";
    }
    leaf counter_slice0_ifg_mac_pool82_tx_mac_partial2_invert_crc_cnt_reg3_tx_mac_partial2_invert_crc_cnt {
      type oc-yang:counter64;
      description
        "Counts the number of transmitted packets with partial CRC type 2.";
    }
    leaf counter_slice0_ifg_mac_pool82_tx_mac_partial2_invert_crc_cnt_reg4_tx_mac_partial2_invert_crc_cnt {
      type oc-yang:counter64;
      description
        "Counts the number of transmitted packets with partial CRC type 2.";
    }
    leaf counter_slice0_ifg_mac_pool82_tx_mac_partial2_invert_crc_cnt_reg5_tx_mac_partial2_invert_crc_cnt {
      type oc-yang:counter64;
      description
        "Counts the number of transmitted packets with partial CRC type 2.";
    }
    leaf counter_slice0_ifg_mac_pool82_tx_mac_partial2_invert_crc_cnt_reg6_tx_mac_partial2_invert_crc_cnt {
      type oc-yang:counter64;
      description
        "Counts the number of transmitted packets with partial CRC type 2.";
    }
    leaf counter_slice0_ifg_mac_pool82_tx_mac_partial2_invert_crc_cnt_reg7_tx_mac_partial2_invert_crc_cnt {
      type oc-yang:counter64;
      description
        "Counts the number of transmitted packets with partial CRC type 2.";
    }
    leaf counter_slice0_ifg_mac_pool83_tx_mac_partial2_invert_crc_cnt_reg0_tx_mac_partial2_invert_crc_cnt {
      type oc-yang:counter64;
      description
        "Counts the number of transmitted packets with partial CRC type 2.";
    }
    leaf counter_slice0_ifg_mac_pool83_tx_mac_partial2_invert_crc_cnt_reg1_tx_mac_partial2_invert_crc_cnt {
      type oc-yang:counter64;
      description
        "Counts the number of transmitted packets with partial CRC type 2.";
    }
    leaf counter_slice0_ifg_mac_pool83_tx_mac_partial2_invert_crc_cnt_reg2_tx_mac_partial2_invert_crc_cnt {
      type oc-yang:counter64;
      description
        "Counts the number of transmitted packets with partial CRC type 2.";
    }
    leaf counter_slice0_ifg_mac_pool83_tx_mac_partial2_invert_crc_cnt_reg3_tx_mac_partial2_invert_crc_cnt {
      type oc-yang:counter64;
      description
        "Counts the number of transmitted packets with partial CRC type 2.";
    }
    leaf counter_slice0_ifg_mac_pool83_tx_mac_partial2_invert_crc_cnt_reg4_tx_mac_partial2_invert_crc_cnt {
      type oc-yang:counter64;
      description
        "Counts the number of transmitted packets with partial CRC type 2.";
    }
    leaf counter_slice0_ifg_mac_pool83_tx_mac_partial2_invert_crc_cnt_reg5_tx_mac_partial2_invert_crc_cnt {
      type oc-yang:counter64;
      description
        "Counts the number of transmitted packets with partial CRC type 2.";
    }
    leaf counter_slice0_ifg_mac_pool83_tx_mac_partial2_invert_crc_cnt_reg6_tx_mac_partial2_invert_crc_cnt {
      type oc-yang:counter64;
      description
        "Counts the number of transmitted packets with partial CRC type 2.";
    }
    leaf counter_slice0_ifg_mac_pool83_tx_mac_partial2_invert_crc_cnt_reg7_tx_mac_partial2_invert_crc_cnt {
      type oc-yang:counter64;
      description
        "Counts the number of transmitted packets with partial CRC type 2.";
    }
    leaf counter_slice0_ifg_mac_pool84_tx_mac_partial2_invert_crc_cnt_reg0_tx_mac_partial2_invert_crc_cnt {
      type oc-yang:counter64;
      description
        "Counts the number of transmitted packets with partial CRC type 2.";
    }
    leaf counter_slice0_ifg_mac_pool84_tx_mac_partial2_invert_crc_cnt_reg1_tx_mac_partial2_invert_crc_cnt {
      type oc-yang:counter64;
      description
        "Counts the number of transmitted packets with partial CRC type 2.";
    }
    leaf counter_slice0_ifg_mac_pool84_tx_mac_partial2_invert_crc_cnt_reg2_tx_mac_partial2_invert_crc_cnt {
      type oc-yang:counter64;
      description
        "Counts the number of transmitted packets with partial CRC type 2.";
    }
    leaf counter_slice0_ifg_mac_pool84_tx_mac_partial2_invert_crc_cnt_reg3_tx_mac_partial2_invert_crc_cnt {
      type oc-yang:counter64;
      description
        "Counts the number of transmitted packets with partial CRC type 2.";
    }
    leaf counter_slice0_ifg_mac_pool84_tx_mac_partial2_invert_crc_cnt_reg4_tx_mac_partial2_invert_crc_cnt {
      type oc-yang:counter64;
      description
        "Counts the number of transmitted packets with partial CRC type 2.";
    }
    leaf counter_slice0_ifg_mac_pool84_tx_mac_partial2_invert_crc_cnt_reg5_tx_mac_partial2_invert_crc_cnt {
      type oc-yang:counter64;
      description
        "Counts the number of transmitted packets with partial CRC type 2.";
    }
    leaf counter_slice0_ifg_mac_pool84_tx_mac_partial2_invert_crc_cnt_reg6_tx_mac_partial2_invert_crc_cnt {
      type oc-yang:counter64;
      description
        "Counts the number of transmitted packets with partial CRC type 2.";
    }
    leaf counter_slice0_ifg_mac_pool84_tx_mac_partial2_invert_crc_cnt_reg7_tx_mac_partial2_invert_crc_cnt {
      type oc-yang:counter64;
      description
        "Counts the number of transmitted packets with partial CRC type 2.";
    }
    leaf counter_slice0_ifg_mac_pool85_tx_mac_partial2_invert_crc_cnt_reg0_tx_mac_partial2_invert_crc_cnt {
      type oc-yang:counter64;
      description
        "Counts the number of transmitted packets with partial CRC type 2.";
    }
    leaf counter_slice0_ifg_mac_pool85_tx_mac_partial2_invert_crc_cnt_reg1_tx_mac_partial2_invert_crc_cnt {
      type oc-yang:counter64;
      description
        "Counts the number of transmitted packets with partial CRC type 2.";
    }
    leaf counter_slice0_ifg_mac_pool85_tx_mac_partial2_invert_crc_cnt_reg2_tx_mac_partial2_invert_crc_cnt {
      type oc-yang:counter64;
      description
        "Counts the number of transmitted packets with partial CRC type 2.";
    }
    leaf counter_slice0_ifg_mac_pool85_tx_mac_partial2_invert_crc_cnt_reg3_tx_mac_partial2_invert_crc_cnt {
      type oc-yang:counter64;
      description
        "Counts the number of transmitted packets with partial CRC type 2.";
    }
    leaf counter_slice0_ifg_mac_pool85_tx_mac_partial2_invert_crc_cnt_reg4_tx_mac_partial2_invert_crc_cnt {
      type oc-yang:counter64;
      description
        "Counts the number of transmitted packets with partial CRC type 2.";
    }
    leaf counter_slice0_ifg_mac_pool85_tx_mac_partial2_invert_crc_cnt_reg5_tx_mac_partial2_invert_crc_cnt {
      type oc-yang:counter64;
      description
        "Counts the number of transmitted packets with partial CRC type 2.";
    }
    leaf counter_slice0_ifg_mac_pool85_tx_mac_partial2_invert_crc_cnt_reg6_tx_mac_partial2_invert_crc_cnt {
      type oc-yang:counter64;
      description
        "Counts the number of transmitted packets with partial CRC type 2.";
    }
    leaf counter_slice0_ifg_mac_pool85_tx_mac_partial2_invert_crc_cnt_reg7_tx_mac_partial2_invert_crc_cnt {
      type oc-yang:counter64;
      description
        "Counts the number of transmitted packets with partial CRC type 2.";
    }
    leaf counter_slice0_ifg_mac_pool86_tx_mac_partial2_invert_crc_cnt_reg0_tx_mac_partial2_invert_crc_cnt {
      type oc-yang:counter64;
      description
        "Counts the number of transmitted packets with partial CRC type 2.";
    }
    leaf counter_slice0_ifg_mac_pool86_tx_mac_partial2_invert_crc_cnt_reg1_tx_mac_partial2_invert_crc_cnt {
      type oc-yang:counter64;
      description
        "Counts the number of transmitted packets with partial CRC type 2.";
    }
    leaf counter_slice0_ifg_mac_pool86_tx_mac_partial2_invert_crc_cnt_reg2_tx_mac_partial2_invert_crc_cnt {
      type oc-yang:counter64;
      description
        "Counts the number of transmitted packets with partial CRC type 2.";
    }
    leaf counter_slice0_ifg_mac_pool86_tx_mac_partial2_invert_crc_cnt_reg3_tx_mac_partial2_invert_crc_cnt {
      type oc-yang:counter64;
      description
        "Counts the number of transmitted packets with partial CRC type 2.";
    }
    leaf counter_slice0_ifg_mac_pool86_tx_mac_partial2_invert_crc_cnt_reg4_tx_mac_partial2_invert_crc_cnt {
      type oc-yang:counter64;
      description
        "Counts the number of transmitted packets with partial CRC type 2.";
    }
    leaf counter_slice0_ifg_mac_pool86_tx_mac_partial2_invert_crc_cnt_reg5_tx_mac_partial2_invert_crc_cnt {
      type oc-yang:counter64;
      description
        "Counts the number of transmitted packets with partial CRC type 2.";
    }
    leaf counter_slice0_ifg_mac_pool86_tx_mac_partial2_invert_crc_cnt_reg6_tx_mac_partial2_invert_crc_cnt {
      type oc-yang:counter64;
      description
        "Counts the number of transmitted packets with partial CRC type 2.";
    }
    leaf counter_slice0_ifg_mac_pool86_tx_mac_partial2_invert_crc_cnt_reg7_tx_mac_partial2_invert_crc_cnt {
      type oc-yang:counter64;
      description
        "Counts the number of transmitted packets with partial CRC type 2.";
    }
    leaf counter_slice0_ifg_mac_pool87_tx_mac_partial2_invert_crc_cnt_reg0_tx_mac_partial2_invert_crc_cnt {
      type oc-yang:counter64;
      description
        "Counts the number of transmitted packets with partial CRC type 2.";
    }
    leaf counter_slice0_ifg_mac_pool87_tx_mac_partial2_invert_crc_cnt_reg1_tx_mac_partial2_invert_crc_cnt {
      type oc-yang:counter64;
      description
        "Counts the number of transmitted packets with partial CRC type 2.";
    }
    leaf counter_slice0_ifg_mac_pool87_tx_mac_partial2_invert_crc_cnt_reg2_tx_mac_partial2_invert_crc_cnt {
      type oc-yang:counter64;
      description
        "Counts the number of transmitted packets with partial CRC type 2.";
    }
    leaf counter_slice0_ifg_mac_pool87_tx_mac_partial2_invert_crc_cnt_reg3_tx_mac_partial2_invert_crc_cnt {
      type oc-yang:counter64;
      description
        "Counts the number of transmitted packets with partial CRC type 2.";
    }
    leaf counter_slice0_ifg_mac_pool87_tx_mac_partial2_invert_crc_cnt_reg4_tx_mac_partial2_invert_crc_cnt {
      type oc-yang:counter64;
      description
        "Counts the number of transmitted packets with partial CRC type 2.";
    }
    leaf counter_slice0_ifg_mac_pool87_tx_mac_partial2_invert_crc_cnt_reg5_tx_mac_partial2_invert_crc_cnt {
      type oc-yang:counter64;
      description
        "Counts the number of transmitted packets with partial CRC type 2.";
    }
    leaf counter_slice0_ifg_mac_pool87_tx_mac_partial2_invert_crc_cnt_reg6_tx_mac_partial2_invert_crc_cnt {
      type oc-yang:counter64;
      description
        "Counts the number of transmitted packets with partial CRC type 2.";
    }
    leaf counter_slice0_ifg_mac_pool87_tx_mac_partial2_invert_crc_cnt_reg7_tx_mac_partial2_invert_crc_cnt {
      type oc-yang:counter64;
      description
        "Counts the number of transmitted packets with partial CRC type 2.";
    }
    leaf counter_slice1_ifg_mac_pool80_tx_mac_partial2_invert_crc_cnt_reg0_tx_mac_partial2_invert_crc_cnt {
      type oc-yang:counter64;
      description
        "Counts the number of transmitted packets with partial CRC type 2.";
    }
    leaf counter_slice1_ifg_mac_pool80_tx_mac_partial2_invert_crc_cnt_reg1_tx_mac_partial2_invert_crc_cnt {
      type oc-yang:counter64;
      description
        "Counts the number of transmitted packets with partial CRC type 2.";
    }
    leaf counter_slice1_ifg_mac_pool80_tx_mac_partial2_invert_crc_cnt_reg2_tx_mac_partial2_invert_crc_cnt {
      type oc-yang:counter64;
      description
        "Counts the number of transmitted packets with partial CRC type 2.";
    }
    leaf counter_slice1_ifg_mac_pool80_tx_mac_partial2_invert_crc_cnt_reg3_tx_mac_partial2_invert_crc_cnt {
      type oc-yang:counter64;
      description
        "Counts the number of transmitted packets with partial CRC type 2.";
    }
    leaf counter_slice1_ifg_mac_pool80_tx_mac_partial2_invert_crc_cnt_reg4_tx_mac_partial2_invert_crc_cnt {
      type oc-yang:counter64;
      description
        "Counts the number of transmitted packets with partial CRC type 2.";
    }
    leaf counter_slice1_ifg_mac_pool80_tx_mac_partial2_invert_crc_cnt_reg5_tx_mac_partial2_invert_crc_cnt {
      type oc-yang:counter64;
      description
        "Counts the number of transmitted packets with partial CRC type 2.";
    }
    leaf counter_slice1_ifg_mac_pool80_tx_mac_partial2_invert_crc_cnt_reg6_tx_mac_partial2_invert_crc_cnt {
      type oc-yang:counter64;
      description
        "Counts the number of transmitted packets with partial CRC type 2.";
    }
    leaf counter_slice1_ifg_mac_pool80_tx_mac_partial2_invert_crc_cnt_reg7_tx_mac_partial2_invert_crc_cnt {
      type oc-yang:counter64;
      description
        "Counts the number of transmitted packets with partial CRC type 2.";
    }
    leaf counter_slice1_ifg_mac_pool81_tx_mac_partial2_invert_crc_cnt_reg0_tx_mac_partial2_invert_crc_cnt {
      type oc-yang:counter64;
      description
        "Counts the number of transmitted packets with partial CRC type 2.";
    }
    leaf counter_slice1_ifg_mac_pool81_tx_mac_partial2_invert_crc_cnt_reg1_tx_mac_partial2_invert_crc_cnt {
      type oc-yang:counter64;
      description
        "Counts the number of transmitted packets with partial CRC type 2.";
    }
    leaf counter_slice1_ifg_mac_pool81_tx_mac_partial2_invert_crc_cnt_reg2_tx_mac_partial2_invert_crc_cnt {
      type oc-yang:counter64;
      description
        "Counts the number of transmitted packets with partial CRC type 2.";
    }
    leaf counter_slice1_ifg_mac_pool81_tx_mac_partial2_invert_crc_cnt_reg3_tx_mac_partial2_invert_crc_cnt {
      type oc-yang:counter64;
      description
        "Counts the number of transmitted packets with partial CRC type 2.";
    }
    leaf counter_slice1_ifg_mac_pool81_tx_mac_partial2_invert_crc_cnt_reg4_tx_mac_partial2_invert_crc_cnt {
      type oc-yang:counter64;
      description
        "Counts the number of transmitted packets with partial CRC type 2.";
    }
    leaf counter_slice1_ifg_mac_pool81_tx_mac_partial2_invert_crc_cnt_reg5_tx_mac_partial2_invert_crc_cnt {
      type oc-yang:counter64;
      description
        "Counts the number of transmitted packets with partial CRC type 2.";
    }
    leaf counter_slice1_ifg_mac_pool81_tx_mac_partial2_invert_crc_cnt_reg6_tx_mac_partial2_invert_crc_cnt {
      type oc-yang:counter64;
      description
        "Counts the number of transmitted packets with partial CRC type 2.";
    }
    leaf counter_slice1_ifg_mac_pool81_tx_mac_partial2_invert_crc_cnt_reg7_tx_mac_partial2_invert_crc_cnt {
      type oc-yang:counter64;
      description
        "Counts the number of transmitted packets with partial CRC type 2.";
    }
    leaf counter_slice1_ifg_mac_pool82_tx_mac_partial2_invert_crc_cnt_reg0_tx_mac_partial2_invert_crc_cnt {
      type oc-yang:counter64;
      description
        "Counts the number of transmitted packets with partial CRC type 2.";
    }
    leaf counter_slice1_ifg_mac_pool82_tx_mac_partial2_invert_crc_cnt_reg1_tx_mac_partial2_invert_crc_cnt {
      type oc-yang:counter64;
      description
        "Counts the number of transmitted packets with partial CRC type 2.";
    }
    leaf counter_slice1_ifg_mac_pool82_tx_mac_partial2_invert_crc_cnt_reg2_tx_mac_partial2_invert_crc_cnt {
      type oc-yang:counter64;
      description
        "Counts the number of transmitted packets with partial CRC type 2.";
    }
    leaf counter_slice1_ifg_mac_pool82_tx_mac_partial2_invert_crc_cnt_reg3_tx_mac_partial2_invert_crc_cnt {
      type oc-yang:counter64;
      description
        "Counts the number of transmitted packets with partial CRC type 2.";
    }
    leaf counter_slice1_ifg_mac_pool82_tx_mac_partial2_invert_crc_cnt_reg4_tx_mac_partial2_invert_crc_cnt {
      type oc-yang:counter64;
      description
        "Counts the number of transmitted packets with partial CRC type 2.";
    }
    leaf counter_slice1_ifg_mac_pool82_tx_mac_partial2_invert_crc_cnt_reg5_tx_mac_partial2_invert_crc_cnt {
      type oc-yang:counter64;
      description
        "Counts the number of transmitted packets with partial CRC type 2.";
    }
    leaf counter_slice1_ifg_mac_pool82_tx_mac_partial2_invert_crc_cnt_reg6_tx_mac_partial2_invert_crc_cnt {
      type oc-yang:counter64;
      description
        "Counts the number of transmitted packets with partial CRC type 2.";
    }
    leaf counter_slice1_ifg_mac_pool82_tx_mac_partial2_invert_crc_cnt_reg7_tx_mac_partial2_invert_crc_cnt {
      type oc-yang:counter64;
      description
        "Counts the number of transmitted packets with partial CRC type 2.";
    }
    leaf counter_slice1_ifg_mac_pool83_tx_mac_partial2_invert_crc_cnt_reg0_tx_mac_partial2_invert_crc_cnt {
      type oc-yang:counter64;
      description
        "Counts the number of transmitted packets with partial CRC type 2.";
    }
    leaf counter_slice1_ifg_mac_pool83_tx_mac_partial2_invert_crc_cnt_reg1_tx_mac_partial2_invert_crc_cnt {
      type oc-yang:counter64;
      description
        "Counts the number of transmitted packets with partial CRC type 2.";
    }
    leaf counter_slice1_ifg_mac_pool83_tx_mac_partial2_invert_crc_cnt_reg2_tx_mac_partial2_invert_crc_cnt {
      type oc-yang:counter64;
      description
        "Counts the number of transmitted packets with partial CRC type 2.";
    }
    leaf counter_slice1_ifg_mac_pool83_tx_mac_partial2_invert_crc_cnt_reg3_tx_mac_partial2_invert_crc_cnt {
      type oc-yang:counter64;
      description
        "Counts the number of transmitted packets with partial CRC type 2.";
    }
    leaf counter_slice1_ifg_mac_pool83_tx_mac_partial2_invert_crc_cnt_reg4_tx_mac_partial2_invert_crc_cnt {
      type oc-yang:counter64;
      description
        "Counts the number of transmitted packets with partial CRC type 2.";
    }
    leaf counter_slice1_ifg_mac_pool83_tx_mac_partial2_invert_crc_cnt_reg5_tx_mac_partial2_invert_crc_cnt {
      type oc-yang:counter64;
      description
        "Counts the number of transmitted packets with partial CRC type 2.";
    }
    leaf counter_slice1_ifg_mac_pool83_tx_mac_partial2_invert_crc_cnt_reg6_tx_mac_partial2_invert_crc_cnt {
      type oc-yang:counter64;
      description
        "Counts the number of transmitted packets with partial CRC type 2.";
    }
    leaf counter_slice1_ifg_mac_pool83_tx_mac_partial2_invert_crc_cnt_reg7_tx_mac_partial2_invert_crc_cnt {
      type oc-yang:counter64;
      description
        "Counts the number of transmitted packets with partial CRC type 2.";
    }
    leaf counter_slice1_ifg_mac_pool84_tx_mac_partial2_invert_crc_cnt_reg0_tx_mac_partial2_invert_crc_cnt {
      type oc-yang:counter64;
      description
        "Counts the number of transmitted packets with partial CRC type 2.";
    }
    leaf counter_slice1_ifg_mac_pool84_tx_mac_partial2_invert_crc_cnt_reg1_tx_mac_partial2_invert_crc_cnt {
      type oc-yang:counter64;
      description
        "Counts the number of transmitted packets with partial CRC type 2.";
    }
    leaf counter_slice1_ifg_mac_pool84_tx_mac_partial2_invert_crc_cnt_reg2_tx_mac_partial2_invert_crc_cnt {
      type oc-yang:counter64;
      description
        "Counts the number of transmitted packets with partial CRC type 2.";
    }
    leaf counter_slice1_ifg_mac_pool84_tx_mac_partial2_invert_crc_cnt_reg3_tx_mac_partial2_invert_crc_cnt {
      type oc-yang:counter64;
      description
        "Counts the number of transmitted packets with partial CRC type 2.";
    }
    leaf counter_slice1_ifg_mac_pool84_tx_mac_partial2_invert_crc_cnt_reg4_tx_mac_partial2_invert_crc_cnt {
      type oc-yang:counter64;
      description
        "Counts the number of transmitted packets with partial CRC type 2.";
    }
    leaf counter_slice1_ifg_mac_pool84_tx_mac_partial2_invert_crc_cnt_reg5_tx_mac_partial2_invert_crc_cnt {
      type oc-yang:counter64;
      description
        "Counts the number of transmitted packets with partial CRC type 2.";
    }
    leaf counter_slice1_ifg_mac_pool84_tx_mac_partial2_invert_crc_cnt_reg6_tx_mac_partial2_invert_crc_cnt {
      type oc-yang:counter64;
      description
        "Counts the number of transmitted packets with partial CRC type 2.";
    }
    leaf counter_slice1_ifg_mac_pool84_tx_mac_partial2_invert_crc_cnt_reg7_tx_mac_partial2_invert_crc_cnt {
      type oc-yang:counter64;
      description
        "Counts the number of transmitted packets with partial CRC type 2.";
    }
    leaf counter_slice1_ifg_mac_pool85_tx_mac_partial2_invert_crc_cnt_reg0_tx_mac_partial2_invert_crc_cnt {
      type oc-yang:counter64;
      description
        "Counts the number of transmitted packets with partial CRC type 2.";
    }
    leaf counter_slice1_ifg_mac_pool85_tx_mac_partial2_invert_crc_cnt_reg1_tx_mac_partial2_invert_crc_cnt {
      type oc-yang:counter64;
      description
        "Counts the number of transmitted packets with partial CRC type 2.";
    }
    leaf counter_slice1_ifg_mac_pool85_tx_mac_partial2_invert_crc_cnt_reg2_tx_mac_partial2_invert_crc_cnt {
      type oc-yang:counter64;
      description
        "Counts the number of transmitted packets with partial CRC type 2.";
    }
    leaf counter_slice1_ifg_mac_pool85_tx_mac_partial2_invert_crc_cnt_reg3_tx_mac_partial2_invert_crc_cnt {
      type oc-yang:counter64;
      description
        "Counts the number of transmitted packets with partial CRC type 2.";
    }
    leaf counter_slice1_ifg_mac_pool85_tx_mac_partial2_invert_crc_cnt_reg4_tx_mac_partial2_invert_crc_cnt {
      type oc-yang:counter64;
      description
        "Counts the number of transmitted packets with partial CRC type 2.";
    }
    leaf counter_slice1_ifg_mac_pool85_tx_mac_partial2_invert_crc_cnt_reg5_tx_mac_partial2_invert_crc_cnt {
      type oc-yang:counter64;
      description
        "Counts the number of transmitted packets with partial CRC type 2.";
    }
    leaf counter_slice1_ifg_mac_pool85_tx_mac_partial2_invert_crc_cnt_reg6_tx_mac_partial2_invert_crc_cnt {
      type oc-yang:counter64;
      description
        "Counts the number of transmitted packets with partial CRC type 2.";
    }
    leaf counter_slice1_ifg_mac_pool85_tx_mac_partial2_invert_crc_cnt_reg7_tx_mac_partial2_invert_crc_cnt {
      type oc-yang:counter64;
      description
        "Counts the number of transmitted packets with partial CRC type 2.";
    }
    leaf counter_slice1_ifg_mac_pool86_tx_mac_partial2_invert_crc_cnt_reg0_tx_mac_partial2_invert_crc_cnt {
      type oc-yang:counter64;
      description
        "Counts the number of transmitted packets with partial CRC type 2.";
    }
    leaf counter_slice1_ifg_mac_pool86_tx_mac_partial2_invert_crc_cnt_reg1_tx_mac_partial2_invert_crc_cnt {
      type oc-yang:counter64;
      description
        "Counts the number of transmitted packets with partial CRC type 2.";
    }
    leaf counter_slice1_ifg_mac_pool86_tx_mac_partial2_invert_crc_cnt_reg2_tx_mac_partial2_invert_crc_cnt {
      type oc-yang:counter64;
      description
        "Counts the number of transmitted packets with partial CRC type 2.";
    }
    leaf counter_slice1_ifg_mac_pool86_tx_mac_partial2_invert_crc_cnt_reg3_tx_mac_partial2_invert_crc_cnt {
      type oc-yang:counter64;
      description
        "Counts the number of transmitted packets with partial CRC type 2.";
    }
    leaf counter_slice1_ifg_mac_pool86_tx_mac_partial2_invert_crc_cnt_reg4_tx_mac_partial2_invert_crc_cnt {
      type oc-yang:counter64;
      description
        "Counts the number of transmitted packets with partial CRC type 2.";
    }
    leaf counter_slice1_ifg_mac_pool86_tx_mac_partial2_invert_crc_cnt_reg5_tx_mac_partial2_invert_crc_cnt {
      type oc-yang:counter64;
      description
        "Counts the number of transmitted packets with partial CRC type 2.";
    }
    leaf counter_slice1_ifg_mac_pool86_tx_mac_partial2_invert_crc_cnt_reg6_tx_mac_partial2_invert_crc_cnt {
      type oc-yang:counter64;
      description
        "Counts the number of transmitted packets with partial CRC type 2.";
    }
    leaf counter_slice1_ifg_mac_pool86_tx_mac_partial2_invert_crc_cnt_reg7_tx_mac_partial2_invert_crc_cnt {
      type oc-yang:counter64;
      description
        "Counts the number of transmitted packets with partial CRC type 2.";
    }
    leaf counter_slice1_ifg_mac_pool87_tx_mac_partial2_invert_crc_cnt_reg0_tx_mac_partial2_invert_crc_cnt {
      type oc-yang:counter64;
      description
        "Counts the number of transmitted packets with partial CRC type 2.";
    }
    leaf counter_slice1_ifg_mac_pool87_tx_mac_partial2_invert_crc_cnt_reg1_tx_mac_partial2_invert_crc_cnt {
      type oc-yang:counter64;
      description
        "Counts the number of transmitted packets with partial CRC type 2.";
    }
    leaf counter_slice1_ifg_mac_pool87_tx_mac_partial2_invert_crc_cnt_reg2_tx_mac_partial2_invert_crc_cnt {
      type oc-yang:counter64;
      description
        "Counts the number of transmitted packets with partial CRC type 2.";
    }
    leaf counter_slice1_ifg_mac_pool87_tx_mac_partial2_invert_crc_cnt_reg3_tx_mac_partial2_invert_crc_cnt {
      type oc-yang:counter64;
      description
        "Counts the number of transmitted packets with partial CRC type 2.";
    }
    leaf counter_slice1_ifg_mac_pool87_tx_mac_partial2_invert_crc_cnt_reg4_tx_mac_partial2_invert_crc_cnt {
      type oc-yang:counter64;
      description
        "Counts the number of transmitted packets with partial CRC type 2.";
    }
    leaf counter_slice1_ifg_mac_pool87_tx_mac_partial2_invert_crc_cnt_reg5_tx_mac_partial2_invert_crc_cnt {
      type oc-yang:counter64;
      description
        "Counts the number of transmitted packets with partial CRC type 2.";
    }
    leaf counter_slice1_ifg_mac_pool87_tx_mac_partial2_invert_crc_cnt_reg6_tx_mac_partial2_invert_crc_cnt {
      type oc-yang:counter64;
      description
        "Counts the number of transmitted packets with partial CRC type 2.";
    }
    leaf counter_slice1_ifg_mac_pool87_tx_mac_partial2_invert_crc_cnt_reg7_tx_mac_partial2_invert_crc_cnt {
      type oc-yang:counter64;
      description
        "Counts the number of transmitted packets with partial CRC type 2.";
    }
    leaf counter_slice2_ifg_mac_pool80_tx_mac_partial2_invert_crc_cnt_reg0_tx_mac_partial2_invert_crc_cnt {
      type oc-yang:counter64;
      description
        "Counts the number of transmitted packets with partial CRC type 2.";
    }
    leaf counter_slice2_ifg_mac_pool80_tx_mac_partial2_invert_crc_cnt_reg1_tx_mac_partial2_invert_crc_cnt {
      type oc-yang:counter64;
      description
        "Counts the number of transmitted packets with partial CRC type 2.";
    }
    leaf counter_slice2_ifg_mac_pool80_tx_mac_partial2_invert_crc_cnt_reg2_tx_mac_partial2_invert_crc_cnt {
      type oc-yang:counter64;
      description
        "Counts the number of transmitted packets with partial CRC type 2.";
    }
    leaf counter_slice2_ifg_mac_pool80_tx_mac_partial2_invert_crc_cnt_reg3_tx_mac_partial2_invert_crc_cnt {
      type oc-yang:counter64;
      description
        "Counts the number of transmitted packets with partial CRC type 2.";
    }
    leaf counter_slice2_ifg_mac_pool80_tx_mac_partial2_invert_crc_cnt_reg4_tx_mac_partial2_invert_crc_cnt {
      type oc-yang:counter64;
      description
        "Counts the number of transmitted packets with partial CRC type 2.";
    }
    leaf counter_slice2_ifg_mac_pool80_tx_mac_partial2_invert_crc_cnt_reg5_tx_mac_partial2_invert_crc_cnt {
      type oc-yang:counter64;
      description
        "Counts the number of transmitted packets with partial CRC type 2.";
    }
    leaf counter_slice2_ifg_mac_pool80_tx_mac_partial2_invert_crc_cnt_reg6_tx_mac_partial2_invert_crc_cnt {
      type oc-yang:counter64;
      description
        "Counts the number of transmitted packets with partial CRC type 2.";
    }
    leaf counter_slice2_ifg_mac_pool80_tx_mac_partial2_invert_crc_cnt_reg7_tx_mac_partial2_invert_crc_cnt {
      type oc-yang:counter64;
      description
        "Counts the number of transmitted packets with partial CRC type 2.";
    }
    leaf counter_slice2_ifg_mac_pool81_tx_mac_partial2_invert_crc_cnt_reg0_tx_mac_partial2_invert_crc_cnt {
      type oc-yang:counter64;
      description
        "Counts the number of transmitted packets with partial CRC type 2.";
    }
    leaf counter_slice2_ifg_mac_pool81_tx_mac_partial2_invert_crc_cnt_reg1_tx_mac_partial2_invert_crc_cnt {
      type oc-yang:counter64;
      description
        "Counts the number of transmitted packets with partial CRC type 2.";
    }
    leaf counter_slice2_ifg_mac_pool81_tx_mac_partial2_invert_crc_cnt_reg2_tx_mac_partial2_invert_crc_cnt {
      type oc-yang:counter64;
      description
        "Counts the number of transmitted packets with partial CRC type 2.";
    }
    leaf counter_slice2_ifg_mac_pool81_tx_mac_partial2_invert_crc_cnt_reg3_tx_mac_partial2_invert_crc_cnt {
      type oc-yang:counter64;
      description
        "Counts the number of transmitted packets with partial CRC type 2.";
    }
    leaf counter_slice2_ifg_mac_pool81_tx_mac_partial2_invert_crc_cnt_reg4_tx_mac_partial2_invert_crc_cnt {
      type oc-yang:counter64;
      description
        "Counts the number of transmitted packets with partial CRC type 2.";
    }
    leaf counter_slice2_ifg_mac_pool81_tx_mac_partial2_invert_crc_cnt_reg5_tx_mac_partial2_invert_crc_cnt {
      type oc-yang:counter64;
      description
        "Counts the number of transmitted packets with partial CRC type 2.";
    }
    leaf counter_slice2_ifg_mac_pool81_tx_mac_partial2_invert_crc_cnt_reg6_tx_mac_partial2_invert_crc_cnt {
      type oc-yang:counter64;
      description
        "Counts the number of transmitted packets with partial CRC type 2.";
    }
    leaf counter_slice2_ifg_mac_pool81_tx_mac_partial2_invert_crc_cnt_reg7_tx_mac_partial2_invert_crc_cnt {
      type oc-yang:counter64;
      description
        "Counts the number of transmitted packets with partial CRC type 2.";
    }
    leaf counter_slice2_ifg_mac_pool82_tx_mac_partial2_invert_crc_cnt_reg0_tx_mac_partial2_invert_crc_cnt {
      type oc-yang:counter64;
      description
        "Counts the number of transmitted packets with partial CRC type 2.";
    }
    leaf counter_slice2_ifg_mac_pool82_tx_mac_partial2_invert_crc_cnt_reg1_tx_mac_partial2_invert_crc_cnt {
      type oc-yang:counter64;
      description
        "Counts the number of transmitted packets with partial CRC type 2.";
    }
    leaf counter_slice2_ifg_mac_pool82_tx_mac_partial2_invert_crc_cnt_reg2_tx_mac_partial2_invert_crc_cnt {
      type oc-yang:counter64;
      description
        "Counts the number of transmitted packets with partial CRC type 2.";
    }
    leaf counter_slice2_ifg_mac_pool82_tx_mac_partial2_invert_crc_cnt_reg3_tx_mac_partial2_invert_crc_cnt {
      type oc-yang:counter64;
      description
        "Counts the number of transmitted packets with partial CRC type 2.";
    }
    leaf counter_slice2_ifg_mac_pool82_tx_mac_partial2_invert_crc_cnt_reg4_tx_mac_partial2_invert_crc_cnt {
      type oc-yang:counter64;
      description
        "Counts the number of transmitted packets with partial CRC type 2.";
    }
    leaf counter_slice2_ifg_mac_pool82_tx_mac_partial2_invert_crc_cnt_reg5_tx_mac_partial2_invert_crc_cnt {
      type oc-yang:counter64;
      description
        "Counts the number of transmitted packets with partial CRC type 2.";
    }
    leaf counter_slice2_ifg_mac_pool82_tx_mac_partial2_invert_crc_cnt_reg6_tx_mac_partial2_invert_crc_cnt {
      type oc-yang:counter64;
      description
        "Counts the number of transmitted packets with partial CRC type 2.";
    }
    leaf counter_slice2_ifg_mac_pool82_tx_mac_partial2_invert_crc_cnt_reg7_tx_mac_partial2_invert_crc_cnt {
      type oc-yang:counter64;
      description
        "Counts the number of transmitted packets with partial CRC type 2.";
    }
    leaf counter_slice2_ifg_mac_pool83_tx_mac_partial2_invert_crc_cnt_reg0_tx_mac_partial2_invert_crc_cnt {
      type oc-yang:counter64;
      description
        "Counts the number of transmitted packets with partial CRC type 2.";
    }
    leaf counter_slice2_ifg_mac_pool83_tx_mac_partial2_invert_crc_cnt_reg1_tx_mac_partial2_invert_crc_cnt {
      type oc-yang:counter64;
      description
        "Counts the number of transmitted packets with partial CRC type 2.";
    }
    leaf counter_slice2_ifg_mac_pool83_tx_mac_partial2_invert_crc_cnt_reg2_tx_mac_partial2_invert_crc_cnt {
      type oc-yang:counter64;
      description
        "Counts the number of transmitted packets with partial CRC type 2.";
    }
    leaf counter_slice2_ifg_mac_pool83_tx_mac_partial2_invert_crc_cnt_reg3_tx_mac_partial2_invert_crc_cnt {
      type oc-yang:counter64;
      description
        "Counts the number of transmitted packets with partial CRC type 2.";
    }
    leaf counter_slice2_ifg_mac_pool83_tx_mac_partial2_invert_crc_cnt_reg4_tx_mac_partial2_invert_crc_cnt {
      type oc-yang:counter64;
      description
        "Counts the number of transmitted packets with partial CRC type 2.";
    }
    leaf counter_slice2_ifg_mac_pool83_tx_mac_partial2_invert_crc_cnt_reg5_tx_mac_partial2_invert_crc_cnt {
      type oc-yang:counter64;
      description
        "Counts the number of transmitted packets with partial CRC type 2.";
    }
    leaf counter_slice2_ifg_mac_pool83_tx_mac_partial2_invert_crc_cnt_reg6_tx_mac_partial2_invert_crc_cnt {
      type oc-yang:counter64;
      description
        "Counts the number of transmitted packets with partial CRC type 2.";
    }
    leaf counter_slice2_ifg_mac_pool83_tx_mac_partial2_invert_crc_cnt_reg7_tx_mac_partial2_invert_crc_cnt {
      type oc-yang:counter64;
      description
        "Counts the number of transmitted packets with partial CRC type 2.";
    }
    leaf counter_slice2_ifg_mac_pool84_tx_mac_partial2_invert_crc_cnt_reg0_tx_mac_partial2_invert_crc_cnt {
      type oc-yang:counter64;
      description
        "Counts the number of transmitted packets with partial CRC type 2.";
    }
    leaf counter_slice2_ifg_mac_pool84_tx_mac_partial2_invert_crc_cnt_reg1_tx_mac_partial2_invert_crc_cnt {
      type oc-yang:counter64;
      description
        "Counts the number of transmitted packets with partial CRC type 2.";
    }
    leaf counter_slice2_ifg_mac_pool84_tx_mac_partial2_invert_crc_cnt_reg2_tx_mac_partial2_invert_crc_cnt {
      type oc-yang:counter64;
      description
        "Counts the number of transmitted packets with partial CRC type 2.";
    }
    leaf counter_slice2_ifg_mac_pool84_tx_mac_partial2_invert_crc_cnt_reg3_tx_mac_partial2_invert_crc_cnt {
      type oc-yang:counter64;
      description
        "Counts the number of transmitted packets with partial CRC type 2.";
    }
    leaf counter_slice2_ifg_mac_pool84_tx_mac_partial2_invert_crc_cnt_reg4_tx_mac_partial2_invert_crc_cnt {
      type oc-yang:counter64;
      description
        "Counts the number of transmitted packets with partial CRC type 2.";
    }
    leaf counter_slice2_ifg_mac_pool84_tx_mac_partial2_invert_crc_cnt_reg5_tx_mac_partial2_invert_crc_cnt {
      type oc-yang:counter64;
      description
        "Counts the number of transmitted packets with partial CRC type 2.";
    }
    leaf counter_slice2_ifg_mac_pool84_tx_mac_partial2_invert_crc_cnt_reg6_tx_mac_partial2_invert_crc_cnt {
      type oc-yang:counter64;
      description
        "Counts the number of transmitted packets with partial CRC type 2.";
    }
    leaf counter_slice2_ifg_mac_pool84_tx_mac_partial2_invert_crc_cnt_reg7_tx_mac_partial2_invert_crc_cnt {
      type oc-yang:counter64;
      description
        "Counts the number of transmitted packets with partial CRC type 2.";
    }
    leaf counter_slice2_ifg_mac_pool85_tx_mac_partial2_invert_crc_cnt_reg0_tx_mac_partial2_invert_crc_cnt {
      type oc-yang:counter64;
      description
        "Counts the number of transmitted packets with partial CRC type 2.";
    }
    leaf counter_slice2_ifg_mac_pool85_tx_mac_partial2_invert_crc_cnt_reg1_tx_mac_partial2_invert_crc_cnt {
      type oc-yang:counter64;
      description
        "Counts the number of transmitted packets with partial CRC type 2.";
    }
    leaf counter_slice2_ifg_mac_pool85_tx_mac_partial2_invert_crc_cnt_reg2_tx_mac_partial2_invert_crc_cnt {
      type oc-yang:counter64;
      description
        "Counts the number of transmitted packets with partial CRC type 2.";
    }
    leaf counter_slice2_ifg_mac_pool85_tx_mac_partial2_invert_crc_cnt_reg3_tx_mac_partial2_invert_crc_cnt {
      type oc-yang:counter64;
      description
        "Counts the number of transmitted packets with partial CRC type 2.";
    }
    leaf counter_slice2_ifg_mac_pool85_tx_mac_partial2_invert_crc_cnt_reg4_tx_mac_partial2_invert_crc_cnt {
      type oc-yang:counter64;
      description
        "Counts the number of transmitted packets with partial CRC type 2.";
    }
    leaf counter_slice2_ifg_mac_pool85_tx_mac_partial2_invert_crc_cnt_reg5_tx_mac_partial2_invert_crc_cnt {
      type oc-yang:counter64;
      description
        "Counts the number of transmitted packets with partial CRC type 2.";
    }
    leaf counter_slice2_ifg_mac_pool85_tx_mac_partial2_invert_crc_cnt_reg6_tx_mac_partial2_invert_crc_cnt {
      type oc-yang:counter64;
      description
        "Counts the number of transmitted packets with partial CRC type 2.";
    }
    leaf counter_slice2_ifg_mac_pool85_tx_mac_partial2_invert_crc_cnt_reg7_tx_mac_partial2_invert_crc_cnt {
      type oc-yang:counter64;
      description
        "Counts the number of transmitted packets with partial CRC type 2.";
    }
    leaf counter_slice2_ifg_mac_pool86_tx_mac_partial2_invert_crc_cnt_reg0_tx_mac_partial2_invert_crc_cnt {
      type oc-yang:counter64;
      description
        "Counts the number of transmitted packets with partial CRC type 2.";
    }
    leaf counter_slice2_ifg_mac_pool86_tx_mac_partial2_invert_crc_cnt_reg1_tx_mac_partial2_invert_crc_cnt {
      type oc-yang:counter64;
      description
        "Counts the number of transmitted packets with partial CRC type 2.";
    }
    leaf counter_slice2_ifg_mac_pool86_tx_mac_partial2_invert_crc_cnt_reg2_tx_mac_partial2_invert_crc_cnt {
      type oc-yang:counter64;
      description
        "Counts the number of transmitted packets with partial CRC type 2.";
    }
    leaf counter_slice2_ifg_mac_pool86_tx_mac_partial2_invert_crc_cnt_reg3_tx_mac_partial2_invert_crc_cnt {
      type oc-yang:counter64;
      description
        "Counts the number of transmitted packets with partial CRC type 2.";
    }
    leaf counter_slice2_ifg_mac_pool86_tx_mac_partial2_invert_crc_cnt_reg4_tx_mac_partial2_invert_crc_cnt {
      type oc-yang:counter64;
      description
        "Counts the number of transmitted packets with partial CRC type 2.";
    }
    leaf counter_slice2_ifg_mac_pool86_tx_mac_partial2_invert_crc_cnt_reg5_tx_mac_partial2_invert_crc_cnt {
      type oc-yang:counter64;
      description
        "Counts the number of transmitted packets with partial CRC type 2.";
    }
    leaf counter_slice2_ifg_mac_pool86_tx_mac_partial2_invert_crc_cnt_reg6_tx_mac_partial2_invert_crc_cnt {
      type oc-yang:counter64;
      description
        "Counts the number of transmitted packets with partial CRC type 2.";
    }
    leaf counter_slice2_ifg_mac_pool86_tx_mac_partial2_invert_crc_cnt_reg7_tx_mac_partial2_invert_crc_cnt {
      type oc-yang:counter64;
      description
        "Counts the number of transmitted packets with partial CRC type 2.";
    }
    leaf counter_slice2_ifg_mac_pool87_tx_mac_partial2_invert_crc_cnt_reg0_tx_mac_partial2_invert_crc_cnt {
      type oc-yang:counter64;
      description
        "Counts the number of transmitted packets with partial CRC type 2.";
    }
    leaf counter_slice2_ifg_mac_pool87_tx_mac_partial2_invert_crc_cnt_reg1_tx_mac_partial2_invert_crc_cnt {
      type oc-yang:counter64;
      description
        "Counts the number of transmitted packets with partial CRC type 2.";
    }
    leaf counter_slice2_ifg_mac_pool87_tx_mac_partial2_invert_crc_cnt_reg2_tx_mac_partial2_invert_crc_cnt {
      type oc-yang:counter64;
      description
        "Counts the number of transmitted packets with partial CRC type 2.";
    }
    leaf counter_slice2_ifg_mac_pool87_tx_mac_partial2_invert_crc_cnt_reg3_tx_mac_partial2_invert_crc_cnt {
      type oc-yang:counter64;
      description
        "Counts the number of transmitted packets with partial CRC type 2.";
    }
    leaf counter_slice2_ifg_mac_pool87_tx_mac_partial2_invert_crc_cnt_reg4_tx_mac_partial2_invert_crc_cnt {
      type oc-yang:counter64;
      description
        "Counts the number of transmitted packets with partial CRC type 2.";
    }
    leaf counter_slice2_ifg_mac_pool87_tx_mac_partial2_invert_crc_cnt_reg5_tx_mac_partial2_invert_crc_cnt {
      type oc-yang:counter64;
      description
        "Counts the number of transmitted packets with partial CRC type 2.";
    }
    leaf counter_slice2_ifg_mac_pool87_tx_mac_partial2_invert_crc_cnt_reg6_tx_mac_partial2_invert_crc_cnt {
      type oc-yang:counter64;
      description
        "Counts the number of transmitted packets with partial CRC type 2.";
    }
    leaf counter_slice2_ifg_mac_pool87_tx_mac_partial2_invert_crc_cnt_reg7_tx_mac_partial2_invert_crc_cnt {
      type oc-yang:counter64;
      description
        "Counts the number of transmitted packets with partial CRC type 2.";
    }
    leaf counter_slice3_ifg_mac_pool80_tx_mac_partial2_invert_crc_cnt_reg0_tx_mac_partial2_invert_crc_cnt {
      type oc-yang:counter64;
      description
        "Counts the number of transmitted packets with partial CRC type 2.";
    }
    leaf counter_slice3_ifg_mac_pool80_tx_mac_partial2_invert_crc_cnt_reg1_tx_mac_partial2_invert_crc_cnt {
      type oc-yang:counter64;
      description
        "Counts the number of transmitted packets with partial CRC type 2.";
    }
    leaf counter_slice3_ifg_mac_pool80_tx_mac_partial2_invert_crc_cnt_reg2_tx_mac_partial2_invert_crc_cnt {
      type oc-yang:counter64;
      description
        "Counts the number of transmitted packets with partial CRC type 2.";
    }
    leaf counter_slice3_ifg_mac_pool80_tx_mac_partial2_invert_crc_cnt_reg3_tx_mac_partial2_invert_crc_cnt {
      type oc-yang:counter64;
      description
        "Counts the number of transmitted packets with partial CRC type 2.";
    }
    leaf counter_slice3_ifg_mac_pool80_tx_mac_partial2_invert_crc_cnt_reg4_tx_mac_partial2_invert_crc_cnt {
      type oc-yang:counter64;
      description
        "Counts the number of transmitted packets with partial CRC type 2.";
    }
    leaf counter_slice3_ifg_mac_pool80_tx_mac_partial2_invert_crc_cnt_reg5_tx_mac_partial2_invert_crc_cnt {
      type oc-yang:counter64;
      description
        "Counts the number of transmitted packets with partial CRC type 2.";
    }
    leaf counter_slice3_ifg_mac_pool80_tx_mac_partial2_invert_crc_cnt_reg6_tx_mac_partial2_invert_crc_cnt {
      type oc-yang:counter64;
      description
        "Counts the number of transmitted packets with partial CRC type 2.";
    }
    leaf counter_slice3_ifg_mac_pool80_tx_mac_partial2_invert_crc_cnt_reg7_tx_mac_partial2_invert_crc_cnt {
      type oc-yang:counter64;
      description
        "Counts the number of transmitted packets with partial CRC type 2.";
    }
    leaf counter_slice3_ifg_mac_pool81_tx_mac_partial2_invert_crc_cnt_reg0_tx_mac_partial2_invert_crc_cnt {
      type oc-yang:counter64;
      description
        "Counts the number of transmitted packets with partial CRC type 2.";
    }
    leaf counter_slice3_ifg_mac_pool81_tx_mac_partial2_invert_crc_cnt_reg1_tx_mac_partial2_invert_crc_cnt {
      type oc-yang:counter64;
      description
        "Counts the number of transmitted packets with partial CRC type 2.";
    }
    leaf counter_slice3_ifg_mac_pool81_tx_mac_partial2_invert_crc_cnt_reg2_tx_mac_partial2_invert_crc_cnt {
      type oc-yang:counter64;
      description
        "Counts the number of transmitted packets with partial CRC type 2.";
    }
    leaf counter_slice3_ifg_mac_pool81_tx_mac_partial2_invert_crc_cnt_reg3_tx_mac_partial2_invert_crc_cnt {
      type oc-yang:counter64;
      description
        "Counts the number of transmitted packets with partial CRC type 2.";
    }
    leaf counter_slice3_ifg_mac_pool81_tx_mac_partial2_invert_crc_cnt_reg4_tx_mac_partial2_invert_crc_cnt {
      type oc-yang:counter64;
      description
        "Counts the number of transmitted packets with partial CRC type 2.";
    }
    leaf counter_slice3_ifg_mac_pool81_tx_mac_partial2_invert_crc_cnt_reg5_tx_mac_partial2_invert_crc_cnt {
      type oc-yang:counter64;
      description
        "Counts the number of transmitted packets with partial CRC type 2.";
    }
    leaf counter_slice3_ifg_mac_pool81_tx_mac_partial2_invert_crc_cnt_reg6_tx_mac_partial2_invert_crc_cnt {
      type oc-yang:counter64;
      description
        "Counts the number of transmitted packets with partial CRC type 2.";
    }
    leaf counter_slice3_ifg_mac_pool81_tx_mac_partial2_invert_crc_cnt_reg7_tx_mac_partial2_invert_crc_cnt {
      type oc-yang:counter64;
      description
        "Counts the number of transmitted packets with partial CRC type 2.";
    }
    leaf counter_slice3_ifg_mac_pool82_tx_mac_partial2_invert_crc_cnt_reg0_tx_mac_partial2_invert_crc_cnt {
      type oc-yang:counter64;
      description
        "Counts the number of transmitted packets with partial CRC type 2.";
    }
    leaf counter_slice3_ifg_mac_pool82_tx_mac_partial2_invert_crc_cnt_reg1_tx_mac_partial2_invert_crc_cnt {
      type oc-yang:counter64;
      description
        "Counts the number of transmitted packets with partial CRC type 2.";
    }
    leaf counter_slice3_ifg_mac_pool82_tx_mac_partial2_invert_crc_cnt_reg2_tx_mac_partial2_invert_crc_cnt {
      type oc-yang:counter64;
      description
        "Counts the number of transmitted packets with partial CRC type 2.";
    }
    leaf counter_slice3_ifg_mac_pool82_tx_mac_partial2_invert_crc_cnt_reg3_tx_mac_partial2_invert_crc_cnt {
      type oc-yang:counter64;
      description
        "Counts the number of transmitted packets with partial CRC type 2.";
    }
    leaf counter_slice3_ifg_mac_pool82_tx_mac_partial2_invert_crc_cnt_reg4_tx_mac_partial2_invert_crc_cnt {
      type oc-yang:counter64;
      description
        "Counts the number of transmitted packets with partial CRC type 2.";
    }
    leaf counter_slice3_ifg_mac_pool82_tx_mac_partial2_invert_crc_cnt_reg5_tx_mac_partial2_invert_crc_cnt {
      type oc-yang:counter64;
      description
        "Counts the number of transmitted packets with partial CRC type 2.";
    }
    leaf counter_slice3_ifg_mac_pool82_tx_mac_partial2_invert_crc_cnt_reg6_tx_mac_partial2_invert_crc_cnt {
      type oc-yang:counter64;
      description
        "Counts the number of transmitted packets with partial CRC type 2.";
    }
    leaf counter_slice3_ifg_mac_pool82_tx_mac_partial2_invert_crc_cnt_reg7_tx_mac_partial2_invert_crc_cnt {
      type oc-yang:counter64;
      description
        "Counts the number of transmitted packets with partial CRC type 2.";
    }
    leaf counter_slice3_ifg_mac_pool83_tx_mac_partial2_invert_crc_cnt_reg0_tx_mac_partial2_invert_crc_cnt {
      type oc-yang:counter64;
      description
        "Counts the number of transmitted packets with partial CRC type 2.";
    }
    leaf counter_slice3_ifg_mac_pool83_tx_mac_partial2_invert_crc_cnt_reg1_tx_mac_partial2_invert_crc_cnt {
      type oc-yang:counter64;
      description
        "Counts the number of transmitted packets with partial CRC type 2.";
    }
    leaf counter_slice3_ifg_mac_pool83_tx_mac_partial2_invert_crc_cnt_reg2_tx_mac_partial2_invert_crc_cnt {
      type oc-yang:counter64;
      description
        "Counts the number of transmitted packets with partial CRC type 2.";
    }
    leaf counter_slice3_ifg_mac_pool83_tx_mac_partial2_invert_crc_cnt_reg3_tx_mac_partial2_invert_crc_cnt {
      type oc-yang:counter64;
      description
        "Counts the number of transmitted packets with partial CRC type 2.";
    }
    leaf counter_slice3_ifg_mac_pool83_tx_mac_partial2_invert_crc_cnt_reg4_tx_mac_partial2_invert_crc_cnt {
      type oc-yang:counter64;
      description
        "Counts the number of transmitted packets with partial CRC type 2.";
    }
    leaf counter_slice3_ifg_mac_pool83_tx_mac_partial2_invert_crc_cnt_reg5_tx_mac_partial2_invert_crc_cnt {
      type oc-yang:counter64;
      description
        "Counts the number of transmitted packets with partial CRC type 2.";
    }
    leaf counter_slice3_ifg_mac_pool83_tx_mac_partial2_invert_crc_cnt_reg6_tx_mac_partial2_invert_crc_cnt {
      type oc-yang:counter64;
      description
        "Counts the number of transmitted packets with partial CRC type 2.";
    }
    leaf counter_slice3_ifg_mac_pool83_tx_mac_partial2_invert_crc_cnt_reg7_tx_mac_partial2_invert_crc_cnt {
      type oc-yang:counter64;
      description
        "Counts the number of transmitted packets with partial CRC type 2.";
    }
    leaf counter_slice3_ifg_mac_pool84_tx_mac_partial2_invert_crc_cnt_reg0_tx_mac_partial2_invert_crc_cnt {
      type oc-yang:counter64;
      description
        "Counts the number of transmitted packets with partial CRC type 2.";
    }
    leaf counter_slice3_ifg_mac_pool84_tx_mac_partial2_invert_crc_cnt_reg1_tx_mac_partial2_invert_crc_cnt {
      type oc-yang:counter64;
      description
        "Counts the number of transmitted packets with partial CRC type 2.";
    }
    leaf counter_slice3_ifg_mac_pool84_tx_mac_partial2_invert_crc_cnt_reg2_tx_mac_partial2_invert_crc_cnt {
      type oc-yang:counter64;
      description
        "Counts the number of transmitted packets with partial CRC type 2.";
    }
    leaf counter_slice3_ifg_mac_pool84_tx_mac_partial2_invert_crc_cnt_reg3_tx_mac_partial2_invert_crc_cnt {
      type oc-yang:counter64;
      description
        "Counts the number of transmitted packets with partial CRC type 2.";
    }
    leaf counter_slice3_ifg_mac_pool84_tx_mac_partial2_invert_crc_cnt_reg4_tx_mac_partial2_invert_crc_cnt {
      type oc-yang:counter64;
      description
        "Counts the number of transmitted packets with partial CRC type 2.";
    }
    leaf counter_slice3_ifg_mac_pool84_tx_mac_partial2_invert_crc_cnt_reg5_tx_mac_partial2_invert_crc_cnt {
      type oc-yang:counter64;
      description
        "Counts the number of transmitted packets with partial CRC type 2.";
    }
    leaf counter_slice3_ifg_mac_pool84_tx_mac_partial2_invert_crc_cnt_reg6_tx_mac_partial2_invert_crc_cnt {
      type oc-yang:counter64;
      description
        "Counts the number of transmitted packets with partial CRC type 2.";
    }
    leaf counter_slice3_ifg_mac_pool84_tx_mac_partial2_invert_crc_cnt_reg7_tx_mac_partial2_invert_crc_cnt {
      type oc-yang:counter64;
      description
        "Counts the number of transmitted packets with partial CRC type 2.";
    }
    leaf counter_slice3_ifg_mac_pool85_tx_mac_partial2_invert_crc_cnt_reg0_tx_mac_partial2_invert_crc_cnt {
      type oc-yang:counter64;
      description
        "Counts the number of transmitted packets with partial CRC type 2.";
    }
    leaf counter_slice3_ifg_mac_pool85_tx_mac_partial2_invert_crc_cnt_reg1_tx_mac_partial2_invert_crc_cnt {
      type oc-yang:counter64;
      description
        "Counts the number of transmitted packets with partial CRC type 2.";
    }
    leaf counter_slice3_ifg_mac_pool85_tx_mac_partial2_invert_crc_cnt_reg2_tx_mac_partial2_invert_crc_cnt {
      type oc-yang:counter64;
      description
        "Counts the number of transmitted packets with partial CRC type 2.";
    }
    leaf counter_slice3_ifg_mac_pool85_tx_mac_partial2_invert_crc_cnt_reg3_tx_mac_partial2_invert_crc_cnt {
      type oc-yang:counter64;
      description
        "Counts the number of transmitted packets with partial CRC type 2.";
    }
    leaf counter_slice3_ifg_mac_pool85_tx_mac_partial2_invert_crc_cnt_reg4_tx_mac_partial2_invert_crc_cnt {
      type oc-yang:counter64;
      description
        "Counts the number of transmitted packets with partial CRC type 2.";
    }
    leaf counter_slice3_ifg_mac_pool85_tx_mac_partial2_invert_crc_cnt_reg5_tx_mac_partial2_invert_crc_cnt {
      type oc-yang:counter64;
      description
        "Counts the number of transmitted packets with partial CRC type 2.";
    }
    leaf counter_slice3_ifg_mac_pool85_tx_mac_partial2_invert_crc_cnt_reg6_tx_mac_partial2_invert_crc_cnt {
      type oc-yang:counter64;
      description
        "Counts the number of transmitted packets with partial CRC type 2.";
    }
    leaf counter_slice3_ifg_mac_pool85_tx_mac_partial2_invert_crc_cnt_reg7_tx_mac_partial2_invert_crc_cnt {
      type oc-yang:counter64;
      description
        "Counts the number of transmitted packets with partial CRC type 2.";
    }
    leaf counter_slice3_ifg_mac_pool86_tx_mac_partial2_invert_crc_cnt_reg0_tx_mac_partial2_invert_crc_cnt {
      type oc-yang:counter64;
      description
        "Counts the number of transmitted packets with partial CRC type 2.";
    }
    leaf counter_slice3_ifg_mac_pool86_tx_mac_partial2_invert_crc_cnt_reg1_tx_mac_partial2_invert_crc_cnt {
      type oc-yang:counter64;
      description
        "Counts the number of transmitted packets with partial CRC type 2.";
    }
    leaf counter_slice3_ifg_mac_pool86_tx_mac_partial2_invert_crc_cnt_reg2_tx_mac_partial2_invert_crc_cnt {
      type oc-yang:counter64;
      description
        "Counts the number of transmitted packets with partial CRC type 2.";
    }
    leaf counter_slice3_ifg_mac_pool86_tx_mac_partial2_invert_crc_cnt_reg3_tx_mac_partial2_invert_crc_cnt {
      type oc-yang:counter64;
      description
        "Counts the number of transmitted packets with partial CRC type 2.";
    }
    leaf counter_slice3_ifg_mac_pool86_tx_mac_partial2_invert_crc_cnt_reg4_tx_mac_partial2_invert_crc_cnt {
      type oc-yang:counter64;
      description
        "Counts the number of transmitted packets with partial CRC type 2.";
    }
    leaf counter_slice3_ifg_mac_pool86_tx_mac_partial2_invert_crc_cnt_reg5_tx_mac_partial2_invert_crc_cnt {
      type oc-yang:counter64;
      description
        "Counts the number of transmitted packets with partial CRC type 2.";
    }
    leaf counter_slice3_ifg_mac_pool86_tx_mac_partial2_invert_crc_cnt_reg6_tx_mac_partial2_invert_crc_cnt {
      type oc-yang:counter64;
      description
        "Counts the number of transmitted packets with partial CRC type 2.";
    }
    leaf counter_slice3_ifg_mac_pool86_tx_mac_partial2_invert_crc_cnt_reg7_tx_mac_partial2_invert_crc_cnt {
      type oc-yang:counter64;
      description
        "Counts the number of transmitted packets with partial CRC type 2.";
    }
    leaf counter_slice3_ifg_mac_pool87_tx_mac_partial2_invert_crc_cnt_reg0_tx_mac_partial2_invert_crc_cnt {
      type oc-yang:counter64;
      description
        "Counts the number of transmitted packets with partial CRC type 2.";
    }
    leaf counter_slice3_ifg_mac_pool87_tx_mac_partial2_invert_crc_cnt_reg1_tx_mac_partial2_invert_crc_cnt {
      type oc-yang:counter64;
      description
        "Counts the number of transmitted packets with partial CRC type 2.";
    }
    leaf counter_slice3_ifg_mac_pool87_tx_mac_partial2_invert_crc_cnt_reg2_tx_mac_partial2_invert_crc_cnt {
      type oc-yang:counter64;
      description
        "Counts the number of transmitted packets with partial CRC type 2.";
    }
    leaf counter_slice3_ifg_mac_pool87_tx_mac_partial2_invert_crc_cnt_reg3_tx_mac_partial2_invert_crc_cnt {
      type oc-yang:counter64;
      description
        "Counts the number of transmitted packets with partial CRC type 2.";
    }
    leaf counter_slice3_ifg_mac_pool87_tx_mac_partial2_invert_crc_cnt_reg4_tx_mac_partial2_invert_crc_cnt {
      type oc-yang:counter64;
      description
        "Counts the number of transmitted packets with partial CRC type 2.";
    }
    leaf counter_slice3_ifg_mac_pool87_tx_mac_partial2_invert_crc_cnt_reg5_tx_mac_partial2_invert_crc_cnt {
      type oc-yang:counter64;
      description
        "Counts the number of transmitted packets with partial CRC type 2.";
    }
    leaf counter_slice3_ifg_mac_pool87_tx_mac_partial2_invert_crc_cnt_reg6_tx_mac_partial2_invert_crc_cnt {
      type oc-yang:counter64;
      description
        "Counts the number of transmitted packets with partial CRC type 2.";
    }
    leaf counter_slice3_ifg_mac_pool87_tx_mac_partial2_invert_crc_cnt_reg7_tx_mac_partial2_invert_crc_cnt {
      type oc-yang:counter64;
      description
        "Counts the number of transmitted packets with partial CRC type 2.";
    }
    leaf counter_slice4_ifg_mac_pool80_tx_mac_partial2_invert_crc_cnt_reg0_tx_mac_partial2_invert_crc_cnt {
      type oc-yang:counter64;
      description
        "Counts the number of transmitted packets with partial CRC type 2.";
    }
    leaf counter_slice4_ifg_mac_pool80_tx_mac_partial2_invert_crc_cnt_reg1_tx_mac_partial2_invert_crc_cnt {
      type oc-yang:counter64;
      description
        "Counts the number of transmitted packets with partial CRC type 2.";
    }
    leaf counter_slice4_ifg_mac_pool80_tx_mac_partial2_invert_crc_cnt_reg2_tx_mac_partial2_invert_crc_cnt {
      type oc-yang:counter64;
      description
        "Counts the number of transmitted packets with partial CRC type 2.";
    }
    leaf counter_slice4_ifg_mac_pool80_tx_mac_partial2_invert_crc_cnt_reg3_tx_mac_partial2_invert_crc_cnt {
      type oc-yang:counter64;
      description
        "Counts the number of transmitted packets with partial CRC type 2.";
    }
    leaf counter_slice4_ifg_mac_pool80_tx_mac_partial2_invert_crc_cnt_reg4_tx_mac_partial2_invert_crc_cnt {
      type oc-yang:counter64;
      description
        "Counts the number of transmitted packets with partial CRC type 2.";
    }
    leaf counter_slice4_ifg_mac_pool80_tx_mac_partial2_invert_crc_cnt_reg5_tx_mac_partial2_invert_crc_cnt {
      type oc-yang:counter64;
      description
        "Counts the number of transmitted packets with partial CRC type 2.";
    }
    leaf counter_slice4_ifg_mac_pool80_tx_mac_partial2_invert_crc_cnt_reg6_tx_mac_partial2_invert_crc_cnt {
      type oc-yang:counter64;
      description
        "Counts the number of transmitted packets with partial CRC type 2.";
    }
    leaf counter_slice4_ifg_mac_pool80_tx_mac_partial2_invert_crc_cnt_reg7_tx_mac_partial2_invert_crc_cnt {
      type oc-yang:counter64;
      description
        "Counts the number of transmitted packets with partial CRC type 2.";
    }
    leaf counter_slice4_ifg_mac_pool81_tx_mac_partial2_invert_crc_cnt_reg0_tx_mac_partial2_invert_crc_cnt {
      type oc-yang:counter64;
      description
        "Counts the number of transmitted packets with partial CRC type 2.";
    }
    leaf counter_slice4_ifg_mac_pool81_tx_mac_partial2_invert_crc_cnt_reg1_tx_mac_partial2_invert_crc_cnt {
      type oc-yang:counter64;
      description
        "Counts the number of transmitted packets with partial CRC type 2.";
    }
    leaf counter_slice4_ifg_mac_pool81_tx_mac_partial2_invert_crc_cnt_reg2_tx_mac_partial2_invert_crc_cnt {
      type oc-yang:counter64;
      description
        "Counts the number of transmitted packets with partial CRC type 2.";
    }
    leaf counter_slice4_ifg_mac_pool81_tx_mac_partial2_invert_crc_cnt_reg3_tx_mac_partial2_invert_crc_cnt {
      type oc-yang:counter64;
      description
        "Counts the number of transmitted packets with partial CRC type 2.";
    }
    leaf counter_slice4_ifg_mac_pool81_tx_mac_partial2_invert_crc_cnt_reg4_tx_mac_partial2_invert_crc_cnt {
      type oc-yang:counter64;
      description
        "Counts the number of transmitted packets with partial CRC type 2.";
    }
    leaf counter_slice4_ifg_mac_pool81_tx_mac_partial2_invert_crc_cnt_reg5_tx_mac_partial2_invert_crc_cnt {
      type oc-yang:counter64;
      description
        "Counts the number of transmitted packets with partial CRC type 2.";
    }
    leaf counter_slice4_ifg_mac_pool81_tx_mac_partial2_invert_crc_cnt_reg6_tx_mac_partial2_invert_crc_cnt {
      type oc-yang:counter64;
      description
        "Counts the number of transmitted packets with partial CRC type 2.";
    }
    leaf counter_slice4_ifg_mac_pool81_tx_mac_partial2_invert_crc_cnt_reg7_tx_mac_partial2_invert_crc_cnt {
      type oc-yang:counter64;
      description
        "Counts the number of transmitted packets with partial CRC type 2.";
    }
    leaf counter_slice4_ifg_mac_pool82_tx_mac_partial2_invert_crc_cnt_reg0_tx_mac_partial2_invert_crc_cnt {
      type oc-yang:counter64;
      description
        "Counts the number of transmitted packets with partial CRC type 2.";
    }
    leaf counter_slice4_ifg_mac_pool82_tx_mac_partial2_invert_crc_cnt_reg1_tx_mac_partial2_invert_crc_cnt {
      type oc-yang:counter64;
      description
        "Counts the number of transmitted packets with partial CRC type 2.";
    }
    leaf counter_slice4_ifg_mac_pool82_tx_mac_partial2_invert_crc_cnt_reg2_tx_mac_partial2_invert_crc_cnt {
      type oc-yang:counter64;
      description
        "Counts the number of transmitted packets with partial CRC type 2.";
    }
    leaf counter_slice4_ifg_mac_pool82_tx_mac_partial2_invert_crc_cnt_reg3_tx_mac_partial2_invert_crc_cnt {
      type oc-yang:counter64;
      description
        "Counts the number of transmitted packets with partial CRC type 2.";
    }
    leaf counter_slice4_ifg_mac_pool82_tx_mac_partial2_invert_crc_cnt_reg4_tx_mac_partial2_invert_crc_cnt {
      type oc-yang:counter64;
      description
        "Counts the number of transmitted packets with partial CRC type 2.";
    }
    leaf counter_slice4_ifg_mac_pool82_tx_mac_partial2_invert_crc_cnt_reg5_tx_mac_partial2_invert_crc_cnt {
      type oc-yang:counter64;
      description
        "Counts the number of transmitted packets with partial CRC type 2.";
    }
    leaf counter_slice4_ifg_mac_pool82_tx_mac_partial2_invert_crc_cnt_reg6_tx_mac_partial2_invert_crc_cnt {
      type oc-yang:counter64;
      description
        "Counts the number of transmitted packets with partial CRC type 2.";
    }
    leaf counter_slice4_ifg_mac_pool82_tx_mac_partial2_invert_crc_cnt_reg7_tx_mac_partial2_invert_crc_cnt {
      type oc-yang:counter64;
      description
        "Counts the number of transmitted packets with partial CRC type 2.";
    }
    leaf counter_slice4_ifg_mac_pool83_tx_mac_partial2_invert_crc_cnt_reg0_tx_mac_partial2_invert_crc_cnt {
      type oc-yang:counter64;
      description
        "Counts the number of transmitted packets with partial CRC type 2.";
    }
    leaf counter_slice4_ifg_mac_pool83_tx_mac_partial2_invert_crc_cnt_reg1_tx_mac_partial2_invert_crc_cnt {
      type oc-yang:counter64;
      description
        "Counts the number of transmitted packets with partial CRC type 2.";
    }
    leaf counter_slice4_ifg_mac_pool83_tx_mac_partial2_invert_crc_cnt_reg2_tx_mac_partial2_invert_crc_cnt {
      type oc-yang:counter64;
      description
        "Counts the number of transmitted packets with partial CRC type 2.";
    }
    leaf counter_slice4_ifg_mac_pool83_tx_mac_partial2_invert_crc_cnt_reg3_tx_mac_partial2_invert_crc_cnt {
      type oc-yang:counter64;
      description
        "Counts the number of transmitted packets with partial CRC type 2.";
    }
    leaf counter_slice4_ifg_mac_pool83_tx_mac_partial2_invert_crc_cnt_reg4_tx_mac_partial2_invert_crc_cnt {
      type oc-yang:counter64;
      description
        "Counts the number of transmitted packets with partial CRC type 2.";
    }
    leaf counter_slice4_ifg_mac_pool83_tx_mac_partial2_invert_crc_cnt_reg5_tx_mac_partial2_invert_crc_cnt {
      type oc-yang:counter64;
      description
        "Counts the number of transmitted packets with partial CRC type 2.";
    }
    leaf counter_slice4_ifg_mac_pool83_tx_mac_partial2_invert_crc_cnt_reg6_tx_mac_partial2_invert_crc_cnt {
      type oc-yang:counter64;
      description
        "Counts the number of transmitted packets with partial CRC type 2.";
    }
    leaf counter_slice4_ifg_mac_pool83_tx_mac_partial2_invert_crc_cnt_reg7_tx_mac_partial2_invert_crc_cnt {
      type oc-yang:counter64;
      description
        "Counts the number of transmitted packets with partial CRC type 2.";
    }
    leaf counter_slice4_ifg_mac_pool84_tx_mac_partial2_invert_crc_cnt_reg0_tx_mac_partial2_invert_crc_cnt {
      type oc-yang:counter64;
      description
        "Counts the number of transmitted packets with partial CRC type 2.";
    }
    leaf counter_slice4_ifg_mac_pool84_tx_mac_partial2_invert_crc_cnt_reg1_tx_mac_partial2_invert_crc_cnt {
      type oc-yang:counter64;
      description
        "Counts the number of transmitted packets with partial CRC type 2.";
    }
    leaf counter_slice4_ifg_mac_pool84_tx_mac_partial2_invert_crc_cnt_reg2_tx_mac_partial2_invert_crc_cnt {
      type oc-yang:counter64;
      description
        "Counts the number of transmitted packets with partial CRC type 2.";
    }
    leaf counter_slice4_ifg_mac_pool84_tx_mac_partial2_invert_crc_cnt_reg3_tx_mac_partial2_invert_crc_cnt {
      type oc-yang:counter64;
      description
        "Counts the number of transmitted packets with partial CRC type 2.";
    }
    leaf counter_slice4_ifg_mac_pool84_tx_mac_partial2_invert_crc_cnt_reg4_tx_mac_partial2_invert_crc_cnt {
      type oc-yang:counter64;
      description
        "Counts the number of transmitted packets with partial CRC type 2.";
    }
    leaf counter_slice4_ifg_mac_pool84_tx_mac_partial2_invert_crc_cnt_reg5_tx_mac_partial2_invert_crc_cnt {
      type oc-yang:counter64;
      description
        "Counts the number of transmitted packets with partial CRC type 2.";
    }
    leaf counter_slice4_ifg_mac_pool84_tx_mac_partial2_invert_crc_cnt_reg6_tx_mac_partial2_invert_crc_cnt {
      type oc-yang:counter64;
      description
        "Counts the number of transmitted packets with partial CRC type 2.";
    }
    leaf counter_slice4_ifg_mac_pool84_tx_mac_partial2_invert_crc_cnt_reg7_tx_mac_partial2_invert_crc_cnt {
      type oc-yang:counter64;
      description
        "Counts the number of transmitted packets with partial CRC type 2.";
    }
    leaf counter_slice4_ifg_mac_pool85_tx_mac_partial2_invert_crc_cnt_reg0_tx_mac_partial2_invert_crc_cnt {
      type oc-yang:counter64;
      description
        "Counts the number of transmitted packets with partial CRC type 2.";
    }
    leaf counter_slice4_ifg_mac_pool85_tx_mac_partial2_invert_crc_cnt_reg1_tx_mac_partial2_invert_crc_cnt {
      type oc-yang:counter64;
      description
        "Counts the number of transmitted packets with partial CRC type 2.";
    }
    leaf counter_slice4_ifg_mac_pool85_tx_mac_partial2_invert_crc_cnt_reg2_tx_mac_partial2_invert_crc_cnt {
      type oc-yang:counter64;
      description
        "Counts the number of transmitted packets with partial CRC type 2.";
    }
    leaf counter_slice4_ifg_mac_pool85_tx_mac_partial2_invert_crc_cnt_reg3_tx_mac_partial2_invert_crc_cnt {
      type oc-yang:counter64;
      description
        "Counts the number of transmitted packets with partial CRC type 2.";
    }
    leaf counter_slice4_ifg_mac_pool85_tx_mac_partial2_invert_crc_cnt_reg4_tx_mac_partial2_invert_crc_cnt {
      type oc-yang:counter64;
      description
        "Counts the number of transmitted packets with partial CRC type 2.";
    }
    leaf counter_slice4_ifg_mac_pool85_tx_mac_partial2_invert_crc_cnt_reg5_tx_mac_partial2_invert_crc_cnt {
      type oc-yang:counter64;
      description
        "Counts the number of transmitted packets with partial CRC type 2.";
    }
    leaf counter_slice4_ifg_mac_pool85_tx_mac_partial2_invert_crc_cnt_reg6_tx_mac_partial2_invert_crc_cnt {
      type oc-yang:counter64;
      description
        "Counts the number of transmitted packets with partial CRC type 2.";
    }
    leaf counter_slice4_ifg_mac_pool85_tx_mac_partial2_invert_crc_cnt_reg7_tx_mac_partial2_invert_crc_cnt {
      type oc-yang:counter64;
      description
        "Counts the number of transmitted packets with partial CRC type 2.";
    }
    leaf counter_slice4_ifg_mac_pool86_tx_mac_partial2_invert_crc_cnt_reg0_tx_mac_partial2_invert_crc_cnt {
      type oc-yang:counter64;
      description
        "Counts the number of transmitted packets with partial CRC type 2.";
    }
    leaf counter_slice4_ifg_mac_pool86_tx_mac_partial2_invert_crc_cnt_reg1_tx_mac_partial2_invert_crc_cnt {
      type oc-yang:counter64;
      description
        "Counts the number of transmitted packets with partial CRC type 2.";
    }
    leaf counter_slice4_ifg_mac_pool86_tx_mac_partial2_invert_crc_cnt_reg2_tx_mac_partial2_invert_crc_cnt {
      type oc-yang:counter64;
      description
        "Counts the number of transmitted packets with partial CRC type 2.";
    }
    leaf counter_slice4_ifg_mac_pool86_tx_mac_partial2_invert_crc_cnt_reg3_tx_mac_partial2_invert_crc_cnt {
      type oc-yang:counter64;
      description
        "Counts the number of transmitted packets with partial CRC type 2.";
    }
    leaf counter_slice4_ifg_mac_pool86_tx_mac_partial2_invert_crc_cnt_reg4_tx_mac_partial2_invert_crc_cnt {
      type oc-yang:counter64;
      description
        "Counts the number of transmitted packets with partial CRC type 2.";
    }
    leaf counter_slice4_ifg_mac_pool86_tx_mac_partial2_invert_crc_cnt_reg5_tx_mac_partial2_invert_crc_cnt {
      type oc-yang:counter64;
      description
        "Counts the number of transmitted packets with partial CRC type 2.";
    }
    leaf counter_slice4_ifg_mac_pool86_tx_mac_partial2_invert_crc_cnt_reg6_tx_mac_partial2_invert_crc_cnt {
      type oc-yang:counter64;
      description
        "Counts the number of transmitted packets with partial CRC type 2.";
    }
    leaf counter_slice4_ifg_mac_pool86_tx_mac_partial2_invert_crc_cnt_reg7_tx_mac_partial2_invert_crc_cnt {
      type oc-yang:counter64;
      description
        "Counts the number of transmitted packets with partial CRC type 2.";
    }
    leaf counter_slice4_ifg_mac_pool87_tx_mac_partial2_invert_crc_cnt_reg0_tx_mac_partial2_invert_crc_cnt {
      type oc-yang:counter64;
      description
        "Counts the number of transmitted packets with partial CRC type 2.";
    }
    leaf counter_slice4_ifg_mac_pool87_tx_mac_partial2_invert_crc_cnt_reg1_tx_mac_partial2_invert_crc_cnt {
      type oc-yang:counter64;
      description
        "Counts the number of transmitted packets with partial CRC type 2.";
    }
    leaf counter_slice4_ifg_mac_pool87_tx_mac_partial2_invert_crc_cnt_reg2_tx_mac_partial2_invert_crc_cnt {
      type oc-yang:counter64;
      description
        "Counts the number of transmitted packets with partial CRC type 2.";
    }
    leaf counter_slice4_ifg_mac_pool87_tx_mac_partial2_invert_crc_cnt_reg3_tx_mac_partial2_invert_crc_cnt {
      type oc-yang:counter64;
      description
        "Counts the number of transmitted packets with partial CRC type 2.";
    }
    leaf counter_slice4_ifg_mac_pool87_tx_mac_partial2_invert_crc_cnt_reg4_tx_mac_partial2_invert_crc_cnt {
      type oc-yang:counter64;
      description
        "Counts the number of transmitted packets with partial CRC type 2.";
    }
    leaf counter_slice4_ifg_mac_pool87_tx_mac_partial2_invert_crc_cnt_reg5_tx_mac_partial2_invert_crc_cnt {
      type oc-yang:counter64;
      description
        "Counts the number of transmitted packets with partial CRC type 2.";
    }
    leaf counter_slice4_ifg_mac_pool87_tx_mac_partial2_invert_crc_cnt_reg6_tx_mac_partial2_invert_crc_cnt {
      type oc-yang:counter64;
      description
        "Counts the number of transmitted packets with partial CRC type 2.";
    }
    leaf counter_slice4_ifg_mac_pool87_tx_mac_partial2_invert_crc_cnt_reg7_tx_mac_partial2_invert_crc_cnt {
      type oc-yang:counter64;
      description
        "Counts the number of transmitted packets with partial CRC type 2.";
    }
    leaf counter_slice5_ifg_mac_pool80_tx_mac_partial2_invert_crc_cnt_reg0_tx_mac_partial2_invert_crc_cnt {
      type oc-yang:counter64;
      description
        "Counts the number of transmitted packets with partial CRC type 2.";
    }
    leaf counter_slice5_ifg_mac_pool80_tx_mac_partial2_invert_crc_cnt_reg1_tx_mac_partial2_invert_crc_cnt {
      type oc-yang:counter64;
      description
        "Counts the number of transmitted packets with partial CRC type 2.";
    }
    leaf counter_slice5_ifg_mac_pool80_tx_mac_partial2_invert_crc_cnt_reg2_tx_mac_partial2_invert_crc_cnt {
      type oc-yang:counter64;
      description
        "Counts the number of transmitted packets with partial CRC type 2.";
    }
    leaf counter_slice5_ifg_mac_pool80_tx_mac_partial2_invert_crc_cnt_reg3_tx_mac_partial2_invert_crc_cnt {
      type oc-yang:counter64;
      description
        "Counts the number of transmitted packets with partial CRC type 2.";
    }
    leaf counter_slice5_ifg_mac_pool80_tx_mac_partial2_invert_crc_cnt_reg4_tx_mac_partial2_invert_crc_cnt {
      type oc-yang:counter64;
      description
        "Counts the number of transmitted packets with partial CRC type 2.";
    }
    leaf counter_slice5_ifg_mac_pool80_tx_mac_partial2_invert_crc_cnt_reg5_tx_mac_partial2_invert_crc_cnt {
      type oc-yang:counter64;
      description
        "Counts the number of transmitted packets with partial CRC type 2.";
    }
    leaf counter_slice5_ifg_mac_pool80_tx_mac_partial2_invert_crc_cnt_reg6_tx_mac_partial2_invert_crc_cnt {
      type oc-yang:counter64;
      description
        "Counts the number of transmitted packets with partial CRC type 2.";
    }
    leaf counter_slice5_ifg_mac_pool80_tx_mac_partial2_invert_crc_cnt_reg7_tx_mac_partial2_invert_crc_cnt {
      type oc-yang:counter64;
      description
        "Counts the number of transmitted packets with partial CRC type 2.";
    }
    leaf counter_slice5_ifg_mac_pool81_tx_mac_partial2_invert_crc_cnt_reg0_tx_mac_partial2_invert_crc_cnt {
      type oc-yang:counter64;
      description
        "Counts the number of transmitted packets with partial CRC type 2.";
    }
    leaf counter_slice5_ifg_mac_pool81_tx_mac_partial2_invert_crc_cnt_reg1_tx_mac_partial2_invert_crc_cnt {
      type oc-yang:counter64;
      description
        "Counts the number of transmitted packets with partial CRC type 2.";
    }
    leaf counter_slice5_ifg_mac_pool81_tx_mac_partial2_invert_crc_cnt_reg2_tx_mac_partial2_invert_crc_cnt {
      type oc-yang:counter64;
      description
        "Counts the number of transmitted packets with partial CRC type 2.";
    }
    leaf counter_slice5_ifg_mac_pool81_tx_mac_partial2_invert_crc_cnt_reg3_tx_mac_partial2_invert_crc_cnt {
      type oc-yang:counter64;
      description
        "Counts the number of transmitted packets with partial CRC type 2.";
    }
    leaf counter_slice5_ifg_mac_pool81_tx_mac_partial2_invert_crc_cnt_reg4_tx_mac_partial2_invert_crc_cnt {
      type oc-yang:counter64;
      description
        "Counts the number of transmitted packets with partial CRC type 2.";
    }
    leaf counter_slice5_ifg_mac_pool81_tx_mac_partial2_invert_crc_cnt_reg5_tx_mac_partial2_invert_crc_cnt {
      type oc-yang:counter64;
      description
        "Counts the number of transmitted packets with partial CRC type 2.";
    }
    leaf counter_slice5_ifg_mac_pool81_tx_mac_partial2_invert_crc_cnt_reg6_tx_mac_partial2_invert_crc_cnt {
      type oc-yang:counter64;
      description
        "Counts the number of transmitted packets with partial CRC type 2.";
    }
    leaf counter_slice5_ifg_mac_pool81_tx_mac_partial2_invert_crc_cnt_reg7_tx_mac_partial2_invert_crc_cnt {
      type oc-yang:counter64;
      description
        "Counts the number of transmitted packets with partial CRC type 2.";
    }
    leaf counter_slice5_ifg_mac_pool82_tx_mac_partial2_invert_crc_cnt_reg0_tx_mac_partial2_invert_crc_cnt {
      type oc-yang:counter64;
      description
        "Counts the number of transmitted packets with partial CRC type 2.";
    }
    leaf counter_slice5_ifg_mac_pool82_tx_mac_partial2_invert_crc_cnt_reg1_tx_mac_partial2_invert_crc_cnt {
      type oc-yang:counter64;
      description
        "Counts the number of transmitted packets with partial CRC type 2.";
    }
    leaf counter_slice5_ifg_mac_pool82_tx_mac_partial2_invert_crc_cnt_reg2_tx_mac_partial2_invert_crc_cnt {
      type oc-yang:counter64;
      description
        "Counts the number of transmitted packets with partial CRC type 2.";
    }
    leaf counter_slice5_ifg_mac_pool82_tx_mac_partial2_invert_crc_cnt_reg3_tx_mac_partial2_invert_crc_cnt {
      type oc-yang:counter64;
      description
        "Counts the number of transmitted packets with partial CRC type 2.";
    }
    leaf counter_slice5_ifg_mac_pool82_tx_mac_partial2_invert_crc_cnt_reg4_tx_mac_partial2_invert_crc_cnt {
      type oc-yang:counter64;
      description
        "Counts the number of transmitted packets with partial CRC type 2.";
    }
    leaf counter_slice5_ifg_mac_pool82_tx_mac_partial2_invert_crc_cnt_reg5_tx_mac_partial2_invert_crc_cnt {
      type oc-yang:counter64;
      description
        "Counts the number of transmitted packets with partial CRC type 2.";
    }
    leaf counter_slice5_ifg_mac_pool82_tx_mac_partial2_invert_crc_cnt_reg6_tx_mac_partial2_invert_crc_cnt {
      type oc-yang:counter64;
      description
        "Counts the number of transmitted packets with partial CRC type 2.";
    }
    leaf counter_slice5_ifg_mac_pool82_tx_mac_partial2_invert_crc_cnt_reg7_tx_mac_partial2_invert_crc_cnt {
      type oc-yang:counter64;
      description
        "Counts the number of transmitted packets with partial CRC type 2.";
    }
    leaf counter_slice5_ifg_mac_pool83_tx_mac_partial2_invert_crc_cnt_reg0_tx_mac_partial2_invert_crc_cnt {
      type oc-yang:counter64;
      description
        "Counts the number of transmitted packets with partial CRC type 2.";
    }
    leaf counter_slice5_ifg_mac_pool83_tx_mac_partial2_invert_crc_cnt_reg1_tx_mac_partial2_invert_crc_cnt {
      type oc-yang:counter64;
      description
        "Counts the number of transmitted packets with partial CRC type 2.";
    }
    leaf counter_slice5_ifg_mac_pool83_tx_mac_partial2_invert_crc_cnt_reg2_tx_mac_partial2_invert_crc_cnt {
      type oc-yang:counter64;
      description
        "Counts the number of transmitted packets with partial CRC type 2.";
    }
    leaf counter_slice5_ifg_mac_pool83_tx_mac_partial2_invert_crc_cnt_reg3_tx_mac_partial2_invert_crc_cnt {
      type oc-yang:counter64;
      description
        "Counts the number of transmitted packets with partial CRC type 2.";
    }
    leaf counter_slice5_ifg_mac_pool83_tx_mac_partial2_invert_crc_cnt_reg4_tx_mac_partial2_invert_crc_cnt {
      type oc-yang:counter64;
      description
        "Counts the number of transmitted packets with partial CRC type 2.";
    }
    leaf counter_slice5_ifg_mac_pool83_tx_mac_partial2_invert_crc_cnt_reg5_tx_mac_partial2_invert_crc_cnt {
      type oc-yang:counter64;
      description
        "Counts the number of transmitted packets with partial CRC type 2.";
    }
    leaf counter_slice5_ifg_mac_pool83_tx_mac_partial2_invert_crc_cnt_reg6_tx_mac_partial2_invert_crc_cnt {
      type oc-yang:counter64;
      description
        "Counts the number of transmitted packets with partial CRC type 2.";
    }
    leaf counter_slice5_ifg_mac_pool83_tx_mac_partial2_invert_crc_cnt_reg7_tx_mac_partial2_invert_crc_cnt {
      type oc-yang:counter64;
      description
        "Counts the number of transmitted packets with partial CRC type 2.";
    }
    leaf counter_slice5_ifg_mac_pool84_tx_mac_partial2_invert_crc_cnt_reg0_tx_mac_partial2_invert_crc_cnt {
      type oc-yang:counter64;
      description
        "Counts the number of transmitted packets with partial CRC type 2.";
    }
    leaf counter_slice5_ifg_mac_pool84_tx_mac_partial2_invert_crc_cnt_reg1_tx_mac_partial2_invert_crc_cnt {
      type oc-yang:counter64;
      description
        "Counts the number of transmitted packets with partial CRC type 2.";
    }
    leaf counter_slice5_ifg_mac_pool84_tx_mac_partial2_invert_crc_cnt_reg2_tx_mac_partial2_invert_crc_cnt {
      type oc-yang:counter64;
      description
        "Counts the number of transmitted packets with partial CRC type 2.";
    }
    leaf counter_slice5_ifg_mac_pool84_tx_mac_partial2_invert_crc_cnt_reg3_tx_mac_partial2_invert_crc_cnt {
      type oc-yang:counter64;
      description
        "Counts the number of transmitted packets with partial CRC type 2.";
    }
    leaf counter_slice5_ifg_mac_pool84_tx_mac_partial2_invert_crc_cnt_reg4_tx_mac_partial2_invert_crc_cnt {
      type oc-yang:counter64;
      description
        "Counts the number of transmitted packets with partial CRC type 2.";
    }
    leaf counter_slice5_ifg_mac_pool84_tx_mac_partial2_invert_crc_cnt_reg5_tx_mac_partial2_invert_crc_cnt {
      type oc-yang:counter64;
      description
        "Counts the number of transmitted packets with partial CRC type 2.";
    }
    leaf counter_slice5_ifg_mac_pool84_tx_mac_partial2_invert_crc_cnt_reg6_tx_mac_partial2_invert_crc_cnt {
      type oc-yang:counter64;
      description
        "Counts the number of transmitted packets with partial CRC type 2.";
    }
    leaf counter_slice5_ifg_mac_pool84_tx_mac_partial2_invert_crc_cnt_reg7_tx_mac_partial2_invert_crc_cnt {
      type oc-yang:counter64;
      description
        "Counts the number of transmitted packets with partial CRC type 2.";
    }
    leaf counter_slice5_ifg_mac_pool85_tx_mac_partial2_invert_crc_cnt_reg0_tx_mac_partial2_invert_crc_cnt {
      type oc-yang:counter64;
      description
        "Counts the number of transmitted packets with partial CRC type 2.";
    }
    leaf counter_slice5_ifg_mac_pool85_tx_mac_partial2_invert_crc_cnt_reg1_tx_mac_partial2_invert_crc_cnt {
      type oc-yang:counter64;
      description
        "Counts the number of transmitted packets with partial CRC type 2.";
    }
    leaf counter_slice5_ifg_mac_pool85_tx_mac_partial2_invert_crc_cnt_reg2_tx_mac_partial2_invert_crc_cnt {
      type oc-yang:counter64;
      description
        "Counts the number of transmitted packets with partial CRC type 2.";
    }
    leaf counter_slice5_ifg_mac_pool85_tx_mac_partial2_invert_crc_cnt_reg3_tx_mac_partial2_invert_crc_cnt {
      type oc-yang:counter64;
      description
        "Counts the number of transmitted packets with partial CRC type 2.";
    }
    leaf counter_slice5_ifg_mac_pool85_tx_mac_partial2_invert_crc_cnt_reg4_tx_mac_partial2_invert_crc_cnt {
      type oc-yang:counter64;
      description
        "Counts the number of transmitted packets with partial CRC type 2.";
    }
    leaf counter_slice5_ifg_mac_pool85_tx_mac_partial2_invert_crc_cnt_reg5_tx_mac_partial2_invert_crc_cnt {
      type oc-yang:counter64;
      description
        "Counts the number of transmitted packets with partial CRC type 2.";
    }
    leaf counter_slice5_ifg_mac_pool85_tx_mac_partial2_invert_crc_cnt_reg6_tx_mac_partial2_invert_crc_cnt {
      type oc-yang:counter64;
      description
        "Counts the number of transmitted packets with partial CRC type 2.";
    }
    leaf counter_slice5_ifg_mac_pool85_tx_mac_partial2_invert_crc_cnt_reg7_tx_mac_partial2_invert_crc_cnt {
      type oc-yang:counter64;
      description
        "Counts the number of transmitted packets with partial CRC type 2.";
    }
    leaf counter_slice5_ifg_mac_pool86_tx_mac_partial2_invert_crc_cnt_reg0_tx_mac_partial2_invert_crc_cnt {
      type oc-yang:counter64;
      description
        "Counts the number of transmitted packets with partial CRC type 2.";
    }
    leaf counter_slice5_ifg_mac_pool86_tx_mac_partial2_invert_crc_cnt_reg1_tx_mac_partial2_invert_crc_cnt {
      type oc-yang:counter64;
      description
        "Counts the number of transmitted packets with partial CRC type 2.";
    }
    leaf counter_slice5_ifg_mac_pool86_tx_mac_partial2_invert_crc_cnt_reg2_tx_mac_partial2_invert_crc_cnt {
      type oc-yang:counter64;
      description
        "Counts the number of transmitted packets with partial CRC type 2.";
    }
    leaf counter_slice5_ifg_mac_pool86_tx_mac_partial2_invert_crc_cnt_reg3_tx_mac_partial2_invert_crc_cnt {
      type oc-yang:counter64;
      description
        "Counts the number of transmitted packets with partial CRC type 2.";
    }
    leaf counter_slice5_ifg_mac_pool86_tx_mac_partial2_invert_crc_cnt_reg4_tx_mac_partial2_invert_crc_cnt {
      type oc-yang:counter64;
      description
        "Counts the number of transmitted packets with partial CRC type 2.";
    }
    leaf counter_slice5_ifg_mac_pool86_tx_mac_partial2_invert_crc_cnt_reg5_tx_mac_partial2_invert_crc_cnt {
      type oc-yang:counter64;
      description
        "Counts the number of transmitted packets with partial CRC type 2.";
    }
    leaf counter_slice5_ifg_mac_pool86_tx_mac_partial2_invert_crc_cnt_reg6_tx_mac_partial2_invert_crc_cnt {
      type oc-yang:counter64;
      description
        "Counts the number of transmitted packets with partial CRC type 2.";
    }
    leaf counter_slice5_ifg_mac_pool86_tx_mac_partial2_invert_crc_cnt_reg7_tx_mac_partial2_invert_crc_cnt {
      type oc-yang:counter64;
      description
        "Counts the number of transmitted packets with partial CRC type 2.";
    }
    leaf counter_slice5_ifg_mac_pool87_tx_mac_partial2_invert_crc_cnt_reg0_tx_mac_partial2_invert_crc_cnt {
      type oc-yang:counter64;
      description
        "Counts the number of transmitted packets with partial CRC type 2.";
    }
    leaf counter_slice5_ifg_mac_pool87_tx_mac_partial2_invert_crc_cnt_reg1_tx_mac_partial2_invert_crc_cnt {
      type oc-yang:counter64;
      description
        "Counts the number of transmitted packets with partial CRC type 2.";
    }
    leaf counter_slice5_ifg_mac_pool87_tx_mac_partial2_invert_crc_cnt_reg2_tx_mac_partial2_invert_crc_cnt {
      type oc-yang:counter64;
      description
        "Counts the number of transmitted packets with partial CRC type 2.";
    }
    leaf counter_slice5_ifg_mac_pool87_tx_mac_partial2_invert_crc_cnt_reg3_tx_mac_partial2_invert_crc_cnt {
      type oc-yang:counter64;
      description
        "Counts the number of transmitted packets with partial CRC type 2.";
    }
    leaf counter_slice5_ifg_mac_pool87_tx_mac_partial2_invert_crc_cnt_reg4_tx_mac_partial2_invert_crc_cnt {
      type oc-yang:counter64;
      description
        "Counts the number of transmitted packets with partial CRC type 2.";
    }
    leaf counter_slice5_ifg_mac_pool87_tx_mac_partial2_invert_crc_cnt_reg5_tx_mac_partial2_invert_crc_cnt {
      type oc-yang:counter64;
      description
        "Counts the number of transmitted packets with partial CRC type 2.";
    }
    leaf counter_slice5_ifg_mac_pool87_tx_mac_partial2_invert_crc_cnt_reg6_tx_mac_partial2_invert_crc_cnt {
      type oc-yang:counter64;
      description
        "Counts the number of transmitted packets with partial CRC type 2.";
    }
    leaf counter_slice5_ifg_mac_pool87_tx_mac_partial2_invert_crc_cnt_reg7_tx_mac_partial2_invert_crc_cnt {
      type oc-yang:counter64;
      description
        "Counts the number of transmitted packets with partial CRC type 2.";
    }
    leaf counter_slice6_ifg_mac_pool80_tx_mac_partial2_invert_crc_cnt_reg0_tx_mac_partial2_invert_crc_cnt {
      type oc-yang:counter64;
      description
        "Counts the number of transmitted packets with partial CRC type 2.";
    }
    leaf counter_slice6_ifg_mac_pool80_tx_mac_partial2_invert_crc_cnt_reg1_tx_mac_partial2_invert_crc_cnt {
      type oc-yang:counter64;
      description
        "Counts the number of transmitted packets with partial CRC type 2.";
    }
    leaf counter_slice6_ifg_mac_pool80_tx_mac_partial2_invert_crc_cnt_reg2_tx_mac_partial2_invert_crc_cnt {
      type oc-yang:counter64;
      description
        "Counts the number of transmitted packets with partial CRC type 2.";
    }
    leaf counter_slice6_ifg_mac_pool80_tx_mac_partial2_invert_crc_cnt_reg3_tx_mac_partial2_invert_crc_cnt {
      type oc-yang:counter64;
      description
        "Counts the number of transmitted packets with partial CRC type 2.";
    }
    leaf counter_slice6_ifg_mac_pool80_tx_mac_partial2_invert_crc_cnt_reg4_tx_mac_partial2_invert_crc_cnt {
      type oc-yang:counter64;
      description
        "Counts the number of transmitted packets with partial CRC type 2.";
    }
    leaf counter_slice6_ifg_mac_pool80_tx_mac_partial2_invert_crc_cnt_reg5_tx_mac_partial2_invert_crc_cnt {
      type oc-yang:counter64;
      description
        "Counts the number of transmitted packets with partial CRC type 2.";
    }
    leaf counter_slice6_ifg_mac_pool80_tx_mac_partial2_invert_crc_cnt_reg6_tx_mac_partial2_invert_crc_cnt {
      type oc-yang:counter64;
      description
        "Counts the number of transmitted packets with partial CRC type 2.";
    }
    leaf counter_slice6_ifg_mac_pool80_tx_mac_partial2_invert_crc_cnt_reg7_tx_mac_partial2_invert_crc_cnt {
      type oc-yang:counter64;
      description
        "Counts the number of transmitted packets with partial CRC type 2.";
    }
    leaf counter_slice6_ifg_mac_pool81_tx_mac_partial2_invert_crc_cnt_reg0_tx_mac_partial2_invert_crc_cnt {
      type oc-yang:counter64;
      description
        "Counts the number of transmitted packets with partial CRC type 2.";
    }
    leaf counter_slice6_ifg_mac_pool81_tx_mac_partial2_invert_crc_cnt_reg1_tx_mac_partial2_invert_crc_cnt {
      type oc-yang:counter64;
      description
        "Counts the number of transmitted packets with partial CRC type 2.";
    }
    leaf counter_slice6_ifg_mac_pool81_tx_mac_partial2_invert_crc_cnt_reg2_tx_mac_partial2_invert_crc_cnt {
      type oc-yang:counter64;
      description
        "Counts the number of transmitted packets with partial CRC type 2.";
    }
    leaf counter_slice6_ifg_mac_pool81_tx_mac_partial2_invert_crc_cnt_reg3_tx_mac_partial2_invert_crc_cnt {
      type oc-yang:counter64;
      description
        "Counts the number of transmitted packets with partial CRC type 2.";
    }
    leaf counter_slice6_ifg_mac_pool81_tx_mac_partial2_invert_crc_cnt_reg4_tx_mac_partial2_invert_crc_cnt {
      type oc-yang:counter64;
      description
        "Counts the number of transmitted packets with partial CRC type 2.";
    }
    leaf counter_slice6_ifg_mac_pool81_tx_mac_partial2_invert_crc_cnt_reg5_tx_mac_partial2_invert_crc_cnt {
      type oc-yang:counter64;
      description
        "Counts the number of transmitted packets with partial CRC type 2.";
    }
    leaf counter_slice6_ifg_mac_pool81_tx_mac_partial2_invert_crc_cnt_reg6_tx_mac_partial2_invert_crc_cnt {
      type oc-yang:counter64;
      description
        "Counts the number of transmitted packets with partial CRC type 2.";
    }
    leaf counter_slice6_ifg_mac_pool81_tx_mac_partial2_invert_crc_cnt_reg7_tx_mac_partial2_invert_crc_cnt {
      type oc-yang:counter64;
      description
        "Counts the number of transmitted packets with partial CRC type 2.";
    }
    leaf counter_slice6_ifg_mac_pool82_tx_mac_partial2_invert_crc_cnt_reg0_tx_mac_partial2_invert_crc_cnt {
      type oc-yang:counter64;
      description
        "Counts the number of transmitted packets with partial CRC type 2.";
    }
    leaf counter_slice6_ifg_mac_pool82_tx_mac_partial2_invert_crc_cnt_reg1_tx_mac_partial2_invert_crc_cnt {
      type oc-yang:counter64;
      description
        "Counts the number of transmitted packets with partial CRC type 2.";
    }
    leaf counter_slice6_ifg_mac_pool82_tx_mac_partial2_invert_crc_cnt_reg2_tx_mac_partial2_invert_crc_cnt {
      type oc-yang:counter64;
      description
        "Counts the number of transmitted packets with partial CRC type 2.";
    }
    leaf counter_slice6_ifg_mac_pool82_tx_mac_partial2_invert_crc_cnt_reg3_tx_mac_partial2_invert_crc_cnt {
      type oc-yang:counter64;
      description
        "Counts the number of transmitted packets with partial CRC type 2.";
    }
    leaf counter_slice6_ifg_mac_pool82_tx_mac_partial2_invert_crc_cnt_reg4_tx_mac_partial2_invert_crc_cnt {
      type oc-yang:counter64;
      description
        "Counts the number of transmitted packets with partial CRC type 2.";
    }
    leaf counter_slice6_ifg_mac_pool82_tx_mac_partial2_invert_crc_cnt_reg5_tx_mac_partial2_invert_crc_cnt {
      type oc-yang:counter64;
      description
        "Counts the number of transmitted packets with partial CRC type 2.";
    }
    leaf counter_slice6_ifg_mac_pool82_tx_mac_partial2_invert_crc_cnt_reg6_tx_mac_partial2_invert_crc_cnt {
      type oc-yang:counter64;
      description
        "Counts the number of transmitted packets with partial CRC type 2.";
    }
    leaf counter_slice6_ifg_mac_pool82_tx_mac_partial2_invert_crc_cnt_reg7_tx_mac_partial2_invert_crc_cnt {
      type oc-yang:counter64;
      description
        "Counts the number of transmitted packets with partial CRC type 2.";
    }
    leaf counter_slice6_ifg_mac_pool83_tx_mac_partial2_invert_crc_cnt_reg0_tx_mac_partial2_invert_crc_cnt {
      type oc-yang:counter64;
      description
        "Counts the number of transmitted packets with partial CRC type 2.";
    }
    leaf counter_slice6_ifg_mac_pool83_tx_mac_partial2_invert_crc_cnt_reg1_tx_mac_partial2_invert_crc_cnt {
      type oc-yang:counter64;
      description
        "Counts the number of transmitted packets with partial CRC type 2.";
    }
    leaf counter_slice6_ifg_mac_pool83_tx_mac_partial2_invert_crc_cnt_reg2_tx_mac_partial2_invert_crc_cnt {
      type oc-yang:counter64;
      description
        "Counts the number of transmitted packets with partial CRC type 2.";
    }
    leaf counter_slice6_ifg_mac_pool83_tx_mac_partial2_invert_crc_cnt_reg3_tx_mac_partial2_invert_crc_cnt {
      type oc-yang:counter64;
      description
        "Counts the number of transmitted packets with partial CRC type 2.";
    }
    leaf counter_slice6_ifg_mac_pool83_tx_mac_partial2_invert_crc_cnt_reg4_tx_mac_partial2_invert_crc_cnt {
      type oc-yang:counter64;
      description
        "Counts the number of transmitted packets with partial CRC type 2.";
    }
    leaf counter_slice6_ifg_mac_pool83_tx_mac_partial2_invert_crc_cnt_reg5_tx_mac_partial2_invert_crc_cnt {
      type oc-yang:counter64;
      description
        "Counts the number of transmitted packets with partial CRC type 2.";
    }
    leaf counter_slice6_ifg_mac_pool83_tx_mac_partial2_invert_crc_cnt_reg6_tx_mac_partial2_invert_crc_cnt {
      type oc-yang:counter64;
      description
        "Counts the number of transmitted packets with partial CRC type 2.";
    }
    leaf counter_slice6_ifg_mac_pool83_tx_mac_partial2_invert_crc_cnt_reg7_tx_mac_partial2_invert_crc_cnt {
      type oc-yang:counter64;
      description
        "Counts the number of transmitted packets with partial CRC type 2.";
    }
    leaf counter_slice6_ifg_mac_pool84_tx_mac_partial2_invert_crc_cnt_reg0_tx_mac_partial2_invert_crc_cnt {
      type oc-yang:counter64;
      description
        "Counts the number of transmitted packets with partial CRC type 2.";
    }
    leaf counter_slice6_ifg_mac_pool84_tx_mac_partial2_invert_crc_cnt_reg1_tx_mac_partial2_invert_crc_cnt {
      type oc-yang:counter64;
      description
        "Counts the number of transmitted packets with partial CRC type 2.";
    }
    leaf counter_slice6_ifg_mac_pool84_tx_mac_partial2_invert_crc_cnt_reg2_tx_mac_partial2_invert_crc_cnt {
      type oc-yang:counter64;
      description
        "Counts the number of transmitted packets with partial CRC type 2.";
    }
    leaf counter_slice6_ifg_mac_pool84_tx_mac_partial2_invert_crc_cnt_reg3_tx_mac_partial2_invert_crc_cnt {
      type oc-yang:counter64;
      description
        "Counts the number of transmitted packets with partial CRC type 2.";
    }
    leaf counter_slice6_ifg_mac_pool84_tx_mac_partial2_invert_crc_cnt_reg4_tx_mac_partial2_invert_crc_cnt {
      type oc-yang:counter64;
      description
        "Counts the number of transmitted packets with partial CRC type 2.";
    }
    leaf counter_slice6_ifg_mac_pool84_tx_mac_partial2_invert_crc_cnt_reg5_tx_mac_partial2_invert_crc_cnt {
      type oc-yang:counter64;
      description
        "Counts the number of transmitted packets with partial CRC type 2.";
    }
    leaf counter_slice6_ifg_mac_pool84_tx_mac_partial2_invert_crc_cnt_reg6_tx_mac_partial2_invert_crc_cnt {
      type oc-yang:counter64;
      description
        "Counts the number of transmitted packets with partial CRC type 2.";
    }
    leaf counter_slice6_ifg_mac_pool84_tx_mac_partial2_invert_crc_cnt_reg7_tx_mac_partial2_invert_crc_cnt {
      type oc-yang:counter64;
      description
        "Counts the number of transmitted packets with partial CRC type 2.";
    }
    leaf counter_slice6_ifg_mac_pool85_tx_mac_partial2_invert_crc_cnt_reg0_tx_mac_partial2_invert_crc_cnt {
      type oc-yang:counter64;
      description
        "Counts the number of transmitted packets with partial CRC type 2.";
    }
    leaf counter_slice6_ifg_mac_pool85_tx_mac_partial2_invert_crc_cnt_reg1_tx_mac_partial2_invert_crc_cnt {
      type oc-yang:counter64;
      description
        "Counts the number of transmitted packets with partial CRC type 2.";
    }
    leaf counter_slice6_ifg_mac_pool85_tx_mac_partial2_invert_crc_cnt_reg2_tx_mac_partial2_invert_crc_cnt {
      type oc-yang:counter64;
      description
        "Counts the number of transmitted packets with partial CRC type 2.";
    }
    leaf counter_slice6_ifg_mac_pool85_tx_mac_partial2_invert_crc_cnt_reg3_tx_mac_partial2_invert_crc_cnt {
      type oc-yang:counter64;
      description
        "Counts the number of transmitted packets with partial CRC type 2.";
    }
    leaf counter_slice6_ifg_mac_pool85_tx_mac_partial2_invert_crc_cnt_reg4_tx_mac_partial2_invert_crc_cnt {
      type oc-yang:counter64;
      description
        "Counts the number of transmitted packets with partial CRC type 2.";
    }
    leaf counter_slice6_ifg_mac_pool85_tx_mac_partial2_invert_crc_cnt_reg5_tx_mac_partial2_invert_crc_cnt {
      type oc-yang:counter64;
      description
        "Counts the number of transmitted packets with partial CRC type 2.";
    }
    leaf counter_slice6_ifg_mac_pool85_tx_mac_partial2_invert_crc_cnt_reg6_tx_mac_partial2_invert_crc_cnt {
      type oc-yang:counter64;
      description
        "Counts the number of transmitted packets with partial CRC type 2.";
    }
    leaf counter_slice6_ifg_mac_pool85_tx_mac_partial2_invert_crc_cnt_reg7_tx_mac_partial2_invert_crc_cnt {
      type oc-yang:counter64;
      description
        "Counts the number of transmitted packets with partial CRC type 2.";
    }
    leaf counter_slice6_ifg_mac_pool86_tx_mac_partial2_invert_crc_cnt_reg0_tx_mac_partial2_invert_crc_cnt {
      type oc-yang:counter64;
      description
        "Counts the number of transmitted packets with partial CRC type 2.";
    }
    leaf counter_slice6_ifg_mac_pool86_tx_mac_partial2_invert_crc_cnt_reg1_tx_mac_partial2_invert_crc_cnt {
      type oc-yang:counter64;
      description
        "Counts the number of transmitted packets with partial CRC type 2.";
    }
    leaf counter_slice6_ifg_mac_pool86_tx_mac_partial2_invert_crc_cnt_reg2_tx_mac_partial2_invert_crc_cnt {
      type oc-yang:counter64;
      description
        "Counts the number of transmitted packets with partial CRC type 2.";
    }
    leaf counter_slice6_ifg_mac_pool86_tx_mac_partial2_invert_crc_cnt_reg3_tx_mac_partial2_invert_crc_cnt {
      type oc-yang:counter64;
      description
        "Counts the number of transmitted packets with partial CRC type 2.";
    }
    leaf counter_slice6_ifg_mac_pool86_tx_mac_partial2_invert_crc_cnt_reg4_tx_mac_partial2_invert_crc_cnt {
      type oc-yang:counter64;
      description
        "Counts the number of transmitted packets with partial CRC type 2.";
    }
    leaf counter_slice6_ifg_mac_pool86_tx_mac_partial2_invert_crc_cnt_reg5_tx_mac_partial2_invert_crc_cnt {
      type oc-yang:counter64;
      description
        "Counts the number of transmitted packets with partial CRC type 2.";
    }
    leaf counter_slice6_ifg_mac_pool86_tx_mac_partial2_invert_crc_cnt_reg6_tx_mac_partial2_invert_crc_cnt {
      type oc-yang:counter64;
      description
        "Counts the number of transmitted packets with partial CRC type 2.";
    }
    leaf counter_slice6_ifg_mac_pool86_tx_mac_partial2_invert_crc_cnt_reg7_tx_mac_partial2_invert_crc_cnt {
      type oc-yang:counter64;
      description
        "Counts the number of transmitted packets with partial CRC type 2.";
    }
    leaf counter_slice6_ifg_mac_pool87_tx_mac_partial2_invert_crc_cnt_reg0_tx_mac_partial2_invert_crc_cnt {
      type oc-yang:counter64;
      description
        "Counts the number of transmitted packets with partial CRC type 2.";
    }
    leaf counter_slice6_ifg_mac_pool87_tx_mac_partial2_invert_crc_cnt_reg1_tx_mac_partial2_invert_crc_cnt {
      type oc-yang:counter64;
      description
        "Counts the number of transmitted packets with partial CRC type 2.";
    }
    leaf counter_slice6_ifg_mac_pool87_tx_mac_partial2_invert_crc_cnt_reg2_tx_mac_partial2_invert_crc_cnt {
      type oc-yang:counter64;
      description
        "Counts the number of transmitted packets with partial CRC type 2.";
    }
    leaf counter_slice6_ifg_mac_pool87_tx_mac_partial2_invert_crc_cnt_reg3_tx_mac_partial2_invert_crc_cnt {
      type oc-yang:counter64;
      description
        "Counts the number of transmitted packets with partial CRC type 2.";
    }
    leaf counter_slice6_ifg_mac_pool87_tx_mac_partial2_invert_crc_cnt_reg4_tx_mac_partial2_invert_crc_cnt {
      type oc-yang:counter64;
      description
        "Counts the number of transmitted packets with partial CRC type 2.";
    }
    leaf counter_slice6_ifg_mac_pool87_tx_mac_partial2_invert_crc_cnt_reg5_tx_mac_partial2_invert_crc_cnt {
      type oc-yang:counter64;
      description
        "Counts the number of transmitted packets with partial CRC type 2.";
    }
    leaf counter_slice6_ifg_mac_pool87_tx_mac_partial2_invert_crc_cnt_reg6_tx_mac_partial2_invert_crc_cnt {
      type oc-yang:counter64;
      description
        "Counts the number of transmitted packets with partial CRC type 2.";
    }
    leaf counter_slice6_ifg_mac_pool87_tx_mac_partial2_invert_crc_cnt_reg7_tx_mac_partial2_invert_crc_cnt {
      type oc-yang:counter64;
      description
        "Counts the number of transmitted packets with partial CRC type 2.";
    }
    leaf counter_slice7_ifg_mac_pool80_tx_mac_partial2_invert_crc_cnt_reg0_tx_mac_partial2_invert_crc_cnt {
      type oc-yang:counter64;
      description
        "Counts the number of transmitted packets with partial CRC type 2.";
    }
    leaf counter_slice7_ifg_mac_pool80_tx_mac_partial2_invert_crc_cnt_reg1_tx_mac_partial2_invert_crc_cnt {
      type oc-yang:counter64;
      description
        "Counts the number of transmitted packets with partial CRC type 2.";
    }
    leaf counter_slice7_ifg_mac_pool80_tx_mac_partial2_invert_crc_cnt_reg2_tx_mac_partial2_invert_crc_cnt {
      type oc-yang:counter64;
      description
        "Counts the number of transmitted packets with partial CRC type 2.";
    }
    leaf counter_slice7_ifg_mac_pool80_tx_mac_partial2_invert_crc_cnt_reg3_tx_mac_partial2_invert_crc_cnt {
      type oc-yang:counter64;
      description
        "Counts the number of transmitted packets with partial CRC type 2.";
    }
    leaf counter_slice7_ifg_mac_pool80_tx_mac_partial2_invert_crc_cnt_reg4_tx_mac_partial2_invert_crc_cnt {
      type oc-yang:counter64;
      description
        "Counts the number of transmitted packets with partial CRC type 2.";
    }
    leaf counter_slice7_ifg_mac_pool80_tx_mac_partial2_invert_crc_cnt_reg5_tx_mac_partial2_invert_crc_cnt {
      type oc-yang:counter64;
      description
        "Counts the number of transmitted packets with partial CRC type 2.";
    }
    leaf counter_slice7_ifg_mac_pool80_tx_mac_partial2_invert_crc_cnt_reg6_tx_mac_partial2_invert_crc_cnt {
      type oc-yang:counter64;
      description
        "Counts the number of transmitted packets with partial CRC type 2.";
    }
    leaf counter_slice7_ifg_mac_pool80_tx_mac_partial2_invert_crc_cnt_reg7_tx_mac_partial2_invert_crc_cnt {
      type oc-yang:counter64;
      description
        "Counts the number of transmitted packets with partial CRC type 2.";
    }
    leaf counter_slice7_ifg_mac_pool81_tx_mac_partial2_invert_crc_cnt_reg0_tx_mac_partial2_invert_crc_cnt {
      type oc-yang:counter64;
      description
        "Counts the number of transmitted packets with partial CRC type 2.";
    }
    leaf counter_slice7_ifg_mac_pool81_tx_mac_partial2_invert_crc_cnt_reg1_tx_mac_partial2_invert_crc_cnt {
      type oc-yang:counter64;
      description
        "Counts the number of transmitted packets with partial CRC type 2.";
    }
    leaf counter_slice7_ifg_mac_pool81_tx_mac_partial2_invert_crc_cnt_reg2_tx_mac_partial2_invert_crc_cnt {
      type oc-yang:counter64;
      description
        "Counts the number of transmitted packets with partial CRC type 2.";
    }
    leaf counter_slice7_ifg_mac_pool81_tx_mac_partial2_invert_crc_cnt_reg3_tx_mac_partial2_invert_crc_cnt {
      type oc-yang:counter64;
      description
        "Counts the number of transmitted packets with partial CRC type 2.";
    }
    leaf counter_slice7_ifg_mac_pool81_tx_mac_partial2_invert_crc_cnt_reg4_tx_mac_partial2_invert_crc_cnt {
      type oc-yang:counter64;
      description
        "Counts the number of transmitted packets with partial CRC type 2.";
    }
    leaf counter_slice7_ifg_mac_pool81_tx_mac_partial2_invert_crc_cnt_reg5_tx_mac_partial2_invert_crc_cnt {
      type oc-yang:counter64;
      description
        "Counts the number of transmitted packets with partial CRC type 2.";
    }
    leaf counter_slice7_ifg_mac_pool81_tx_mac_partial2_invert_crc_cnt_reg6_tx_mac_partial2_invert_crc_cnt {
      type oc-yang:counter64;
      description
        "Counts the number of transmitted packets with partial CRC type 2.";
    }
    leaf counter_slice7_ifg_mac_pool81_tx_mac_partial2_invert_crc_cnt_reg7_tx_mac_partial2_invert_crc_cnt {
      type oc-yang:counter64;
      description
        "Counts the number of transmitted packets with partial CRC type 2.";
    }
    leaf counter_slice7_ifg_mac_pool82_tx_mac_partial2_invert_crc_cnt_reg0_tx_mac_partial2_invert_crc_cnt {
      type oc-yang:counter64;
      description
        "Counts the number of transmitted packets with partial CRC type 2.";
    }
    leaf counter_slice7_ifg_mac_pool82_tx_mac_partial2_invert_crc_cnt_reg1_tx_mac_partial2_invert_crc_cnt {
      type oc-yang:counter64;
      description
        "Counts the number of transmitted packets with partial CRC type 2.";
    }
    leaf counter_slice7_ifg_mac_pool82_tx_mac_partial2_invert_crc_cnt_reg2_tx_mac_partial2_invert_crc_cnt {
      type oc-yang:counter64;
      description
        "Counts the number of transmitted packets with partial CRC type 2.";
    }
    leaf counter_slice7_ifg_mac_pool82_tx_mac_partial2_invert_crc_cnt_reg3_tx_mac_partial2_invert_crc_cnt {
      type oc-yang:counter64;
      description
        "Counts the number of transmitted packets with partial CRC type 2.";
    }
    leaf counter_slice7_ifg_mac_pool82_tx_mac_partial2_invert_crc_cnt_reg4_tx_mac_partial2_invert_crc_cnt {
      type oc-yang:counter64;
      description
        "Counts the number of transmitted packets with partial CRC type 2.";
    }
    leaf counter_slice7_ifg_mac_pool82_tx_mac_partial2_invert_crc_cnt_reg5_tx_mac_partial2_invert_crc_cnt {
      type oc-yang:counter64;
      description
        "Counts the number of transmitted packets with partial CRC type 2.";
    }
    leaf counter_slice7_ifg_mac_pool82_tx_mac_partial2_invert_crc_cnt_reg6_tx_mac_partial2_invert_crc_cnt {
      type oc-yang:counter64;
      description
        "Counts the number of transmitted packets with partial CRC type 2.";
    }
    leaf counter_slice7_ifg_mac_pool82_tx_mac_partial2_invert_crc_cnt_reg7_tx_mac_partial2_invert_crc_cnt {
      type oc-yang:counter64;
      description
        "Counts the number of transmitted packets with partial CRC type 2.";
    }
    leaf counter_slice7_ifg_mac_pool83_tx_mac_partial2_invert_crc_cnt_reg0_tx_mac_partial2_invert_crc_cnt {
      type oc-yang:counter64;
      description
        "Counts the number of transmitted packets with partial CRC type 2.";
    }
    leaf counter_slice7_ifg_mac_pool83_tx_mac_partial2_invert_crc_cnt_reg1_tx_mac_partial2_invert_crc_cnt {
      type oc-yang:counter64;
      description
        "Counts the number of transmitted packets with partial CRC type 2.";
    }
    leaf counter_slice7_ifg_mac_pool83_tx_mac_partial2_invert_crc_cnt_reg2_tx_mac_partial2_invert_crc_cnt {
      type oc-yang:counter64;
      description
        "Counts the number of transmitted packets with partial CRC type 2.";
    }
    leaf counter_slice7_ifg_mac_pool83_tx_mac_partial2_invert_crc_cnt_reg3_tx_mac_partial2_invert_crc_cnt {
      type oc-yang:counter64;
      description
        "Counts the number of transmitted packets with partial CRC type 2.";
    }
    leaf counter_slice7_ifg_mac_pool83_tx_mac_partial2_invert_crc_cnt_reg4_tx_mac_partial2_invert_crc_cnt {
      type oc-yang:counter64;
      description
        "Counts the number of transmitted packets with partial CRC type 2.";
    }
    leaf counter_slice7_ifg_mac_pool83_tx_mac_partial2_invert_crc_cnt_reg5_tx_mac_partial2_invert_crc_cnt {
      type oc-yang:counter64;
      description
        "Counts the number of transmitted packets with partial CRC type 2.";
    }
    leaf counter_slice7_ifg_mac_pool83_tx_mac_partial2_invert_crc_cnt_reg6_tx_mac_partial2_invert_crc_cnt {
      type oc-yang:counter64;
      description
        "Counts the number of transmitted packets with partial CRC type 2.";
    }
    leaf counter_slice7_ifg_mac_pool83_tx_mac_partial2_invert_crc_cnt_reg7_tx_mac_partial2_invert_crc_cnt {
      type oc-yang:counter64;
      description
        "Counts the number of transmitted packets with partial CRC type 2.";
    }
    leaf counter_slice7_ifg_mac_pool84_tx_mac_partial2_invert_crc_cnt_reg0_tx_mac_partial2_invert_crc_cnt {
      type oc-yang:counter64;
      description
        "Counts the number of transmitted packets with partial CRC type 2.";
    }
    leaf counter_slice7_ifg_mac_pool84_tx_mac_partial2_invert_crc_cnt_reg1_tx_mac_partial2_invert_crc_cnt {
      type oc-yang:counter64;
      description
        "Counts the number of transmitted packets with partial CRC type 2.";
    }
    leaf counter_slice7_ifg_mac_pool84_tx_mac_partial2_invert_crc_cnt_reg2_tx_mac_partial2_invert_crc_cnt {
      type oc-yang:counter64;
      description
        "Counts the number of transmitted packets with partial CRC type 2.";
    }
    leaf counter_slice7_ifg_mac_pool84_tx_mac_partial2_invert_crc_cnt_reg3_tx_mac_partial2_invert_crc_cnt {
      type oc-yang:counter64;
      description
        "Counts the number of transmitted packets with partial CRC type 2.";
    }
    leaf counter_slice7_ifg_mac_pool84_tx_mac_partial2_invert_crc_cnt_reg4_tx_mac_partial2_invert_crc_cnt {
      type oc-yang:counter64;
      description
        "Counts the number of transmitted packets with partial CRC type 2.";
    }
    leaf counter_slice7_ifg_mac_pool84_tx_mac_partial2_invert_crc_cnt_reg5_tx_mac_partial2_invert_crc_cnt {
      type oc-yang:counter64;
      description
        "Counts the number of transmitted packets with partial CRC type 2.";
    }
    leaf counter_slice7_ifg_mac_pool84_tx_mac_partial2_invert_crc_cnt_reg6_tx_mac_partial2_invert_crc_cnt {
      type oc-yang:counter64;
      description
        "Counts the number of transmitted packets with partial CRC type 2.";
    }
    leaf counter_slice7_ifg_mac_pool84_tx_mac_partial2_invert_crc_cnt_reg7_tx_mac_partial2_invert_crc_cnt {
      type oc-yang:counter64;
      description
        "Counts the number of transmitted packets with partial CRC type 2.";
    }
    leaf counter_slice7_ifg_mac_pool85_tx_mac_partial2_invert_crc_cnt_reg0_tx_mac_partial2_invert_crc_cnt {
      type oc-yang:counter64;
      description
        "Counts the number of transmitted packets with partial CRC type 2.";
    }
    leaf counter_slice7_ifg_mac_pool85_tx_mac_partial2_invert_crc_cnt_reg1_tx_mac_partial2_invert_crc_cnt {
      type oc-yang:counter64;
      description
        "Counts the number of transmitted packets with partial CRC type 2.";
    }
    leaf counter_slice7_ifg_mac_pool85_tx_mac_partial2_invert_crc_cnt_reg2_tx_mac_partial2_invert_crc_cnt {
      type oc-yang:counter64;
      description
        "Counts the number of transmitted packets with partial CRC type 2.";
    }
    leaf counter_slice7_ifg_mac_pool85_tx_mac_partial2_invert_crc_cnt_reg3_tx_mac_partial2_invert_crc_cnt {
      type oc-yang:counter64;
      description
        "Counts the number of transmitted packets with partial CRC type 2.";
    }
    leaf counter_slice7_ifg_mac_pool85_tx_mac_partial2_invert_crc_cnt_reg4_tx_mac_partial2_invert_crc_cnt {
      type oc-yang:counter64;
      description
        "Counts the number of transmitted packets with partial CRC type 2.";
    }
    leaf counter_slice7_ifg_mac_pool85_tx_mac_partial2_invert_crc_cnt_reg5_tx_mac_partial2_invert_crc_cnt {
      type oc-yang:counter64;
      description
        "Counts the number of transmitted packets with partial CRC type 2.";
    }
    leaf counter_slice7_ifg_mac_pool85_tx_mac_partial2_invert_crc_cnt_reg6_tx_mac_partial2_invert_crc_cnt {
      type oc-yang:counter64;
      description
        "Counts the number of transmitted packets with partial CRC type 2.";
    }
    leaf counter_slice7_ifg_mac_pool85_tx_mac_partial2_invert_crc_cnt_reg7_tx_mac_partial2_invert_crc_cnt {
      type oc-yang:counter64;
      description
        "Counts the number of transmitted packets with partial CRC type 2.";
    }
    leaf counter_slice7_ifg_mac_pool86_tx_mac_partial2_invert_crc_cnt_reg0_tx_mac_partial2_invert_crc_cnt {
      type oc-yang:counter64;
      description
        "Counts the number of transmitted packets with partial CRC type 2.";
    }
    leaf counter_slice7_ifg_mac_pool86_tx_mac_partial2_invert_crc_cnt_reg1_tx_mac_partial2_invert_crc_cnt {
      type oc-yang:counter64;
      description
        "Counts the number of transmitted packets with partial CRC type 2.";
    }
    leaf counter_slice7_ifg_mac_pool86_tx_mac_partial2_invert_crc_cnt_reg2_tx_mac_partial2_invert_crc_cnt {
      type oc-yang:counter64;
      description
        "Counts the number of transmitted packets with partial CRC type 2.";
    }
    leaf counter_slice7_ifg_mac_pool86_tx_mac_partial2_invert_crc_cnt_reg3_tx_mac_partial2_invert_crc_cnt {
      type oc-yang:counter64;
      description
        "Counts the number of transmitted packets with partial CRC type 2.";
    }
    leaf counter_slice7_ifg_mac_pool86_tx_mac_partial2_invert_crc_cnt_reg4_tx_mac_partial2_invert_crc_cnt {
      type oc-yang:counter64;
      description
        "Counts the number of transmitted packets with partial CRC type 2.";
    }
    leaf counter_slice7_ifg_mac_pool86_tx_mac_partial2_invert_crc_cnt_reg5_tx_mac_partial2_invert_crc_cnt {
      type oc-yang:counter64;
      description
        "Counts the number of transmitted packets with partial CRC type 2.";
    }
    leaf counter_slice7_ifg_mac_pool86_tx_mac_partial2_invert_crc_cnt_reg6_tx_mac_partial2_invert_crc_cnt {
      type oc-yang:counter64;
      description
        "Counts the number of transmitted packets with partial CRC type 2.";
    }
    leaf counter_slice7_ifg_mac_pool86_tx_mac_partial2_invert_crc_cnt_reg7_tx_mac_partial2_invert_crc_cnt {
      type oc-yang:counter64;
      description
        "Counts the number of transmitted packets with partial CRC type 2.";
    }
    leaf counter_slice7_ifg_mac_pool87_tx_mac_partial2_invert_crc_cnt_reg0_tx_mac_partial2_invert_crc_cnt {
      type oc-yang:counter64;
      description
        "Counts the number of transmitted packets with partial CRC type 2.";
    }
    leaf counter_slice7_ifg_mac_pool87_tx_mac_partial2_invert_crc_cnt_reg1_tx_mac_partial2_invert_crc_cnt {
      type oc-yang:counter64;
      description
        "Counts the number of transmitted packets with partial CRC type 2.";
    }
    leaf counter_slice7_ifg_mac_pool87_tx_mac_partial2_invert_crc_cnt_reg2_tx_mac_partial2_invert_crc_cnt {
      type oc-yang:counter64;
      description
        "Counts the number of transmitted packets with partial CRC type 2.";
    }
    leaf counter_slice7_ifg_mac_pool87_tx_mac_partial2_invert_crc_cnt_reg3_tx_mac_partial2_invert_crc_cnt {
      type oc-yang:counter64;
      description
        "Counts the number of transmitted packets with partial CRC type 2.";
    }
    leaf counter_slice7_ifg_mac_pool87_tx_mac_partial2_invert_crc_cnt_reg4_tx_mac_partial2_invert_crc_cnt {
      type oc-yang:counter64;
      description
        "Counts the number of transmitted packets with partial CRC type 2.";
    }
    leaf counter_slice7_ifg_mac_pool87_tx_mac_partial2_invert_crc_cnt_reg5_tx_mac_partial2_invert_crc_cnt {
      type oc-yang:counter64;
      description
        "Counts the number of transmitted packets with partial CRC type 2.";
    }
    leaf counter_slice7_ifg_mac_pool87_tx_mac_partial2_invert_crc_cnt_reg6_tx_mac_partial2_invert_crc_cnt {
      type oc-yang:counter64;
      description
        "Counts the number of transmitted packets with partial CRC type 2.";
    }
    leaf counter_slice7_ifg_mac_pool87_tx_mac_partial2_invert_crc_cnt_reg7_tx_mac_partial2_invert_crc_cnt {
      type oc-yang:counter64;
      description
        "Counts the number of transmitted packets with partial CRC type 2.";
    }
    leaf counter_slice8_ifg_mac_pool80_tx_mac_partial2_invert_crc_cnt_reg0_tx_mac_partial2_invert_crc_cnt {
      type oc-yang:counter64;
      description
        "Counts the number of transmitted packets with partial CRC type 2.";
    }
    leaf counter_slice8_ifg_mac_pool80_tx_mac_partial2_invert_crc_cnt_reg1_tx_mac_partial2_invert_crc_cnt {
      type oc-yang:counter64;
      description
        "Counts the number of transmitted packets with partial CRC type 2.";
    }
    leaf counter_slice8_ifg_mac_pool80_tx_mac_partial2_invert_crc_cnt_reg2_tx_mac_partial2_invert_crc_cnt {
      type oc-yang:counter64;
      description
        "Counts the number of transmitted packets with partial CRC type 2.";
    }
    leaf counter_slice8_ifg_mac_pool80_tx_mac_partial2_invert_crc_cnt_reg3_tx_mac_partial2_invert_crc_cnt {
      type oc-yang:counter64;
      description
        "Counts the number of transmitted packets with partial CRC type 2.";
    }
    leaf counter_slice8_ifg_mac_pool80_tx_mac_partial2_invert_crc_cnt_reg4_tx_mac_partial2_invert_crc_cnt {
      type oc-yang:counter64;
      description
        "Counts the number of transmitted packets with partial CRC type 2.";
    }
    leaf counter_slice8_ifg_mac_pool80_tx_mac_partial2_invert_crc_cnt_reg5_tx_mac_partial2_invert_crc_cnt {
      type oc-yang:counter64;
      description
        "Counts the number of transmitted packets with partial CRC type 2.";
    }
    leaf counter_slice8_ifg_mac_pool80_tx_mac_partial2_invert_crc_cnt_reg6_tx_mac_partial2_invert_crc_cnt {
      type oc-yang:counter64;
      description
        "Counts the number of transmitted packets with partial CRC type 2.";
    }
    leaf counter_slice8_ifg_mac_pool80_tx_mac_partial2_invert_crc_cnt_reg7_tx_mac_partial2_invert_crc_cnt {
      type oc-yang:counter64;
      description
        "Counts the number of transmitted packets with partial CRC type 2.";
    }
    leaf counter_slice8_ifg_mac_pool81_tx_mac_partial2_invert_crc_cnt_reg0_tx_mac_partial2_invert_crc_cnt {
      type oc-yang:counter64;
      description
        "Counts the number of transmitted packets with partial CRC type 2.";
    }
    leaf counter_slice8_ifg_mac_pool81_tx_mac_partial2_invert_crc_cnt_reg1_tx_mac_partial2_invert_crc_cnt {
      type oc-yang:counter64;
      description
        "Counts the number of transmitted packets with partial CRC type 2.";
    }
    leaf counter_slice8_ifg_mac_pool81_tx_mac_partial2_invert_crc_cnt_reg2_tx_mac_partial2_invert_crc_cnt {
      type oc-yang:counter64;
      description
        "Counts the number of transmitted packets with partial CRC type 2.";
    }
    leaf counter_slice8_ifg_mac_pool81_tx_mac_partial2_invert_crc_cnt_reg3_tx_mac_partial2_invert_crc_cnt {
      type oc-yang:counter64;
      description
        "Counts the number of transmitted packets with partial CRC type 2.";
    }
    leaf counter_slice8_ifg_mac_pool81_tx_mac_partial2_invert_crc_cnt_reg4_tx_mac_partial2_invert_crc_cnt {
      type oc-yang:counter64;
      description
        "Counts the number of transmitted packets with partial CRC type 2.";
    }
    leaf counter_slice8_ifg_mac_pool81_tx_mac_partial2_invert_crc_cnt_reg5_tx_mac_partial2_invert_crc_cnt {
      type oc-yang:counter64;
      description
        "Counts the number of transmitted packets with partial CRC type 2.";
    }
    leaf counter_slice8_ifg_mac_pool81_tx_mac_partial2_invert_crc_cnt_reg6_tx_mac_partial2_invert_crc_cnt {
      type oc-yang:counter64;
      description
        "Counts the number of transmitted packets with partial CRC type 2.";
    }
    leaf counter_slice8_ifg_mac_pool81_tx_mac_partial2_invert_crc_cnt_reg7_tx_mac_partial2_invert_crc_cnt {
      type oc-yang:counter64;
      description
        "Counts the number of transmitted packets with partial CRC type 2.";
    }
    leaf counter_slice8_ifg_mac_pool82_tx_mac_partial2_invert_crc_cnt_reg0_tx_mac_partial2_invert_crc_cnt {
      type oc-yang:counter64;
      description
        "Counts the number of transmitted packets with partial CRC type 2.";
    }
    leaf counter_slice8_ifg_mac_pool82_tx_mac_partial2_invert_crc_cnt_reg1_tx_mac_partial2_invert_crc_cnt {
      type oc-yang:counter64;
      description
        "Counts the number of transmitted packets with partial CRC type 2.";
    }
    leaf counter_slice8_ifg_mac_pool82_tx_mac_partial2_invert_crc_cnt_reg2_tx_mac_partial2_invert_crc_cnt {
      type oc-yang:counter64;
      description
        "Counts the number of transmitted packets with partial CRC type 2.";
    }
    leaf counter_slice8_ifg_mac_pool82_tx_mac_partial2_invert_crc_cnt_reg3_tx_mac_partial2_invert_crc_cnt {
      type oc-yang:counter64;
      description
        "Counts the number of transmitted packets with partial CRC type 2.";
    }
    leaf counter_slice8_ifg_mac_pool82_tx_mac_partial2_invert_crc_cnt_reg4_tx_mac_partial2_invert_crc_cnt {
      type oc-yang:counter64;
      description
        "Counts the number of transmitted packets with partial CRC type 2.";
    }
    leaf counter_slice8_ifg_mac_pool82_tx_mac_partial2_invert_crc_cnt_reg5_tx_mac_partial2_invert_crc_cnt {
      type oc-yang:counter64;
      description
        "Counts the number of transmitted packets with partial CRC type 2.";
    }
    leaf counter_slice8_ifg_mac_pool82_tx_mac_partial2_invert_crc_cnt_reg6_tx_mac_partial2_invert_crc_cnt {
      type oc-yang:counter64;
      description
        "Counts the number of transmitted packets with partial CRC type 2.";
    }
    leaf counter_slice8_ifg_mac_pool82_tx_mac_partial2_invert_crc_cnt_reg7_tx_mac_partial2_invert_crc_cnt {
      type oc-yang:counter64;
      description
        "Counts the number of transmitted packets with partial CRC type 2.";
    }
    leaf counter_slice8_ifg_mac_pool83_tx_mac_partial2_invert_crc_cnt_reg0_tx_mac_partial2_invert_crc_cnt {
      type oc-yang:counter64;
      description
        "Counts the number of transmitted packets with partial CRC type 2.";
    }
    leaf counter_slice8_ifg_mac_pool83_tx_mac_partial2_invert_crc_cnt_reg1_tx_mac_partial2_invert_crc_cnt {
      type oc-yang:counter64;
      description
        "Counts the number of transmitted packets with partial CRC type 2.";
    }
    leaf counter_slice8_ifg_mac_pool83_tx_mac_partial2_invert_crc_cnt_reg2_tx_mac_partial2_invert_crc_cnt {
      type oc-yang:counter64;
      description
        "Counts the number of transmitted packets with partial CRC type 2.";
    }
    leaf counter_slice8_ifg_mac_pool83_tx_mac_partial2_invert_crc_cnt_reg3_tx_mac_partial2_invert_crc_cnt {
      type oc-yang:counter64;
      description
        "Counts the number of transmitted packets with partial CRC type 2.";
    }
    leaf counter_slice8_ifg_mac_pool83_tx_mac_partial2_invert_crc_cnt_reg4_tx_mac_partial2_invert_crc_cnt {
      type oc-yang:counter64;
      description
        "Counts the number of transmitted packets with partial CRC type 2.";
    }
    leaf counter_slice8_ifg_mac_pool83_tx_mac_partial2_invert_crc_cnt_reg5_tx_mac_partial2_invert_crc_cnt {
      type oc-yang:counter64;
      description
        "Counts the number of transmitted packets with partial CRC type 2.";
    }
    leaf counter_slice8_ifg_mac_pool83_tx_mac_partial2_invert_crc_cnt_reg6_tx_mac_partial2_invert_crc_cnt {
      type oc-yang:counter64;
      description
        "Counts the number of transmitted packets with partial CRC type 2.";
    }
    leaf counter_slice8_ifg_mac_pool83_tx_mac_partial2_invert_crc_cnt_reg7_tx_mac_partial2_invert_crc_cnt {
      type oc-yang:counter64;
      description
        "Counts the number of transmitted packets with partial CRC type 2.";
    }
    leaf counter_slice8_ifg_mac_pool84_tx_mac_partial2_invert_crc_cnt_reg0_tx_mac_partial2_invert_crc_cnt {
      type oc-yang:counter64;
      description
        "Counts the number of transmitted packets with partial CRC type 2.";
    }
    leaf counter_slice8_ifg_mac_pool84_tx_mac_partial2_invert_crc_cnt_reg1_tx_mac_partial2_invert_crc_cnt {
      type oc-yang:counter64;
      description
        "Counts the number of transmitted packets with partial CRC type 2.";
    }
    leaf counter_slice8_ifg_mac_pool84_tx_mac_partial2_invert_crc_cnt_reg2_tx_mac_partial2_invert_crc_cnt {
      type oc-yang:counter64;
      description
        "Counts the number of transmitted packets with partial CRC type 2.";
    }
    leaf counter_slice8_ifg_mac_pool84_tx_mac_partial2_invert_crc_cnt_reg3_tx_mac_partial2_invert_crc_cnt {
      type oc-yang:counter64;
      description
        "Counts the number of transmitted packets with partial CRC type 2.";
    }
    leaf counter_slice8_ifg_mac_pool84_tx_mac_partial2_invert_crc_cnt_reg4_tx_mac_partial2_invert_crc_cnt {
      type oc-yang:counter64;
      description
        "Counts the number of transmitted packets with partial CRC type 2.";
    }
    leaf counter_slice8_ifg_mac_pool84_tx_mac_partial2_invert_crc_cnt_reg5_tx_mac_partial2_invert_crc_cnt {
      type oc-yang:counter64;
      description
        "Counts the number of transmitted packets with partial CRC type 2.";
    }
    leaf counter_slice8_ifg_mac_pool84_tx_mac_partial2_invert_crc_cnt_reg6_tx_mac_partial2_invert_crc_cnt {
      type oc-yang:counter64;
      description
        "Counts the number of transmitted packets with partial CRC type 2.";
    }
    leaf counter_slice8_ifg_mac_pool84_tx_mac_partial2_invert_crc_cnt_reg7_tx_mac_partial2_invert_crc_cnt {
      type oc-yang:counter64;
      description
        "Counts the number of transmitted packets with partial CRC type 2.";
    }
    leaf counter_slice8_ifg_mac_pool85_tx_mac_partial2_invert_crc_cnt_reg0_tx_mac_partial2_invert_crc_cnt {
      type oc-yang:counter64;
      description
        "Counts the number of transmitted packets with partial CRC type 2.";
    }
    leaf counter_slice8_ifg_mac_pool85_tx_mac_partial2_invert_crc_cnt_reg1_tx_mac_partial2_invert_crc_cnt {
      type oc-yang:counter64;
      description
        "Counts the number of transmitted packets with partial CRC type 2.";
    }
    leaf counter_slice8_ifg_mac_pool85_tx_mac_partial2_invert_crc_cnt_reg2_tx_mac_partial2_invert_crc_cnt {
      type oc-yang:counter64;
      description
        "Counts the number of transmitted packets with partial CRC type 2.";
    }
    leaf counter_slice8_ifg_mac_pool85_tx_mac_partial2_invert_crc_cnt_reg3_tx_mac_partial2_invert_crc_cnt {
      type oc-yang:counter64;
      description
        "Counts the number of transmitted packets with partial CRC type 2.";
    }
    leaf counter_slice8_ifg_mac_pool85_tx_mac_partial2_invert_crc_cnt_reg4_tx_mac_partial2_invert_crc_cnt {
      type oc-yang:counter64;
      description
        "Counts the number of transmitted packets with partial CRC type 2.";
    }
    leaf counter_slice8_ifg_mac_pool85_tx_mac_partial2_invert_crc_cnt_reg5_tx_mac_partial2_invert_crc_cnt {
      type oc-yang:counter64;
      description
        "Counts the number of transmitted packets with partial CRC type 2.";
    }
    leaf counter_slice8_ifg_mac_pool85_tx_mac_partial2_invert_crc_cnt_reg6_tx_mac_partial2_invert_crc_cnt {
      type oc-yang:counter64;
      description
        "Counts the number of transmitted packets with partial CRC type 2.";
    }
    leaf counter_slice8_ifg_mac_pool85_tx_mac_partial2_invert_crc_cnt_reg7_tx_mac_partial2_invert_crc_cnt {
      type oc-yang:counter64;
      description
        "Counts the number of transmitted packets with partial CRC type 2.";
    }
    leaf counter_slice8_ifg_mac_pool86_tx_mac_partial2_invert_crc_cnt_reg0_tx_mac_partial2_invert_crc_cnt {
      type oc-yang:counter64;
      description
        "Counts the number of transmitted packets with partial CRC type 2.";
    }
    leaf counter_slice8_ifg_mac_pool86_tx_mac_partial2_invert_crc_cnt_reg1_tx_mac_partial2_invert_crc_cnt {
      type oc-yang:counter64;
      description
        "Counts the number of transmitted packets with partial CRC type 2.";
    }
    leaf counter_slice8_ifg_mac_pool86_tx_mac_partial2_invert_crc_cnt_reg2_tx_mac_partial2_invert_crc_cnt {
      type oc-yang:counter64;
      description
        "Counts the number of transmitted packets with partial CRC type 2.";
    }
    leaf counter_slice8_ifg_mac_pool86_tx_mac_partial2_invert_crc_cnt_reg3_tx_mac_partial2_invert_crc_cnt {
      type oc-yang:counter64;
      description
        "Counts the number of transmitted packets with partial CRC type 2.";
    }
    leaf counter_slice8_ifg_mac_pool86_tx_mac_partial2_invert_crc_cnt_reg4_tx_mac_partial2_invert_crc_cnt {
      type oc-yang:counter64;
      description
        "Counts the number of transmitted packets with partial CRC type 2.";
    }
    leaf counter_slice8_ifg_mac_pool86_tx_mac_partial2_invert_crc_cnt_reg5_tx_mac_partial2_invert_crc_cnt {
      type oc-yang:counter64;
      description
        "Counts the number of transmitted packets with partial CRC type 2.";
    }
    leaf counter_slice8_ifg_mac_pool86_tx_mac_partial2_invert_crc_cnt_reg6_tx_mac_partial2_invert_crc_cnt {
      type oc-yang:counter64;
      description
        "Counts the number of transmitted packets with partial CRC type 2.";
    }
    leaf counter_slice8_ifg_mac_pool86_tx_mac_partial2_invert_crc_cnt_reg7_tx_mac_partial2_invert_crc_cnt {
      type oc-yang:counter64;
      description
        "Counts the number of transmitted packets with partial CRC type 2.";
    }
    leaf counter_slice8_ifg_mac_pool87_tx_mac_partial2_invert_crc_cnt_reg0_tx_mac_partial2_invert_crc_cnt {
      type oc-yang:counter64;
      description
        "Counts the number of transmitted packets with partial CRC type 2.";
    }
    leaf counter_slice8_ifg_mac_pool87_tx_mac_partial2_invert_crc_cnt_reg1_tx_mac_partial2_invert_crc_cnt {
      type oc-yang:counter64;
      description
        "Counts the number of transmitted packets with partial CRC type 2.";
    }
    leaf counter_slice8_ifg_mac_pool87_tx_mac_partial2_invert_crc_cnt_reg2_tx_mac_partial2_invert_crc_cnt {
      type oc-yang:counter64;
      description
        "Counts the number of transmitted packets with partial CRC type 2.";
    }
    leaf counter_slice8_ifg_mac_pool87_tx_mac_partial2_invert_crc_cnt_reg3_tx_mac_partial2_invert_crc_cnt {
      type oc-yang:counter64;
      description
        "Counts the number of transmitted packets with partial CRC type 2.";
    }
    leaf counter_slice8_ifg_mac_pool87_tx_mac_partial2_invert_crc_cnt_reg4_tx_mac_partial2_invert_crc_cnt {
      type oc-yang:counter64;
      description
        "Counts the number of transmitted packets with partial CRC type 2.";
    }
    leaf counter_slice8_ifg_mac_pool87_tx_mac_partial2_invert_crc_cnt_reg5_tx_mac_partial2_invert_crc_cnt {
      type oc-yang:counter64;
      description
        "Counts the number of transmitted packets with partial CRC type 2.";
    }
    leaf counter_slice8_ifg_mac_pool87_tx_mac_partial2_invert_crc_cnt_reg6_tx_mac_partial2_invert_crc_cnt {
      type oc-yang:counter64;
      description
        "Counts the number of transmitted packets with partial CRC type 2.";
    }
    leaf counter_slice8_ifg_mac_pool87_tx_mac_partial2_invert_crc_cnt_reg7_tx_mac_partial2_invert_crc_cnt {
      type oc-yang:counter64;
      description
        "Counts the number of transmitted packets with partial CRC type 2.";
    }
    leaf counter_slice9_ifg_mac_pool80_tx_mac_partial2_invert_crc_cnt_reg0_tx_mac_partial2_invert_crc_cnt {
      type oc-yang:counter64;
      description
        "Counts the number of transmitted packets with partial CRC type 2.";
    }
    leaf counter_slice9_ifg_mac_pool80_tx_mac_partial2_invert_crc_cnt_reg1_tx_mac_partial2_invert_crc_cnt {
      type oc-yang:counter64;
      description
        "Counts the number of transmitted packets with partial CRC type 2.";
    }
    leaf counter_slice9_ifg_mac_pool80_tx_mac_partial2_invert_crc_cnt_reg2_tx_mac_partial2_invert_crc_cnt {
      type oc-yang:counter64;
      description
        "Counts the number of transmitted packets with partial CRC type 2.";
    }
    leaf counter_slice9_ifg_mac_pool80_tx_mac_partial2_invert_crc_cnt_reg3_tx_mac_partial2_invert_crc_cnt {
      type oc-yang:counter64;
      description
        "Counts the number of transmitted packets with partial CRC type 2.";
    }
    leaf counter_slice9_ifg_mac_pool80_tx_mac_partial2_invert_crc_cnt_reg4_tx_mac_partial2_invert_crc_cnt {
      type oc-yang:counter64;
      description
        "Counts the number of transmitted packets with partial CRC type 2.";
    }
    leaf counter_slice9_ifg_mac_pool80_tx_mac_partial2_invert_crc_cnt_reg5_tx_mac_partial2_invert_crc_cnt {
      type oc-yang:counter64;
      description
        "Counts the number of transmitted packets with partial CRC type 2.";
    }
    leaf counter_slice9_ifg_mac_pool80_tx_mac_partial2_invert_crc_cnt_reg6_tx_mac_partial2_invert_crc_cnt {
      type oc-yang:counter64;
      description
        "Counts the number of transmitted packets with partial CRC type 2.";
    }
    leaf counter_slice9_ifg_mac_pool80_tx_mac_partial2_invert_crc_cnt_reg7_tx_mac_partial2_invert_crc_cnt {
      type oc-yang:counter64;
      description
        "Counts the number of transmitted packets with partial CRC type 2.";
    }
    leaf counter_slice9_ifg_mac_pool81_tx_mac_partial2_invert_crc_cnt_reg0_tx_mac_partial2_invert_crc_cnt {
      type oc-yang:counter64;
      description
        "Counts the number of transmitted packets with partial CRC type 2.";
    }
    leaf counter_slice9_ifg_mac_pool81_tx_mac_partial2_invert_crc_cnt_reg1_tx_mac_partial2_invert_crc_cnt {
      type oc-yang:counter64;
      description
        "Counts the number of transmitted packets with partial CRC type 2.";
    }
    leaf counter_slice9_ifg_mac_pool81_tx_mac_partial2_invert_crc_cnt_reg2_tx_mac_partial2_invert_crc_cnt {
      type oc-yang:counter64;
      description
        "Counts the number of transmitted packets with partial CRC type 2.";
    }
    leaf counter_slice9_ifg_mac_pool81_tx_mac_partial2_invert_crc_cnt_reg3_tx_mac_partial2_invert_crc_cnt {
      type oc-yang:counter64;
      description
        "Counts the number of transmitted packets with partial CRC type 2.";
    }
    leaf counter_slice9_ifg_mac_pool81_tx_mac_partial2_invert_crc_cnt_reg4_tx_mac_partial2_invert_crc_cnt {
      type oc-yang:counter64;
      description
        "Counts the number of transmitted packets with partial CRC type 2.";
    }
    leaf counter_slice9_ifg_mac_pool81_tx_mac_partial2_invert_crc_cnt_reg5_tx_mac_partial2_invert_crc_cnt {
      type oc-yang:counter64;
      description
        "Counts the number of transmitted packets with partial CRC type 2.";
    }
    leaf counter_slice9_ifg_mac_pool81_tx_mac_partial2_invert_crc_cnt_reg6_tx_mac_partial2_invert_crc_cnt {
      type oc-yang:counter64;
      description
        "Counts the number of transmitted packets with partial CRC type 2.";
    }
    leaf counter_slice9_ifg_mac_pool81_tx_mac_partial2_invert_crc_cnt_reg7_tx_mac_partial2_invert_crc_cnt {
      type oc-yang:counter64;
      description
        "Counts the number of transmitted packets with partial CRC type 2.";
    }
    leaf counter_slice9_ifg_mac_pool82_tx_mac_partial2_invert_crc_cnt_reg0_tx_mac_partial2_invert_crc_cnt {
      type oc-yang:counter64;
      description
        "Counts the number of transmitted packets with partial CRC type 2.";
    }
    leaf counter_slice9_ifg_mac_pool82_tx_mac_partial2_invert_crc_cnt_reg1_tx_mac_partial2_invert_crc_cnt {
      type oc-yang:counter64;
      description
        "Counts the number of transmitted packets with partial CRC type 2.";
    }
    leaf counter_slice9_ifg_mac_pool82_tx_mac_partial2_invert_crc_cnt_reg2_tx_mac_partial2_invert_crc_cnt {
      type oc-yang:counter64;
      description
        "Counts the number of transmitted packets with partial CRC type 2.";
    }
    leaf counter_slice9_ifg_mac_pool82_tx_mac_partial2_invert_crc_cnt_reg3_tx_mac_partial2_invert_crc_cnt {
      type oc-yang:counter64;
      description
        "Counts the number of transmitted packets with partial CRC type 2.";
    }
    leaf counter_slice9_ifg_mac_pool82_tx_mac_partial2_invert_crc_cnt_reg4_tx_mac_partial2_invert_crc_cnt {
      type oc-yang:counter64;
      description
        "Counts the number of transmitted packets with partial CRC type 2.";
    }
    leaf counter_slice9_ifg_mac_pool82_tx_mac_partial2_invert_crc_cnt_reg5_tx_mac_partial2_invert_crc_cnt {
      type oc-yang:counter64;
      description
        "Counts the number of transmitted packets with partial CRC type 2.";
    }
    leaf counter_slice9_ifg_mac_pool82_tx_mac_partial2_invert_crc_cnt_reg6_tx_mac_partial2_invert_crc_cnt {
      type oc-yang:counter64;
      description
        "Counts the number of transmitted packets with partial CRC type 2.";
    }
    leaf counter_slice9_ifg_mac_pool82_tx_mac_partial2_invert_crc_cnt_reg7_tx_mac_partial2_invert_crc_cnt {
      type oc-yang:counter64;
      description
        "Counts the number of transmitted packets with partial CRC type 2.";
    }
    leaf counter_slice9_ifg_mac_pool83_tx_mac_partial2_invert_crc_cnt_reg0_tx_mac_partial2_invert_crc_cnt {
      type oc-yang:counter64;
      description
        "Counts the number of transmitted packets with partial CRC type 2.";
    }
    leaf counter_slice9_ifg_mac_pool83_tx_mac_partial2_invert_crc_cnt_reg1_tx_mac_partial2_invert_crc_cnt {
      type oc-yang:counter64;
      description
        "Counts the number of transmitted packets with partial CRC type 2.";
    }
    leaf counter_slice9_ifg_mac_pool83_tx_mac_partial2_invert_crc_cnt_reg2_tx_mac_partial2_invert_crc_cnt {
      type oc-yang:counter64;
      description
        "Counts the number of transmitted packets with partial CRC type 2.";
    }
    leaf counter_slice9_ifg_mac_pool83_tx_mac_partial2_invert_crc_cnt_reg3_tx_mac_partial2_invert_crc_cnt {
      type oc-yang:counter64;
      description
        "Counts the number of transmitted packets with partial CRC type 2.";
    }
    leaf counter_slice9_ifg_mac_pool83_tx_mac_partial2_invert_crc_cnt_reg4_tx_mac_partial2_invert_crc_cnt {
      type oc-yang:counter64;
      description
        "Counts the number of transmitted packets with partial CRC type 2.";
    }
    leaf counter_slice9_ifg_mac_pool83_tx_mac_partial2_invert_crc_cnt_reg5_tx_mac_partial2_invert_crc_cnt {
      type oc-yang:counter64;
      description
        "Counts the number of transmitted packets with partial CRC type 2.";
    }
    leaf counter_slice9_ifg_mac_pool83_tx_mac_partial2_invert_crc_cnt_reg6_tx_mac_partial2_invert_crc_cnt {
      type oc-yang:counter64;
      description
        "Counts the number of transmitted packets with partial CRC type 2.";
    }
    leaf counter_slice9_ifg_mac_pool83_tx_mac_partial2_invert_crc_cnt_reg7_tx_mac_partial2_invert_crc_cnt {
      type oc-yang:counter64;
      description
        "Counts the number of transmitted packets with partial CRC type 2.";
    }
    leaf counter_slice9_ifg_mac_pool84_tx_mac_partial2_invert_crc_cnt_reg0_tx_mac_partial2_invert_crc_cnt {
      type oc-yang:counter64;
      description
        "Counts the number of transmitted packets with partial CRC type 2.";
    }
    leaf counter_slice9_ifg_mac_pool84_tx_mac_partial2_invert_crc_cnt_reg1_tx_mac_partial2_invert_crc_cnt {
      type oc-yang:counter64;
      description
        "Counts the number of transmitted packets with partial CRC type 2.";
    }
    leaf counter_slice9_ifg_mac_pool84_tx_mac_partial2_invert_crc_cnt_reg2_tx_mac_partial2_invert_crc_cnt {
      type oc-yang:counter64;
      description
        "Counts the number of transmitted packets with partial CRC type 2.";
    }
    leaf counter_slice9_ifg_mac_pool84_tx_mac_partial2_invert_crc_cnt_reg3_tx_mac_partial2_invert_crc_cnt {
      type oc-yang:counter64;
      description
        "Counts the number of transmitted packets with partial CRC type 2.";
    }
    leaf counter_slice9_ifg_mac_pool84_tx_mac_partial2_invert_crc_cnt_reg4_tx_mac_partial2_invert_crc_cnt {
      type oc-yang:counter64;
      description
        "Counts the number of transmitted packets with partial CRC type 2.";
    }
    leaf counter_slice9_ifg_mac_pool84_tx_mac_partial2_invert_crc_cnt_reg5_tx_mac_partial2_invert_crc_cnt {
      type oc-yang:counter64;
      description
        "Counts the number of transmitted packets with partial CRC type 2.";
    }
    leaf counter_slice9_ifg_mac_pool84_tx_mac_partial2_invert_crc_cnt_reg6_tx_mac_partial2_invert_crc_cnt {
      type oc-yang:counter64;
      description
        "Counts the number of transmitted packets with partial CRC type 2.";
    }
    leaf counter_slice9_ifg_mac_pool84_tx_mac_partial2_invert_crc_cnt_reg7_tx_mac_partial2_invert_crc_cnt {
      type oc-yang:counter64;
      description
        "Counts the number of transmitted packets with partial CRC type 2.";
    }
    leaf counter_slice9_ifg_mac_pool85_tx_mac_partial2_invert_crc_cnt_reg0_tx_mac_partial2_invert_crc_cnt {
      type oc-yang:counter64;
      description
        "Counts the number of transmitted packets with partial CRC type 2.";
    }
    leaf counter_slice9_ifg_mac_pool85_tx_mac_partial2_invert_crc_cnt_reg1_tx_mac_partial2_invert_crc_cnt {
      type oc-yang:counter64;
      description
        "Counts the number of transmitted packets with partial CRC type 2.";
    }
    leaf counter_slice9_ifg_mac_pool85_tx_mac_partial2_invert_crc_cnt_reg2_tx_mac_partial2_invert_crc_cnt {
      type oc-yang:counter64;
      description
        "Counts the number of transmitted packets with partial CRC type 2.";
    }
    leaf counter_slice9_ifg_mac_pool85_tx_mac_partial2_invert_crc_cnt_reg3_tx_mac_partial2_invert_crc_cnt {
      type oc-yang:counter64;
      description
        "Counts the number of transmitted packets with partial CRC type 2.";
    }
    leaf counter_slice9_ifg_mac_pool85_tx_mac_partial2_invert_crc_cnt_reg4_tx_mac_partial2_invert_crc_cnt {
      type oc-yang:counter64;
      description
        "Counts the number of transmitted packets with partial CRC type 2.";
    }
    leaf counter_slice9_ifg_mac_pool85_tx_mac_partial2_invert_crc_cnt_reg5_tx_mac_partial2_invert_crc_cnt {
      type oc-yang:counter64;
      description
        "Counts the number of transmitted packets with partial CRC type 2.";
    }
    leaf counter_slice9_ifg_mac_pool85_tx_mac_partial2_invert_crc_cnt_reg6_tx_mac_partial2_invert_crc_cnt {
      type oc-yang:counter64;
      description
        "Counts the number of transmitted packets with partial CRC type 2.";
    }
    leaf counter_slice9_ifg_mac_pool85_tx_mac_partial2_invert_crc_cnt_reg7_tx_mac_partial2_invert_crc_cnt {
      type oc-yang:counter64;
      description
        "Counts the number of transmitted packets with partial CRC type 2.";
    }
    leaf counter_slice9_ifg_mac_pool86_tx_mac_partial2_invert_crc_cnt_reg0_tx_mac_partial2_invert_crc_cnt {
      type oc-yang:counter64;
      description
        "Counts the number of transmitted packets with partial CRC type 2.";
    }
    leaf counter_slice9_ifg_mac_pool86_tx_mac_partial2_invert_crc_cnt_reg1_tx_mac_partial2_invert_crc_cnt {
      type oc-yang:counter64;
      description
        "Counts the number of transmitted packets with partial CRC type 2.";
    }
    leaf counter_slice9_ifg_mac_pool86_tx_mac_partial2_invert_crc_cnt_reg2_tx_mac_partial2_invert_crc_cnt {
      type oc-yang:counter64;
      description
        "Counts the number of transmitted packets with partial CRC type 2.";
    }
    leaf counter_slice9_ifg_mac_pool86_tx_mac_partial2_invert_crc_cnt_reg3_tx_mac_partial2_invert_crc_cnt {
      type oc-yang:counter64;
      description
        "Counts the number of transmitted packets with partial CRC type 2.";
    }
    leaf counter_slice9_ifg_mac_pool86_tx_mac_partial2_invert_crc_cnt_reg4_tx_mac_partial2_invert_crc_cnt {
      type oc-yang:counter64;
      description
        "Counts the number of transmitted packets with partial CRC type 2.";
    }
    leaf counter_slice9_ifg_mac_pool86_tx_mac_partial2_invert_crc_cnt_reg5_tx_mac_partial2_invert_crc_cnt {
      type oc-yang:counter64;
      description
        "Counts the number of transmitted packets with partial CRC type 2.";
    }
    leaf counter_slice9_ifg_mac_pool86_tx_mac_partial2_invert_crc_cnt_reg6_tx_mac_partial2_invert_crc_cnt {
      type oc-yang:counter64;
      description
        "Counts the number of transmitted packets with partial CRC type 2.";
    }
    leaf counter_slice9_ifg_mac_pool86_tx_mac_partial2_invert_crc_cnt_reg7_tx_mac_partial2_invert_crc_cnt {
      type oc-yang:counter64;
      description
        "Counts the number of transmitted packets with partial CRC type 2.";
    }
    leaf counter_slice9_ifg_mac_pool87_tx_mac_partial2_invert_crc_cnt_reg0_tx_mac_partial2_invert_crc_cnt {
      type oc-yang:counter64;
      description
        "Counts the number of transmitted packets with partial CRC type 2.";
    }
    leaf counter_slice9_ifg_mac_pool87_tx_mac_partial2_invert_crc_cnt_reg1_tx_mac_partial2_invert_crc_cnt {
      type oc-yang:counter64;
      description
        "Counts the number of transmitted packets with partial CRC type 2.";
    }
    leaf counter_slice9_ifg_mac_pool87_tx_mac_partial2_invert_crc_cnt_reg2_tx_mac_partial2_invert_crc_cnt {
      type oc-yang:counter64;
      description
        "Counts the number of transmitted packets with partial CRC type 2.";
    }
    leaf counter_slice9_ifg_mac_pool87_tx_mac_partial2_invert_crc_cnt_reg3_tx_mac_partial2_invert_crc_cnt {
      type oc-yang:counter64;
      description
        "Counts the number of transmitted packets with partial CRC type 2.";
    }
    leaf counter_slice9_ifg_mac_pool87_tx_mac_partial2_invert_crc_cnt_reg4_tx_mac_partial2_invert_crc_cnt {
      type oc-yang:counter64;
      description
        "Counts the number of transmitted packets with partial CRC type 2.";
    }
    leaf counter_slice9_ifg_mac_pool87_tx_mac_partial2_invert_crc_cnt_reg5_tx_mac_partial2_invert_crc_cnt {
      type oc-yang:counter64;
      description
        "Counts the number of transmitted packets with partial CRC type 2.";
    }
    leaf counter_slice9_ifg_mac_pool87_tx_mac_partial2_invert_crc_cnt_reg6_tx_mac_partial2_invert_crc_cnt {
      type oc-yang:counter64;
      description
        "Counts the number of transmitted packets with partial CRC type 2.";
    }
    leaf counter_slice9_ifg_mac_pool87_tx_mac_partial2_invert_crc_cnt_reg7_tx_mac_partial2_invert_crc_cnt {
      type oc-yang:counter64;
      description
        "Counts the number of transmitted packets with partial CRC type 2.";
    }
    leaf counter_slice10_ifg_mac_pool80_tx_mac_partial2_invert_crc_cnt_reg0_tx_mac_partial2_invert_crc_cnt {
      type oc-yang:counter64;
      description
        "Counts the number of transmitted packets with partial CRC type 2.";
    }
    leaf counter_slice10_ifg_mac_pool80_tx_mac_partial2_invert_crc_cnt_reg1_tx_mac_partial2_invert_crc_cnt {
      type oc-yang:counter64;
      description
        "Counts the number of transmitted packets with partial CRC type 2.";
    }
    leaf counter_slice10_ifg_mac_pool80_tx_mac_partial2_invert_crc_cnt_reg2_tx_mac_partial2_invert_crc_cnt {
      type oc-yang:counter64;
      description
        "Counts the number of transmitted packets with partial CRC type 2.";
    }
    leaf counter_slice10_ifg_mac_pool80_tx_mac_partial2_invert_crc_cnt_reg3_tx_mac_partial2_invert_crc_cnt {
      type oc-yang:counter64;
      description
        "Counts the number of transmitted packets with partial CRC type 2.";
    }
    leaf counter_slice10_ifg_mac_pool80_tx_mac_partial2_invert_crc_cnt_reg4_tx_mac_partial2_invert_crc_cnt {
      type oc-yang:counter64;
      description
        "Counts the number of transmitted packets with partial CRC type 2.";
    }
    leaf counter_slice10_ifg_mac_pool80_tx_mac_partial2_invert_crc_cnt_reg5_tx_mac_partial2_invert_crc_cnt {
      type oc-yang:counter64;
      description
        "Counts the number of transmitted packets with partial CRC type 2.";
    }
    leaf counter_slice10_ifg_mac_pool80_tx_mac_partial2_invert_crc_cnt_reg6_tx_mac_partial2_invert_crc_cnt {
      type oc-yang:counter64;
      description
        "Counts the number of transmitted packets with partial CRC type 2.";
    }
    leaf counter_slice10_ifg_mac_pool80_tx_mac_partial2_invert_crc_cnt_reg7_tx_mac_partial2_invert_crc_cnt {
      type oc-yang:counter64;
      description
        "Counts the number of transmitted packets with partial CRC type 2.";
    }
    leaf counter_slice10_ifg_mac_pool81_tx_mac_partial2_invert_crc_cnt_reg0_tx_mac_partial2_invert_crc_cnt {
      type oc-yang:counter64;
      description
        "Counts the number of transmitted packets with partial CRC type 2.";
    }
    leaf counter_slice10_ifg_mac_pool81_tx_mac_partial2_invert_crc_cnt_reg1_tx_mac_partial2_invert_crc_cnt {
      type oc-yang:counter64;
      description
        "Counts the number of transmitted packets with partial CRC type 2.";
    }
    leaf counter_slice10_ifg_mac_pool81_tx_mac_partial2_invert_crc_cnt_reg2_tx_mac_partial2_invert_crc_cnt {
      type oc-yang:counter64;
      description
        "Counts the number of transmitted packets with partial CRC type 2.";
    }
    leaf counter_slice10_ifg_mac_pool81_tx_mac_partial2_invert_crc_cnt_reg3_tx_mac_partial2_invert_crc_cnt {
      type oc-yang:counter64;
      description
        "Counts the number of transmitted packets with partial CRC type 2.";
    }
    leaf counter_slice10_ifg_mac_pool81_tx_mac_partial2_invert_crc_cnt_reg4_tx_mac_partial2_invert_crc_cnt {
      type oc-yang:counter64;
      description
        "Counts the number of transmitted packets with partial CRC type 2.";
    }
    leaf counter_slice10_ifg_mac_pool81_tx_mac_partial2_invert_crc_cnt_reg5_tx_mac_partial2_invert_crc_cnt {
      type oc-yang:counter64;
      description
        "Counts the number of transmitted packets with partial CRC type 2.";
    }
    leaf counter_slice10_ifg_mac_pool81_tx_mac_partial2_invert_crc_cnt_reg6_tx_mac_partial2_invert_crc_cnt {
      type oc-yang:counter64;
      description
        "Counts the number of transmitted packets with partial CRC type 2.";
    }
    leaf counter_slice10_ifg_mac_pool81_tx_mac_partial2_invert_crc_cnt_reg7_tx_mac_partial2_invert_crc_cnt {
      type oc-yang:counter64;
      description
        "Counts the number of transmitted packets with partial CRC type 2.";
    }
    leaf counter_slice10_ifg_mac_pool82_tx_mac_partial2_invert_crc_cnt_reg0_tx_mac_partial2_invert_crc_cnt {
      type oc-yang:counter64;
      description
        "Counts the number of transmitted packets with partial CRC type 2.";
    }
    leaf counter_slice10_ifg_mac_pool82_tx_mac_partial2_invert_crc_cnt_reg1_tx_mac_partial2_invert_crc_cnt {
      type oc-yang:counter64;
      description
        "Counts the number of transmitted packets with partial CRC type 2.";
    }
    leaf counter_slice10_ifg_mac_pool82_tx_mac_partial2_invert_crc_cnt_reg2_tx_mac_partial2_invert_crc_cnt {
      type oc-yang:counter64;
      description
        "Counts the number of transmitted packets with partial CRC type 2.";
    }
    leaf counter_slice10_ifg_mac_pool82_tx_mac_partial2_invert_crc_cnt_reg3_tx_mac_partial2_invert_crc_cnt {
      type oc-yang:counter64;
      description
        "Counts the number of transmitted packets with partial CRC type 2.";
    }
    leaf counter_slice10_ifg_mac_pool82_tx_mac_partial2_invert_crc_cnt_reg4_tx_mac_partial2_invert_crc_cnt {
      type oc-yang:counter64;
      description
        "Counts the number of transmitted packets with partial CRC type 2.";
    }
    leaf counter_slice10_ifg_mac_pool82_tx_mac_partial2_invert_crc_cnt_reg5_tx_mac_partial2_invert_crc_cnt {
      type oc-yang:counter64;
      description
        "Counts the number of transmitted packets with partial CRC type 2.";
    }
    leaf counter_slice10_ifg_mac_pool82_tx_mac_partial2_invert_crc_cnt_reg6_tx_mac_partial2_invert_crc_cnt {
      type oc-yang:counter64;
      description
        "Counts the number of transmitted packets with partial CRC type 2.";
    }
    leaf counter_slice10_ifg_mac_pool82_tx_mac_partial2_invert_crc_cnt_reg7_tx_mac_partial2_invert_crc_cnt {
      type oc-yang:counter64;
      description
        "Counts the number of transmitted packets with partial CRC type 2.";
    }
    leaf counter_slice10_ifg_mac_pool83_tx_mac_partial2_invert_crc_cnt_reg0_tx_mac_partial2_invert_crc_cnt {
      type oc-yang:counter64;
      description
        "Counts the number of transmitted packets with partial CRC type 2.";
    }
    leaf counter_slice10_ifg_mac_pool83_tx_mac_partial2_invert_crc_cnt_reg1_tx_mac_partial2_invert_crc_cnt {
      type oc-yang:counter64;
      description
        "Counts the number of transmitted packets with partial CRC type 2.";
    }
    leaf counter_slice10_ifg_mac_pool83_tx_mac_partial2_invert_crc_cnt_reg2_tx_mac_partial2_invert_crc_cnt {
      type oc-yang:counter64;
      description
        "Counts the number of transmitted packets with partial CRC type 2.";
    }
    leaf counter_slice10_ifg_mac_pool83_tx_mac_partial2_invert_crc_cnt_reg3_tx_mac_partial2_invert_crc_cnt {
      type oc-yang:counter64;
      description
        "Counts the number of transmitted packets with partial CRC type 2.";
    }
    leaf counter_slice10_ifg_mac_pool83_tx_mac_partial2_invert_crc_cnt_reg4_tx_mac_partial2_invert_crc_cnt {
      type oc-yang:counter64;
      description
        "Counts the number of transmitted packets with partial CRC type 2.";
    }
    leaf counter_slice10_ifg_mac_pool83_tx_mac_partial2_invert_crc_cnt_reg5_tx_mac_partial2_invert_crc_cnt {
      type oc-yang:counter64;
      description
        "Counts the number of transmitted packets with partial CRC type 2.";
    }
    leaf counter_slice10_ifg_mac_pool83_tx_mac_partial2_invert_crc_cnt_reg6_tx_mac_partial2_invert_crc_cnt {
      type oc-yang:counter64;
      description
        "Counts the number of transmitted packets with partial CRC type 2.";
    }
    leaf counter_slice10_ifg_mac_pool83_tx_mac_partial2_invert_crc_cnt_reg7_tx_mac_partial2_invert_crc_cnt {
      type oc-yang:counter64;
      description
        "Counts the number of transmitted packets with partial CRC type 2.";
    }
    leaf counter_slice10_ifg_mac_pool84_tx_mac_partial2_invert_crc_cnt_reg0_tx_mac_partial2_invert_crc_cnt {
      type oc-yang:counter64;
      description
        "Counts the number of transmitted packets with partial CRC type 2.";
    }
    leaf counter_slice10_ifg_mac_pool84_tx_mac_partial2_invert_crc_cnt_reg1_tx_mac_partial2_invert_crc_cnt {
      type oc-yang:counter64;
      description
        "Counts the number of transmitted packets with partial CRC type 2.";
    }
    leaf counter_slice10_ifg_mac_pool84_tx_mac_partial2_invert_crc_cnt_reg2_tx_mac_partial2_invert_crc_cnt {
      type oc-yang:counter64;
      description
        "Counts the number of transmitted packets with partial CRC type 2.";
    }
    leaf counter_slice10_ifg_mac_pool84_tx_mac_partial2_invert_crc_cnt_reg3_tx_mac_partial2_invert_crc_cnt {
      type oc-yang:counter64;
      description
        "Counts the number of transmitted packets with partial CRC type 2.";
    }
    leaf counter_slice10_ifg_mac_pool84_tx_mac_partial2_invert_crc_cnt_reg4_tx_mac_partial2_invert_crc_cnt {
      type oc-yang:counter64;
      description
        "Counts the number of transmitted packets with partial CRC type 2.";
    }
    leaf counter_slice10_ifg_mac_pool84_tx_mac_partial2_invert_crc_cnt_reg5_tx_mac_partial2_invert_crc_cnt {
      type oc-yang:counter64;
      description
        "Counts the number of transmitted packets with partial CRC type 2.";
    }
    leaf counter_slice10_ifg_mac_pool84_tx_mac_partial2_invert_crc_cnt_reg6_tx_mac_partial2_invert_crc_cnt {
      type oc-yang:counter64;
      description
        "Counts the number of transmitted packets with partial CRC type 2.";
    }
    leaf counter_slice10_ifg_mac_pool84_tx_mac_partial2_invert_crc_cnt_reg7_tx_mac_partial2_invert_crc_cnt {
      type oc-yang:counter64;
      description
        "Counts the number of transmitted packets with partial CRC type 2.";
    }
    leaf counter_slice10_ifg_mac_pool85_tx_mac_partial2_invert_crc_cnt_reg0_tx_mac_partial2_invert_crc_cnt {
      type oc-yang:counter64;
      description
        "Counts the number of transmitted packets with partial CRC type 2.";
    }
    leaf counter_slice10_ifg_mac_pool85_tx_mac_partial2_invert_crc_cnt_reg1_tx_mac_partial2_invert_crc_cnt {
      type oc-yang:counter64;
      description
        "Counts the number of transmitted packets with partial CRC type 2.";
    }
    leaf counter_slice10_ifg_mac_pool85_tx_mac_partial2_invert_crc_cnt_reg2_tx_mac_partial2_invert_crc_cnt {
      type oc-yang:counter64;
      description
        "Counts the number of transmitted packets with partial CRC type 2.";
    }
    leaf counter_slice10_ifg_mac_pool85_tx_mac_partial2_invert_crc_cnt_reg3_tx_mac_partial2_invert_crc_cnt {
      type oc-yang:counter64;
      description
        "Counts the number of transmitted packets with partial CRC type 2.";
    }
    leaf counter_slice10_ifg_mac_pool85_tx_mac_partial2_invert_crc_cnt_reg4_tx_mac_partial2_invert_crc_cnt {
      type oc-yang:counter64;
      description
        "Counts the number of transmitted packets with partial CRC type 2.";
    }
    leaf counter_slice10_ifg_mac_pool85_tx_mac_partial2_invert_crc_cnt_reg5_tx_mac_partial2_invert_crc_cnt {
      type oc-yang:counter64;
      description
        "Counts the number of transmitted packets with partial CRC type 2.";
    }
    leaf counter_slice10_ifg_mac_pool85_tx_mac_partial2_invert_crc_cnt_reg6_tx_mac_partial2_invert_crc_cnt {
      type oc-yang:counter64;
      description
        "Counts the number of transmitted packets with partial CRC type 2.";
    }
    leaf counter_slice10_ifg_mac_pool85_tx_mac_partial2_invert_crc_cnt_reg7_tx_mac_partial2_invert_crc_cnt {
      type oc-yang:counter64;
      description
        "Counts the number of transmitted packets with partial CRC type 2.";
    }
    leaf counter_slice10_ifg_mac_pool86_tx_mac_partial2_invert_crc_cnt_reg0_tx_mac_partial2_invert_crc_cnt {
      type oc-yang:counter64;
      description
        "Counts the number of transmitted packets with partial CRC type 2.";
    }
    leaf counter_slice10_ifg_mac_pool86_tx_mac_partial2_invert_crc_cnt_reg1_tx_mac_partial2_invert_crc_cnt {
      type oc-yang:counter64;
      description
        "Counts the number of transmitted packets with partial CRC type 2.";
    }
    leaf counter_slice10_ifg_mac_pool86_tx_mac_partial2_invert_crc_cnt_reg2_tx_mac_partial2_invert_crc_cnt {
      type oc-yang:counter64;
      description
        "Counts the number of transmitted packets with partial CRC type 2.";
    }
    leaf counter_slice10_ifg_mac_pool86_tx_mac_partial2_invert_crc_cnt_reg3_tx_mac_partial2_invert_crc_cnt {
      type oc-yang:counter64;
      description
        "Counts the number of transmitted packets with partial CRC type 2.";
    }
    leaf counter_slice10_ifg_mac_pool86_tx_mac_partial2_invert_crc_cnt_reg4_tx_mac_partial2_invert_crc_cnt {
      type oc-yang:counter64;
      description
        "Counts the number of transmitted packets with partial CRC type 2.";
    }
    leaf counter_slice10_ifg_mac_pool86_tx_mac_partial2_invert_crc_cnt_reg5_tx_mac_partial2_invert_crc_cnt {
      type oc-yang:counter64;
      description
        "Counts the number of transmitted packets with partial CRC type 2.";
    }
    leaf counter_slice10_ifg_mac_pool86_tx_mac_partial2_invert_crc_cnt_reg6_tx_mac_partial2_invert_crc_cnt {
      type oc-yang:counter64;
      description
        "Counts the number of transmitted packets with partial CRC type 2.";
    }
    leaf counter_slice10_ifg_mac_pool86_tx_mac_partial2_invert_crc_cnt_reg7_tx_mac_partial2_invert_crc_cnt {
      type oc-yang:counter64;
      description
        "Counts the number of transmitted packets with partial CRC type 2.";
    }
    leaf counter_slice10_ifg_mac_pool87_tx_mac_partial2_invert_crc_cnt_reg0_tx_mac_partial2_invert_crc_cnt {
      type oc-yang:counter64;
      description
        "Counts the number of transmitted packets with partial CRC type 2.";
    }
    leaf counter_slice10_ifg_mac_pool87_tx_mac_partial2_invert_crc_cnt_reg1_tx_mac_partial2_invert_crc_cnt {
      type oc-yang:counter64;
      description
        "Counts the number of transmitted packets with partial CRC type 2.";
    }
    leaf counter_slice10_ifg_mac_pool87_tx_mac_partial2_invert_crc_cnt_reg2_tx_mac_partial2_invert_crc_cnt {
      type oc-yang:counter64;
      description
        "Counts the number of transmitted packets with partial CRC type 2.";
    }
    leaf counter_slice10_ifg_mac_pool87_tx_mac_partial2_invert_crc_cnt_reg3_tx_mac_partial2_invert_crc_cnt {
      type oc-yang:counter64;
      description
        "Counts the number of transmitted packets with partial CRC type 2.";
    }
    leaf counter_slice10_ifg_mac_pool87_tx_mac_partial2_invert_crc_cnt_reg4_tx_mac_partial2_invert_crc_cnt {
      type oc-yang:counter64;
      description
        "Counts the number of transmitted packets with partial CRC type 2.";
    }
    leaf counter_slice10_ifg_mac_pool87_tx_mac_partial2_invert_crc_cnt_reg5_tx_mac_partial2_invert_crc_cnt {
      type oc-yang:counter64;
      description
        "Counts the number of transmitted packets with partial CRC type 2.";
    }
    leaf counter_slice10_ifg_mac_pool87_tx_mac_partial2_invert_crc_cnt_reg6_tx_mac_partial2_invert_crc_cnt {
      type oc-yang:counter64;
      description
        "Counts the number of transmitted packets with partial CRC type 2.";
    }
    leaf counter_slice10_ifg_mac_pool87_tx_mac_partial2_invert_crc_cnt_reg7_tx_mac_partial2_invert_crc_cnt {
      type oc-yang:counter64;
      description
        "Counts the number of transmitted packets with partial CRC type 2.";
    }
    leaf counter_slice11_ifg_mac_pool80_tx_mac_partial2_invert_crc_cnt_reg0_tx_mac_partial2_invert_crc_cnt {
      type oc-yang:counter64;
      description
        "Counts the number of transmitted packets with partial CRC type 2.";
    }
    leaf counter_slice11_ifg_mac_pool80_tx_mac_partial2_invert_crc_cnt_reg1_tx_mac_partial2_invert_crc_cnt {
      type oc-yang:counter64;
      description
        "Counts the number of transmitted packets with partial CRC type 2.";
    }
    leaf counter_slice11_ifg_mac_pool80_tx_mac_partial2_invert_crc_cnt_reg2_tx_mac_partial2_invert_crc_cnt {
      type oc-yang:counter64;
      description
        "Counts the number of transmitted packets with partial CRC type 2.";
    }
    leaf counter_slice11_ifg_mac_pool80_tx_mac_partial2_invert_crc_cnt_reg3_tx_mac_partial2_invert_crc_cnt {
      type oc-yang:counter64;
      description
        "Counts the number of transmitted packets with partial CRC type 2.";
    }
    leaf counter_slice11_ifg_mac_pool80_tx_mac_partial2_invert_crc_cnt_reg4_tx_mac_partial2_invert_crc_cnt {
      type oc-yang:counter64;
      description
        "Counts the number of transmitted packets with partial CRC type 2.";
    }
    leaf counter_slice11_ifg_mac_pool80_tx_mac_partial2_invert_crc_cnt_reg5_tx_mac_partial2_invert_crc_cnt {
      type oc-yang:counter64;
      description
        "Counts the number of transmitted packets with partial CRC type 2.";
    }
    leaf counter_slice11_ifg_mac_pool80_tx_mac_partial2_invert_crc_cnt_reg6_tx_mac_partial2_invert_crc_cnt {
      type oc-yang:counter64;
      description
        "Counts the number of transmitted packets with partial CRC type 2.";
    }
    leaf counter_slice11_ifg_mac_pool80_tx_mac_partial2_invert_crc_cnt_reg7_tx_mac_partial2_invert_crc_cnt {
      type oc-yang:counter64;
      description
        "Counts the number of transmitted packets with partial CRC type 2.";
    }
    leaf counter_slice11_ifg_mac_pool81_tx_mac_partial2_invert_crc_cnt_reg0_tx_mac_partial2_invert_crc_cnt {
      type oc-yang:counter64;
      description
        "Counts the number of transmitted packets with partial CRC type 2.";
    }
    leaf counter_slice11_ifg_mac_pool81_tx_mac_partial2_invert_crc_cnt_reg1_tx_mac_partial2_invert_crc_cnt {
      type oc-yang:counter64;
      description
        "Counts the number of transmitted packets with partial CRC type 2.";
    }
    leaf counter_slice11_ifg_mac_pool81_tx_mac_partial2_invert_crc_cnt_reg2_tx_mac_partial2_invert_crc_cnt {
      type oc-yang:counter64;
      description
        "Counts the number of transmitted packets with partial CRC type 2.";
    }
    leaf counter_slice11_ifg_mac_pool81_tx_mac_partial2_invert_crc_cnt_reg3_tx_mac_partial2_invert_crc_cnt {
      type oc-yang:counter64;
      description
        "Counts the number of transmitted packets with partial CRC type 2.";
    }
    leaf counter_slice11_ifg_mac_pool81_tx_mac_partial2_invert_crc_cnt_reg4_tx_mac_partial2_invert_crc_cnt {
      type oc-yang:counter64;
      description
        "Counts the number of transmitted packets with partial CRC type 2.";
    }
    leaf counter_slice11_ifg_mac_pool81_tx_mac_partial2_invert_crc_cnt_reg5_tx_mac_partial2_invert_crc_cnt {
      type oc-yang:counter64;
      description
        "Counts the number of transmitted packets with partial CRC type 2.";
    }
    leaf counter_slice11_ifg_mac_pool81_tx_mac_partial2_invert_crc_cnt_reg6_tx_mac_partial2_invert_crc_cnt {
      type oc-yang:counter64;
      description
        "Counts the number of transmitted packets with partial CRC type 2.";
    }
    leaf counter_slice11_ifg_mac_pool81_tx_mac_partial2_invert_crc_cnt_reg7_tx_mac_partial2_invert_crc_cnt {
      type oc-yang:counter64;
      description
        "Counts the number of transmitted packets with partial CRC type 2.";
    }
    leaf counter_slice11_ifg_mac_pool82_tx_mac_partial2_invert_crc_cnt_reg0_tx_mac_partial2_invert_crc_cnt {
      type oc-yang:counter64;
      description
        "Counts the number of transmitted packets with partial CRC type 2.";
    }
    leaf counter_slice11_ifg_mac_pool82_tx_mac_partial2_invert_crc_cnt_reg1_tx_mac_partial2_invert_crc_cnt {
      type oc-yang:counter64;
      description
        "Counts the number of transmitted packets with partial CRC type 2.";
    }
    leaf counter_slice11_ifg_mac_pool82_tx_mac_partial2_invert_crc_cnt_reg2_tx_mac_partial2_invert_crc_cnt {
      type oc-yang:counter64;
      description
        "Counts the number of transmitted packets with partial CRC type 2.";
    }
    leaf counter_slice11_ifg_mac_pool82_tx_mac_partial2_invert_crc_cnt_reg3_tx_mac_partial2_invert_crc_cnt {
      type oc-yang:counter64;
      description
        "Counts the number of transmitted packets with partial CRC type 2.";
    }
    leaf counter_slice11_ifg_mac_pool82_tx_mac_partial2_invert_crc_cnt_reg4_tx_mac_partial2_invert_crc_cnt {
      type oc-yang:counter64;
      description
        "Counts the number of transmitted packets with partial CRC type 2.";
    }
    leaf counter_slice11_ifg_mac_pool82_tx_mac_partial2_invert_crc_cnt_reg5_tx_mac_partial2_invert_crc_cnt {
      type oc-yang:counter64;
      description
        "Counts the number of transmitted packets with partial CRC type 2.";
    }
    leaf counter_slice11_ifg_mac_pool82_tx_mac_partial2_invert_crc_cnt_reg6_tx_mac_partial2_invert_crc_cnt {
      type oc-yang:counter64;
      description
        "Counts the number of transmitted packets with partial CRC type 2.";
    }
    leaf counter_slice11_ifg_mac_pool82_tx_mac_partial2_invert_crc_cnt_reg7_tx_mac_partial2_invert_crc_cnt {
      type oc-yang:counter64;
      description
        "Counts the number of transmitted packets with partial CRC type 2.";
    }
    leaf counter_slice11_ifg_mac_pool83_tx_mac_partial2_invert_crc_cnt_reg0_tx_mac_partial2_invert_crc_cnt {
      type oc-yang:counter64;
      description
        "Counts the number of transmitted packets with partial CRC type 2.";
    }
    leaf counter_slice11_ifg_mac_pool83_tx_mac_partial2_invert_crc_cnt_reg1_tx_mac_partial2_invert_crc_cnt {
      type oc-yang:counter64;
      description
        "Counts the number of transmitted packets with partial CRC type 2.";
    }
    leaf counter_slice11_ifg_mac_pool83_tx_mac_partial2_invert_crc_cnt_reg2_tx_mac_partial2_invert_crc_cnt {
      type oc-yang:counter64;
      description
        "Counts the number of transmitted packets with partial CRC type 2.";
    }
    leaf counter_slice11_ifg_mac_pool83_tx_mac_partial2_invert_crc_cnt_reg3_tx_mac_partial2_invert_crc_cnt {
      type oc-yang:counter64;
      description
        "Counts the number of transmitted packets with partial CRC type 2.";
    }
    leaf counter_slice11_ifg_mac_pool83_tx_mac_partial2_invert_crc_cnt_reg4_tx_mac_partial2_invert_crc_cnt {
      type oc-yang:counter64;
      description
        "Counts the number of transmitted packets with partial CRC type 2.";
    }
    leaf counter_slice11_ifg_mac_pool83_tx_mac_partial2_invert_crc_cnt_reg5_tx_mac_partial2_invert_crc_cnt {
      type oc-yang:counter64;
      description
        "Counts the number of transmitted packets with partial CRC type 2.";
    }
    leaf counter_slice11_ifg_mac_pool83_tx_mac_partial2_invert_crc_cnt_reg6_tx_mac_partial2_invert_crc_cnt {
      type oc-yang:counter64;
      description
        "Counts the number of transmitted packets with partial CRC type 2.";
    }
    leaf counter_slice11_ifg_mac_pool83_tx_mac_partial2_invert_crc_cnt_reg7_tx_mac_partial2_invert_crc_cnt {
      type oc-yang:counter64;
      description
        "Counts the number of transmitted packets with partial CRC type 2.";
    }
    leaf counter_slice11_ifg_mac_pool84_tx_mac_partial2_invert_crc_cnt_reg0_tx_mac_partial2_invert_crc_cnt {
      type oc-yang:counter64;
      description
        "Counts the number of transmitted packets with partial CRC type 2.";
    }
    leaf counter_slice11_ifg_mac_pool84_tx_mac_partial2_invert_crc_cnt_reg1_tx_mac_partial2_invert_crc_cnt {
      type oc-yang:counter64;
      description
        "Counts the number of transmitted packets with partial CRC type 2.";
    }
    leaf counter_slice11_ifg_mac_pool84_tx_mac_partial2_invert_crc_cnt_reg2_tx_mac_partial2_invert_crc_cnt {
      type oc-yang:counter64;
      description
        "Counts the number of transmitted packets with partial CRC type 2.";
    }
    leaf counter_slice11_ifg_mac_pool84_tx_mac_partial2_invert_crc_cnt_reg3_tx_mac_partial2_invert_crc_cnt {
      type oc-yang:counter64;
      description
        "Counts the number of transmitted packets with partial CRC type 2.";
    }
    leaf counter_slice11_ifg_mac_pool84_tx_mac_partial2_invert_crc_cnt_reg4_tx_mac_partial2_invert_crc_cnt {
      type oc-yang:counter64;
      description
        "Counts the number of transmitted packets with partial CRC type 2.";
    }
    leaf counter_slice11_ifg_mac_pool84_tx_mac_partial2_invert_crc_cnt_reg5_tx_mac_partial2_invert_crc_cnt {
      type oc-yang:counter64;
      description
        "Counts the number of transmitted packets with partial CRC type 2.";
    }
    leaf counter_slice11_ifg_mac_pool84_tx_mac_partial2_invert_crc_cnt_reg6_tx_mac_partial2_invert_crc_cnt {
      type oc-yang:counter64;
      description
        "Counts the number of transmitted packets with partial CRC type 2.";
    }
    leaf counter_slice11_ifg_mac_pool84_tx_mac_partial2_invert_crc_cnt_reg7_tx_mac_partial2_invert_crc_cnt {
      type oc-yang:counter64;
      description
        "Counts the number of transmitted packets with partial CRC type 2.";
    }
    leaf counter_slice11_ifg_mac_pool85_tx_mac_partial2_invert_crc_cnt_reg0_tx_mac_partial2_invert_crc_cnt {
      type oc-yang:counter64;
      description
        "Counts the number of transmitted packets with partial CRC type 2.";
    }
    leaf counter_slice11_ifg_mac_pool85_tx_mac_partial2_invert_crc_cnt_reg1_tx_mac_partial2_invert_crc_cnt {
      type oc-yang:counter64;
      description
        "Counts the number of transmitted packets with partial CRC type 2.";
    }
    leaf counter_slice11_ifg_mac_pool85_tx_mac_partial2_invert_crc_cnt_reg2_tx_mac_partial2_invert_crc_cnt {
      type oc-yang:counter64;
      description
        "Counts the number of transmitted packets with partial CRC type 2.";
    }
    leaf counter_slice11_ifg_mac_pool85_tx_mac_partial2_invert_crc_cnt_reg3_tx_mac_partial2_invert_crc_cnt {
      type oc-yang:counter64;
      description
        "Counts the number of transmitted packets with partial CRC type 2.";
    }
    leaf counter_slice11_ifg_mac_pool85_tx_mac_partial2_invert_crc_cnt_reg4_tx_mac_partial2_invert_crc_cnt {
      type oc-yang:counter64;
      description
        "Counts the number of transmitted packets with partial CRC type 2.";
    }
    leaf counter_slice11_ifg_mac_pool85_tx_mac_partial2_invert_crc_cnt_reg5_tx_mac_partial2_invert_crc_cnt {
      type oc-yang:counter64;
      description
        "Counts the number of transmitted packets with partial CRC type 2.";
    }
    leaf counter_slice11_ifg_mac_pool85_tx_mac_partial2_invert_crc_cnt_reg6_tx_mac_partial2_invert_crc_cnt {
      type oc-yang:counter64;
      description
        "Counts the number of transmitted packets with partial CRC type 2.";
    }
    leaf counter_slice11_ifg_mac_pool85_tx_mac_partial2_invert_crc_cnt_reg7_tx_mac_partial2_invert_crc_cnt {
      type oc-yang:counter64;
      description
        "Counts the number of transmitted packets with partial CRC type 2.";
    }
    leaf counter_slice11_ifg_mac_pool86_tx_mac_partial2_invert_crc_cnt_reg0_tx_mac_partial2_invert_crc_cnt {
      type oc-yang:counter64;
      description
        "Counts the number of transmitted packets with partial CRC type 2.";
    }
    leaf counter_slice11_ifg_mac_pool86_tx_mac_partial2_invert_crc_cnt_reg1_tx_mac_partial2_invert_crc_cnt {
      type oc-yang:counter64;
      description
        "Counts the number of transmitted packets with partial CRC type 2.";
    }
    leaf counter_slice11_ifg_mac_pool86_tx_mac_partial2_invert_crc_cnt_reg2_tx_mac_partial2_invert_crc_cnt {
      type oc-yang:counter64;
      description
        "Counts the number of transmitted packets with partial CRC type 2.";
    }
    leaf counter_slice11_ifg_mac_pool86_tx_mac_partial2_invert_crc_cnt_reg3_tx_mac_partial2_invert_crc_cnt {
      type oc-yang:counter64;
      description
        "Counts the number of transmitted packets with partial CRC type 2.";
    }
    leaf counter_slice11_ifg_mac_pool86_tx_mac_partial2_invert_crc_cnt_reg4_tx_mac_partial2_invert_crc_cnt {
      type oc-yang:counter64;
      description
        "Counts the number of transmitted packets with partial CRC type 2.";
    }
    leaf counter_slice11_ifg_mac_pool86_tx_mac_partial2_invert_crc_cnt_reg5_tx_mac_partial2_invert_crc_cnt {
      type oc-yang:counter64;
      description
        "Counts the number of transmitted packets with partial CRC type 2.";
    }
    leaf counter_slice11_ifg_mac_pool86_tx_mac_partial2_invert_crc_cnt_reg6_tx_mac_partial2_invert_crc_cnt {
      type oc-yang:counter64;
      description
        "Counts the number of transmitted packets with partial CRC type 2.";
    }
    leaf counter_slice11_ifg_mac_pool86_tx_mac_partial2_invert_crc_cnt_reg7_tx_mac_partial2_invert_crc_cnt {
      type oc-yang:counter64;
      description
        "Counts the number of transmitted packets with partial CRC type 2.";
    }
    leaf counter_slice11_ifg_mac_pool87_tx_mac_partial2_invert_crc_cnt_reg0_tx_mac_partial2_invert_crc_cnt {
      type oc-yang:counter64;
      description
        "Counts the number of transmitted packets with partial CRC type 2.";
    }
    leaf counter_slice11_ifg_mac_pool87_tx_mac_partial2_invert_crc_cnt_reg1_tx_mac_partial2_invert_crc_cnt {
      type oc-yang:counter64;
      description
        "Counts the number of transmitted packets with partial CRC type 2.";
    }
    leaf counter_slice11_ifg_mac_pool87_tx_mac_partial2_invert_crc_cnt_reg2_tx_mac_partial2_invert_crc_cnt {
      type oc-yang:counter64;
      description
        "Counts the number of transmitted packets with partial CRC type 2.";
    }
    leaf counter_slice11_ifg_mac_pool87_tx_mac_partial2_invert_crc_cnt_reg3_tx_mac_partial2_invert_crc_cnt {
      type oc-yang:counter64;
      description
        "Counts the number of transmitted packets with partial CRC type 2.";
    }
    leaf counter_slice11_ifg_mac_pool87_tx_mac_partial2_invert_crc_cnt_reg4_tx_mac_partial2_invert_crc_cnt {
      type oc-yang:counter64;
      description
        "Counts the number of transmitted packets with partial CRC type 2.";
    }
    leaf counter_slice11_ifg_mac_pool87_tx_mac_partial2_invert_crc_cnt_reg5_tx_mac_partial2_invert_crc_cnt {
      type oc-yang:counter64;
      description
        "Counts the number of transmitted packets with partial CRC type 2.";
    }
    leaf counter_slice11_ifg_mac_pool87_tx_mac_partial2_invert_crc_cnt_reg6_tx_mac_partial2_invert_crc_cnt {
      type oc-yang:counter64;
      description
        "Counts the number of transmitted packets with partial CRC type 2.";
    }
    leaf counter_slice11_ifg_mac_pool87_tx_mac_partial2_invert_crc_cnt_reg7_tx_mac_partial2_invert_crc_cnt {
      type oc-yang:counter64;
      description
        "Counts the number of transmitted packets with partial CRC type 2.";
    }
    leaf counter_slice12_ifg_mac_pool80_tx_mac_partial2_invert_crc_cnt_reg0_tx_mac_partial2_invert_crc_cnt {
      type oc-yang:counter64;
      description
        "Counts the number of transmitted packets with partial CRC type 2.";
    }
    leaf counter_slice12_ifg_mac_pool80_tx_mac_partial2_invert_crc_cnt_reg1_tx_mac_partial2_invert_crc_cnt {
      type oc-yang:counter64;
      description
        "Counts the number of transmitted packets with partial CRC type 2.";
    }
    leaf counter_slice12_ifg_mac_pool80_tx_mac_partial2_invert_crc_cnt_reg2_tx_mac_partial2_invert_crc_cnt {
      type oc-yang:counter64;
      description
        "Counts the number of transmitted packets with partial CRC type 2.";
    }
    leaf counter_slice12_ifg_mac_pool80_tx_mac_partial2_invert_crc_cnt_reg3_tx_mac_partial2_invert_crc_cnt {
      type oc-yang:counter64;
      description
        "Counts the number of transmitted packets with partial CRC type 2.";
    }
    leaf counter_slice12_ifg_mac_pool80_tx_mac_partial2_invert_crc_cnt_reg4_tx_mac_partial2_invert_crc_cnt {
      type oc-yang:counter64;
      description
        "Counts the number of transmitted packets with partial CRC type 2.";
    }
    leaf counter_slice12_ifg_mac_pool80_tx_mac_partial2_invert_crc_cnt_reg5_tx_mac_partial2_invert_crc_cnt {
      type oc-yang:counter64;
      description
        "Counts the number of transmitted packets with partial CRC type 2.";
    }
    leaf counter_slice12_ifg_mac_pool80_tx_mac_partial2_invert_crc_cnt_reg6_tx_mac_partial2_invert_crc_cnt {
      type oc-yang:counter64;
      description
        "Counts the number of transmitted packets with partial CRC type 2.";
    }
    leaf counter_slice12_ifg_mac_pool80_tx_mac_partial2_invert_crc_cnt_reg7_tx_mac_partial2_invert_crc_cnt {
      type oc-yang:counter64;
      description
        "Counts the number of transmitted packets with partial CRC type 2.";
    }
    leaf counter_slice12_ifg_mac_pool81_tx_mac_partial2_invert_crc_cnt_reg0_tx_mac_partial2_invert_crc_cnt {
      type oc-yang:counter64;
      description
        "Counts the number of transmitted packets with partial CRC type 2.";
    }
    leaf counter_slice12_ifg_mac_pool81_tx_mac_partial2_invert_crc_cnt_reg1_tx_mac_partial2_invert_crc_cnt {
      type oc-yang:counter64;
      description
        "Counts the number of transmitted packets with partial CRC type 2.";
    }
    leaf counter_slice12_ifg_mac_pool81_tx_mac_partial2_invert_crc_cnt_reg2_tx_mac_partial2_invert_crc_cnt {
      type oc-yang:counter64;
      description
        "Counts the number of transmitted packets with partial CRC type 2.";
    }
    leaf counter_slice12_ifg_mac_pool81_tx_mac_partial2_invert_crc_cnt_reg3_tx_mac_partial2_invert_crc_cnt {
      type oc-yang:counter64;
      description
        "Counts the number of transmitted packets with partial CRC type 2.";
    }
    leaf counter_slice12_ifg_mac_pool81_tx_mac_partial2_invert_crc_cnt_reg4_tx_mac_partial2_invert_crc_cnt {
      type oc-yang:counter64;
      description
        "Counts the number of transmitted packets with partial CRC type 2.";
    }
    leaf counter_slice12_ifg_mac_pool81_tx_mac_partial2_invert_crc_cnt_reg5_tx_mac_partial2_invert_crc_cnt {
      type oc-yang:counter64;
      description
        "Counts the number of transmitted packets with partial CRC type 2.";
    }
    leaf counter_slice12_ifg_mac_pool81_tx_mac_partial2_invert_crc_cnt_reg6_tx_mac_partial2_invert_crc_cnt {
      type oc-yang:counter64;
      description
        "Counts the number of transmitted packets with partial CRC type 2.";
    }
    leaf counter_slice12_ifg_mac_pool81_tx_mac_partial2_invert_crc_cnt_reg7_tx_mac_partial2_invert_crc_cnt {
      type oc-yang:counter64;
      description
        "Counts the number of transmitted packets with partial CRC type 2.";
    }
    leaf counter_slice12_ifg_mac_pool82_tx_mac_partial2_invert_crc_cnt_reg0_tx_mac_partial2_invert_crc_cnt {
      type oc-yang:counter64;
      description
        "Counts the number of transmitted packets with partial CRC type 2.";
    }
    leaf counter_slice12_ifg_mac_pool82_tx_mac_partial2_invert_crc_cnt_reg1_tx_mac_partial2_invert_crc_cnt {
      type oc-yang:counter64;
      description
        "Counts the number of transmitted packets with partial CRC type 2.";
    }
    leaf counter_slice12_ifg_mac_pool82_tx_mac_partial2_invert_crc_cnt_reg2_tx_mac_partial2_invert_crc_cnt {
      type oc-yang:counter64;
      description
        "Counts the number of transmitted packets with partial CRC type 2.";
    }
    leaf counter_slice12_ifg_mac_pool82_tx_mac_partial2_invert_crc_cnt_reg3_tx_mac_partial2_invert_crc_cnt {
      type oc-yang:counter64;
      description
        "Counts the number of transmitted packets with partial CRC type 2.";
    }
    leaf counter_slice12_ifg_mac_pool82_tx_mac_partial2_invert_crc_cnt_reg4_tx_mac_partial2_invert_crc_cnt {
      type oc-yang:counter64;
      description
        "Counts the number of transmitted packets with partial CRC type 2.";
    }
    leaf counter_slice12_ifg_mac_pool82_tx_mac_partial2_invert_crc_cnt_reg5_tx_mac_partial2_invert_crc_cnt {
      type oc-yang:counter64;
      description
        "Counts the number of transmitted packets with partial CRC type 2.";
    }
    leaf counter_slice12_ifg_mac_pool82_tx_mac_partial2_invert_crc_cnt_reg6_tx_mac_partial2_invert_crc_cnt {
      type oc-yang:counter64;
      description
        "Counts the number of transmitted packets with partial CRC type 2.";
    }
    leaf counter_slice12_ifg_mac_pool82_tx_mac_partial2_invert_crc_cnt_reg7_tx_mac_partial2_invert_crc_cnt {
      type oc-yang:counter64;
      description
        "Counts the number of transmitted packets with partial CRC type 2.";
    }
    leaf counter_slice12_ifg_mac_pool83_tx_mac_partial2_invert_crc_cnt_reg0_tx_mac_partial2_invert_crc_cnt {
      type oc-yang:counter64;
      description
        "Counts the number of transmitted packets with partial CRC type 2.";
    }
    leaf counter_slice12_ifg_mac_pool83_tx_mac_partial2_invert_crc_cnt_reg1_tx_mac_partial2_invert_crc_cnt {
      type oc-yang:counter64;
      description
        "Counts the number of transmitted packets with partial CRC type 2.";
    }
    leaf counter_slice12_ifg_mac_pool83_tx_mac_partial2_invert_crc_cnt_reg2_tx_mac_partial2_invert_crc_cnt {
      type oc-yang:counter64;
      description
        "Counts the number of transmitted packets with partial CRC type 2.";
    }
    leaf counter_slice12_ifg_mac_pool83_tx_mac_partial2_invert_crc_cnt_reg3_tx_mac_partial2_invert_crc_cnt {
      type oc-yang:counter64;
      description
        "Counts the number of transmitted packets with partial CRC type 2.";
    }
    leaf counter_slice12_ifg_mac_pool83_tx_mac_partial2_invert_crc_cnt_reg4_tx_mac_partial2_invert_crc_cnt {
      type oc-yang:counter64;
      description
        "Counts the number of transmitted packets with partial CRC type 2.";
    }
    leaf counter_slice12_ifg_mac_pool83_tx_mac_partial2_invert_crc_cnt_reg5_tx_mac_partial2_invert_crc_cnt {
      type oc-yang:counter64;
      description
        "Counts the number of transmitted packets with partial CRC type 2.";
    }
    leaf counter_slice12_ifg_mac_pool83_tx_mac_partial2_invert_crc_cnt_reg6_tx_mac_partial2_invert_crc_cnt {
      type oc-yang:counter64;
      description
        "Counts the number of transmitted packets with partial CRC type 2.";
    }
    leaf counter_slice12_ifg_mac_pool83_tx_mac_partial2_invert_crc_cnt_reg7_tx_mac_partial2_invert_crc_cnt {
      type oc-yang:counter64;
      description
        "Counts the number of transmitted packets with partial CRC type 2.";
    }
    leaf counter_slice12_ifg_mac_pool84_tx_mac_partial2_invert_crc_cnt_reg0_tx_mac_partial2_invert_crc_cnt {
      type oc-yang:counter64;
      description
        "Counts the number of transmitted packets with partial CRC type 2.";
    }
    leaf counter_slice12_ifg_mac_pool84_tx_mac_partial2_invert_crc_cnt_reg1_tx_mac_partial2_invert_crc_cnt {
      type oc-yang:counter64;
      description
        "Counts the number of transmitted packets with partial CRC type 2.";
    }
    leaf counter_slice12_ifg_mac_pool84_tx_mac_partial2_invert_crc_cnt_reg2_tx_mac_partial2_invert_crc_cnt {
      type oc-yang:counter64;
      description
        "Counts the number of transmitted packets with partial CRC type 2.";
    }
    leaf counter_slice12_ifg_mac_pool84_tx_mac_partial2_invert_crc_cnt_reg3_tx_mac_partial2_invert_crc_cnt {
      type oc-yang:counter64;
      description
        "Counts the number of transmitted packets with partial CRC type 2.";
    }
    leaf counter_slice12_ifg_mac_pool84_tx_mac_partial2_invert_crc_cnt_reg4_tx_mac_partial2_invert_crc_cnt {
      type oc-yang:counter64;
      description
        "Counts the number of transmitted packets with partial CRC type 2.";
    }
    leaf counter_slice12_ifg_mac_pool84_tx_mac_partial2_invert_crc_cnt_reg5_tx_mac_partial2_invert_crc_cnt {
      type oc-yang:counter64;
      description
        "Counts the number of transmitted packets with partial CRC type 2.";
    }
    leaf counter_slice12_ifg_mac_pool84_tx_mac_partial2_invert_crc_cnt_reg6_tx_mac_partial2_invert_crc_cnt {
      type oc-yang:counter64;
      description
        "Counts the number of transmitted packets with partial CRC type 2.";
    }
    leaf counter_slice12_ifg_mac_pool84_tx_mac_partial2_invert_crc_cnt_reg7_tx_mac_partial2_invert_crc_cnt {
      type oc-yang:counter64;
      description
        "Counts the number of transmitted packets with partial CRC type 2.";
    }
    leaf counter_slice12_ifg_mac_pool85_tx_mac_partial2_invert_crc_cnt_reg0_tx_mac_partial2_invert_crc_cnt {
      type oc-yang:counter64;
      description
        "Counts the number of transmitted packets with partial CRC type 2.";
    }
    leaf counter_slice12_ifg_mac_pool85_tx_mac_partial2_invert_crc_cnt_reg1_tx_mac_partial2_invert_crc_cnt {
      type oc-yang:counter64;
      description
        "Counts the number of transmitted packets with partial CRC type 2.";
    }
    leaf counter_slice12_ifg_mac_pool85_tx_mac_partial2_invert_crc_cnt_reg2_tx_mac_partial2_invert_crc_cnt {
      type oc-yang:counter64;
      description
        "Counts the number of transmitted packets with partial CRC type 2.";
    }
    leaf counter_slice12_ifg_mac_pool85_tx_mac_partial2_invert_crc_cnt_reg3_tx_mac_partial2_invert_crc_cnt {
      type oc-yang:counter64;
      description
        "Counts the number of transmitted packets with partial CRC type 2.";
    }
    leaf counter_slice12_ifg_mac_pool85_tx_mac_partial2_invert_crc_cnt_reg4_tx_mac_partial2_invert_crc_cnt {
      type oc-yang:counter64;
      description
        "Counts the number of transmitted packets with partial CRC type 2.";
    }
    leaf counter_slice12_ifg_mac_pool85_tx_mac_partial2_invert_crc_cnt_reg5_tx_mac_partial2_invert_crc_cnt {
      type oc-yang:counter64;
      description
        "Counts the number of transmitted packets with partial CRC type 2.";
    }
    leaf counter_slice12_ifg_mac_pool85_tx_mac_partial2_invert_crc_cnt_reg6_tx_mac_partial2_invert_crc_cnt {
      type oc-yang:counter64;
      description
        "Counts the number of transmitted packets with partial CRC type 2.";
    }
    leaf counter_slice12_ifg_mac_pool85_tx_mac_partial2_invert_crc_cnt_reg7_tx_mac_partial2_invert_crc_cnt {
      type oc-yang:counter64;
      description
        "Counts the number of transmitted packets with partial CRC type 2.";
    }
    leaf counter_slice12_ifg_mac_pool86_tx_mac_partial2_invert_crc_cnt_reg0_tx_mac_partial2_invert_crc_cnt {
      type oc-yang:counter64;
      description
        "Counts the number of transmitted packets with partial CRC type 2.";
    }
    leaf counter_slice12_ifg_mac_pool86_tx_mac_partial2_invert_crc_cnt_reg1_tx_mac_partial2_invert_crc_cnt {
      type oc-yang:counter64;
      description
        "Counts the number of transmitted packets with partial CRC type 2.";
    }
    leaf counter_slice12_ifg_mac_pool86_tx_mac_partial2_invert_crc_cnt_reg2_tx_mac_partial2_invert_crc_cnt {
      type oc-yang:counter64;
      description
        "Counts the number of transmitted packets with partial CRC type 2.";
    }
    leaf counter_slice12_ifg_mac_pool86_tx_mac_partial2_invert_crc_cnt_reg3_tx_mac_partial2_invert_crc_cnt {
      type oc-yang:counter64;
      description
        "Counts the number of transmitted packets with partial CRC type 2.";
    }
    leaf counter_slice12_ifg_mac_pool86_tx_mac_partial2_invert_crc_cnt_reg4_tx_mac_partial2_invert_crc_cnt {
      type oc-yang:counter64;
      description
        "Counts the number of transmitted packets with partial CRC type 2.";
    }
    leaf counter_slice12_ifg_mac_pool86_tx_mac_partial2_invert_crc_cnt_reg5_tx_mac_partial2_invert_crc_cnt {
      type oc-yang:counter64;
      description
        "Counts the number of transmitted packets with partial CRC type 2.";
    }
    leaf counter_slice12_ifg_mac_pool86_tx_mac_partial2_invert_crc_cnt_reg6_tx_mac_partial2_invert_crc_cnt {
      type oc-yang:counter64;
      description
        "Counts the number of transmitted packets with partial CRC type 2.";
    }
    leaf counter_slice12_ifg_mac_pool86_tx_mac_partial2_invert_crc_cnt_reg7_tx_mac_partial2_invert_crc_cnt {
      type oc-yang:counter64;
      description
        "Counts the number of transmitted packets with partial CRC type 2.";
    }
    leaf counter_slice12_ifg_mac_pool87_tx_mac_partial2_invert_crc_cnt_reg0_tx_mac_partial2_invert_crc_cnt {
      type oc-yang:counter64;
      description
        "Counts the number of transmitted packets with partial CRC type 2.";
    }
    leaf counter_slice12_ifg_mac_pool87_tx_mac_partial2_invert_crc_cnt_reg1_tx_mac_partial2_invert_crc_cnt {
      type oc-yang:counter64;
      description
        "Counts the number of transmitted packets with partial CRC type 2.";
    }
    leaf counter_slice12_ifg_mac_pool87_tx_mac_partial2_invert_crc_cnt_reg2_tx_mac_partial2_invert_crc_cnt {
      type oc-yang:counter64;
      description
        "Counts the number of transmitted packets with partial CRC type 2.";
    }
    leaf counter_slice12_ifg_mac_pool87_tx_mac_partial2_invert_crc_cnt_reg3_tx_mac_partial2_invert_crc_cnt {
      type oc-yang:counter64;
      description
        "Counts the number of transmitted packets with partial CRC type 2.";
    }
    leaf counter_slice12_ifg_mac_pool87_tx_mac_partial2_invert_crc_cnt_reg4_tx_mac_partial2_invert_crc_cnt {
      type oc-yang:counter64;
      description
        "Counts the number of transmitted packets with partial CRC type 2.";
    }
    leaf counter_slice12_ifg_mac_pool87_tx_mac_partial2_invert_crc_cnt_reg5_tx_mac_partial2_invert_crc_cnt {
      type oc-yang:counter64;
      description
        "Counts the number of transmitted packets with partial CRC type 2.";
    }
    leaf counter_slice12_ifg_mac_pool87_tx_mac_partial2_invert_crc_cnt_reg6_tx_mac_partial2_invert_crc_cnt {
      type oc-yang:counter64;
      description
        "Counts the number of transmitted packets with partial CRC type 2.";
    }
    leaf counter_slice12_ifg_mac_pool87_tx_mac_partial2_invert_crc_cnt_reg7_tx_mac_partial2_invert_crc_cnt {
      type oc-yang:counter64;
      description
        "Counts the number of transmitted packets with partial CRC type 2.";
    }
    leaf counter_slice13_ifg_mac_pool80_tx_mac_partial2_invert_crc_cnt_reg0_tx_mac_partial2_invert_crc_cnt {
      type oc-yang:counter64;
      description
        "Counts the number of transmitted packets with partial CRC type 2.";
    }
    leaf counter_slice13_ifg_mac_pool80_tx_mac_partial2_invert_crc_cnt_reg1_tx_mac_partial2_invert_crc_cnt {
      type oc-yang:counter64;
      description
        "Counts the number of transmitted packets with partial CRC type 2.";
    }
    leaf counter_slice13_ifg_mac_pool80_tx_mac_partial2_invert_crc_cnt_reg2_tx_mac_partial2_invert_crc_cnt {
      type oc-yang:counter64;
      description
        "Counts the number of transmitted packets with partial CRC type 2.";
    }
    leaf counter_slice13_ifg_mac_pool80_tx_mac_partial2_invert_crc_cnt_reg3_tx_mac_partial2_invert_crc_cnt {
      type oc-yang:counter64;
      description
        "Counts the number of transmitted packets with partial CRC type 2.";
    }
    leaf counter_slice13_ifg_mac_pool80_tx_mac_partial2_invert_crc_cnt_reg4_tx_mac_partial2_invert_crc_cnt {
      type oc-yang:counter64;
      description
        "Counts the number of transmitted packets with partial CRC type 2.";
    }
    leaf counter_slice13_ifg_mac_pool80_tx_mac_partial2_invert_crc_cnt_reg5_tx_mac_partial2_invert_crc_cnt {
      type oc-yang:counter64;
      description
        "Counts the number of transmitted packets with partial CRC type 2.";
    }
    leaf counter_slice13_ifg_mac_pool80_tx_mac_partial2_invert_crc_cnt_reg6_tx_mac_partial2_invert_crc_cnt {
      type oc-yang:counter64;
      description
        "Counts the number of transmitted packets with partial CRC type 2.";
    }
    leaf counter_slice13_ifg_mac_pool80_tx_mac_partial2_invert_crc_cnt_reg7_tx_mac_partial2_invert_crc_cnt {
      type oc-yang:counter64;
      description
        "Counts the number of transmitted packets with partial CRC type 2.";
    }
    leaf counter_slice13_ifg_mac_pool81_tx_mac_partial2_invert_crc_cnt_reg0_tx_mac_partial2_invert_crc_cnt {
      type oc-yang:counter64;
      description
        "Counts the number of transmitted packets with partial CRC type 2.";
    }
    leaf counter_slice13_ifg_mac_pool81_tx_mac_partial2_invert_crc_cnt_reg1_tx_mac_partial2_invert_crc_cnt {
      type oc-yang:counter64;
      description
        "Counts the number of transmitted packets with partial CRC type 2.";
    }
    leaf counter_slice13_ifg_mac_pool81_tx_mac_partial2_invert_crc_cnt_reg2_tx_mac_partial2_invert_crc_cnt {
      type oc-yang:counter64;
      description
        "Counts the number of transmitted packets with partial CRC type 2.";
    }
    leaf counter_slice13_ifg_mac_pool81_tx_mac_partial2_invert_crc_cnt_reg3_tx_mac_partial2_invert_crc_cnt {
      type oc-yang:counter64;
      description
        "Counts the number of transmitted packets with partial CRC type 2.";
    }
    leaf counter_slice13_ifg_mac_pool81_tx_mac_partial2_invert_crc_cnt_reg4_tx_mac_partial2_invert_crc_cnt {
      type oc-yang:counter64;
      description
        "Counts the number of transmitted packets with partial CRC type 2.";
    }
    leaf counter_slice13_ifg_mac_pool81_tx_mac_partial2_invert_crc_cnt_reg5_tx_mac_partial2_invert_crc_cnt {
      type oc-yang:counter64;
      description
        "Counts the number of transmitted packets with partial CRC type 2.";
    }
    leaf counter_slice13_ifg_mac_pool81_tx_mac_partial2_invert_crc_cnt_reg6_tx_mac_partial2_invert_crc_cnt {
      type oc-yang:counter64;
      description
        "Counts the number of transmitted packets with partial CRC type 2.";
    }
    leaf counter_slice13_ifg_mac_pool81_tx_mac_partial2_invert_crc_cnt_reg7_tx_mac_partial2_invert_crc_cnt {
      type oc-yang:counter64;
      description
        "Counts the number of transmitted packets with partial CRC type 2.";
    }
    leaf counter_slice13_ifg_mac_pool82_tx_mac_partial2_invert_crc_cnt_reg0_tx_mac_partial2_invert_crc_cnt {
      type oc-yang:counter64;
      description
        "Counts the number of transmitted packets with partial CRC type 2.";
    }
    leaf counter_slice13_ifg_mac_pool82_tx_mac_partial2_invert_crc_cnt_reg1_tx_mac_partial2_invert_crc_cnt {
      type oc-yang:counter64;
      description
        "Counts the number of transmitted packets with partial CRC type 2.";
    }
    leaf counter_slice13_ifg_mac_pool82_tx_mac_partial2_invert_crc_cnt_reg2_tx_mac_partial2_invert_crc_cnt {
      type oc-yang:counter64;
      description
        "Counts the number of transmitted packets with partial CRC type 2.";
    }
    leaf counter_slice13_ifg_mac_pool82_tx_mac_partial2_invert_crc_cnt_reg3_tx_mac_partial2_invert_crc_cnt {
      type oc-yang:counter64;
      description
        "Counts the number of transmitted packets with partial CRC type 2.";
    }
    leaf counter_slice13_ifg_mac_pool82_tx_mac_partial2_invert_crc_cnt_reg4_tx_mac_partial2_invert_crc_cnt {
      type oc-yang:counter64;
      description
        "Counts the number of transmitted packets with partial CRC type 2.";
    }
    leaf counter_slice13_ifg_mac_pool82_tx_mac_partial2_invert_crc_cnt_reg5_tx_mac_partial2_invert_crc_cnt {
      type oc-yang:counter64;
      description
        "Counts the number of transmitted packets with partial CRC type 2.";
    }
    leaf counter_slice13_ifg_mac_pool82_tx_mac_partial2_invert_crc_cnt_reg6_tx_mac_partial2_invert_crc_cnt {
      type oc-yang:counter64;
      description
        "Counts the number of transmitted packets with partial CRC type 2.";
    }
    leaf counter_slice13_ifg_mac_pool82_tx_mac_partial2_invert_crc_cnt_reg7_tx_mac_partial2_invert_crc_cnt {
      type oc-yang:counter64;
      description
        "Counts the number of transmitted packets with partial CRC type 2.";
    }
    leaf counter_slice13_ifg_mac_pool83_tx_mac_partial2_invert_crc_cnt_reg0_tx_mac_partial2_invert_crc_cnt {
      type oc-yang:counter64;
      description
        "Counts the number of transmitted packets with partial CRC type 2.";
    }
    leaf counter_slice13_ifg_mac_pool83_tx_mac_partial2_invert_crc_cnt_reg1_tx_mac_partial2_invert_crc_cnt {
      type oc-yang:counter64;
      description
        "Counts the number of transmitted packets with partial CRC type 2.";
    }
    leaf counter_slice13_ifg_mac_pool83_tx_mac_partial2_invert_crc_cnt_reg2_tx_mac_partial2_invert_crc_cnt {
      type oc-yang:counter64;
      description
        "Counts the number of transmitted packets with partial CRC type 2.";
    }
    leaf counter_slice13_ifg_mac_pool83_tx_mac_partial2_invert_crc_cnt_reg3_tx_mac_partial2_invert_crc_cnt {
      type oc-yang:counter64;
      description
        "Counts the number of transmitted packets with partial CRC type 2.";
    }
    leaf counter_slice13_ifg_mac_pool83_tx_mac_partial2_invert_crc_cnt_reg4_tx_mac_partial2_invert_crc_cnt {
      type oc-yang:counter64;
      description
        "Counts the number of transmitted packets with partial CRC type 2.";
    }
    leaf counter_slice13_ifg_mac_pool83_tx_mac_partial2_invert_crc_cnt_reg5_tx_mac_partial2_invert_crc_cnt {
      type oc-yang:counter64;
      description
        "Counts the number of transmitted packets with partial CRC type 2.";
    }
    leaf counter_slice13_ifg_mac_pool83_tx_mac_partial2_invert_crc_cnt_reg6_tx_mac_partial2_invert_crc_cnt {
      type oc-yang:counter64;
      description
        "Counts the number of transmitted packets with partial CRC type 2.";
    }
    leaf counter_slice13_ifg_mac_pool83_tx_mac_partial2_invert_crc_cnt_reg7_tx_mac_partial2_invert_crc_cnt {
      type oc-yang:counter64;
      description
        "Counts the number of transmitted packets with partial CRC type 2.";
    }
    leaf counter_slice13_ifg_mac_pool84_tx_mac_partial2_invert_crc_cnt_reg0_tx_mac_partial2_invert_crc_cnt {
      type oc-yang:counter64;
      description
        "Counts the number of transmitted packets with partial CRC type 2.";
    }
    leaf counter_slice13_ifg_mac_pool84_tx_mac_partial2_invert_crc_cnt_reg1_tx_mac_partial2_invert_crc_cnt {
      type oc-yang:counter64;
      description
        "Counts the number of transmitted packets with partial CRC type 2.";
    }
    leaf counter_slice13_ifg_mac_pool84_tx_mac_partial2_invert_crc_cnt_reg2_tx_mac_partial2_invert_crc_cnt {
      type oc-yang:counter64;
      description
        "Counts the number of transmitted packets with partial CRC type 2.";
    }
    leaf counter_slice13_ifg_mac_pool84_tx_mac_partial2_invert_crc_cnt_reg3_tx_mac_partial2_invert_crc_cnt {
      type oc-yang:counter64;
      description
        "Counts the number of transmitted packets with partial CRC type 2.";
    }
    leaf counter_slice13_ifg_mac_pool84_tx_mac_partial2_invert_crc_cnt_reg4_tx_mac_partial2_invert_crc_cnt {
      type oc-yang:counter64;
      description
        "Counts the number of transmitted packets with partial CRC type 2.";
    }
    leaf counter_slice13_ifg_mac_pool84_tx_mac_partial2_invert_crc_cnt_reg5_tx_mac_partial2_invert_crc_cnt {
      type oc-yang:counter64;
      description
        "Counts the number of transmitted packets with partial CRC type 2.";
    }
    leaf counter_slice13_ifg_mac_pool84_tx_mac_partial2_invert_crc_cnt_reg6_tx_mac_partial2_invert_crc_cnt {
      type oc-yang:counter64;
      description
        "Counts the number of transmitted packets with partial CRC type 2.";
    }
    leaf counter_slice13_ifg_mac_pool84_tx_mac_partial2_invert_crc_cnt_reg7_tx_mac_partial2_invert_crc_cnt {
      type oc-yang:counter64;
      description
        "Counts the number of transmitted packets with partial CRC type 2.";
    }
    leaf counter_slice13_ifg_mac_pool85_tx_mac_partial2_invert_crc_cnt_reg0_tx_mac_partial2_invert_crc_cnt {
      type oc-yang:counter64;
      description
        "Counts the number of transmitted packets with partial CRC type 2.";
    }
    leaf counter_slice13_ifg_mac_pool85_tx_mac_partial2_invert_crc_cnt_reg1_tx_mac_partial2_invert_crc_cnt {
      type oc-yang:counter64;
      description
        "Counts the number of transmitted packets with partial CRC type 2.";
    }
    leaf counter_slice13_ifg_mac_pool85_tx_mac_partial2_invert_crc_cnt_reg2_tx_mac_partial2_invert_crc_cnt {
      type oc-yang:counter64;
      description
        "Counts the number of transmitted packets with partial CRC type 2.";
    }
    leaf counter_slice13_ifg_mac_pool85_tx_mac_partial2_invert_crc_cnt_reg3_tx_mac_partial2_invert_crc_cnt {
      type oc-yang:counter64;
      description
        "Counts the number of transmitted packets with partial CRC type 2.";
    }
    leaf counter_slice13_ifg_mac_pool85_tx_mac_partial2_invert_crc_cnt_reg4_tx_mac_partial2_invert_crc_cnt {
      type oc-yang:counter64;
      description
        "Counts the number of transmitted packets with partial CRC type 2.";
    }
    leaf counter_slice13_ifg_mac_pool85_tx_mac_partial2_invert_crc_cnt_reg5_tx_mac_partial2_invert_crc_cnt {
      type oc-yang:counter64;
      description
        "Counts the number of transmitted packets with partial CRC type 2.";
    }
    leaf counter_slice13_ifg_mac_pool85_tx_mac_partial2_invert_crc_cnt_reg6_tx_mac_partial2_invert_crc_cnt {
      type oc-yang:counter64;
      description
        "Counts the number of transmitted packets with partial CRC type 2.";
    }
    leaf counter_slice13_ifg_mac_pool85_tx_mac_partial2_invert_crc_cnt_reg7_tx_mac_partial2_invert_crc_cnt {
      type oc-yang:counter64;
      description
        "Counts the number of transmitted packets with partial CRC type 2.";
    }
    leaf counter_slice13_ifg_mac_pool86_tx_mac_partial2_invert_crc_cnt_reg0_tx_mac_partial2_invert_crc_cnt {
      type oc-yang:counter64;
      description
        "Counts the number of transmitted packets with partial CRC type 2.";
    }
    leaf counter_slice13_ifg_mac_pool86_tx_mac_partial2_invert_crc_cnt_reg1_tx_mac_partial2_invert_crc_cnt {
      type oc-yang:counter64;
      description
        "Counts the number of transmitted packets with partial CRC type 2.";
    }
    leaf counter_slice13_ifg_mac_pool86_tx_mac_partial2_invert_crc_cnt_reg2_tx_mac_partial2_invert_crc_cnt {
      type oc-yang:counter64;
      description
        "Counts the number of transmitted packets with partial CRC type 2.";
    }
    leaf counter_slice13_ifg_mac_pool86_tx_mac_partial2_invert_crc_cnt_reg3_tx_mac_partial2_invert_crc_cnt {
      type oc-yang:counter64;
      description
        "Counts the number of transmitted packets with partial CRC type 2.";
    }
    leaf counter_slice13_ifg_mac_pool86_tx_mac_partial2_invert_crc_cnt_reg4_tx_mac_partial2_invert_crc_cnt {
      type oc-yang:counter64;
      description
        "Counts the number of transmitted packets with partial CRC type 2.";
    }
    leaf counter_slice13_ifg_mac_pool86_tx_mac_partial2_invert_crc_cnt_reg5_tx_mac_partial2_invert_crc_cnt {
      type oc-yang:counter64;
      description
        "Counts the number of transmitted packets with partial CRC type 2.";
    }
    leaf counter_slice13_ifg_mac_pool86_tx_mac_partial2_invert_crc_cnt_reg6_tx_mac_partial2_invert_crc_cnt {
      type oc-yang:counter64;
      description
        "Counts the number of transmitted packets with partial CRC type 2.";
    }
    leaf counter_slice13_ifg_mac_pool86_tx_mac_partial2_invert_crc_cnt_reg7_tx_mac_partial2_invert_crc_cnt {
      type oc-yang:counter64;
      description
        "Counts the number of transmitted packets with partial CRC type 2.";
    }
    leaf counter_slice13_ifg_mac_pool87_tx_mac_partial2_invert_crc_cnt_reg0_tx_mac_partial2_invert_crc_cnt {
      type oc-yang:counter64;
      description
        "Counts the number of transmitted packets with partial CRC type 2.";
    }
    leaf counter_slice13_ifg_mac_pool87_tx_mac_partial2_invert_crc_cnt_reg1_tx_mac_partial2_invert_crc_cnt {
      type oc-yang:counter64;
      description
        "Counts the number of transmitted packets with partial CRC type 2.";
    }
    leaf counter_slice13_ifg_mac_pool87_tx_mac_partial2_invert_crc_cnt_reg2_tx_mac_partial2_invert_crc_cnt {
      type oc-yang:counter64;
      description
        "Counts the number of transmitted packets with partial CRC type 2.";
    }
    leaf counter_slice13_ifg_mac_pool87_tx_mac_partial2_invert_crc_cnt_reg3_tx_mac_partial2_invert_crc_cnt {
      type oc-yang:counter64;
      description
        "Counts the number of transmitted packets with partial CRC type 2.";
    }
    leaf counter_slice13_ifg_mac_pool87_tx_mac_partial2_invert_crc_cnt_reg4_tx_mac_partial2_invert_crc_cnt {
      type oc-yang:counter64;
      description
        "Counts the number of transmitted packets with partial CRC type 2.";
    }
    leaf counter_slice13_ifg_mac_pool87_tx_mac_partial2_invert_crc_cnt_reg5_tx_mac_partial2_invert_crc_cnt {
      type oc-yang:counter64;
      description
        "Counts the number of transmitted packets with partial CRC type 2.";
    }
    leaf counter_slice13_ifg_mac_pool87_tx_mac_partial2_invert_crc_cnt_reg6_tx_mac_partial2_invert_crc_cnt {
      type oc-yang:counter64;
      description
        "Counts the number of transmitted packets with partial CRC type 2.";
    }
    leaf counter_slice13_ifg_mac_pool87_tx_mac_partial2_invert_crc_cnt_reg7_tx_mac_partial2_invert_crc_cnt {
      type oc-yang:counter64;
      description
        "Counts the number of transmitted packets with partial CRC type 2.";
    }
    leaf counter_slice14_ifg_mac_pool80_tx_mac_partial2_invert_crc_cnt_reg0_tx_mac_partial2_invert_crc_cnt {
      type oc-yang:counter64;
      description
        "Counts the number of transmitted packets with partial CRC type 2.";
    }
    leaf counter_slice14_ifg_mac_pool80_tx_mac_partial2_invert_crc_cnt_reg1_tx_mac_partial2_invert_crc_cnt {
      type oc-yang:counter64;
      description
        "Counts the number of transmitted packets with partial CRC type 2.";
    }
    leaf counter_slice14_ifg_mac_pool80_tx_mac_partial2_invert_crc_cnt_reg2_tx_mac_partial2_invert_crc_cnt {
      type oc-yang:counter64;
      description
        "Counts the number of transmitted packets with partial CRC type 2.";
    }
    leaf counter_slice14_ifg_mac_pool80_tx_mac_partial2_invert_crc_cnt_reg3_tx_mac_partial2_invert_crc_cnt {
      type oc-yang:counter64;
      description
        "Counts the number of transmitted packets with partial CRC type 2.";
    }
    leaf counter_slice14_ifg_mac_pool80_tx_mac_partial2_invert_crc_cnt_reg4_tx_mac_partial2_invert_crc_cnt {
      type oc-yang:counter64;
      description
        "Counts the number of transmitted packets with partial CRC type 2.";
    }
    leaf counter_slice14_ifg_mac_pool80_tx_mac_partial2_invert_crc_cnt_reg5_tx_mac_partial2_invert_crc_cnt {
      type oc-yang:counter64;
      description
        "Counts the number of transmitted packets with partial CRC type 2.";
    }
    leaf counter_slice14_ifg_mac_pool80_tx_mac_partial2_invert_crc_cnt_reg6_tx_mac_partial2_invert_crc_cnt {
      type oc-yang:counter64;
      description
        "Counts the number of transmitted packets with partial CRC type 2.";
    }
    leaf counter_slice14_ifg_mac_pool80_tx_mac_partial2_invert_crc_cnt_reg7_tx_mac_partial2_invert_crc_cnt {
      type oc-yang:counter64;
      description
        "Counts the number of transmitted packets with partial CRC type 2.";
    }
    leaf counter_slice14_ifg_mac_pool81_tx_mac_partial2_invert_crc_cnt_reg0_tx_mac_partial2_invert_crc_cnt {
      type oc-yang:counter64;
      description
        "Counts the number of transmitted packets with partial CRC type 2.";
    }
    leaf counter_slice14_ifg_mac_pool81_tx_mac_partial2_invert_crc_cnt_reg1_tx_mac_partial2_invert_crc_cnt {
      type oc-yang:counter64;
      description
        "Counts the number of transmitted packets with partial CRC type 2.";
    }
    leaf counter_slice14_ifg_mac_pool81_tx_mac_partial2_invert_crc_cnt_reg2_tx_mac_partial2_invert_crc_cnt {
      type oc-yang:counter64;
      description
        "Counts the number of transmitted packets with partial CRC type 2.";
    }
    leaf counter_slice14_ifg_mac_pool81_tx_mac_partial2_invert_crc_cnt_reg3_tx_mac_partial2_invert_crc_cnt {
      type oc-yang:counter64;
      description
        "Counts the number of transmitted packets with partial CRC type 2.";
    }
    leaf counter_slice14_ifg_mac_pool81_tx_mac_partial2_invert_crc_cnt_reg4_tx_mac_partial2_invert_crc_cnt {
      type oc-yang:counter64;
      description
        "Counts the number of transmitted packets with partial CRC type 2.";
    }
    leaf counter_slice14_ifg_mac_pool81_tx_mac_partial2_invert_crc_cnt_reg5_tx_mac_partial2_invert_crc_cnt {
      type oc-yang:counter64;
      description
        "Counts the number of transmitted packets with partial CRC type 2.";
    }
    leaf counter_slice14_ifg_mac_pool81_tx_mac_partial2_invert_crc_cnt_reg6_tx_mac_partial2_invert_crc_cnt {
      type oc-yang:counter64;
      description
        "Counts the number of transmitted packets with partial CRC type 2.";
    }
    leaf counter_slice14_ifg_mac_pool81_tx_mac_partial2_invert_crc_cnt_reg7_tx_mac_partial2_invert_crc_cnt {
      type oc-yang:counter64;
      description
        "Counts the number of transmitted packets with partial CRC type 2.";
    }
    leaf counter_slice14_ifg_mac_pool82_tx_mac_partial2_invert_crc_cnt_reg0_tx_mac_partial2_invert_crc_cnt {
      type oc-yang:counter64;
      description
        "Counts the number of transmitted packets with partial CRC type 2.";
    }
    leaf counter_slice14_ifg_mac_pool82_tx_mac_partial2_invert_crc_cnt_reg1_tx_mac_partial2_invert_crc_cnt {
      type oc-yang:counter64;
      description
        "Counts the number of transmitted packets with partial CRC type 2.";
    }
    leaf counter_slice14_ifg_mac_pool82_tx_mac_partial2_invert_crc_cnt_reg2_tx_mac_partial2_invert_crc_cnt {
      type oc-yang:counter64;
      description
        "Counts the number of transmitted packets with partial CRC type 2.";
    }
    leaf counter_slice14_ifg_mac_pool82_tx_mac_partial2_invert_crc_cnt_reg3_tx_mac_partial2_invert_crc_cnt {
      type oc-yang:counter64;
      description
        "Counts the number of transmitted packets with partial CRC type 2.";
    }
    leaf counter_slice14_ifg_mac_pool82_tx_mac_partial2_invert_crc_cnt_reg4_tx_mac_partial2_invert_crc_cnt {
      type oc-yang:counter64;
      description
        "Counts the number of transmitted packets with partial CRC type 2.";
    }
    leaf counter_slice14_ifg_mac_pool82_tx_mac_partial2_invert_crc_cnt_reg5_tx_mac_partial2_invert_crc_cnt {
      type oc-yang:counter64;
      description
        "Counts the number of transmitted packets with partial CRC type 2.";
    }
    leaf counter_slice14_ifg_mac_pool82_tx_mac_partial2_invert_crc_cnt_reg6_tx_mac_partial2_invert_crc_cnt {
      type oc-yang:counter64;
      description
        "Counts the number of transmitted packets with partial CRC type 2.";
    }
    leaf counter_slice14_ifg_mac_pool82_tx_mac_partial2_invert_crc_cnt_reg7_tx_mac_partial2_invert_crc_cnt {
      type oc-yang:counter64;
      description
        "Counts the number of transmitted packets with partial CRC type 2.";
    }
    leaf counter_slice14_ifg_mac_pool83_tx_mac_partial2_invert_crc_cnt_reg0_tx_mac_partial2_invert_crc_cnt {
      type oc-yang:counter64;
      description
        "Counts the number of transmitted packets with partial CRC type 2.";
    }
    leaf counter_slice14_ifg_mac_pool83_tx_mac_partial2_invert_crc_cnt_reg1_tx_mac_partial2_invert_crc_cnt {
      type oc-yang:counter64;
      description
        "Counts the number of transmitted packets with partial CRC type 2.";
    }
    leaf counter_slice14_ifg_mac_pool83_tx_mac_partial2_invert_crc_cnt_reg2_tx_mac_partial2_invert_crc_cnt {
      type oc-yang:counter64;
      description
        "Counts the number of transmitted packets with partial CRC type 2.";
    }
    leaf counter_slice14_ifg_mac_pool83_tx_mac_partial2_invert_crc_cnt_reg3_tx_mac_partial2_invert_crc_cnt {
      type oc-yang:counter64;
      description
        "Counts the number of transmitted packets with partial CRC type 2.";
    }
    leaf counter_slice14_ifg_mac_pool83_tx_mac_partial2_invert_crc_cnt_reg4_tx_mac_partial2_invert_crc_cnt {
      type oc-yang:counter64;
      description
        "Counts the number of transmitted packets with partial CRC type 2.";
    }
    leaf counter_slice14_ifg_mac_pool83_tx_mac_partial2_invert_crc_cnt_reg5_tx_mac_partial2_invert_crc_cnt {
      type oc-yang:counter64;
      description
        "Counts the number of transmitted packets with partial CRC type 2.";
    }
    leaf counter_slice14_ifg_mac_pool83_tx_mac_partial2_invert_crc_cnt_reg6_tx_mac_partial2_invert_crc_cnt {
      type oc-yang:counter64;
      description
        "Counts the number of transmitted packets with partial CRC type 2.";
    }
    leaf counter_slice14_ifg_mac_pool83_tx_mac_partial2_invert_crc_cnt_reg7_tx_mac_partial2_invert_crc_cnt {
      type oc-yang:counter64;
      description
        "Counts the number of transmitted packets with partial CRC type 2.";
    }
    leaf counter_slice14_ifg_mac_pool84_tx_mac_partial2_invert_crc_cnt_reg0_tx_mac_partial2_invert_crc_cnt {
      type oc-yang:counter64;
      description
        "Counts the number of transmitted packets with partial CRC type 2.";
    }
    leaf counter_slice14_ifg_mac_pool84_tx_mac_partial2_invert_crc_cnt_reg1_tx_mac_partial2_invert_crc_cnt {
      type oc-yang:counter64;
      description
        "Counts the number of transmitted packets with partial CRC type 2.";
    }
    leaf counter_slice14_ifg_mac_pool84_tx_mac_partial2_invert_crc_cnt_reg2_tx_mac_partial2_invert_crc_cnt {
      type oc-yang:counter64;
      description
        "Counts the number of transmitted packets with partial CRC type 2.";
    }
    leaf counter_slice14_ifg_mac_pool84_tx_mac_partial2_invert_crc_cnt_reg3_tx_mac_partial2_invert_crc_cnt {
      type oc-yang:counter64;
      description
        "Counts the number of transmitted packets with partial CRC type 2.";
    }
    leaf counter_slice14_ifg_mac_pool84_tx_mac_partial2_invert_crc_cnt_reg4_tx_mac_partial2_invert_crc_cnt {
      type oc-yang:counter64;
      description
        "Counts the number of transmitted packets with partial CRC type 2.";
    }
    leaf counter_slice14_ifg_mac_pool84_tx_mac_partial2_invert_crc_cnt_reg5_tx_mac_partial2_invert_crc_cnt {
      type oc-yang:counter64;
      description
        "Counts the number of transmitted packets with partial CRC type 2.";
    }
    leaf counter_slice14_ifg_mac_pool84_tx_mac_partial2_invert_crc_cnt_reg6_tx_mac_partial2_invert_crc_cnt {
      type oc-yang:counter64;
      description
        "Counts the number of transmitted packets with partial CRC type 2.";
    }
    leaf counter_slice14_ifg_mac_pool84_tx_mac_partial2_invert_crc_cnt_reg7_tx_mac_partial2_invert_crc_cnt {
      type oc-yang:counter64;
      description
        "Counts the number of transmitted packets with partial CRC type 2.";
    }
    leaf counter_slice14_ifg_mac_pool85_tx_mac_partial2_invert_crc_cnt_reg0_tx_mac_partial2_invert_crc_cnt {
      type oc-yang:counter64;
      description
        "Counts the number of transmitted packets with partial CRC type 2.";
    }
    leaf counter_slice14_ifg_mac_pool85_tx_mac_partial2_invert_crc_cnt_reg1_tx_mac_partial2_invert_crc_cnt {
      type oc-yang:counter64;
      description
        "Counts the number of transmitted packets with partial CRC type 2.";
    }
    leaf counter_slice14_ifg_mac_pool85_tx_mac_partial2_invert_crc_cnt_reg2_tx_mac_partial2_invert_crc_cnt {
      type oc-yang:counter64;
      description
        "Counts the number of transmitted packets with partial CRC type 2.";
    }
    leaf counter_slice14_ifg_mac_pool85_tx_mac_partial2_invert_crc_cnt_reg3_tx_mac_partial2_invert_crc_cnt {
      type oc-yang:counter64;
      description
        "Counts the number of transmitted packets with partial CRC type 2.";
    }
    leaf counter_slice14_ifg_mac_pool85_tx_mac_partial2_invert_crc_cnt_reg4_tx_mac_partial2_invert_crc_cnt {
      type oc-yang:counter64;
      description
        "Counts the number of transmitted packets with partial CRC type 2.";
    }
    leaf counter_slice14_ifg_mac_pool85_tx_mac_partial2_invert_crc_cnt_reg5_tx_mac_partial2_invert_crc_cnt {
      type oc-yang:counter64;
      description
        "Counts the number of transmitted packets with partial CRC type 2.";
    }
    leaf counter_slice14_ifg_mac_pool85_tx_mac_partial2_invert_crc_cnt_reg6_tx_mac_partial2_invert_crc_cnt {
      type oc-yang:counter64;
      description
        "Counts the number of transmitted packets with partial CRC type 2.";
    }
    leaf counter_slice14_ifg_mac_pool85_tx_mac_partial2_invert_crc_cnt_reg7_tx_mac_partial2_invert_crc_cnt {
      type oc-yang:counter64;
      description
        "Counts the number of transmitted packets with partial CRC type 2.";
    }
    leaf counter_slice14_ifg_mac_pool86_tx_mac_partial2_invert_crc_cnt_reg0_tx_mac_partial2_invert_crc_cnt {
      type oc-yang:counter64;
      description
        "Counts the number of transmitted packets with partial CRC type 2.";
    }
    leaf counter_slice14_ifg_mac_pool86_tx_mac_partial2_invert_crc_cnt_reg1_tx_mac_partial2_invert_crc_cnt {
      type oc-yang:counter64;
      description
        "Counts the number of transmitted packets with partial CRC type 2.";
    }
    leaf counter_slice14_ifg_mac_pool86_tx_mac_partial2_invert_crc_cnt_reg2_tx_mac_partial2_invert_crc_cnt {
      type oc-yang:counter64;
      description
        "Counts the number of transmitted packets with partial CRC type 2.";
    }
    leaf counter_slice14_ifg_mac_pool86_tx_mac_partial2_invert_crc_cnt_reg3_tx_mac_partial2_invert_crc_cnt {
      type oc-yang:counter64;
      description
        "Counts the number of transmitted packets with partial CRC type 2.";
    }
    leaf counter_slice14_ifg_mac_pool86_tx_mac_partial2_invert_crc_cnt_reg4_tx_mac_partial2_invert_crc_cnt {
      type oc-yang:counter64;
      description
        "Counts the number of transmitted packets with partial CRC type 2.";
    }
    leaf counter_slice14_ifg_mac_pool86_tx_mac_partial2_invert_crc_cnt_reg5_tx_mac_partial2_invert_crc_cnt {
      type oc-yang:counter64;
      description
        "Counts the number of transmitted packets with partial CRC type 2.";
    }
    leaf counter_slice14_ifg_mac_pool86_tx_mac_partial2_invert_crc_cnt_reg6_tx_mac_partial2_invert_crc_cnt {
      type oc-yang:counter64;
      description
        "Counts the number of transmitted packets with partial CRC type 2.";
    }
    leaf counter_slice14_ifg_mac_pool86_tx_mac_partial2_invert_crc_cnt_reg7_tx_mac_partial2_invert_crc_cnt {
      type oc-yang:counter64;
      description
        "Counts the number of transmitted packets with partial CRC type 2.";
    }
    leaf counter_slice14_ifg_mac_pool87_tx_mac_partial2_invert_crc_cnt_reg0_tx_mac_partial2_invert_crc_cnt {
      type oc-yang:counter64;
      description
        "Counts the number of transmitted packets with partial CRC type 2.";
    }
    leaf counter_slice14_ifg_mac_pool87_tx_mac_partial2_invert_crc_cnt_reg1_tx_mac_partial2_invert_crc_cnt {
      type oc-yang:counter64;
      description
        "Counts the number of transmitted packets with partial CRC type 2.";
    }
    leaf counter_slice14_ifg_mac_pool87_tx_mac_partial2_invert_crc_cnt_reg2_tx_mac_partial2_invert_crc_cnt {
      type oc-yang:counter64;
      description
        "Counts the number of transmitted packets with partial CRC type 2.";
    }
    leaf counter_slice14_ifg_mac_pool87_tx_mac_partial2_invert_crc_cnt_reg3_tx_mac_partial2_invert_crc_cnt {
      type oc-yang:counter64;
      description
        "Counts the number of transmitted packets with partial CRC type 2.";
    }
    leaf counter_slice14_ifg_mac_pool87_tx_mac_partial2_invert_crc_cnt_reg4_tx_mac_partial2_invert_crc_cnt {
      type oc-yang:counter64;
      description
        "Counts the number of transmitted packets with partial CRC type 2.";
    }
    leaf counter_slice14_ifg_mac_pool87_tx_mac_partial2_invert_crc_cnt_reg5_tx_mac_partial2_invert_crc_cnt {
      type oc-yang:counter64;
      description
        "Counts the number of transmitted packets with partial CRC type 2.";
    }
    leaf counter_slice14_ifg_mac_pool87_tx_mac_partial2_invert_crc_cnt_reg6_tx_mac_partial2_invert_crc_cnt {
      type oc-yang:counter64;
      description
        "Counts the number of transmitted packets with partial CRC type 2.";
    }
    leaf counter_slice14_ifg_mac_pool87_tx_mac_partial2_invert_crc_cnt_reg7_tx_mac_partial2_invert_crc_cnt {
      type oc-yang:counter64;
      description
        "Counts the number of transmitted packets with partial CRC type 2.";
    }
    leaf counter_slice15_ifg_mac_pool80_tx_mac_partial2_invert_crc_cnt_reg0_tx_mac_partial2_invert_crc_cnt {
      type oc-yang:counter64;
      description
        "Counts the number of transmitted packets with partial CRC type 2.";
    }
    leaf counter_slice15_ifg_mac_pool80_tx_mac_partial2_invert_crc_cnt_reg1_tx_mac_partial2_invert_crc_cnt {
      type oc-yang:counter64;
      description
        "Counts the number of transmitted packets with partial CRC type 2.";
    }
    leaf counter_slice15_ifg_mac_pool80_tx_mac_partial2_invert_crc_cnt_reg2_tx_mac_partial2_invert_crc_cnt {
      type oc-yang:counter64;
      description
        "Counts the number of transmitted packets with partial CRC type 2.";
    }
    leaf counter_slice15_ifg_mac_pool80_tx_mac_partial2_invert_crc_cnt_reg3_tx_mac_partial2_invert_crc_cnt {
      type oc-yang:counter64;
      description
        "Counts the number of transmitted packets with partial CRC type 2.";
    }
    leaf counter_slice15_ifg_mac_pool80_tx_mac_partial2_invert_crc_cnt_reg4_tx_mac_partial2_invert_crc_cnt {
      type oc-yang:counter64;
      description
        "Counts the number of transmitted packets with partial CRC type 2.";
    }
    leaf counter_slice15_ifg_mac_pool80_tx_mac_partial2_invert_crc_cnt_reg5_tx_mac_partial2_invert_crc_cnt {
      type oc-yang:counter64;
      description
        "Counts the number of transmitted packets with partial CRC type 2.";
    }
    leaf counter_slice15_ifg_mac_pool80_tx_mac_partial2_invert_crc_cnt_reg6_tx_mac_partial2_invert_crc_cnt {
      type oc-yang:counter64;
      description
        "Counts the number of transmitted packets with partial CRC type 2.";
    }
    leaf counter_slice15_ifg_mac_pool80_tx_mac_partial2_invert_crc_cnt_reg7_tx_mac_partial2_invert_crc_cnt {
      type oc-yang:counter64;
      description
        "Counts the number of transmitted packets with partial CRC type 2.";
    }
    leaf counter_slice15_ifg_mac_pool81_tx_mac_partial2_invert_crc_cnt_reg0_tx_mac_partial2_invert_crc_cnt {
      type oc-yang:counter64;
      description
        "Counts the number of transmitted packets with partial CRC type 2.";
    }
    leaf counter_slice15_ifg_mac_pool81_tx_mac_partial2_invert_crc_cnt_reg1_tx_mac_partial2_invert_crc_cnt {
      type oc-yang:counter64;
      description
        "Counts the number of transmitted packets with partial CRC type 2.";
    }
    leaf counter_slice15_ifg_mac_pool81_tx_mac_partial2_invert_crc_cnt_reg2_tx_mac_partial2_invert_crc_cnt {
      type oc-yang:counter64;
      description
        "Counts the number of transmitted packets with partial CRC type 2.";
    }
    leaf counter_slice15_ifg_mac_pool81_tx_mac_partial2_invert_crc_cnt_reg3_tx_mac_partial2_invert_crc_cnt {
      type oc-yang:counter64;
      description
        "Counts the number of transmitted packets with partial CRC type 2.";
    }
    leaf counter_slice15_ifg_mac_pool81_tx_mac_partial2_invert_crc_cnt_reg4_tx_mac_partial2_invert_crc_cnt {
      type oc-yang:counter64;
      description
        "Counts the number of transmitted packets with partial CRC type 2.";
    }
    leaf counter_slice15_ifg_mac_pool81_tx_mac_partial2_invert_crc_cnt_reg5_tx_mac_partial2_invert_crc_cnt {
      type oc-yang:counter64;
      description
        "Counts the number of transmitted packets with partial CRC type 2.";
    }
    leaf counter_slice15_ifg_mac_pool81_tx_mac_partial2_invert_crc_cnt_reg6_tx_mac_partial2_invert_crc_cnt {
      type oc-yang:counter64;
      description
        "Counts the number of transmitted packets with partial CRC type 2.";
    }
    leaf counter_slice15_ifg_mac_pool81_tx_mac_partial2_invert_crc_cnt_reg7_tx_mac_partial2_invert_crc_cnt {
      type oc-yang:counter64;
      description
        "Counts the number of transmitted packets with partial CRC type 2.";
    }
    leaf counter_slice15_ifg_mac_pool82_tx_mac_partial2_invert_crc_cnt_reg0_tx_mac_partial2_invert_crc_cnt {
      type oc-yang:counter64;
      description
        "Counts the number of transmitted packets with partial CRC type 2.";
    }
    leaf counter_slice15_ifg_mac_pool82_tx_mac_partial2_invert_crc_cnt_reg1_tx_mac_partial2_invert_crc_cnt {
      type oc-yang:counter64;
      description
        "Counts the number of transmitted packets with partial CRC type 2.";
    }
    leaf counter_slice15_ifg_mac_pool82_tx_mac_partial2_invert_crc_cnt_reg2_tx_mac_partial2_invert_crc_cnt {
      type oc-yang:counter64;
      description
        "Counts the number of transmitted packets with partial CRC type 2.";
    }
    leaf counter_slice15_ifg_mac_pool82_tx_mac_partial2_invert_crc_cnt_reg3_tx_mac_partial2_invert_crc_cnt {
      type oc-yang:counter64;
      description
        "Counts the number of transmitted packets with partial CRC type 2.";
    }
    leaf counter_slice15_ifg_mac_pool82_tx_mac_partial2_invert_crc_cnt_reg4_tx_mac_partial2_invert_crc_cnt {
      type oc-yang:counter64;
      description
        "Counts the number of transmitted packets with partial CRC type 2.";
    }
    leaf counter_slice15_ifg_mac_pool82_tx_mac_partial2_invert_crc_cnt_reg5_tx_mac_partial2_invert_crc_cnt {
      type oc-yang:counter64;
      description
        "Counts the number of transmitted packets with partial CRC type 2.";
    }
    leaf counter_slice15_ifg_mac_pool82_tx_mac_partial2_invert_crc_cnt_reg6_tx_mac_partial2_invert_crc_cnt {
      type oc-yang:counter64;
      description
        "Counts the number of transmitted packets with partial CRC type 2.";
    }
    leaf counter_slice15_ifg_mac_pool82_tx_mac_partial2_invert_crc_cnt_reg7_tx_mac_partial2_invert_crc_cnt {
      type oc-yang:counter64;
      description
        "Counts the number of transmitted packets with partial CRC type 2.";
    }
    leaf counter_slice15_ifg_mac_pool83_tx_mac_partial2_invert_crc_cnt_reg0_tx_mac_partial2_invert_crc_cnt {
      type oc-yang:counter64;
      description
        "Counts the number of transmitted packets with partial CRC type 2.";
    }
    leaf counter_slice15_ifg_mac_pool83_tx_mac_partial2_invert_crc_cnt_reg1_tx_mac_partial2_invert_crc_cnt {
      type oc-yang:counter64;
      description
        "Counts the number of transmitted packets with partial CRC type 2.";
    }
    leaf counter_slice15_ifg_mac_pool83_tx_mac_partial2_invert_crc_cnt_reg2_tx_mac_partial2_invert_crc_cnt {
      type oc-yang:counter64;
      description
        "Counts the number of transmitted packets with partial CRC type 2.";
    }
    leaf counter_slice15_ifg_mac_pool83_tx_mac_partial2_invert_crc_cnt_reg3_tx_mac_partial2_invert_crc_cnt {
      type oc-yang:counter64;
      description
        "Counts the number of transmitted packets with partial CRC type 2.";
    }
    leaf counter_slice15_ifg_mac_pool83_tx_mac_partial2_invert_crc_cnt_reg4_tx_mac_partial2_invert_crc_cnt {
      type oc-yang:counter64;
      description
        "Counts the number of transmitted packets with partial CRC type 2.";
    }
    leaf counter_slice15_ifg_mac_pool83_tx_mac_partial2_invert_crc_cnt_reg5_tx_mac_partial2_invert_crc_cnt {
      type oc-yang:counter64;
      description
        "Counts the number of transmitted packets with partial CRC type 2.";
    }
    leaf counter_slice15_ifg_mac_pool83_tx_mac_partial2_invert_crc_cnt_reg6_tx_mac_partial2_invert_crc_cnt {
      type oc-yang:counter64;
      description
        "Counts the number of transmitted packets with partial CRC type 2.";
    }
    leaf counter_slice15_ifg_mac_pool83_tx_mac_partial2_invert_crc_cnt_reg7_tx_mac_partial2_invert_crc_cnt {
      type oc-yang:counter64;
      description
        "Counts the number of transmitted packets with partial CRC type 2.";
    }
    leaf counter_slice15_ifg_mac_pool84_tx_mac_partial2_invert_crc_cnt_reg0_tx_mac_partial2_invert_crc_cnt {
      type oc-yang:counter64;
      description
        "Counts the number of transmitted packets with partial CRC type 2.";
    }
    leaf counter_slice15_ifg_mac_pool84_tx_mac_partial2_invert_crc_cnt_reg1_tx_mac_partial2_invert_crc_cnt {
      type oc-yang:counter64;
      description
        "Counts the number of transmitted packets with partial CRC type 2.";
    }
    leaf counter_slice15_ifg_mac_pool84_tx_mac_partial2_invert_crc_cnt_reg2_tx_mac_partial2_invert_crc_cnt {
      type oc-yang:counter64;
      description
        "Counts the number of transmitted packets with partial CRC type 2.";
    }
    leaf counter_slice15_ifg_mac_pool84_tx_mac_partial2_invert_crc_cnt_reg3_tx_mac_partial2_invert_crc_cnt {
      type oc-yang:counter64;
      description
        "Counts the number of transmitted packets with partial CRC type 2.";
    }
    leaf counter_slice15_ifg_mac_pool84_tx_mac_partial2_invert_crc_cnt_reg4_tx_mac_partial2_invert_crc_cnt {
      type oc-yang:counter64;
      description
        "Counts the number of transmitted packets with partial CRC type 2.";
    }
    leaf counter_slice15_ifg_mac_pool84_tx_mac_partial2_invert_crc_cnt_reg5_tx_mac_partial2_invert_crc_cnt {
      type oc-yang:counter64;
      description
        "Counts the number of transmitted packets with partial CRC type 2.";
    }
    leaf counter_slice15_ifg_mac_pool84_tx_mac_partial2_invert_crc_cnt_reg6_tx_mac_partial2_invert_crc_cnt {
      type oc-yang:counter64;
      description
        "Counts the number of transmitted packets with partial CRC type 2.";
    }
    leaf counter_slice15_ifg_mac_pool84_tx_mac_partial2_invert_crc_cnt_reg7_tx_mac_partial2_invert_crc_cnt {
      type oc-yang:counter64;
      description
        "Counts the number of transmitted packets with partial CRC type 2.";
    }
    leaf counter_slice15_ifg_mac_pool85_tx_mac_partial2_invert_crc_cnt_reg0_tx_mac_partial2_invert_crc_cnt {
      type oc-yang:counter64;
      description
        "Counts the number of transmitted packets with partial CRC type 2.";
    }
    leaf counter_slice15_ifg_mac_pool85_tx_mac_partial2_invert_crc_cnt_reg1_tx_mac_partial2_invert_crc_cnt {
      type oc-yang:counter64;
      description
        "Counts the number of transmitted packets with partial CRC type 2.";
    }
    leaf counter_slice15_ifg_mac_pool85_tx_mac_partial2_invert_crc_cnt_reg2_tx_mac_partial2_invert_crc_cnt {
      type oc-yang:counter64;
      description
        "Counts the number of transmitted packets with partial CRC type 2.";
    }
    leaf counter_slice15_ifg_mac_pool85_tx_mac_partial2_invert_crc_cnt_reg3_tx_mac_partial2_invert_crc_cnt {
      type oc-yang:counter64;
      description
        "Counts the number of transmitted packets with partial CRC type 2.";
    }
    leaf counter_slice15_ifg_mac_pool85_tx_mac_partial2_invert_crc_cnt_reg4_tx_mac_partial2_invert_crc_cnt {
      type oc-yang:counter64;
      description
        "Counts the number of transmitted packets with partial CRC type 2.";
    }
    leaf counter_slice15_ifg_mac_pool85_tx_mac_partial2_invert_crc_cnt_reg5_tx_mac_partial2_invert_crc_cnt {
      type oc-yang:counter64;
      description
        "Counts the number of transmitted packets with partial CRC type 2.";
    }
    leaf counter_slice15_ifg_mac_pool85_tx_mac_partial2_invert_crc_cnt_reg6_tx_mac_partial2_invert_crc_cnt {
      type oc-yang:counter64;
      description
        "Counts the number of transmitted packets with partial CRC type 2.";
    }
    leaf counter_slice15_ifg_mac_pool85_tx_mac_partial2_invert_crc_cnt_reg7_tx_mac_partial2_invert_crc_cnt {
      type oc-yang:counter64;
      description
        "Counts the number of transmitted packets with partial CRC type 2.";
    }
    leaf counter_slice15_ifg_mac_pool86_tx_mac_partial2_invert_crc_cnt_reg0_tx_mac_partial2_invert_crc_cnt {
      type oc-yang:counter64;
      description
        "Counts the number of transmitted packets with partial CRC type 2.";
    }
    leaf counter_slice15_ifg_mac_pool86_tx_mac_partial2_invert_crc_cnt_reg1_tx_mac_partial2_invert_crc_cnt {
      type oc-yang:counter64;
      description
        "Counts the number of transmitted packets with partial CRC type 2.";
    }
    leaf counter_slice15_ifg_mac_pool86_tx_mac_partial2_invert_crc_cnt_reg2_tx_mac_partial2_invert_crc_cnt {
      type oc-yang:counter64;
      description
        "Counts the number of transmitted packets with partial CRC type 2.";
    }
    leaf counter_slice15_ifg_mac_pool86_tx_mac_partial2_invert_crc_cnt_reg3_tx_mac_partial2_invert_crc_cnt {
      type oc-yang:counter64;
      description
        "Counts the number of transmitted packets with partial CRC type 2.";
    }
    leaf counter_slice15_ifg_mac_pool86_tx_mac_partial2_invert_crc_cnt_reg4_tx_mac_partial2_invert_crc_cnt {
      type oc-yang:counter64;
      description
        "Counts the number of transmitted packets with partial CRC type 2.";
    }
    leaf counter_slice15_ifg_mac_pool86_tx_mac_partial2_invert_crc_cnt_reg5_tx_mac_partial2_invert_crc_cnt {
      type oc-yang:counter64;
      description
        "Counts the number of transmitted packets with partial CRC type 2.";
    }
    leaf counter_slice15_ifg_mac_pool86_tx_mac_partial2_invert_crc_cnt_reg6_tx_mac_partial2_invert_crc_cnt {
      type oc-yang:counter64;
      description
        "Counts the number of transmitted packets with partial CRC type 2.";
    }
    leaf counter_slice15_ifg_mac_pool86_tx_mac_partial2_invert_crc_cnt_reg7_tx_mac_partial2_invert_crc_cnt {
      type oc-yang:counter64;
      description
        "Counts the number of transmitted packets with partial CRC type 2.";
    }
    leaf counter_slice15_ifg_mac_pool87_tx_mac_partial2_invert_crc_cnt_reg0_tx_mac_partial2_invert_crc_cnt {
      type oc-yang:counter64;
      description
        "Counts the number of transmitted packets with partial CRC type 2.";
    }
    leaf counter_slice15_ifg_mac_pool87_tx_mac_partial2_invert_crc_cnt_reg1_tx_mac_partial2_invert_crc_cnt {
      type oc-yang:counter64;
      description
        "Counts the number of transmitted packets with partial CRC type 2.";
    }
    leaf counter_slice15_ifg_mac_pool87_tx_mac_partial2_invert_crc_cnt_reg2_tx_mac_partial2_invert_crc_cnt {
      type oc-yang:counter64;
      description
        "Counts the number of transmitted packets with partial CRC type 2.";
    }
    leaf counter_slice15_ifg_mac_pool87_tx_mac_partial2_invert_crc_cnt_reg3_tx_mac_partial2_invert_crc_cnt {
      type oc-yang:counter64;
      description
        "Counts the number of transmitted packets with partial CRC type 2.";
    }
    leaf counter_slice15_ifg_mac_pool87_tx_mac_partial2_invert_crc_cnt_reg4_tx_mac_partial2_invert_crc_cnt {
      type oc-yang:counter64;
      description
        "Counts the number of transmitted packets with partial CRC type 2.";
    }
    leaf counter_slice15_ifg_mac_pool87_tx_mac_partial2_invert_crc_cnt_reg5_tx_mac_partial2_invert_crc_cnt {
      type oc-yang:counter64;
      description
        "Counts the number of transmitted packets with partial CRC type 2.";
    }
    leaf counter_slice15_ifg_mac_pool87_tx_mac_partial2_invert_crc_cnt_reg6_tx_mac_partial2_invert_crc_cnt {
      type oc-yang:counter64;
      description
        "Counts the number of transmitted packets with partial CRC type 2.";
    }
    leaf counter_slice15_ifg_mac_pool87_tx_mac_partial2_invert_crc_cnt_reg7_tx_mac_partial2_invert_crc_cnt {
      type oc-yang:counter64;
      description
        "Counts the number of transmitted packets with partial CRC type 2.";
    }
    leaf counter_slice0_ifg_mac_pool80_tx_oobi_pkt_drop_counter0_tx_oobi_pkt_drop {
      type oc-yang:counter64;
      description
        "counter for OOBI okt drops";
    }
    leaf counter_slice0_ifg_mac_pool80_tx_oobi_pkt_drop_counter1_tx_oobi_pkt_drop {
      type oc-yang:counter64;
      description
        "counter for OOBI okt drops";
    }
    leaf counter_slice0_ifg_mac_pool80_tx_oobi_pkt_drop_counter2_tx_oobi_pkt_drop {
      type oc-yang:counter64;
      description
        "counter for OOBI okt drops";
    }
    leaf counter_slice0_ifg_mac_pool80_tx_oobi_pkt_drop_counter3_tx_oobi_pkt_drop {
      type oc-yang:counter64;
      description
        "counter for OOBI okt drops";
    }
    leaf counter_slice0_ifg_mac_pool80_tx_oobi_pkt_drop_counter4_tx_oobi_pkt_drop {
      type oc-yang:counter64;
      description
        "counter for OOBI okt drops";
    }
    leaf counter_slice0_ifg_mac_pool80_tx_oobi_pkt_drop_counter5_tx_oobi_pkt_drop {
      type oc-yang:counter64;
      description
        "counter for OOBI okt drops";
    }
    leaf counter_slice0_ifg_mac_pool80_tx_oobi_pkt_drop_counter6_tx_oobi_pkt_drop {
      type oc-yang:counter64;
      description
        "counter for OOBI okt drops";
    }
    leaf counter_slice0_ifg_mac_pool80_tx_oobi_pkt_drop_counter7_tx_oobi_pkt_drop {
      type oc-yang:counter64;
      description
        "counter for OOBI okt drops";
    }
    leaf counter_slice0_ifg_mac_pool81_tx_oobi_pkt_drop_counter0_tx_oobi_pkt_drop {
      type oc-yang:counter64;
      description
        "counter for OOBI okt drops";
    }
    leaf counter_slice0_ifg_mac_pool81_tx_oobi_pkt_drop_counter1_tx_oobi_pkt_drop {
      type oc-yang:counter64;
      description
        "counter for OOBI okt drops";
    }
    leaf counter_slice0_ifg_mac_pool81_tx_oobi_pkt_drop_counter2_tx_oobi_pkt_drop {
      type oc-yang:counter64;
      description
        "counter for OOBI okt drops";
    }
    leaf counter_slice0_ifg_mac_pool81_tx_oobi_pkt_drop_counter3_tx_oobi_pkt_drop {
      type oc-yang:counter64;
      description
        "counter for OOBI okt drops";
    }
    leaf counter_slice0_ifg_mac_pool81_tx_oobi_pkt_drop_counter4_tx_oobi_pkt_drop {
      type oc-yang:counter64;
      description
        "counter for OOBI okt drops";
    }
    leaf counter_slice0_ifg_mac_pool81_tx_oobi_pkt_drop_counter5_tx_oobi_pkt_drop {
      type oc-yang:counter64;
      description
        "counter for OOBI okt drops";
    }
    leaf counter_slice0_ifg_mac_pool81_tx_oobi_pkt_drop_counter6_tx_oobi_pkt_drop {
      type oc-yang:counter64;
      description
        "counter for OOBI okt drops";
    }
    leaf counter_slice0_ifg_mac_pool81_tx_oobi_pkt_drop_counter7_tx_oobi_pkt_drop {
      type oc-yang:counter64;
      description
        "counter for OOBI okt drops";
    }
    leaf counter_slice0_ifg_mac_pool82_tx_oobi_pkt_drop_counter0_tx_oobi_pkt_drop {
      type oc-yang:counter64;
      description
        "counter for OOBI okt drops";
    }
    leaf counter_slice0_ifg_mac_pool82_tx_oobi_pkt_drop_counter1_tx_oobi_pkt_drop {
      type oc-yang:counter64;
      description
        "counter for OOBI okt drops";
    }
    leaf counter_slice0_ifg_mac_pool82_tx_oobi_pkt_drop_counter2_tx_oobi_pkt_drop {
      type oc-yang:counter64;
      description
        "counter for OOBI okt drops";
    }
    leaf counter_slice0_ifg_mac_pool82_tx_oobi_pkt_drop_counter3_tx_oobi_pkt_drop {
      type oc-yang:counter64;
      description
        "counter for OOBI okt drops";
    }
    leaf counter_slice0_ifg_mac_pool82_tx_oobi_pkt_drop_counter4_tx_oobi_pkt_drop {
      type oc-yang:counter64;
      description
        "counter for OOBI okt drops";
    }
    leaf counter_slice0_ifg_mac_pool82_tx_oobi_pkt_drop_counter5_tx_oobi_pkt_drop {
      type oc-yang:counter64;
      description
        "counter for OOBI okt drops";
    }
    leaf counter_slice0_ifg_mac_pool82_tx_oobi_pkt_drop_counter6_tx_oobi_pkt_drop {
      type oc-yang:counter64;
      description
        "counter for OOBI okt drops";
    }
    leaf counter_slice0_ifg_mac_pool82_tx_oobi_pkt_drop_counter7_tx_oobi_pkt_drop {
      type oc-yang:counter64;
      description
        "counter for OOBI okt drops";
    }
    leaf counter_slice0_ifg_mac_pool83_tx_oobi_pkt_drop_counter0_tx_oobi_pkt_drop {
      type oc-yang:counter64;
      description
        "counter for OOBI okt drops";
    }
    leaf counter_slice0_ifg_mac_pool83_tx_oobi_pkt_drop_counter1_tx_oobi_pkt_drop {
      type oc-yang:counter64;
      description
        "counter for OOBI okt drops";
    }
    leaf counter_slice0_ifg_mac_pool83_tx_oobi_pkt_drop_counter2_tx_oobi_pkt_drop {
      type oc-yang:counter64;
      description
        "counter for OOBI okt drops";
    }
    leaf counter_slice0_ifg_mac_pool83_tx_oobi_pkt_drop_counter3_tx_oobi_pkt_drop {
      type oc-yang:counter64;
      description
        "counter for OOBI okt drops";
    }
    leaf counter_slice0_ifg_mac_pool83_tx_oobi_pkt_drop_counter4_tx_oobi_pkt_drop {
      type oc-yang:counter64;
      description
        "counter for OOBI okt drops";
    }
    leaf counter_slice0_ifg_mac_pool83_tx_oobi_pkt_drop_counter5_tx_oobi_pkt_drop {
      type oc-yang:counter64;
      description
        "counter for OOBI okt drops";
    }
    leaf counter_slice0_ifg_mac_pool83_tx_oobi_pkt_drop_counter6_tx_oobi_pkt_drop {
      type oc-yang:counter64;
      description
        "counter for OOBI okt drops";
    }
    leaf counter_slice0_ifg_mac_pool83_tx_oobi_pkt_drop_counter7_tx_oobi_pkt_drop {
      type oc-yang:counter64;
      description
        "counter for OOBI okt drops";
    }
    leaf counter_slice0_ifg_mac_pool84_tx_oobi_pkt_drop_counter0_tx_oobi_pkt_drop {
      type oc-yang:counter64;
      description
        "counter for OOBI okt drops";
    }
    leaf counter_slice0_ifg_mac_pool84_tx_oobi_pkt_drop_counter1_tx_oobi_pkt_drop {
      type oc-yang:counter64;
      description
        "counter for OOBI okt drops";
    }
    leaf counter_slice0_ifg_mac_pool84_tx_oobi_pkt_drop_counter2_tx_oobi_pkt_drop {
      type oc-yang:counter64;
      description
        "counter for OOBI okt drops";
    }
    leaf counter_slice0_ifg_mac_pool84_tx_oobi_pkt_drop_counter3_tx_oobi_pkt_drop {
      type oc-yang:counter64;
      description
        "counter for OOBI okt drops";
    }
    leaf counter_slice0_ifg_mac_pool84_tx_oobi_pkt_drop_counter4_tx_oobi_pkt_drop {
      type oc-yang:counter64;
      description
        "counter for OOBI okt drops";
    }
    leaf counter_slice0_ifg_mac_pool84_tx_oobi_pkt_drop_counter5_tx_oobi_pkt_drop {
      type oc-yang:counter64;
      description
        "counter for OOBI okt drops";
    }
    leaf counter_slice0_ifg_mac_pool84_tx_oobi_pkt_drop_counter6_tx_oobi_pkt_drop {
      type oc-yang:counter64;
      description
        "counter for OOBI okt drops";
    }
    leaf counter_slice0_ifg_mac_pool84_tx_oobi_pkt_drop_counter7_tx_oobi_pkt_drop {
      type oc-yang:counter64;
      description
        "counter for OOBI okt drops";
    }
    leaf counter_slice0_ifg_mac_pool85_tx_oobi_pkt_drop_counter0_tx_oobi_pkt_drop {
      type oc-yang:counter64;
      description
        "counter for OOBI okt drops";
    }
    leaf counter_slice0_ifg_mac_pool85_tx_oobi_pkt_drop_counter1_tx_oobi_pkt_drop {
      type oc-yang:counter64;
      description
        "counter for OOBI okt drops";
    }
    leaf counter_slice0_ifg_mac_pool85_tx_oobi_pkt_drop_counter2_tx_oobi_pkt_drop {
      type oc-yang:counter64;
      description
        "counter for OOBI okt drops";
    }
    leaf counter_slice0_ifg_mac_pool85_tx_oobi_pkt_drop_counter3_tx_oobi_pkt_drop {
      type oc-yang:counter64;
      description
        "counter for OOBI okt drops";
    }
    leaf counter_slice0_ifg_mac_pool85_tx_oobi_pkt_drop_counter4_tx_oobi_pkt_drop {
      type oc-yang:counter64;
      description
        "counter for OOBI okt drops";
    }
    leaf counter_slice0_ifg_mac_pool85_tx_oobi_pkt_drop_counter5_tx_oobi_pkt_drop {
      type oc-yang:counter64;
      description
        "counter for OOBI okt drops";
    }
    leaf counter_slice0_ifg_mac_pool85_tx_oobi_pkt_drop_counter6_tx_oobi_pkt_drop {
      type oc-yang:counter64;
      description
        "counter for OOBI okt drops";
    }
    leaf counter_slice0_ifg_mac_pool85_tx_oobi_pkt_drop_counter7_tx_oobi_pkt_drop {
      type oc-yang:counter64;
      description
        "counter for OOBI okt drops";
    }
    leaf counter_slice0_ifg_mac_pool86_tx_oobi_pkt_drop_counter0_tx_oobi_pkt_drop {
      type oc-yang:counter64;
      description
        "counter for OOBI okt drops";
    }
    leaf counter_slice0_ifg_mac_pool86_tx_oobi_pkt_drop_counter1_tx_oobi_pkt_drop {
      type oc-yang:counter64;
      description
        "counter for OOBI okt drops";
    }
    leaf counter_slice0_ifg_mac_pool86_tx_oobi_pkt_drop_counter2_tx_oobi_pkt_drop {
      type oc-yang:counter64;
      description
        "counter for OOBI okt drops";
    }
    leaf counter_slice0_ifg_mac_pool86_tx_oobi_pkt_drop_counter3_tx_oobi_pkt_drop {
      type oc-yang:counter64;
      description
        "counter for OOBI okt drops";
    }
    leaf counter_slice0_ifg_mac_pool86_tx_oobi_pkt_drop_counter4_tx_oobi_pkt_drop {
      type oc-yang:counter64;
      description
        "counter for OOBI okt drops";
    }
    leaf counter_slice0_ifg_mac_pool86_tx_oobi_pkt_drop_counter5_tx_oobi_pkt_drop {
      type oc-yang:counter64;
      description
        "counter for OOBI okt drops";
    }
    leaf counter_slice0_ifg_mac_pool86_tx_oobi_pkt_drop_counter6_tx_oobi_pkt_drop {
      type oc-yang:counter64;
      description
        "counter for OOBI okt drops";
    }
    leaf counter_slice0_ifg_mac_pool86_tx_oobi_pkt_drop_counter7_tx_oobi_pkt_drop {
      type oc-yang:counter64;
      description
        "counter for OOBI okt drops";
    }
    leaf counter_slice0_ifg_mac_pool87_tx_oobi_pkt_drop_counter0_tx_oobi_pkt_drop {
      type oc-yang:counter64;
      description
        "counter for OOBI okt drops";
    }
    leaf counter_slice0_ifg_mac_pool87_tx_oobi_pkt_drop_counter1_tx_oobi_pkt_drop {
      type oc-yang:counter64;
      description
        "counter for OOBI okt drops";
    }
    leaf counter_slice0_ifg_mac_pool87_tx_oobi_pkt_drop_counter2_tx_oobi_pkt_drop {
      type oc-yang:counter64;
      description
        "counter for OOBI okt drops";
    }
    leaf counter_slice0_ifg_mac_pool87_tx_oobi_pkt_drop_counter3_tx_oobi_pkt_drop {
      type oc-yang:counter64;
      description
        "counter for OOBI okt drops";
    }
    leaf counter_slice0_ifg_mac_pool87_tx_oobi_pkt_drop_counter4_tx_oobi_pkt_drop {
      type oc-yang:counter64;
      description
        "counter for OOBI okt drops";
    }
    leaf counter_slice0_ifg_mac_pool87_tx_oobi_pkt_drop_counter5_tx_oobi_pkt_drop {
      type oc-yang:counter64;
      description
        "counter for OOBI okt drops";
    }
    leaf counter_slice0_ifg_mac_pool87_tx_oobi_pkt_drop_counter6_tx_oobi_pkt_drop {
      type oc-yang:counter64;
      description
        "counter for OOBI okt drops";
    }
    leaf counter_slice0_ifg_mac_pool87_tx_oobi_pkt_drop_counter7_tx_oobi_pkt_drop {
      type oc-yang:counter64;
      description
        "counter for OOBI okt drops";
    }
    leaf counter_slice1_ifg_mac_pool80_tx_oobi_pkt_drop_counter0_tx_oobi_pkt_drop {
      type oc-yang:counter64;
      description
        "counter for OOBI okt drops";
    }
    leaf counter_slice1_ifg_mac_pool80_tx_oobi_pkt_drop_counter1_tx_oobi_pkt_drop {
      type oc-yang:counter64;
      description
        "counter for OOBI okt drops";
    }
    leaf counter_slice1_ifg_mac_pool80_tx_oobi_pkt_drop_counter2_tx_oobi_pkt_drop {
      type oc-yang:counter64;
      description
        "counter for OOBI okt drops";
    }
    leaf counter_slice1_ifg_mac_pool80_tx_oobi_pkt_drop_counter3_tx_oobi_pkt_drop {
      type oc-yang:counter64;
      description
        "counter for OOBI okt drops";
    }
    leaf counter_slice1_ifg_mac_pool80_tx_oobi_pkt_drop_counter4_tx_oobi_pkt_drop {
      type oc-yang:counter64;
      description
        "counter for OOBI okt drops";
    }
    leaf counter_slice1_ifg_mac_pool80_tx_oobi_pkt_drop_counter5_tx_oobi_pkt_drop {
      type oc-yang:counter64;
      description
        "counter for OOBI okt drops";
    }
    leaf counter_slice1_ifg_mac_pool80_tx_oobi_pkt_drop_counter6_tx_oobi_pkt_drop {
      type oc-yang:counter64;
      description
        "counter for OOBI okt drops";
    }
    leaf counter_slice1_ifg_mac_pool80_tx_oobi_pkt_drop_counter7_tx_oobi_pkt_drop {
      type oc-yang:counter64;
      description
        "counter for OOBI okt drops";
    }
    leaf counter_slice1_ifg_mac_pool81_tx_oobi_pkt_drop_counter0_tx_oobi_pkt_drop {
      type oc-yang:counter64;
      description
        "counter for OOBI okt drops";
    }
    leaf counter_slice1_ifg_mac_pool81_tx_oobi_pkt_drop_counter1_tx_oobi_pkt_drop {
      type oc-yang:counter64;
      description
        "counter for OOBI okt drops";
    }
    leaf counter_slice1_ifg_mac_pool81_tx_oobi_pkt_drop_counter2_tx_oobi_pkt_drop {
      type oc-yang:counter64;
      description
        "counter for OOBI okt drops";
    }
    leaf counter_slice1_ifg_mac_pool81_tx_oobi_pkt_drop_counter3_tx_oobi_pkt_drop {
      type oc-yang:counter64;
      description
        "counter for OOBI okt drops";
    }
    leaf counter_slice1_ifg_mac_pool81_tx_oobi_pkt_drop_counter4_tx_oobi_pkt_drop {
      type oc-yang:counter64;
      description
        "counter for OOBI okt drops";
    }
    leaf counter_slice1_ifg_mac_pool81_tx_oobi_pkt_drop_counter5_tx_oobi_pkt_drop {
      type oc-yang:counter64;
      description
        "counter for OOBI okt drops";
    }
    leaf counter_slice1_ifg_mac_pool81_tx_oobi_pkt_drop_counter6_tx_oobi_pkt_drop {
      type oc-yang:counter64;
      description
        "counter for OOBI okt drops";
    }
    leaf counter_slice1_ifg_mac_pool81_tx_oobi_pkt_drop_counter7_tx_oobi_pkt_drop {
      type oc-yang:counter64;
      description
        "counter for OOBI okt drops";
    }
    leaf counter_slice1_ifg_mac_pool82_tx_oobi_pkt_drop_counter0_tx_oobi_pkt_drop {
      type oc-yang:counter64;
      description
        "counter for OOBI okt drops";
    }
    leaf counter_slice1_ifg_mac_pool82_tx_oobi_pkt_drop_counter1_tx_oobi_pkt_drop {
      type oc-yang:counter64;
      description
        "counter for OOBI okt drops";
    }
    leaf counter_slice1_ifg_mac_pool82_tx_oobi_pkt_drop_counter2_tx_oobi_pkt_drop {
      type oc-yang:counter64;
      description
        "counter for OOBI okt drops";
    }
    leaf counter_slice1_ifg_mac_pool82_tx_oobi_pkt_drop_counter3_tx_oobi_pkt_drop {
      type oc-yang:counter64;
      description
        "counter for OOBI okt drops";
    }
    leaf counter_slice1_ifg_mac_pool82_tx_oobi_pkt_drop_counter4_tx_oobi_pkt_drop {
      type oc-yang:counter64;
      description
        "counter for OOBI okt drops";
    }
    leaf counter_slice1_ifg_mac_pool82_tx_oobi_pkt_drop_counter5_tx_oobi_pkt_drop {
      type oc-yang:counter64;
      description
        "counter for OOBI okt drops";
    }
    leaf counter_slice1_ifg_mac_pool82_tx_oobi_pkt_drop_counter6_tx_oobi_pkt_drop {
      type oc-yang:counter64;
      description
        "counter for OOBI okt drops";
    }
    leaf counter_slice1_ifg_mac_pool82_tx_oobi_pkt_drop_counter7_tx_oobi_pkt_drop {
      type oc-yang:counter64;
      description
        "counter for OOBI okt drops";
    }
    leaf counter_slice1_ifg_mac_pool83_tx_oobi_pkt_drop_counter0_tx_oobi_pkt_drop {
      type oc-yang:counter64;
      description
        "counter for OOBI okt drops";
    }
    leaf counter_slice1_ifg_mac_pool83_tx_oobi_pkt_drop_counter1_tx_oobi_pkt_drop {
      type oc-yang:counter64;
      description
        "counter for OOBI okt drops";
    }
    leaf counter_slice1_ifg_mac_pool83_tx_oobi_pkt_drop_counter2_tx_oobi_pkt_drop {
      type oc-yang:counter64;
      description
        "counter for OOBI okt drops";
    }
    leaf counter_slice1_ifg_mac_pool83_tx_oobi_pkt_drop_counter3_tx_oobi_pkt_drop {
      type oc-yang:counter64;
      description
        "counter for OOBI okt drops";
    }
    leaf counter_slice1_ifg_mac_pool83_tx_oobi_pkt_drop_counter4_tx_oobi_pkt_drop {
      type oc-yang:counter64;
      description
        "counter for OOBI okt drops";
    }
    leaf counter_slice1_ifg_mac_pool83_tx_oobi_pkt_drop_counter5_tx_oobi_pkt_drop {
      type oc-yang:counter64;
      description
        "counter for OOBI okt drops";
    }
    leaf counter_slice1_ifg_mac_pool83_tx_oobi_pkt_drop_counter6_tx_oobi_pkt_drop {
      type oc-yang:counter64;
      description
        "counter for OOBI okt drops";
    }
    leaf counter_slice1_ifg_mac_pool83_tx_oobi_pkt_drop_counter7_tx_oobi_pkt_drop {
      type oc-yang:counter64;
      description
        "counter for OOBI okt drops";
    }
    leaf counter_slice1_ifg_mac_pool84_tx_oobi_pkt_drop_counter0_tx_oobi_pkt_drop {
      type oc-yang:counter64;
      description
        "counter for OOBI okt drops";
    }
    leaf counter_slice1_ifg_mac_pool84_tx_oobi_pkt_drop_counter1_tx_oobi_pkt_drop {
      type oc-yang:counter64;
      description
        "counter for OOBI okt drops";
    }
    leaf counter_slice1_ifg_mac_pool84_tx_oobi_pkt_drop_counter2_tx_oobi_pkt_drop {
      type oc-yang:counter64;
      description
        "counter for OOBI okt drops";
    }
    leaf counter_slice1_ifg_mac_pool84_tx_oobi_pkt_drop_counter3_tx_oobi_pkt_drop {
      type oc-yang:counter64;
      description
        "counter for OOBI okt drops";
    }
    leaf counter_slice1_ifg_mac_pool84_tx_oobi_pkt_drop_counter4_tx_oobi_pkt_drop {
      type oc-yang:counter64;
      description
        "counter for OOBI okt drops";
    }
    leaf counter_slice1_ifg_mac_pool84_tx_oobi_pkt_drop_counter5_tx_oobi_pkt_drop {
      type oc-yang:counter64;
      description
        "counter for OOBI okt drops";
    }
    leaf counter_slice1_ifg_mac_pool84_tx_oobi_pkt_drop_counter6_tx_oobi_pkt_drop {
      type oc-yang:counter64;
      description
        "counter for OOBI okt drops";
    }
    leaf counter_slice1_ifg_mac_pool84_tx_oobi_pkt_drop_counter7_tx_oobi_pkt_drop {
      type oc-yang:counter64;
      description
        "counter for OOBI okt drops";
    }
    leaf counter_slice1_ifg_mac_pool85_tx_oobi_pkt_drop_counter0_tx_oobi_pkt_drop {
      type oc-yang:counter64;
      description
        "counter for OOBI okt drops";
    }
    leaf counter_slice1_ifg_mac_pool85_tx_oobi_pkt_drop_counter1_tx_oobi_pkt_drop {
      type oc-yang:counter64;
      description
        "counter for OOBI okt drops";
    }
    leaf counter_slice1_ifg_mac_pool85_tx_oobi_pkt_drop_counter2_tx_oobi_pkt_drop {
      type oc-yang:counter64;
      description
        "counter for OOBI okt drops";
    }
    leaf counter_slice1_ifg_mac_pool85_tx_oobi_pkt_drop_counter3_tx_oobi_pkt_drop {
      type oc-yang:counter64;
      description
        "counter for OOBI okt drops";
    }
    leaf counter_slice1_ifg_mac_pool85_tx_oobi_pkt_drop_counter4_tx_oobi_pkt_drop {
      type oc-yang:counter64;
      description
        "counter for OOBI okt drops";
    }
    leaf counter_slice1_ifg_mac_pool85_tx_oobi_pkt_drop_counter5_tx_oobi_pkt_drop {
      type oc-yang:counter64;
      description
        "counter for OOBI okt drops";
    }
    leaf counter_slice1_ifg_mac_pool85_tx_oobi_pkt_drop_counter6_tx_oobi_pkt_drop {
      type oc-yang:counter64;
      description
        "counter for OOBI okt drops";
    }
    leaf counter_slice1_ifg_mac_pool85_tx_oobi_pkt_drop_counter7_tx_oobi_pkt_drop {
      type oc-yang:counter64;
      description
        "counter for OOBI okt drops";
    }
    leaf counter_slice1_ifg_mac_pool86_tx_oobi_pkt_drop_counter0_tx_oobi_pkt_drop {
      type oc-yang:counter64;
      description
        "counter for OOBI okt drops";
    }
    leaf counter_slice1_ifg_mac_pool86_tx_oobi_pkt_drop_counter1_tx_oobi_pkt_drop {
      type oc-yang:counter64;
      description
        "counter for OOBI okt drops";
    }
    leaf counter_slice1_ifg_mac_pool86_tx_oobi_pkt_drop_counter2_tx_oobi_pkt_drop {
      type oc-yang:counter64;
      description
        "counter for OOBI okt drops";
    }
    leaf counter_slice1_ifg_mac_pool86_tx_oobi_pkt_drop_counter3_tx_oobi_pkt_drop {
      type oc-yang:counter64;
      description
        "counter for OOBI okt drops";
    }
    leaf counter_slice1_ifg_mac_pool86_tx_oobi_pkt_drop_counter4_tx_oobi_pkt_drop {
      type oc-yang:counter64;
      description
        "counter for OOBI okt drops";
    }
    leaf counter_slice1_ifg_mac_pool86_tx_oobi_pkt_drop_counter5_tx_oobi_pkt_drop {
      type oc-yang:counter64;
      description
        "counter for OOBI okt drops";
    }
    leaf counter_slice1_ifg_mac_pool86_tx_oobi_pkt_drop_counter6_tx_oobi_pkt_drop {
      type oc-yang:counter64;
      description
        "counter for OOBI okt drops";
    }
    leaf counter_slice1_ifg_mac_pool86_tx_oobi_pkt_drop_counter7_tx_oobi_pkt_drop {
      type oc-yang:counter64;
      description
        "counter for OOBI okt drops";
    }
    leaf counter_slice1_ifg_mac_pool87_tx_oobi_pkt_drop_counter0_tx_oobi_pkt_drop {
      type oc-yang:counter64;
      description
        "counter for OOBI okt drops";
    }
    leaf counter_slice1_ifg_mac_pool87_tx_oobi_pkt_drop_counter1_tx_oobi_pkt_drop {
      type oc-yang:counter64;
      description
        "counter for OOBI okt drops";
    }
    leaf counter_slice1_ifg_mac_pool87_tx_oobi_pkt_drop_counter2_tx_oobi_pkt_drop {
      type oc-yang:counter64;
      description
        "counter for OOBI okt drops";
    }
    leaf counter_slice1_ifg_mac_pool87_tx_oobi_pkt_drop_counter3_tx_oobi_pkt_drop {
      type oc-yang:counter64;
      description
        "counter for OOBI okt drops";
    }
    leaf counter_slice1_ifg_mac_pool87_tx_oobi_pkt_drop_counter4_tx_oobi_pkt_drop {
      type oc-yang:counter64;
      description
        "counter for OOBI okt drops";
    }
    leaf counter_slice1_ifg_mac_pool87_tx_oobi_pkt_drop_counter5_tx_oobi_pkt_drop {
      type oc-yang:counter64;
      description
        "counter for OOBI okt drops";
    }
    leaf counter_slice1_ifg_mac_pool87_tx_oobi_pkt_drop_counter6_tx_oobi_pkt_drop {
      type oc-yang:counter64;
      description
        "counter for OOBI okt drops";
    }
    leaf counter_slice1_ifg_mac_pool87_tx_oobi_pkt_drop_counter7_tx_oobi_pkt_drop {
      type oc-yang:counter64;
      description
        "counter for OOBI okt drops";
    }
    leaf counter_slice2_ifg_mac_pool80_tx_oobi_pkt_drop_counter0_tx_oobi_pkt_drop {
      type oc-yang:counter64;
      description
        "counter for OOBI okt drops";
    }
    leaf counter_slice2_ifg_mac_pool80_tx_oobi_pkt_drop_counter1_tx_oobi_pkt_drop {
      type oc-yang:counter64;
      description
        "counter for OOBI okt drops";
    }
    leaf counter_slice2_ifg_mac_pool80_tx_oobi_pkt_drop_counter2_tx_oobi_pkt_drop {
      type oc-yang:counter64;
      description
        "counter for OOBI okt drops";
    }
    leaf counter_slice2_ifg_mac_pool80_tx_oobi_pkt_drop_counter3_tx_oobi_pkt_drop {
      type oc-yang:counter64;
      description
        "counter for OOBI okt drops";
    }
    leaf counter_slice2_ifg_mac_pool80_tx_oobi_pkt_drop_counter4_tx_oobi_pkt_drop {
      type oc-yang:counter64;
      description
        "counter for OOBI okt drops";
    }
    leaf counter_slice2_ifg_mac_pool80_tx_oobi_pkt_drop_counter5_tx_oobi_pkt_drop {
      type oc-yang:counter64;
      description
        "counter for OOBI okt drops";
    }
    leaf counter_slice2_ifg_mac_pool80_tx_oobi_pkt_drop_counter6_tx_oobi_pkt_drop {
      type oc-yang:counter64;
      description
        "counter for OOBI okt drops";
    }
    leaf counter_slice2_ifg_mac_pool80_tx_oobi_pkt_drop_counter7_tx_oobi_pkt_drop {
      type oc-yang:counter64;
      description
        "counter for OOBI okt drops";
    }
    leaf counter_slice2_ifg_mac_pool81_tx_oobi_pkt_drop_counter0_tx_oobi_pkt_drop {
      type oc-yang:counter64;
      description
        "counter for OOBI okt drops";
    }
    leaf counter_slice2_ifg_mac_pool81_tx_oobi_pkt_drop_counter1_tx_oobi_pkt_drop {
      type oc-yang:counter64;
      description
        "counter for OOBI okt drops";
    }
    leaf counter_slice2_ifg_mac_pool81_tx_oobi_pkt_drop_counter2_tx_oobi_pkt_drop {
      type oc-yang:counter64;
      description
        "counter for OOBI okt drops";
    }
    leaf counter_slice2_ifg_mac_pool81_tx_oobi_pkt_drop_counter3_tx_oobi_pkt_drop {
      type oc-yang:counter64;
      description
        "counter for OOBI okt drops";
    }
    leaf counter_slice2_ifg_mac_pool81_tx_oobi_pkt_drop_counter4_tx_oobi_pkt_drop {
      type oc-yang:counter64;
      description
        "counter for OOBI okt drops";
    }
    leaf counter_slice2_ifg_mac_pool81_tx_oobi_pkt_drop_counter5_tx_oobi_pkt_drop {
      type oc-yang:counter64;
      description
        "counter for OOBI okt drops";
    }
    leaf counter_slice2_ifg_mac_pool81_tx_oobi_pkt_drop_counter6_tx_oobi_pkt_drop {
      type oc-yang:counter64;
      description
        "counter for OOBI okt drops";
    }
    leaf counter_slice2_ifg_mac_pool81_tx_oobi_pkt_drop_counter7_tx_oobi_pkt_drop {
      type oc-yang:counter64;
      description
        "counter for OOBI okt drops";
    }
    leaf counter_slice2_ifg_mac_pool82_tx_oobi_pkt_drop_counter0_tx_oobi_pkt_drop {
      type oc-yang:counter64;
      description
        "counter for OOBI okt drops";
    }
    leaf counter_slice2_ifg_mac_pool82_tx_oobi_pkt_drop_counter1_tx_oobi_pkt_drop {
      type oc-yang:counter64;
      description
        "counter for OOBI okt drops";
    }
    leaf counter_slice2_ifg_mac_pool82_tx_oobi_pkt_drop_counter2_tx_oobi_pkt_drop {
      type oc-yang:counter64;
      description
        "counter for OOBI okt drops";
    }
    leaf counter_slice2_ifg_mac_pool82_tx_oobi_pkt_drop_counter3_tx_oobi_pkt_drop {
      type oc-yang:counter64;
      description
        "counter for OOBI okt drops";
    }
    leaf counter_slice2_ifg_mac_pool82_tx_oobi_pkt_drop_counter4_tx_oobi_pkt_drop {
      type oc-yang:counter64;
      description
        "counter for OOBI okt drops";
    }
    leaf counter_slice2_ifg_mac_pool82_tx_oobi_pkt_drop_counter5_tx_oobi_pkt_drop {
      type oc-yang:counter64;
      description
        "counter for OOBI okt drops";
    }
    leaf counter_slice2_ifg_mac_pool82_tx_oobi_pkt_drop_counter6_tx_oobi_pkt_drop {
      type oc-yang:counter64;
      description
        "counter for OOBI okt drops";
    }
    leaf counter_slice2_ifg_mac_pool82_tx_oobi_pkt_drop_counter7_tx_oobi_pkt_drop {
      type oc-yang:counter64;
      description
        "counter for OOBI okt drops";
    }
    leaf counter_slice2_ifg_mac_pool83_tx_oobi_pkt_drop_counter0_tx_oobi_pkt_drop {
      type oc-yang:counter64;
      description
        "counter for OOBI okt drops";
    }
    leaf counter_slice2_ifg_mac_pool83_tx_oobi_pkt_drop_counter1_tx_oobi_pkt_drop {
      type oc-yang:counter64;
      description
        "counter for OOBI okt drops";
    }
    leaf counter_slice2_ifg_mac_pool83_tx_oobi_pkt_drop_counter2_tx_oobi_pkt_drop {
      type oc-yang:counter64;
      description
        "counter for OOBI okt drops";
    }
    leaf counter_slice2_ifg_mac_pool83_tx_oobi_pkt_drop_counter3_tx_oobi_pkt_drop {
      type oc-yang:counter64;
      description
        "counter for OOBI okt drops";
    }
    leaf counter_slice2_ifg_mac_pool83_tx_oobi_pkt_drop_counter4_tx_oobi_pkt_drop {
      type oc-yang:counter64;
      description
        "counter for OOBI okt drops";
    }
    leaf counter_slice2_ifg_mac_pool83_tx_oobi_pkt_drop_counter5_tx_oobi_pkt_drop {
      type oc-yang:counter64;
      description
        "counter for OOBI okt drops";
    }
    leaf counter_slice2_ifg_mac_pool83_tx_oobi_pkt_drop_counter6_tx_oobi_pkt_drop {
      type oc-yang:counter64;
      description
        "counter for OOBI okt drops";
    }
    leaf counter_slice2_ifg_mac_pool83_tx_oobi_pkt_drop_counter7_tx_oobi_pkt_drop {
      type oc-yang:counter64;
      description
        "counter for OOBI okt drops";
    }
    leaf counter_slice2_ifg_mac_pool84_tx_oobi_pkt_drop_counter0_tx_oobi_pkt_drop {
      type oc-yang:counter64;
      description
        "counter for OOBI okt drops";
    }
    leaf counter_slice2_ifg_mac_pool84_tx_oobi_pkt_drop_counter1_tx_oobi_pkt_drop {
      type oc-yang:counter64;
      description
        "counter for OOBI okt drops";
    }
    leaf counter_slice2_ifg_mac_pool84_tx_oobi_pkt_drop_counter2_tx_oobi_pkt_drop {
      type oc-yang:counter64;
      description
        "counter for OOBI okt drops";
    }
    leaf counter_slice2_ifg_mac_pool84_tx_oobi_pkt_drop_counter3_tx_oobi_pkt_drop {
      type oc-yang:counter64;
      description
        "counter for OOBI okt drops";
    }
    leaf counter_slice2_ifg_mac_pool84_tx_oobi_pkt_drop_counter4_tx_oobi_pkt_drop {
      type oc-yang:counter64;
      description
        "counter for OOBI okt drops";
    }
    leaf counter_slice2_ifg_mac_pool84_tx_oobi_pkt_drop_counter5_tx_oobi_pkt_drop {
      type oc-yang:counter64;
      description
        "counter for OOBI okt drops";
    }
    leaf counter_slice2_ifg_mac_pool84_tx_oobi_pkt_drop_counter6_tx_oobi_pkt_drop {
      type oc-yang:counter64;
      description
        "counter for OOBI okt drops";
    }
    leaf counter_slice2_ifg_mac_pool84_tx_oobi_pkt_drop_counter7_tx_oobi_pkt_drop {
      type oc-yang:counter64;
      description
        "counter for OOBI okt drops";
    }
    leaf counter_slice2_ifg_mac_pool85_tx_oobi_pkt_drop_counter0_tx_oobi_pkt_drop {
      type oc-yang:counter64;
      description
        "counter for OOBI okt drops";
    }
    leaf counter_slice2_ifg_mac_pool85_tx_oobi_pkt_drop_counter1_tx_oobi_pkt_drop {
      type oc-yang:counter64;
      description
        "counter for OOBI okt drops";
    }
    leaf counter_slice2_ifg_mac_pool85_tx_oobi_pkt_drop_counter2_tx_oobi_pkt_drop {
      type oc-yang:counter64;
      description
        "counter for OOBI okt drops";
    }
    leaf counter_slice2_ifg_mac_pool85_tx_oobi_pkt_drop_counter3_tx_oobi_pkt_drop {
      type oc-yang:counter64;
      description
        "counter for OOBI okt drops";
    }
    leaf counter_slice2_ifg_mac_pool85_tx_oobi_pkt_drop_counter4_tx_oobi_pkt_drop {
      type oc-yang:counter64;
      description
        "counter for OOBI okt drops";
    }
    leaf counter_slice2_ifg_mac_pool85_tx_oobi_pkt_drop_counter5_tx_oobi_pkt_drop {
      type oc-yang:counter64;
      description
        "counter for OOBI okt drops";
    }
    leaf counter_slice2_ifg_mac_pool85_tx_oobi_pkt_drop_counter6_tx_oobi_pkt_drop {
      type oc-yang:counter64;
      description
        "counter for OOBI okt drops";
    }
    leaf counter_slice2_ifg_mac_pool85_tx_oobi_pkt_drop_counter7_tx_oobi_pkt_drop {
      type oc-yang:counter64;
      description
        "counter for OOBI okt drops";
    }
    leaf counter_slice2_ifg_mac_pool86_tx_oobi_pkt_drop_counter0_tx_oobi_pkt_drop {
      type oc-yang:counter64;
      description
        "counter for OOBI okt drops";
    }
    leaf counter_slice2_ifg_mac_pool86_tx_oobi_pkt_drop_counter1_tx_oobi_pkt_drop {
      type oc-yang:counter64;
      description
        "counter for OOBI okt drops";
    }
    leaf counter_slice2_ifg_mac_pool86_tx_oobi_pkt_drop_counter2_tx_oobi_pkt_drop {
      type oc-yang:counter64;
      description
        "counter for OOBI okt drops";
    }
    leaf counter_slice2_ifg_mac_pool86_tx_oobi_pkt_drop_counter3_tx_oobi_pkt_drop {
      type oc-yang:counter64;
      description
        "counter for OOBI okt drops";
    }
    leaf counter_slice2_ifg_mac_pool86_tx_oobi_pkt_drop_counter4_tx_oobi_pkt_drop {
      type oc-yang:counter64;
      description
        "counter for OOBI okt drops";
    }
    leaf counter_slice2_ifg_mac_pool86_tx_oobi_pkt_drop_counter5_tx_oobi_pkt_drop {
      type oc-yang:counter64;
      description
        "counter for OOBI okt drops";
    }
    leaf counter_slice2_ifg_mac_pool86_tx_oobi_pkt_drop_counter6_tx_oobi_pkt_drop {
      type oc-yang:counter64;
      description
        "counter for OOBI okt drops";
    }
    leaf counter_slice2_ifg_mac_pool86_tx_oobi_pkt_drop_counter7_tx_oobi_pkt_drop {
      type oc-yang:counter64;
      description
        "counter for OOBI okt drops";
    }
    leaf counter_slice2_ifg_mac_pool87_tx_oobi_pkt_drop_counter0_tx_oobi_pkt_drop {
      type oc-yang:counter64;
      description
        "counter for OOBI okt drops";
    }
    leaf counter_slice2_ifg_mac_pool87_tx_oobi_pkt_drop_counter1_tx_oobi_pkt_drop {
      type oc-yang:counter64;
      description
        "counter for OOBI okt drops";
    }
    leaf counter_slice2_ifg_mac_pool87_tx_oobi_pkt_drop_counter2_tx_oobi_pkt_drop {
      type oc-yang:counter64;
      description
        "counter for OOBI okt drops";
    }
    leaf counter_slice2_ifg_mac_pool87_tx_oobi_pkt_drop_counter3_tx_oobi_pkt_drop {
      type oc-yang:counter64;
      description
        "counter for OOBI okt drops";
    }
    leaf counter_slice2_ifg_mac_pool87_tx_oobi_pkt_drop_counter4_tx_oobi_pkt_drop {
      type oc-yang:counter64;
      description
        "counter for OOBI okt drops";
    }
    leaf counter_slice2_ifg_mac_pool87_tx_oobi_pkt_drop_counter5_tx_oobi_pkt_drop {
      type oc-yang:counter64;
      description
        "counter for OOBI okt drops";
    }
    leaf counter_slice2_ifg_mac_pool87_tx_oobi_pkt_drop_counter6_tx_oobi_pkt_drop {
      type oc-yang:counter64;
      description
        "counter for OOBI okt drops";
    }
    leaf counter_slice2_ifg_mac_pool87_tx_oobi_pkt_drop_counter7_tx_oobi_pkt_drop {
      type oc-yang:counter64;
      description
        "counter for OOBI okt drops";
    }
    leaf counter_slice3_ifg_mac_pool80_tx_oobi_pkt_drop_counter0_tx_oobi_pkt_drop {
      type oc-yang:counter64;
      description
        "counter for OOBI okt drops";
    }
    leaf counter_slice3_ifg_mac_pool80_tx_oobi_pkt_drop_counter1_tx_oobi_pkt_drop {
      type oc-yang:counter64;
      description
        "counter for OOBI okt drops";
    }
    leaf counter_slice3_ifg_mac_pool80_tx_oobi_pkt_drop_counter2_tx_oobi_pkt_drop {
      type oc-yang:counter64;
      description
        "counter for OOBI okt drops";
    }
    leaf counter_slice3_ifg_mac_pool80_tx_oobi_pkt_drop_counter3_tx_oobi_pkt_drop {
      type oc-yang:counter64;
      description
        "counter for OOBI okt drops";
    }
    leaf counter_slice3_ifg_mac_pool80_tx_oobi_pkt_drop_counter4_tx_oobi_pkt_drop {
      type oc-yang:counter64;
      description
        "counter for OOBI okt drops";
    }
    leaf counter_slice3_ifg_mac_pool80_tx_oobi_pkt_drop_counter5_tx_oobi_pkt_drop {
      type oc-yang:counter64;
      description
        "counter for OOBI okt drops";
    }
    leaf counter_slice3_ifg_mac_pool80_tx_oobi_pkt_drop_counter6_tx_oobi_pkt_drop {
      type oc-yang:counter64;
      description
        "counter for OOBI okt drops";
    }
    leaf counter_slice3_ifg_mac_pool80_tx_oobi_pkt_drop_counter7_tx_oobi_pkt_drop {
      type oc-yang:counter64;
      description
        "counter for OOBI okt drops";
    }
    leaf counter_slice3_ifg_mac_pool81_tx_oobi_pkt_drop_counter0_tx_oobi_pkt_drop {
      type oc-yang:counter64;
      description
        "counter for OOBI okt drops";
    }
    leaf counter_slice3_ifg_mac_pool81_tx_oobi_pkt_drop_counter1_tx_oobi_pkt_drop {
      type oc-yang:counter64;
      description
        "counter for OOBI okt drops";
    }
    leaf counter_slice3_ifg_mac_pool81_tx_oobi_pkt_drop_counter2_tx_oobi_pkt_drop {
      type oc-yang:counter64;
      description
        "counter for OOBI okt drops";
    }
    leaf counter_slice3_ifg_mac_pool81_tx_oobi_pkt_drop_counter3_tx_oobi_pkt_drop {
      type oc-yang:counter64;
      description
        "counter for OOBI okt drops";
    }
    leaf counter_slice3_ifg_mac_pool81_tx_oobi_pkt_drop_counter4_tx_oobi_pkt_drop {
      type oc-yang:counter64;
      description
        "counter for OOBI okt drops";
    }
    leaf counter_slice3_ifg_mac_pool81_tx_oobi_pkt_drop_counter5_tx_oobi_pkt_drop {
      type oc-yang:counter64;
      description
        "counter for OOBI okt drops";
    }
    leaf counter_slice3_ifg_mac_pool81_tx_oobi_pkt_drop_counter6_tx_oobi_pkt_drop {
      type oc-yang:counter64;
      description
        "counter for OOBI okt drops";
    }
    leaf counter_slice3_ifg_mac_pool81_tx_oobi_pkt_drop_counter7_tx_oobi_pkt_drop {
      type oc-yang:counter64;
      description
        "counter for OOBI okt drops";
    }
    leaf counter_slice3_ifg_mac_pool82_tx_oobi_pkt_drop_counter0_tx_oobi_pkt_drop {
      type oc-yang:counter64;
      description
        "counter for OOBI okt drops";
    }
    leaf counter_slice3_ifg_mac_pool82_tx_oobi_pkt_drop_counter1_tx_oobi_pkt_drop {
      type oc-yang:counter64;
      description
        "counter for OOBI okt drops";
    }
    leaf counter_slice3_ifg_mac_pool82_tx_oobi_pkt_drop_counter2_tx_oobi_pkt_drop {
      type oc-yang:counter64;
      description
        "counter for OOBI okt drops";
    }
    leaf counter_slice3_ifg_mac_pool82_tx_oobi_pkt_drop_counter3_tx_oobi_pkt_drop {
      type oc-yang:counter64;
      description
        "counter for OOBI okt drops";
    }
    leaf counter_slice3_ifg_mac_pool82_tx_oobi_pkt_drop_counter4_tx_oobi_pkt_drop {
      type oc-yang:counter64;
      description
        "counter for OOBI okt drops";
    }
    leaf counter_slice3_ifg_mac_pool82_tx_oobi_pkt_drop_counter5_tx_oobi_pkt_drop {
      type oc-yang:counter64;
      description
        "counter for OOBI okt drops";
    }
    leaf counter_slice3_ifg_mac_pool82_tx_oobi_pkt_drop_counter6_tx_oobi_pkt_drop {
      type oc-yang:counter64;
      description
        "counter for OOBI okt drops";
    }
    leaf counter_slice3_ifg_mac_pool82_tx_oobi_pkt_drop_counter7_tx_oobi_pkt_drop {
      type oc-yang:counter64;
      description
        "counter for OOBI okt drops";
    }
    leaf counter_slice3_ifg_mac_pool83_tx_oobi_pkt_drop_counter0_tx_oobi_pkt_drop {
      type oc-yang:counter64;
      description
        "counter for OOBI okt drops";
    }
    leaf counter_slice3_ifg_mac_pool83_tx_oobi_pkt_drop_counter1_tx_oobi_pkt_drop {
      type oc-yang:counter64;
      description
        "counter for OOBI okt drops";
    }
    leaf counter_slice3_ifg_mac_pool83_tx_oobi_pkt_drop_counter2_tx_oobi_pkt_drop {
      type oc-yang:counter64;
      description
        "counter for OOBI okt drops";
    }
    leaf counter_slice3_ifg_mac_pool83_tx_oobi_pkt_drop_counter3_tx_oobi_pkt_drop {
      type oc-yang:counter64;
      description
        "counter for OOBI okt drops";
    }
    leaf counter_slice3_ifg_mac_pool83_tx_oobi_pkt_drop_counter4_tx_oobi_pkt_drop {
      type oc-yang:counter64;
      description
        "counter for OOBI okt drops";
    }
    leaf counter_slice3_ifg_mac_pool83_tx_oobi_pkt_drop_counter5_tx_oobi_pkt_drop {
      type oc-yang:counter64;
      description
        "counter for OOBI okt drops";
    }
    leaf counter_slice3_ifg_mac_pool83_tx_oobi_pkt_drop_counter6_tx_oobi_pkt_drop {
      type oc-yang:counter64;
      description
        "counter for OOBI okt drops";
    }
    leaf counter_slice3_ifg_mac_pool83_tx_oobi_pkt_drop_counter7_tx_oobi_pkt_drop {
      type oc-yang:counter64;
      description
        "counter for OOBI okt drops";
    }
    leaf counter_slice3_ifg_mac_pool84_tx_oobi_pkt_drop_counter0_tx_oobi_pkt_drop {
      type oc-yang:counter64;
      description
        "counter for OOBI okt drops";
    }
    leaf counter_slice3_ifg_mac_pool84_tx_oobi_pkt_drop_counter1_tx_oobi_pkt_drop {
      type oc-yang:counter64;
      description
        "counter for OOBI okt drops";
    }
    leaf counter_slice3_ifg_mac_pool84_tx_oobi_pkt_drop_counter2_tx_oobi_pkt_drop {
      type oc-yang:counter64;
      description
        "counter for OOBI okt drops";
    }
    leaf counter_slice3_ifg_mac_pool84_tx_oobi_pkt_drop_counter3_tx_oobi_pkt_drop {
      type oc-yang:counter64;
      description
        "counter for OOBI okt drops";
    }
    leaf counter_slice3_ifg_mac_pool84_tx_oobi_pkt_drop_counter4_tx_oobi_pkt_drop {
      type oc-yang:counter64;
      description
        "counter for OOBI okt drops";
    }
    leaf counter_slice3_ifg_mac_pool84_tx_oobi_pkt_drop_counter5_tx_oobi_pkt_drop {
      type oc-yang:counter64;
      description
        "counter for OOBI okt drops";
    }
    leaf counter_slice3_ifg_mac_pool84_tx_oobi_pkt_drop_counter6_tx_oobi_pkt_drop {
      type oc-yang:counter64;
      description
        "counter for OOBI okt drops";
    }
    leaf counter_slice3_ifg_mac_pool84_tx_oobi_pkt_drop_counter7_tx_oobi_pkt_drop {
      type oc-yang:counter64;
      description
        "counter for OOBI okt drops";
    }
    leaf counter_slice3_ifg_mac_pool85_tx_oobi_pkt_drop_counter0_tx_oobi_pkt_drop {
      type oc-yang:counter64;
      description
        "counter for OOBI okt drops";
    }
    leaf counter_slice3_ifg_mac_pool85_tx_oobi_pkt_drop_counter1_tx_oobi_pkt_drop {
      type oc-yang:counter64;
      description
        "counter for OOBI okt drops";
    }
    leaf counter_slice3_ifg_mac_pool85_tx_oobi_pkt_drop_counter2_tx_oobi_pkt_drop {
      type oc-yang:counter64;
      description
        "counter for OOBI okt drops";
    }
    leaf counter_slice3_ifg_mac_pool85_tx_oobi_pkt_drop_counter3_tx_oobi_pkt_drop {
      type oc-yang:counter64;
      description
        "counter for OOBI okt drops";
    }
    leaf counter_slice3_ifg_mac_pool85_tx_oobi_pkt_drop_counter4_tx_oobi_pkt_drop {
      type oc-yang:counter64;
      description
        "counter for OOBI okt drops";
    }
    leaf counter_slice3_ifg_mac_pool85_tx_oobi_pkt_drop_counter5_tx_oobi_pkt_drop {
      type oc-yang:counter64;
      description
        "counter for OOBI okt drops";
    }
    leaf counter_slice3_ifg_mac_pool85_tx_oobi_pkt_drop_counter6_tx_oobi_pkt_drop {
      type oc-yang:counter64;
      description
        "counter for OOBI okt drops";
    }
    leaf counter_slice3_ifg_mac_pool85_tx_oobi_pkt_drop_counter7_tx_oobi_pkt_drop {
      type oc-yang:counter64;
      description
        "counter for OOBI okt drops";
    }
    leaf counter_slice3_ifg_mac_pool86_tx_oobi_pkt_drop_counter0_tx_oobi_pkt_drop {
      type oc-yang:counter64;
      description
        "counter for OOBI okt drops";
    }
    leaf counter_slice3_ifg_mac_pool86_tx_oobi_pkt_drop_counter1_tx_oobi_pkt_drop {
      type oc-yang:counter64;
      description
        "counter for OOBI okt drops";
    }
    leaf counter_slice3_ifg_mac_pool86_tx_oobi_pkt_drop_counter2_tx_oobi_pkt_drop {
      type oc-yang:counter64;
      description
        "counter for OOBI okt drops";
    }
    leaf counter_slice3_ifg_mac_pool86_tx_oobi_pkt_drop_counter3_tx_oobi_pkt_drop {
      type oc-yang:counter64;
      description
        "counter for OOBI okt drops";
    }
    leaf counter_slice3_ifg_mac_pool86_tx_oobi_pkt_drop_counter4_tx_oobi_pkt_drop {
      type oc-yang:counter64;
      description
        "counter for OOBI okt drops";
    }
    leaf counter_slice3_ifg_mac_pool86_tx_oobi_pkt_drop_counter5_tx_oobi_pkt_drop {
      type oc-yang:counter64;
      description
        "counter for OOBI okt drops";
    }
    leaf counter_slice3_ifg_mac_pool86_tx_oobi_pkt_drop_counter6_tx_oobi_pkt_drop {
      type oc-yang:counter64;
      description
        "counter for OOBI okt drops";
    }
    leaf counter_slice3_ifg_mac_pool86_tx_oobi_pkt_drop_counter7_tx_oobi_pkt_drop {
      type oc-yang:counter64;
      description
        "counter for OOBI okt drops";
    }
    leaf counter_slice3_ifg_mac_pool87_tx_oobi_pkt_drop_counter0_tx_oobi_pkt_drop {
      type oc-yang:counter64;
      description
        "counter for OOBI okt drops";
    }
    leaf counter_slice3_ifg_mac_pool87_tx_oobi_pkt_drop_counter1_tx_oobi_pkt_drop {
      type oc-yang:counter64;
      description
        "counter for OOBI okt drops";
    }
    leaf counter_slice3_ifg_mac_pool87_tx_oobi_pkt_drop_counter2_tx_oobi_pkt_drop {
      type oc-yang:counter64;
      description
        "counter for OOBI okt drops";
    }
    leaf counter_slice3_ifg_mac_pool87_tx_oobi_pkt_drop_counter3_tx_oobi_pkt_drop {
      type oc-yang:counter64;
      description
        "counter for OOBI okt drops";
    }
    leaf counter_slice3_ifg_mac_pool87_tx_oobi_pkt_drop_counter4_tx_oobi_pkt_drop {
      type oc-yang:counter64;
      description
        "counter for OOBI okt drops";
    }
    leaf counter_slice3_ifg_mac_pool87_tx_oobi_pkt_drop_counter5_tx_oobi_pkt_drop {
      type oc-yang:counter64;
      description
        "counter for OOBI okt drops";
    }
    leaf counter_slice3_ifg_mac_pool87_tx_oobi_pkt_drop_counter6_tx_oobi_pkt_drop {
      type oc-yang:counter64;
      description
        "counter for OOBI okt drops";
    }
    leaf counter_slice3_ifg_mac_pool87_tx_oobi_pkt_drop_counter7_tx_oobi_pkt_drop {
      type oc-yang:counter64;
      description
        "counter for OOBI okt drops";
    }
    leaf counter_slice4_ifg_mac_pool80_tx_oobi_pkt_drop_counter0_tx_oobi_pkt_drop {
      type oc-yang:counter64;
      description
        "counter for OOBI okt drops";
    }
    leaf counter_slice4_ifg_mac_pool80_tx_oobi_pkt_drop_counter1_tx_oobi_pkt_drop {
      type oc-yang:counter64;
      description
        "counter for OOBI okt drops";
    }
    leaf counter_slice4_ifg_mac_pool80_tx_oobi_pkt_drop_counter2_tx_oobi_pkt_drop {
      type oc-yang:counter64;
      description
        "counter for OOBI okt drops";
    }
    leaf counter_slice4_ifg_mac_pool80_tx_oobi_pkt_drop_counter3_tx_oobi_pkt_drop {
      type oc-yang:counter64;
      description
        "counter for OOBI okt drops";
    }
    leaf counter_slice4_ifg_mac_pool80_tx_oobi_pkt_drop_counter4_tx_oobi_pkt_drop {
      type oc-yang:counter64;
      description
        "counter for OOBI okt drops";
    }
    leaf counter_slice4_ifg_mac_pool80_tx_oobi_pkt_drop_counter5_tx_oobi_pkt_drop {
      type oc-yang:counter64;
      description
        "counter for OOBI okt drops";
    }
    leaf counter_slice4_ifg_mac_pool80_tx_oobi_pkt_drop_counter6_tx_oobi_pkt_drop {
      type oc-yang:counter64;
      description
        "counter for OOBI okt drops";
    }
    leaf counter_slice4_ifg_mac_pool80_tx_oobi_pkt_drop_counter7_tx_oobi_pkt_drop {
      type oc-yang:counter64;
      description
        "counter for OOBI okt drops";
    }
    leaf counter_slice4_ifg_mac_pool81_tx_oobi_pkt_drop_counter0_tx_oobi_pkt_drop {
      type oc-yang:counter64;
      description
        "counter for OOBI okt drops";
    }
    leaf counter_slice4_ifg_mac_pool81_tx_oobi_pkt_drop_counter1_tx_oobi_pkt_drop {
      type oc-yang:counter64;
      description
        "counter for OOBI okt drops";
    }
    leaf counter_slice4_ifg_mac_pool81_tx_oobi_pkt_drop_counter2_tx_oobi_pkt_drop {
      type oc-yang:counter64;
      description
        "counter for OOBI okt drops";
    }
    leaf counter_slice4_ifg_mac_pool81_tx_oobi_pkt_drop_counter3_tx_oobi_pkt_drop {
      type oc-yang:counter64;
      description
        "counter for OOBI okt drops";
    }
    leaf counter_slice4_ifg_mac_pool81_tx_oobi_pkt_drop_counter4_tx_oobi_pkt_drop {
      type oc-yang:counter64;
      description
        "counter for OOBI okt drops";
    }
    leaf counter_slice4_ifg_mac_pool81_tx_oobi_pkt_drop_counter5_tx_oobi_pkt_drop {
      type oc-yang:counter64;
      description
        "counter for OOBI okt drops";
    }
    leaf counter_slice4_ifg_mac_pool81_tx_oobi_pkt_drop_counter6_tx_oobi_pkt_drop {
      type oc-yang:counter64;
      description
        "counter for OOBI okt drops";
    }
    leaf counter_slice4_ifg_mac_pool81_tx_oobi_pkt_drop_counter7_tx_oobi_pkt_drop {
      type oc-yang:counter64;
      description
        "counter for OOBI okt drops";
    }
    leaf counter_slice4_ifg_mac_pool82_tx_oobi_pkt_drop_counter0_tx_oobi_pkt_drop {
      type oc-yang:counter64;
      description
        "counter for OOBI okt drops";
    }
    leaf counter_slice4_ifg_mac_pool82_tx_oobi_pkt_drop_counter1_tx_oobi_pkt_drop {
      type oc-yang:counter64;
      description
        "counter for OOBI okt drops";
    }
    leaf counter_slice4_ifg_mac_pool82_tx_oobi_pkt_drop_counter2_tx_oobi_pkt_drop {
      type oc-yang:counter64;
      description
        "counter for OOBI okt drops";
    }
    leaf counter_slice4_ifg_mac_pool82_tx_oobi_pkt_drop_counter3_tx_oobi_pkt_drop {
      type oc-yang:counter64;
      description
        "counter for OOBI okt drops";
    }
    leaf counter_slice4_ifg_mac_pool82_tx_oobi_pkt_drop_counter4_tx_oobi_pkt_drop {
      type oc-yang:counter64;
      description
        "counter for OOBI okt drops";
    }
    leaf counter_slice4_ifg_mac_pool82_tx_oobi_pkt_drop_counter5_tx_oobi_pkt_drop {
      type oc-yang:counter64;
      description
        "counter for OOBI okt drops";
    }
    leaf counter_slice4_ifg_mac_pool82_tx_oobi_pkt_drop_counter6_tx_oobi_pkt_drop {
      type oc-yang:counter64;
      description
        "counter for OOBI okt drops";
    }
    leaf counter_slice4_ifg_mac_pool82_tx_oobi_pkt_drop_counter7_tx_oobi_pkt_drop {
      type oc-yang:counter64;
      description
        "counter for OOBI okt drops";
    }
    leaf counter_slice4_ifg_mac_pool83_tx_oobi_pkt_drop_counter0_tx_oobi_pkt_drop {
      type oc-yang:counter64;
      description
        "counter for OOBI okt drops";
    }
    leaf counter_slice4_ifg_mac_pool83_tx_oobi_pkt_drop_counter1_tx_oobi_pkt_drop {
      type oc-yang:counter64;
      description
        "counter for OOBI okt drops";
    }
    leaf counter_slice4_ifg_mac_pool83_tx_oobi_pkt_drop_counter2_tx_oobi_pkt_drop {
      type oc-yang:counter64;
      description
        "counter for OOBI okt drops";
    }
    leaf counter_slice4_ifg_mac_pool83_tx_oobi_pkt_drop_counter3_tx_oobi_pkt_drop {
      type oc-yang:counter64;
      description
        "counter for OOBI okt drops";
    }
    leaf counter_slice4_ifg_mac_pool83_tx_oobi_pkt_drop_counter4_tx_oobi_pkt_drop {
      type oc-yang:counter64;
      description
        "counter for OOBI okt drops";
    }
    leaf counter_slice4_ifg_mac_pool83_tx_oobi_pkt_drop_counter5_tx_oobi_pkt_drop {
      type oc-yang:counter64;
      description
        "counter for OOBI okt drops";
    }
    leaf counter_slice4_ifg_mac_pool83_tx_oobi_pkt_drop_counter6_tx_oobi_pkt_drop {
      type oc-yang:counter64;
      description
        "counter for OOBI okt drops";
    }
    leaf counter_slice4_ifg_mac_pool83_tx_oobi_pkt_drop_counter7_tx_oobi_pkt_drop {
      type oc-yang:counter64;
      description
        "counter for OOBI okt drops";
    }
    leaf counter_slice4_ifg_mac_pool84_tx_oobi_pkt_drop_counter0_tx_oobi_pkt_drop {
      type oc-yang:counter64;
      description
        "counter for OOBI okt drops";
    }
    leaf counter_slice4_ifg_mac_pool84_tx_oobi_pkt_drop_counter1_tx_oobi_pkt_drop {
      type oc-yang:counter64;
      description
        "counter for OOBI okt drops";
    }
    leaf counter_slice4_ifg_mac_pool84_tx_oobi_pkt_drop_counter2_tx_oobi_pkt_drop {
      type oc-yang:counter64;
      description
        "counter for OOBI okt drops";
    }
    leaf counter_slice4_ifg_mac_pool84_tx_oobi_pkt_drop_counter3_tx_oobi_pkt_drop {
      type oc-yang:counter64;
      description
        "counter for OOBI okt drops";
    }
    leaf counter_slice4_ifg_mac_pool84_tx_oobi_pkt_drop_counter4_tx_oobi_pkt_drop {
      type oc-yang:counter64;
      description
        "counter for OOBI okt drops";
    }
    leaf counter_slice4_ifg_mac_pool84_tx_oobi_pkt_drop_counter5_tx_oobi_pkt_drop {
      type oc-yang:counter64;
      description
        "counter for OOBI okt drops";
    }
    leaf counter_slice4_ifg_mac_pool84_tx_oobi_pkt_drop_counter6_tx_oobi_pkt_drop {
      type oc-yang:counter64;
      description
        "counter for OOBI okt drops";
    }
    leaf counter_slice4_ifg_mac_pool84_tx_oobi_pkt_drop_counter7_tx_oobi_pkt_drop {
      type oc-yang:counter64;
      description
        "counter for OOBI okt drops";
    }
    leaf counter_slice4_ifg_mac_pool85_tx_oobi_pkt_drop_counter0_tx_oobi_pkt_drop {
      type oc-yang:counter64;
      description
        "counter for OOBI okt drops";
    }
    leaf counter_slice4_ifg_mac_pool85_tx_oobi_pkt_drop_counter1_tx_oobi_pkt_drop {
      type oc-yang:counter64;
      description
        "counter for OOBI okt drops";
    }
    leaf counter_slice4_ifg_mac_pool85_tx_oobi_pkt_drop_counter2_tx_oobi_pkt_drop {
      type oc-yang:counter64;
      description
        "counter for OOBI okt drops";
    }
    leaf counter_slice4_ifg_mac_pool85_tx_oobi_pkt_drop_counter3_tx_oobi_pkt_drop {
      type oc-yang:counter64;
      description
        "counter for OOBI okt drops";
    }
    leaf counter_slice4_ifg_mac_pool85_tx_oobi_pkt_drop_counter4_tx_oobi_pkt_drop {
      type oc-yang:counter64;
      description
        "counter for OOBI okt drops";
    }
    leaf counter_slice4_ifg_mac_pool85_tx_oobi_pkt_drop_counter5_tx_oobi_pkt_drop {
      type oc-yang:counter64;
      description
        "counter for OOBI okt drops";
    }
    leaf counter_slice4_ifg_mac_pool85_tx_oobi_pkt_drop_counter6_tx_oobi_pkt_drop {
      type oc-yang:counter64;
      description
        "counter for OOBI okt drops";
    }
    leaf counter_slice4_ifg_mac_pool85_tx_oobi_pkt_drop_counter7_tx_oobi_pkt_drop {
      type oc-yang:counter64;
      description
        "counter for OOBI okt drops";
    }
    leaf counter_slice4_ifg_mac_pool86_tx_oobi_pkt_drop_counter0_tx_oobi_pkt_drop {
      type oc-yang:counter64;
      description
        "counter for OOBI okt drops";
    }
    leaf counter_slice4_ifg_mac_pool86_tx_oobi_pkt_drop_counter1_tx_oobi_pkt_drop {
      type oc-yang:counter64;
      description
        "counter for OOBI okt drops";
    }
    leaf counter_slice4_ifg_mac_pool86_tx_oobi_pkt_drop_counter2_tx_oobi_pkt_drop {
      type oc-yang:counter64;
      description
        "counter for OOBI okt drops";
    }
    leaf counter_slice4_ifg_mac_pool86_tx_oobi_pkt_drop_counter3_tx_oobi_pkt_drop {
      type oc-yang:counter64;
      description
        "counter for OOBI okt drops";
    }
    leaf counter_slice4_ifg_mac_pool86_tx_oobi_pkt_drop_counter4_tx_oobi_pkt_drop {
      type oc-yang:counter64;
      description
        "counter for OOBI okt drops";
    }
    leaf counter_slice4_ifg_mac_pool86_tx_oobi_pkt_drop_counter5_tx_oobi_pkt_drop {
      type oc-yang:counter64;
      description
        "counter for OOBI okt drops";
    }
    leaf counter_slice4_ifg_mac_pool86_tx_oobi_pkt_drop_counter6_tx_oobi_pkt_drop {
      type oc-yang:counter64;
      description
        "counter for OOBI okt drops";
    }
    leaf counter_slice4_ifg_mac_pool86_tx_oobi_pkt_drop_counter7_tx_oobi_pkt_drop {
      type oc-yang:counter64;
      description
        "counter for OOBI okt drops";
    }
    leaf counter_slice4_ifg_mac_pool87_tx_oobi_pkt_drop_counter0_tx_oobi_pkt_drop {
      type oc-yang:counter64;
      description
        "counter for OOBI okt drops";
    }
    leaf counter_slice4_ifg_mac_pool87_tx_oobi_pkt_drop_counter1_tx_oobi_pkt_drop {
      type oc-yang:counter64;
      description
        "counter for OOBI okt drops";
    }
    leaf counter_slice4_ifg_mac_pool87_tx_oobi_pkt_drop_counter2_tx_oobi_pkt_drop {
      type oc-yang:counter64;
      description
        "counter for OOBI okt drops";
    }
    leaf counter_slice4_ifg_mac_pool87_tx_oobi_pkt_drop_counter3_tx_oobi_pkt_drop {
      type oc-yang:counter64;
      description
        "counter for OOBI okt drops";
    }
    leaf counter_slice4_ifg_mac_pool87_tx_oobi_pkt_drop_counter4_tx_oobi_pkt_drop {
      type oc-yang:counter64;
      description
        "counter for OOBI okt drops";
    }
    leaf counter_slice4_ifg_mac_pool87_tx_oobi_pkt_drop_counter5_tx_oobi_pkt_drop {
      type oc-yang:counter64;
      description
        "counter for OOBI okt drops";
    }
    leaf counter_slice4_ifg_mac_pool87_tx_oobi_pkt_drop_counter6_tx_oobi_pkt_drop {
      type oc-yang:counter64;
      description
        "counter for OOBI okt drops";
    }
    leaf counter_slice4_ifg_mac_pool87_tx_oobi_pkt_drop_counter7_tx_oobi_pkt_drop {
      type oc-yang:counter64;
      description
        "counter for OOBI okt drops";
    }
    leaf counter_slice5_ifg_mac_pool80_tx_oobi_pkt_drop_counter0_tx_oobi_pkt_drop {
      type oc-yang:counter64;
      description
        "counter for OOBI okt drops";
    }
    leaf counter_slice5_ifg_mac_pool80_tx_oobi_pkt_drop_counter1_tx_oobi_pkt_drop {
      type oc-yang:counter64;
      description
        "counter for OOBI okt drops";
    }
    leaf counter_slice5_ifg_mac_pool80_tx_oobi_pkt_drop_counter2_tx_oobi_pkt_drop {
      type oc-yang:counter64;
      description
        "counter for OOBI okt drops";
    }
    leaf counter_slice5_ifg_mac_pool80_tx_oobi_pkt_drop_counter3_tx_oobi_pkt_drop {
      type oc-yang:counter64;
      description
        "counter for OOBI okt drops";
    }
    leaf counter_slice5_ifg_mac_pool80_tx_oobi_pkt_drop_counter4_tx_oobi_pkt_drop {
      type oc-yang:counter64;
      description
        "counter for OOBI okt drops";
    }
    leaf counter_slice5_ifg_mac_pool80_tx_oobi_pkt_drop_counter5_tx_oobi_pkt_drop {
      type oc-yang:counter64;
      description
        "counter for OOBI okt drops";
    }
    leaf counter_slice5_ifg_mac_pool80_tx_oobi_pkt_drop_counter6_tx_oobi_pkt_drop {
      type oc-yang:counter64;
      description
        "counter for OOBI okt drops";
    }
    leaf counter_slice5_ifg_mac_pool80_tx_oobi_pkt_drop_counter7_tx_oobi_pkt_drop {
      type oc-yang:counter64;
      description
        "counter for OOBI okt drops";
    }
    leaf counter_slice5_ifg_mac_pool81_tx_oobi_pkt_drop_counter0_tx_oobi_pkt_drop {
      type oc-yang:counter64;
      description
        "counter for OOBI okt drops";
    }
    leaf counter_slice5_ifg_mac_pool81_tx_oobi_pkt_drop_counter1_tx_oobi_pkt_drop {
      type oc-yang:counter64;
      description
        "counter for OOBI okt drops";
    }
    leaf counter_slice5_ifg_mac_pool81_tx_oobi_pkt_drop_counter2_tx_oobi_pkt_drop {
      type oc-yang:counter64;
      description
        "counter for OOBI okt drops";
    }
    leaf counter_slice5_ifg_mac_pool81_tx_oobi_pkt_drop_counter3_tx_oobi_pkt_drop {
      type oc-yang:counter64;
      description
        "counter for OOBI okt drops";
    }
    leaf counter_slice5_ifg_mac_pool81_tx_oobi_pkt_drop_counter4_tx_oobi_pkt_drop {
      type oc-yang:counter64;
      description
        "counter for OOBI okt drops";
    }
    leaf counter_slice5_ifg_mac_pool81_tx_oobi_pkt_drop_counter5_tx_oobi_pkt_drop {
      type oc-yang:counter64;
      description
        "counter for OOBI okt drops";
    }
    leaf counter_slice5_ifg_mac_pool81_tx_oobi_pkt_drop_counter6_tx_oobi_pkt_drop {
      type oc-yang:counter64;
      description
        "counter for OOBI okt drops";
    }
    leaf counter_slice5_ifg_mac_pool81_tx_oobi_pkt_drop_counter7_tx_oobi_pkt_drop {
      type oc-yang:counter64;
      description
        "counter for OOBI okt drops";
    }
    leaf counter_slice5_ifg_mac_pool82_tx_oobi_pkt_drop_counter0_tx_oobi_pkt_drop {
      type oc-yang:counter64;
      description
        "counter for OOBI okt drops";
    }
    leaf counter_slice5_ifg_mac_pool82_tx_oobi_pkt_drop_counter1_tx_oobi_pkt_drop {
      type oc-yang:counter64;
      description
        "counter for OOBI okt drops";
    }
    leaf counter_slice5_ifg_mac_pool82_tx_oobi_pkt_drop_counter2_tx_oobi_pkt_drop {
      type oc-yang:counter64;
      description
        "counter for OOBI okt drops";
    }
    leaf counter_slice5_ifg_mac_pool82_tx_oobi_pkt_drop_counter3_tx_oobi_pkt_drop {
      type oc-yang:counter64;
      description
        "counter for OOBI okt drops";
    }
    leaf counter_slice5_ifg_mac_pool82_tx_oobi_pkt_drop_counter4_tx_oobi_pkt_drop {
      type oc-yang:counter64;
      description
        "counter for OOBI okt drops";
    }
    leaf counter_slice5_ifg_mac_pool82_tx_oobi_pkt_drop_counter5_tx_oobi_pkt_drop {
      type oc-yang:counter64;
      description
        "counter for OOBI okt drops";
    }
    leaf counter_slice5_ifg_mac_pool82_tx_oobi_pkt_drop_counter6_tx_oobi_pkt_drop {
      type oc-yang:counter64;
      description
        "counter for OOBI okt drops";
    }
    leaf counter_slice5_ifg_mac_pool82_tx_oobi_pkt_drop_counter7_tx_oobi_pkt_drop {
      type oc-yang:counter64;
      description
        "counter for OOBI okt drops";
    }
    leaf counter_slice5_ifg_mac_pool83_tx_oobi_pkt_drop_counter0_tx_oobi_pkt_drop {
      type oc-yang:counter64;
      description
        "counter for OOBI okt drops";
    }
    leaf counter_slice5_ifg_mac_pool83_tx_oobi_pkt_drop_counter1_tx_oobi_pkt_drop {
      type oc-yang:counter64;
      description
        "counter for OOBI okt drops";
    }
    leaf counter_slice5_ifg_mac_pool83_tx_oobi_pkt_drop_counter2_tx_oobi_pkt_drop {
      type oc-yang:counter64;
      description
        "counter for OOBI okt drops";
    }
    leaf counter_slice5_ifg_mac_pool83_tx_oobi_pkt_drop_counter3_tx_oobi_pkt_drop {
      type oc-yang:counter64;
      description
        "counter for OOBI okt drops";
    }
    leaf counter_slice5_ifg_mac_pool83_tx_oobi_pkt_drop_counter4_tx_oobi_pkt_drop {
      type oc-yang:counter64;
      description
        "counter for OOBI okt drops";
    }
    leaf counter_slice5_ifg_mac_pool83_tx_oobi_pkt_drop_counter5_tx_oobi_pkt_drop {
      type oc-yang:counter64;
      description
        "counter for OOBI okt drops";
    }
    leaf counter_slice5_ifg_mac_pool83_tx_oobi_pkt_drop_counter6_tx_oobi_pkt_drop {
      type oc-yang:counter64;
      description
        "counter for OOBI okt drops";
    }
    leaf counter_slice5_ifg_mac_pool83_tx_oobi_pkt_drop_counter7_tx_oobi_pkt_drop {
      type oc-yang:counter64;
      description
        "counter for OOBI okt drops";
    }
    leaf counter_slice5_ifg_mac_pool84_tx_oobi_pkt_drop_counter0_tx_oobi_pkt_drop {
      type oc-yang:counter64;
      description
        "counter for OOBI okt drops";
    }
    leaf counter_slice5_ifg_mac_pool84_tx_oobi_pkt_drop_counter1_tx_oobi_pkt_drop {
      type oc-yang:counter64;
      description
        "counter for OOBI okt drops";
    }
    leaf counter_slice5_ifg_mac_pool84_tx_oobi_pkt_drop_counter2_tx_oobi_pkt_drop {
      type oc-yang:counter64;
      description
        "counter for OOBI okt drops";
    }
    leaf counter_slice5_ifg_mac_pool84_tx_oobi_pkt_drop_counter3_tx_oobi_pkt_drop {
      type oc-yang:counter64;
      description
        "counter for OOBI okt drops";
    }
    leaf counter_slice5_ifg_mac_pool84_tx_oobi_pkt_drop_counter4_tx_oobi_pkt_drop {
      type oc-yang:counter64;
      description
        "counter for OOBI okt drops";
    }
    leaf counter_slice5_ifg_mac_pool84_tx_oobi_pkt_drop_counter5_tx_oobi_pkt_drop {
      type oc-yang:counter64;
      description
        "counter for OOBI okt drops";
    }
    leaf counter_slice5_ifg_mac_pool84_tx_oobi_pkt_drop_counter6_tx_oobi_pkt_drop {
      type oc-yang:counter64;
      description
        "counter for OOBI okt drops";
    }
    leaf counter_slice5_ifg_mac_pool84_tx_oobi_pkt_drop_counter7_tx_oobi_pkt_drop {
      type oc-yang:counter64;
      description
        "counter for OOBI okt drops";
    }
    leaf counter_slice5_ifg_mac_pool85_tx_oobi_pkt_drop_counter0_tx_oobi_pkt_drop {
      type oc-yang:counter64;
      description
        "counter for OOBI okt drops";
    }
    leaf counter_slice5_ifg_mac_pool85_tx_oobi_pkt_drop_counter1_tx_oobi_pkt_drop {
      type oc-yang:counter64;
      description
        "counter for OOBI okt drops";
    }
    leaf counter_slice5_ifg_mac_pool85_tx_oobi_pkt_drop_counter2_tx_oobi_pkt_drop {
      type oc-yang:counter64;
      description
        "counter for OOBI okt drops";
    }
    leaf counter_slice5_ifg_mac_pool85_tx_oobi_pkt_drop_counter3_tx_oobi_pkt_drop {
      type oc-yang:counter64;
      description
        "counter for OOBI okt drops";
    }
    leaf counter_slice5_ifg_mac_pool85_tx_oobi_pkt_drop_counter4_tx_oobi_pkt_drop {
      type oc-yang:counter64;
      description
        "counter for OOBI okt drops";
    }
    leaf counter_slice5_ifg_mac_pool85_tx_oobi_pkt_drop_counter5_tx_oobi_pkt_drop {
      type oc-yang:counter64;
      description
        "counter for OOBI okt drops";
    }
    leaf counter_slice5_ifg_mac_pool85_tx_oobi_pkt_drop_counter6_tx_oobi_pkt_drop {
      type oc-yang:counter64;
      description
        "counter for OOBI okt drops";
    }
    leaf counter_slice5_ifg_mac_pool85_tx_oobi_pkt_drop_counter7_tx_oobi_pkt_drop {
      type oc-yang:counter64;
      description
        "counter for OOBI okt drops";
    }
    leaf counter_slice5_ifg_mac_pool86_tx_oobi_pkt_drop_counter0_tx_oobi_pkt_drop {
      type oc-yang:counter64;
      description
        "counter for OOBI okt drops";
    }
    leaf counter_slice5_ifg_mac_pool86_tx_oobi_pkt_drop_counter1_tx_oobi_pkt_drop {
      type oc-yang:counter64;
      description
        "counter for OOBI okt drops";
    }
    leaf counter_slice5_ifg_mac_pool86_tx_oobi_pkt_drop_counter2_tx_oobi_pkt_drop {
      type oc-yang:counter64;
      description
        "counter for OOBI okt drops";
    }
    leaf counter_slice5_ifg_mac_pool86_tx_oobi_pkt_drop_counter3_tx_oobi_pkt_drop {
      type oc-yang:counter64;
      description
        "counter for OOBI okt drops";
    }
    leaf counter_slice5_ifg_mac_pool86_tx_oobi_pkt_drop_counter4_tx_oobi_pkt_drop {
      type oc-yang:counter64;
      description
        "counter for OOBI okt drops";
    }
    leaf counter_slice5_ifg_mac_pool86_tx_oobi_pkt_drop_counter5_tx_oobi_pkt_drop {
      type oc-yang:counter64;
      description
        "counter for OOBI okt drops";
    }
    leaf counter_slice5_ifg_mac_pool86_tx_oobi_pkt_drop_counter6_tx_oobi_pkt_drop {
      type oc-yang:counter64;
      description
        "counter for OOBI okt drops";
    }
    leaf counter_slice5_ifg_mac_pool86_tx_oobi_pkt_drop_counter7_tx_oobi_pkt_drop {
      type oc-yang:counter64;
      description
        "counter for OOBI okt drops";
    }
    leaf counter_slice5_ifg_mac_pool87_tx_oobi_pkt_drop_counter0_tx_oobi_pkt_drop {
      type oc-yang:counter64;
      description
        "counter for OOBI okt drops";
    }
    leaf counter_slice5_ifg_mac_pool87_tx_oobi_pkt_drop_counter1_tx_oobi_pkt_drop {
      type oc-yang:counter64;
      description
        "counter for OOBI okt drops";
    }
    leaf counter_slice5_ifg_mac_pool87_tx_oobi_pkt_drop_counter2_tx_oobi_pkt_drop {
      type oc-yang:counter64;
      description
        "counter for OOBI okt drops";
    }
    leaf counter_slice5_ifg_mac_pool87_tx_oobi_pkt_drop_counter3_tx_oobi_pkt_drop {
      type oc-yang:counter64;
      description
        "counter for OOBI okt drops";
    }
    leaf counter_slice5_ifg_mac_pool87_tx_oobi_pkt_drop_counter4_tx_oobi_pkt_drop {
      type oc-yang:counter64;
      description
        "counter for OOBI okt drops";
    }
    leaf counter_slice5_ifg_mac_pool87_tx_oobi_pkt_drop_counter5_tx_oobi_pkt_drop {
      type oc-yang:counter64;
      description
        "counter for OOBI okt drops";
    }
    leaf counter_slice5_ifg_mac_pool87_tx_oobi_pkt_drop_counter6_tx_oobi_pkt_drop {
      type oc-yang:counter64;
      description
        "counter for OOBI okt drops";
    }
    leaf counter_slice5_ifg_mac_pool87_tx_oobi_pkt_drop_counter7_tx_oobi_pkt_drop {
      type oc-yang:counter64;
      description
        "counter for OOBI okt drops";
    }
    leaf counter_slice6_ifg_mac_pool80_tx_oobi_pkt_drop_counter0_tx_oobi_pkt_drop {
      type oc-yang:counter64;
      description
        "counter for OOBI okt drops";
    }
    leaf counter_slice6_ifg_mac_pool80_tx_oobi_pkt_drop_counter1_tx_oobi_pkt_drop {
      type oc-yang:counter64;
      description
        "counter for OOBI okt drops";
    }
    leaf counter_slice6_ifg_mac_pool80_tx_oobi_pkt_drop_counter2_tx_oobi_pkt_drop {
      type oc-yang:counter64;
      description
        "counter for OOBI okt drops";
    }
    leaf counter_slice6_ifg_mac_pool80_tx_oobi_pkt_drop_counter3_tx_oobi_pkt_drop {
      type oc-yang:counter64;
      description
        "counter for OOBI okt drops";
    }
    leaf counter_slice6_ifg_mac_pool80_tx_oobi_pkt_drop_counter4_tx_oobi_pkt_drop {
      type oc-yang:counter64;
      description
        "counter for OOBI okt drops";
    }
    leaf counter_slice6_ifg_mac_pool80_tx_oobi_pkt_drop_counter5_tx_oobi_pkt_drop {
      type oc-yang:counter64;
      description
        "counter for OOBI okt drops";
    }
    leaf counter_slice6_ifg_mac_pool80_tx_oobi_pkt_drop_counter6_tx_oobi_pkt_drop {
      type oc-yang:counter64;
      description
        "counter for OOBI okt drops";
    }
    leaf counter_slice6_ifg_mac_pool80_tx_oobi_pkt_drop_counter7_tx_oobi_pkt_drop {
      type oc-yang:counter64;
      description
        "counter for OOBI okt drops";
    }
    leaf counter_slice6_ifg_mac_pool81_tx_oobi_pkt_drop_counter0_tx_oobi_pkt_drop {
      type oc-yang:counter64;
      description
        "counter for OOBI okt drops";
    }
    leaf counter_slice6_ifg_mac_pool81_tx_oobi_pkt_drop_counter1_tx_oobi_pkt_drop {
      type oc-yang:counter64;
      description
        "counter for OOBI okt drops";
    }
    leaf counter_slice6_ifg_mac_pool81_tx_oobi_pkt_drop_counter2_tx_oobi_pkt_drop {
      type oc-yang:counter64;
      description
        "counter for OOBI okt drops";
    }
    leaf counter_slice6_ifg_mac_pool81_tx_oobi_pkt_drop_counter3_tx_oobi_pkt_drop {
      type oc-yang:counter64;
      description
        "counter for OOBI okt drops";
    }
    leaf counter_slice6_ifg_mac_pool81_tx_oobi_pkt_drop_counter4_tx_oobi_pkt_drop {
      type oc-yang:counter64;
      description
        "counter for OOBI okt drops";
    }
    leaf counter_slice6_ifg_mac_pool81_tx_oobi_pkt_drop_counter5_tx_oobi_pkt_drop {
      type oc-yang:counter64;
      description
        "counter for OOBI okt drops";
    }
    leaf counter_slice6_ifg_mac_pool81_tx_oobi_pkt_drop_counter6_tx_oobi_pkt_drop {
      type oc-yang:counter64;
      description
        "counter for OOBI okt drops";
    }
    leaf counter_slice6_ifg_mac_pool81_tx_oobi_pkt_drop_counter7_tx_oobi_pkt_drop {
      type oc-yang:counter64;
      description
        "counter for OOBI okt drops";
    }
    leaf counter_slice6_ifg_mac_pool82_tx_oobi_pkt_drop_counter0_tx_oobi_pkt_drop {
      type oc-yang:counter64;
      description
        "counter for OOBI okt drops";
    }
    leaf counter_slice6_ifg_mac_pool82_tx_oobi_pkt_drop_counter1_tx_oobi_pkt_drop {
      type oc-yang:counter64;
      description
        "counter for OOBI okt drops";
    }
    leaf counter_slice6_ifg_mac_pool82_tx_oobi_pkt_drop_counter2_tx_oobi_pkt_drop {
      type oc-yang:counter64;
      description
        "counter for OOBI okt drops";
    }
    leaf counter_slice6_ifg_mac_pool82_tx_oobi_pkt_drop_counter3_tx_oobi_pkt_drop {
      type oc-yang:counter64;
      description
        "counter for OOBI okt drops";
    }
    leaf counter_slice6_ifg_mac_pool82_tx_oobi_pkt_drop_counter4_tx_oobi_pkt_drop {
      type oc-yang:counter64;
      description
        "counter for OOBI okt drops";
    }
    leaf counter_slice6_ifg_mac_pool82_tx_oobi_pkt_drop_counter5_tx_oobi_pkt_drop {
      type oc-yang:counter64;
      description
        "counter for OOBI okt drops";
    }
    leaf counter_slice6_ifg_mac_pool82_tx_oobi_pkt_drop_counter6_tx_oobi_pkt_drop {
      type oc-yang:counter64;
      description
        "counter for OOBI okt drops";
    }
    leaf counter_slice6_ifg_mac_pool82_tx_oobi_pkt_drop_counter7_tx_oobi_pkt_drop {
      type oc-yang:counter64;
      description
        "counter for OOBI okt drops";
    }
    leaf counter_slice6_ifg_mac_pool83_tx_oobi_pkt_drop_counter0_tx_oobi_pkt_drop {
      type oc-yang:counter64;
      description
        "counter for OOBI okt drops";
    }
    leaf counter_slice6_ifg_mac_pool83_tx_oobi_pkt_drop_counter1_tx_oobi_pkt_drop {
      type oc-yang:counter64;
      description
        "counter for OOBI okt drops";
    }
    leaf counter_slice6_ifg_mac_pool83_tx_oobi_pkt_drop_counter2_tx_oobi_pkt_drop {
      type oc-yang:counter64;
      description
        "counter for OOBI okt drops";
    }
    leaf counter_slice6_ifg_mac_pool83_tx_oobi_pkt_drop_counter3_tx_oobi_pkt_drop {
      type oc-yang:counter64;
      description
        "counter for OOBI okt drops";
    }
    leaf counter_slice6_ifg_mac_pool83_tx_oobi_pkt_drop_counter4_tx_oobi_pkt_drop {
      type oc-yang:counter64;
      description
        "counter for OOBI okt drops";
    }
    leaf counter_slice6_ifg_mac_pool83_tx_oobi_pkt_drop_counter5_tx_oobi_pkt_drop {
      type oc-yang:counter64;
      description
        "counter for OOBI okt drops";
    }
    leaf counter_slice6_ifg_mac_pool83_tx_oobi_pkt_drop_counter6_tx_oobi_pkt_drop {
      type oc-yang:counter64;
      description
        "counter for OOBI okt drops";
    }
    leaf counter_slice6_ifg_mac_pool83_tx_oobi_pkt_drop_counter7_tx_oobi_pkt_drop {
      type oc-yang:counter64;
      description
        "counter for OOBI okt drops";
    }
    leaf counter_slice6_ifg_mac_pool84_tx_oobi_pkt_drop_counter0_tx_oobi_pkt_drop {
      type oc-yang:counter64;
      description
        "counter for OOBI okt drops";
    }
    leaf counter_slice6_ifg_mac_pool84_tx_oobi_pkt_drop_counter1_tx_oobi_pkt_drop {
      type oc-yang:counter64;
      description
        "counter for OOBI okt drops";
    }
    leaf counter_slice6_ifg_mac_pool84_tx_oobi_pkt_drop_counter2_tx_oobi_pkt_drop {
      type oc-yang:counter64;
      description
        "counter for OOBI okt drops";
    }
    leaf counter_slice6_ifg_mac_pool84_tx_oobi_pkt_drop_counter3_tx_oobi_pkt_drop {
      type oc-yang:counter64;
      description
        "counter for OOBI okt drops";
    }
    leaf counter_slice6_ifg_mac_pool84_tx_oobi_pkt_drop_counter4_tx_oobi_pkt_drop {
      type oc-yang:counter64;
      description
        "counter for OOBI okt drops";
    }
    leaf counter_slice6_ifg_mac_pool84_tx_oobi_pkt_drop_counter5_tx_oobi_pkt_drop {
      type oc-yang:counter64;
      description
        "counter for OOBI okt drops";
    }
    leaf counter_slice6_ifg_mac_pool84_tx_oobi_pkt_drop_counter6_tx_oobi_pkt_drop {
      type oc-yang:counter64;
      description
        "counter for OOBI okt drops";
    }
    leaf counter_slice6_ifg_mac_pool84_tx_oobi_pkt_drop_counter7_tx_oobi_pkt_drop {
      type oc-yang:counter64;
      description
        "counter for OOBI okt drops";
    }
    leaf counter_slice6_ifg_mac_pool85_tx_oobi_pkt_drop_counter0_tx_oobi_pkt_drop {
      type oc-yang:counter64;
      description
        "counter for OOBI okt drops";
    }
    leaf counter_slice6_ifg_mac_pool85_tx_oobi_pkt_drop_counter1_tx_oobi_pkt_drop {
      type oc-yang:counter64;
      description
        "counter for OOBI okt drops";
    }
    leaf counter_slice6_ifg_mac_pool85_tx_oobi_pkt_drop_counter2_tx_oobi_pkt_drop {
      type oc-yang:counter64;
      description
        "counter for OOBI okt drops";
    }
    leaf counter_slice6_ifg_mac_pool85_tx_oobi_pkt_drop_counter3_tx_oobi_pkt_drop {
      type oc-yang:counter64;
      description
        "counter for OOBI okt drops";
    }
    leaf counter_slice6_ifg_mac_pool85_tx_oobi_pkt_drop_counter4_tx_oobi_pkt_drop {
      type oc-yang:counter64;
      description
        "counter for OOBI okt drops";
    }
    leaf counter_slice6_ifg_mac_pool85_tx_oobi_pkt_drop_counter5_tx_oobi_pkt_drop {
      type oc-yang:counter64;
      description
        "counter for OOBI okt drops";
    }
    leaf counter_slice6_ifg_mac_pool85_tx_oobi_pkt_drop_counter6_tx_oobi_pkt_drop {
      type oc-yang:counter64;
      description
        "counter for OOBI okt drops";
    }
    leaf counter_slice6_ifg_mac_pool85_tx_oobi_pkt_drop_counter7_tx_oobi_pkt_drop {
      type oc-yang:counter64;
      description
        "counter for OOBI okt drops";
    }
    leaf counter_slice6_ifg_mac_pool86_tx_oobi_pkt_drop_counter0_tx_oobi_pkt_drop {
      type oc-yang:counter64;
      description
        "counter for OOBI okt drops";
    }
    leaf counter_slice6_ifg_mac_pool86_tx_oobi_pkt_drop_counter1_tx_oobi_pkt_drop {
      type oc-yang:counter64;
      description
        "counter for OOBI okt drops";
    }
    leaf counter_slice6_ifg_mac_pool86_tx_oobi_pkt_drop_counter2_tx_oobi_pkt_drop {
      type oc-yang:counter64;
      description
        "counter for OOBI okt drops";
    }
    leaf counter_slice6_ifg_mac_pool86_tx_oobi_pkt_drop_counter3_tx_oobi_pkt_drop {
      type oc-yang:counter64;
      description
        "counter for OOBI okt drops";
    }
    leaf counter_slice6_ifg_mac_pool86_tx_oobi_pkt_drop_counter4_tx_oobi_pkt_drop {
      type oc-yang:counter64;
      description
        "counter for OOBI okt drops";
    }
    leaf counter_slice6_ifg_mac_pool86_tx_oobi_pkt_drop_counter5_tx_oobi_pkt_drop {
      type oc-yang:counter64;
      description
        "counter for OOBI okt drops";
    }
    leaf counter_slice6_ifg_mac_pool86_tx_oobi_pkt_drop_counter6_tx_oobi_pkt_drop {
      type oc-yang:counter64;
      description
        "counter for OOBI okt drops";
    }
    leaf counter_slice6_ifg_mac_pool86_tx_oobi_pkt_drop_counter7_tx_oobi_pkt_drop {
      type oc-yang:counter64;
      description
        "counter for OOBI okt drops";
    }
    leaf counter_slice6_ifg_mac_pool87_tx_oobi_pkt_drop_counter0_tx_oobi_pkt_drop {
      type oc-yang:counter64;
      description
        "counter for OOBI okt drops";
    }
    leaf counter_slice6_ifg_mac_pool87_tx_oobi_pkt_drop_counter1_tx_oobi_pkt_drop {
      type oc-yang:counter64;
      description
        "counter for OOBI okt drops";
    }
    leaf counter_slice6_ifg_mac_pool87_tx_oobi_pkt_drop_counter2_tx_oobi_pkt_drop {
      type oc-yang:counter64;
      description
        "counter for OOBI okt drops";
    }
    leaf counter_slice6_ifg_mac_pool87_tx_oobi_pkt_drop_counter3_tx_oobi_pkt_drop {
      type oc-yang:counter64;
      description
        "counter for OOBI okt drops";
    }
    leaf counter_slice6_ifg_mac_pool87_tx_oobi_pkt_drop_counter4_tx_oobi_pkt_drop {
      type oc-yang:counter64;
      description
        "counter for OOBI okt drops";
    }
    leaf counter_slice6_ifg_mac_pool87_tx_oobi_pkt_drop_counter5_tx_oobi_pkt_drop {
      type oc-yang:counter64;
      description
        "counter for OOBI okt drops";
    }
    leaf counter_slice6_ifg_mac_pool87_tx_oobi_pkt_drop_counter6_tx_oobi_pkt_drop {
      type oc-yang:counter64;
      description
        "counter for OOBI okt drops";
    }
    leaf counter_slice6_ifg_mac_pool87_tx_oobi_pkt_drop_counter7_tx_oobi_pkt_drop {
      type oc-yang:counter64;
      description
        "counter for OOBI okt drops";
    }
    leaf counter_slice7_ifg_mac_pool80_tx_oobi_pkt_drop_counter0_tx_oobi_pkt_drop {
      type oc-yang:counter64;
      description
        "counter for OOBI okt drops";
    }
    leaf counter_slice7_ifg_mac_pool80_tx_oobi_pkt_drop_counter1_tx_oobi_pkt_drop {
      type oc-yang:counter64;
      description
        "counter for OOBI okt drops";
    }
    leaf counter_slice7_ifg_mac_pool80_tx_oobi_pkt_drop_counter2_tx_oobi_pkt_drop {
      type oc-yang:counter64;
      description
        "counter for OOBI okt drops";
    }
    leaf counter_slice7_ifg_mac_pool80_tx_oobi_pkt_drop_counter3_tx_oobi_pkt_drop {
      type oc-yang:counter64;
      description
        "counter for OOBI okt drops";
    }
    leaf counter_slice7_ifg_mac_pool80_tx_oobi_pkt_drop_counter4_tx_oobi_pkt_drop {
      type oc-yang:counter64;
      description
        "counter for OOBI okt drops";
    }
    leaf counter_slice7_ifg_mac_pool80_tx_oobi_pkt_drop_counter5_tx_oobi_pkt_drop {
      type oc-yang:counter64;
      description
        "counter for OOBI okt drops";
    }
    leaf counter_slice7_ifg_mac_pool80_tx_oobi_pkt_drop_counter6_tx_oobi_pkt_drop {
      type oc-yang:counter64;
      description
        "counter for OOBI okt drops";
    }
    leaf counter_slice7_ifg_mac_pool80_tx_oobi_pkt_drop_counter7_tx_oobi_pkt_drop {
      type oc-yang:counter64;
      description
        "counter for OOBI okt drops";
    }
    leaf counter_slice7_ifg_mac_pool81_tx_oobi_pkt_drop_counter0_tx_oobi_pkt_drop {
      type oc-yang:counter64;
      description
        "counter for OOBI okt drops";
    }
    leaf counter_slice7_ifg_mac_pool81_tx_oobi_pkt_drop_counter1_tx_oobi_pkt_drop {
      type oc-yang:counter64;
      description
        "counter for OOBI okt drops";
    }
    leaf counter_slice7_ifg_mac_pool81_tx_oobi_pkt_drop_counter2_tx_oobi_pkt_drop {
      type oc-yang:counter64;
      description
        "counter for OOBI okt drops";
    }
    leaf counter_slice7_ifg_mac_pool81_tx_oobi_pkt_drop_counter3_tx_oobi_pkt_drop {
      type oc-yang:counter64;
      description
        "counter for OOBI okt drops";
    }
    leaf counter_slice7_ifg_mac_pool81_tx_oobi_pkt_drop_counter4_tx_oobi_pkt_drop {
      type oc-yang:counter64;
      description
        "counter for OOBI okt drops";
    }
    leaf counter_slice7_ifg_mac_pool81_tx_oobi_pkt_drop_counter5_tx_oobi_pkt_drop {
      type oc-yang:counter64;
      description
        "counter for OOBI okt drops";
    }
    leaf counter_slice7_ifg_mac_pool81_tx_oobi_pkt_drop_counter6_tx_oobi_pkt_drop {
      type oc-yang:counter64;
      description
        "counter for OOBI okt drops";
    }
    leaf counter_slice7_ifg_mac_pool81_tx_oobi_pkt_drop_counter7_tx_oobi_pkt_drop {
      type oc-yang:counter64;
      description
        "counter for OOBI okt drops";
    }
    leaf counter_slice7_ifg_mac_pool82_tx_oobi_pkt_drop_counter0_tx_oobi_pkt_drop {
      type oc-yang:counter64;
      description
        "counter for OOBI okt drops";
    }
    leaf counter_slice7_ifg_mac_pool82_tx_oobi_pkt_drop_counter1_tx_oobi_pkt_drop {
      type oc-yang:counter64;
      description
        "counter for OOBI okt drops";
    }
    leaf counter_slice7_ifg_mac_pool82_tx_oobi_pkt_drop_counter2_tx_oobi_pkt_drop {
      type oc-yang:counter64;
      description
        "counter for OOBI okt drops";
    }
    leaf counter_slice7_ifg_mac_pool82_tx_oobi_pkt_drop_counter3_tx_oobi_pkt_drop {
      type oc-yang:counter64;
      description
        "counter for OOBI okt drops";
    }
    leaf counter_slice7_ifg_mac_pool82_tx_oobi_pkt_drop_counter4_tx_oobi_pkt_drop {
      type oc-yang:counter64;
      description
        "counter for OOBI okt drops";
    }
    leaf counter_slice7_ifg_mac_pool82_tx_oobi_pkt_drop_counter5_tx_oobi_pkt_drop {
      type oc-yang:counter64;
      description
        "counter for OOBI okt drops";
    }
    leaf counter_slice7_ifg_mac_pool82_tx_oobi_pkt_drop_counter6_tx_oobi_pkt_drop {
      type oc-yang:counter64;
      description
        "counter for OOBI okt drops";
    }
    leaf counter_slice7_ifg_mac_pool82_tx_oobi_pkt_drop_counter7_tx_oobi_pkt_drop {
      type oc-yang:counter64;
      description
        "counter for OOBI okt drops";
    }
    leaf counter_slice7_ifg_mac_pool83_tx_oobi_pkt_drop_counter0_tx_oobi_pkt_drop {
      type oc-yang:counter64;
      description
        "counter for OOBI okt drops";
    }
    leaf counter_slice7_ifg_mac_pool83_tx_oobi_pkt_drop_counter1_tx_oobi_pkt_drop {
      type oc-yang:counter64;
      description
        "counter for OOBI okt drops";
    }
    leaf counter_slice7_ifg_mac_pool83_tx_oobi_pkt_drop_counter2_tx_oobi_pkt_drop {
      type oc-yang:counter64;
      description
        "counter for OOBI okt drops";
    }
    leaf counter_slice7_ifg_mac_pool83_tx_oobi_pkt_drop_counter3_tx_oobi_pkt_drop {
      type oc-yang:counter64;
      description
        "counter for OOBI okt drops";
    }
    leaf counter_slice7_ifg_mac_pool83_tx_oobi_pkt_drop_counter4_tx_oobi_pkt_drop {
      type oc-yang:counter64;
      description
        "counter for OOBI okt drops";
    }
    leaf counter_slice7_ifg_mac_pool83_tx_oobi_pkt_drop_counter5_tx_oobi_pkt_drop {
      type oc-yang:counter64;
      description
        "counter for OOBI okt drops";
    }
    leaf counter_slice7_ifg_mac_pool83_tx_oobi_pkt_drop_counter6_tx_oobi_pkt_drop {
      type oc-yang:counter64;
      description
        "counter for OOBI okt drops";
    }
    leaf counter_slice7_ifg_mac_pool83_tx_oobi_pkt_drop_counter7_tx_oobi_pkt_drop {
      type oc-yang:counter64;
      description
        "counter for OOBI okt drops";
    }
    leaf counter_slice7_ifg_mac_pool84_tx_oobi_pkt_drop_counter0_tx_oobi_pkt_drop {
      type oc-yang:counter64;
      description
        "counter for OOBI okt drops";
    }
    leaf counter_slice7_ifg_mac_pool84_tx_oobi_pkt_drop_counter1_tx_oobi_pkt_drop {
      type oc-yang:counter64;
      description
        "counter for OOBI okt drops";
    }
    leaf counter_slice7_ifg_mac_pool84_tx_oobi_pkt_drop_counter2_tx_oobi_pkt_drop {
      type oc-yang:counter64;
      description
        "counter for OOBI okt drops";
    }
    leaf counter_slice7_ifg_mac_pool84_tx_oobi_pkt_drop_counter3_tx_oobi_pkt_drop {
      type oc-yang:counter64;
      description
        "counter for OOBI okt drops";
    }
    leaf counter_slice7_ifg_mac_pool84_tx_oobi_pkt_drop_counter4_tx_oobi_pkt_drop {
      type oc-yang:counter64;
      description
        "counter for OOBI okt drops";
    }
    leaf counter_slice7_ifg_mac_pool84_tx_oobi_pkt_drop_counter5_tx_oobi_pkt_drop {
      type oc-yang:counter64;
      description
        "counter for OOBI okt drops";
    }
    leaf counter_slice7_ifg_mac_pool84_tx_oobi_pkt_drop_counter6_tx_oobi_pkt_drop {
      type oc-yang:counter64;
      description
        "counter for OOBI okt drops";
    }
    leaf counter_slice7_ifg_mac_pool84_tx_oobi_pkt_drop_counter7_tx_oobi_pkt_drop {
      type oc-yang:counter64;
      description
        "counter for OOBI okt drops";
    }
    leaf counter_slice7_ifg_mac_pool85_tx_oobi_pkt_drop_counter0_tx_oobi_pkt_drop {
      type oc-yang:counter64;
      description
        "counter for OOBI okt drops";
    }
    leaf counter_slice7_ifg_mac_pool85_tx_oobi_pkt_drop_counter1_tx_oobi_pkt_drop {
      type oc-yang:counter64;
      description
        "counter for OOBI okt drops";
    }
    leaf counter_slice7_ifg_mac_pool85_tx_oobi_pkt_drop_counter2_tx_oobi_pkt_drop {
      type oc-yang:counter64;
      description
        "counter for OOBI okt drops";
    }
    leaf counter_slice7_ifg_mac_pool85_tx_oobi_pkt_drop_counter3_tx_oobi_pkt_drop {
      type oc-yang:counter64;
      description
        "counter for OOBI okt drops";
    }
    leaf counter_slice7_ifg_mac_pool85_tx_oobi_pkt_drop_counter4_tx_oobi_pkt_drop {
      type oc-yang:counter64;
      description
        "counter for OOBI okt drops";
    }
    leaf counter_slice7_ifg_mac_pool85_tx_oobi_pkt_drop_counter5_tx_oobi_pkt_drop {
      type oc-yang:counter64;
      description
        "counter for OOBI okt drops";
    }
    leaf counter_slice7_ifg_mac_pool85_tx_oobi_pkt_drop_counter6_tx_oobi_pkt_drop {
      type oc-yang:counter64;
      description
        "counter for OOBI okt drops";
    }
    leaf counter_slice7_ifg_mac_pool85_tx_oobi_pkt_drop_counter7_tx_oobi_pkt_drop {
      type oc-yang:counter64;
      description
        "counter for OOBI okt drops";
    }
    leaf counter_slice7_ifg_mac_pool86_tx_oobi_pkt_drop_counter0_tx_oobi_pkt_drop {
      type oc-yang:counter64;
      description
        "counter for OOBI okt drops";
    }
    leaf counter_slice7_ifg_mac_pool86_tx_oobi_pkt_drop_counter1_tx_oobi_pkt_drop {
      type oc-yang:counter64;
      description
        "counter for OOBI okt drops";
    }
    leaf counter_slice7_ifg_mac_pool86_tx_oobi_pkt_drop_counter2_tx_oobi_pkt_drop {
      type oc-yang:counter64;
      description
        "counter for OOBI okt drops";
    }
    leaf counter_slice7_ifg_mac_pool86_tx_oobi_pkt_drop_counter3_tx_oobi_pkt_drop {
      type oc-yang:counter64;
      description
        "counter for OOBI okt drops";
    }
    leaf counter_slice7_ifg_mac_pool86_tx_oobi_pkt_drop_counter4_tx_oobi_pkt_drop {
      type oc-yang:counter64;
      description
        "counter for OOBI okt drops";
    }
    leaf counter_slice7_ifg_mac_pool86_tx_oobi_pkt_drop_counter5_tx_oobi_pkt_drop {
      type oc-yang:counter64;
      description
        "counter for OOBI okt drops";
    }
    leaf counter_slice7_ifg_mac_pool86_tx_oobi_pkt_drop_counter6_tx_oobi_pkt_drop {
      type oc-yang:counter64;
      description
        "counter for OOBI okt drops";
    }
    leaf counter_slice7_ifg_mac_pool86_tx_oobi_pkt_drop_counter7_tx_oobi_pkt_drop {
      type oc-yang:counter64;
      description
        "counter for OOBI okt drops";
    }
    leaf counter_slice7_ifg_mac_pool87_tx_oobi_pkt_drop_counter0_tx_oobi_pkt_drop {
      type oc-yang:counter64;
      description
        "counter for OOBI okt drops";
    }
    leaf counter_slice7_ifg_mac_pool87_tx_oobi_pkt_drop_counter1_tx_oobi_pkt_drop {
      type oc-yang:counter64;
      description
        "counter for OOBI okt drops";
    }
    leaf counter_slice7_ifg_mac_pool87_tx_oobi_pkt_drop_counter2_tx_oobi_pkt_drop {
      type oc-yang:counter64;
      description
        "counter for OOBI okt drops";
    }
    leaf counter_slice7_ifg_mac_pool87_tx_oobi_pkt_drop_counter3_tx_oobi_pkt_drop {
      type oc-yang:counter64;
      description
        "counter for OOBI okt drops";
    }
    leaf counter_slice7_ifg_mac_pool87_tx_oobi_pkt_drop_counter4_tx_oobi_pkt_drop {
      type oc-yang:counter64;
      description
        "counter for OOBI okt drops";
    }
    leaf counter_slice7_ifg_mac_pool87_tx_oobi_pkt_drop_counter5_tx_oobi_pkt_drop {
      type oc-yang:counter64;
      description
        "counter for OOBI okt drops";
    }
    leaf counter_slice7_ifg_mac_pool87_tx_oobi_pkt_drop_counter6_tx_oobi_pkt_drop {
      type oc-yang:counter64;
      description
        "counter for OOBI okt drops";
    }
    leaf counter_slice7_ifg_mac_pool87_tx_oobi_pkt_drop_counter7_tx_oobi_pkt_drop {
      type oc-yang:counter64;
      description
        "counter for OOBI okt drops";
    }
    leaf counter_slice8_ifg_mac_pool80_tx_oobi_pkt_drop_counter0_tx_oobi_pkt_drop {
      type oc-yang:counter64;
      description
        "counter for OOBI okt drops";
    }
    leaf counter_slice8_ifg_mac_pool80_tx_oobi_pkt_drop_counter1_tx_oobi_pkt_drop {
      type oc-yang:counter64;
      description
        "counter for OOBI okt drops";
    }
    leaf counter_slice8_ifg_mac_pool80_tx_oobi_pkt_drop_counter2_tx_oobi_pkt_drop {
      type oc-yang:counter64;
      description
        "counter for OOBI okt drops";
    }
    leaf counter_slice8_ifg_mac_pool80_tx_oobi_pkt_drop_counter3_tx_oobi_pkt_drop {
      type oc-yang:counter64;
      description
        "counter for OOBI okt drops";
    }
    leaf counter_slice8_ifg_mac_pool80_tx_oobi_pkt_drop_counter4_tx_oobi_pkt_drop {
      type oc-yang:counter64;
      description
        "counter for OOBI okt drops";
    }
    leaf counter_slice8_ifg_mac_pool80_tx_oobi_pkt_drop_counter5_tx_oobi_pkt_drop {
      type oc-yang:counter64;
      description
        "counter for OOBI okt drops";
    }
    leaf counter_slice8_ifg_mac_pool80_tx_oobi_pkt_drop_counter6_tx_oobi_pkt_drop {
      type oc-yang:counter64;
      description
        "counter for OOBI okt drops";
    }
    leaf counter_slice8_ifg_mac_pool80_tx_oobi_pkt_drop_counter7_tx_oobi_pkt_drop {
      type oc-yang:counter64;
      description
        "counter for OOBI okt drops";
    }
    leaf counter_slice8_ifg_mac_pool81_tx_oobi_pkt_drop_counter0_tx_oobi_pkt_drop {
      type oc-yang:counter64;
      description
        "counter for OOBI okt drops";
    }
    leaf counter_slice8_ifg_mac_pool81_tx_oobi_pkt_drop_counter1_tx_oobi_pkt_drop {
      type oc-yang:counter64;
      description
        "counter for OOBI okt drops";
    }
    leaf counter_slice8_ifg_mac_pool81_tx_oobi_pkt_drop_counter2_tx_oobi_pkt_drop {
      type oc-yang:counter64;
      description
        "counter for OOBI okt drops";
    }
    leaf counter_slice8_ifg_mac_pool81_tx_oobi_pkt_drop_counter3_tx_oobi_pkt_drop {
      type oc-yang:counter64;
      description
        "counter for OOBI okt drops";
    }
    leaf counter_slice8_ifg_mac_pool81_tx_oobi_pkt_drop_counter4_tx_oobi_pkt_drop {
      type oc-yang:counter64;
      description
        "counter for OOBI okt drops";
    }
    leaf counter_slice8_ifg_mac_pool81_tx_oobi_pkt_drop_counter5_tx_oobi_pkt_drop {
      type oc-yang:counter64;
      description
        "counter for OOBI okt drops";
    }
    leaf counter_slice8_ifg_mac_pool81_tx_oobi_pkt_drop_counter6_tx_oobi_pkt_drop {
      type oc-yang:counter64;
      description
        "counter for OOBI okt drops";
    }
    leaf counter_slice8_ifg_mac_pool81_tx_oobi_pkt_drop_counter7_tx_oobi_pkt_drop {
      type oc-yang:counter64;
      description
        "counter for OOBI okt drops";
    }
    leaf counter_slice8_ifg_mac_pool82_tx_oobi_pkt_drop_counter0_tx_oobi_pkt_drop {
      type oc-yang:counter64;
      description
        "counter for OOBI okt drops";
    }
    leaf counter_slice8_ifg_mac_pool82_tx_oobi_pkt_drop_counter1_tx_oobi_pkt_drop {
      type oc-yang:counter64;
      description
        "counter for OOBI okt drops";
    }
    leaf counter_slice8_ifg_mac_pool82_tx_oobi_pkt_drop_counter2_tx_oobi_pkt_drop {
      type oc-yang:counter64;
      description
        "counter for OOBI okt drops";
    }
    leaf counter_slice8_ifg_mac_pool82_tx_oobi_pkt_drop_counter3_tx_oobi_pkt_drop {
      type oc-yang:counter64;
      description
        "counter for OOBI okt drops";
    }
    leaf counter_slice8_ifg_mac_pool82_tx_oobi_pkt_drop_counter4_tx_oobi_pkt_drop {
      type oc-yang:counter64;
      description
        "counter for OOBI okt drops";
    }
    leaf counter_slice8_ifg_mac_pool82_tx_oobi_pkt_drop_counter5_tx_oobi_pkt_drop {
      type oc-yang:counter64;
      description
        "counter for OOBI okt drops";
    }
    leaf counter_slice8_ifg_mac_pool82_tx_oobi_pkt_drop_counter6_tx_oobi_pkt_drop {
      type oc-yang:counter64;
      description
        "counter for OOBI okt drops";
    }
    leaf counter_slice8_ifg_mac_pool82_tx_oobi_pkt_drop_counter7_tx_oobi_pkt_drop {
      type oc-yang:counter64;
      description
        "counter for OOBI okt drops";
    }
    leaf counter_slice8_ifg_mac_pool83_tx_oobi_pkt_drop_counter0_tx_oobi_pkt_drop {
      type oc-yang:counter64;
      description
        "counter for OOBI okt drops";
    }
    leaf counter_slice8_ifg_mac_pool83_tx_oobi_pkt_drop_counter1_tx_oobi_pkt_drop {
      type oc-yang:counter64;
      description
        "counter for OOBI okt drops";
    }
    leaf counter_slice8_ifg_mac_pool83_tx_oobi_pkt_drop_counter2_tx_oobi_pkt_drop {
      type oc-yang:counter64;
      description
        "counter for OOBI okt drops";
    }
    leaf counter_slice8_ifg_mac_pool83_tx_oobi_pkt_drop_counter3_tx_oobi_pkt_drop {
      type oc-yang:counter64;
      description
        "counter for OOBI okt drops";
    }
    leaf counter_slice8_ifg_mac_pool83_tx_oobi_pkt_drop_counter4_tx_oobi_pkt_drop {
      type oc-yang:counter64;
      description
        "counter for OOBI okt drops";
    }
    leaf counter_slice8_ifg_mac_pool83_tx_oobi_pkt_drop_counter5_tx_oobi_pkt_drop {
      type oc-yang:counter64;
      description
        "counter for OOBI okt drops";
    }
    leaf counter_slice8_ifg_mac_pool83_tx_oobi_pkt_drop_counter6_tx_oobi_pkt_drop {
      type oc-yang:counter64;
      description
        "counter for OOBI okt drops";
    }
    leaf counter_slice8_ifg_mac_pool83_tx_oobi_pkt_drop_counter7_tx_oobi_pkt_drop {
      type oc-yang:counter64;
      description
        "counter for OOBI okt drops";
    }
    leaf counter_slice8_ifg_mac_pool84_tx_oobi_pkt_drop_counter0_tx_oobi_pkt_drop {
      type oc-yang:counter64;
      description
        "counter for OOBI okt drops";
    }
    leaf counter_slice8_ifg_mac_pool84_tx_oobi_pkt_drop_counter1_tx_oobi_pkt_drop {
      type oc-yang:counter64;
      description
        "counter for OOBI okt drops";
    }
    leaf counter_slice8_ifg_mac_pool84_tx_oobi_pkt_drop_counter2_tx_oobi_pkt_drop {
      type oc-yang:counter64;
      description
        "counter for OOBI okt drops";
    }
    leaf counter_slice8_ifg_mac_pool84_tx_oobi_pkt_drop_counter3_tx_oobi_pkt_drop {
      type oc-yang:counter64;
      description
        "counter for OOBI okt drops";
    }
    leaf counter_slice8_ifg_mac_pool84_tx_oobi_pkt_drop_counter4_tx_oobi_pkt_drop {
      type oc-yang:counter64;
      description
        "counter for OOBI okt drops";
    }
    leaf counter_slice8_ifg_mac_pool84_tx_oobi_pkt_drop_counter5_tx_oobi_pkt_drop {
      type oc-yang:counter64;
      description
        "counter for OOBI okt drops";
    }
    leaf counter_slice8_ifg_mac_pool84_tx_oobi_pkt_drop_counter6_tx_oobi_pkt_drop {
      type oc-yang:counter64;
      description
        "counter for OOBI okt drops";
    }
    leaf counter_slice8_ifg_mac_pool84_tx_oobi_pkt_drop_counter7_tx_oobi_pkt_drop {
      type oc-yang:counter64;
      description
        "counter for OOBI okt drops";
    }
    leaf counter_slice8_ifg_mac_pool85_tx_oobi_pkt_drop_counter0_tx_oobi_pkt_drop {
      type oc-yang:counter64;
      description
        "counter for OOBI okt drops";
    }
    leaf counter_slice8_ifg_mac_pool85_tx_oobi_pkt_drop_counter1_tx_oobi_pkt_drop {
      type oc-yang:counter64;
      description
        "counter for OOBI okt drops";
    }
    leaf counter_slice8_ifg_mac_pool85_tx_oobi_pkt_drop_counter2_tx_oobi_pkt_drop {
      type oc-yang:counter64;
      description
        "counter for OOBI okt drops";
    }
    leaf counter_slice8_ifg_mac_pool85_tx_oobi_pkt_drop_counter3_tx_oobi_pkt_drop {
      type oc-yang:counter64;
      description
        "counter for OOBI okt drops";
    }
    leaf counter_slice8_ifg_mac_pool85_tx_oobi_pkt_drop_counter4_tx_oobi_pkt_drop {
      type oc-yang:counter64;
      description
        "counter for OOBI okt drops";
    }
    leaf counter_slice8_ifg_mac_pool85_tx_oobi_pkt_drop_counter5_tx_oobi_pkt_drop {
      type oc-yang:counter64;
      description
        "counter for OOBI okt drops";
    }
    leaf counter_slice8_ifg_mac_pool85_tx_oobi_pkt_drop_counter6_tx_oobi_pkt_drop {
      type oc-yang:counter64;
      description
        "counter for OOBI okt drops";
    }
    leaf counter_slice8_ifg_mac_pool85_tx_oobi_pkt_drop_counter7_tx_oobi_pkt_drop {
      type oc-yang:counter64;
      description
        "counter for OOBI okt drops";
    }
    leaf counter_slice8_ifg_mac_pool86_tx_oobi_pkt_drop_counter0_tx_oobi_pkt_drop {
      type oc-yang:counter64;
      description
        "counter for OOBI okt drops";
    }
    leaf counter_slice8_ifg_mac_pool86_tx_oobi_pkt_drop_counter1_tx_oobi_pkt_drop {
      type oc-yang:counter64;
      description
        "counter for OOBI okt drops";
    }
    leaf counter_slice8_ifg_mac_pool86_tx_oobi_pkt_drop_counter2_tx_oobi_pkt_drop {
      type oc-yang:counter64;
      description
        "counter for OOBI okt drops";
    }
    leaf counter_slice8_ifg_mac_pool86_tx_oobi_pkt_drop_counter3_tx_oobi_pkt_drop {
      type oc-yang:counter64;
      description
        "counter for OOBI okt drops";
    }
    leaf counter_slice8_ifg_mac_pool86_tx_oobi_pkt_drop_counter4_tx_oobi_pkt_drop {
      type oc-yang:counter64;
      description
        "counter for OOBI okt drops";
    }
    leaf counter_slice8_ifg_mac_pool86_tx_oobi_pkt_drop_counter5_tx_oobi_pkt_drop {
      type oc-yang:counter64;
      description
        "counter for OOBI okt drops";
    }
    leaf counter_slice8_ifg_mac_pool86_tx_oobi_pkt_drop_counter6_tx_oobi_pkt_drop {
      type oc-yang:counter64;
      description
        "counter for OOBI okt drops";
    }
    leaf counter_slice8_ifg_mac_pool86_tx_oobi_pkt_drop_counter7_tx_oobi_pkt_drop {
      type oc-yang:counter64;
      description
        "counter for OOBI okt drops";
    }
    leaf counter_slice8_ifg_mac_pool87_tx_oobi_pkt_drop_counter0_tx_oobi_pkt_drop {
      type oc-yang:counter64;
      description
        "counter for OOBI okt drops";
    }
    leaf counter_slice8_ifg_mac_pool87_tx_oobi_pkt_drop_counter1_tx_oobi_pkt_drop {
      type oc-yang:counter64;
      description
        "counter for OOBI okt drops";
    }
    leaf counter_slice8_ifg_mac_pool87_tx_oobi_pkt_drop_counter2_tx_oobi_pkt_drop {
      type oc-yang:counter64;
      description
        "counter for OOBI okt drops";
    }
    leaf counter_slice8_ifg_mac_pool87_tx_oobi_pkt_drop_counter3_tx_oobi_pkt_drop {
      type oc-yang:counter64;
      description
        "counter for OOBI okt drops";
    }
    leaf counter_slice8_ifg_mac_pool87_tx_oobi_pkt_drop_counter4_tx_oobi_pkt_drop {
      type oc-yang:counter64;
      description
        "counter for OOBI okt drops";
    }
    leaf counter_slice8_ifg_mac_pool87_tx_oobi_pkt_drop_counter5_tx_oobi_pkt_drop {
      type oc-yang:counter64;
      description
        "counter for OOBI okt drops";
    }
    leaf counter_slice8_ifg_mac_pool87_tx_oobi_pkt_drop_counter6_tx_oobi_pkt_drop {
      type oc-yang:counter64;
      description
        "counter for OOBI okt drops";
    }
    leaf counter_slice8_ifg_mac_pool87_tx_oobi_pkt_drop_counter7_tx_oobi_pkt_drop {
      type oc-yang:counter64;
      description
        "counter for OOBI okt drops";
    }
    leaf counter_slice9_ifg_mac_pool80_tx_oobi_pkt_drop_counter0_tx_oobi_pkt_drop {
      type oc-yang:counter64;
      description
        "counter for OOBI okt drops";
    }
    leaf counter_slice9_ifg_mac_pool80_tx_oobi_pkt_drop_counter1_tx_oobi_pkt_drop {
      type oc-yang:counter64;
      description
        "counter for OOBI okt drops";
    }
    leaf counter_slice9_ifg_mac_pool80_tx_oobi_pkt_drop_counter2_tx_oobi_pkt_drop {
      type oc-yang:counter64;
      description
        "counter for OOBI okt drops";
    }
    leaf counter_slice9_ifg_mac_pool80_tx_oobi_pkt_drop_counter3_tx_oobi_pkt_drop {
      type oc-yang:counter64;
      description
        "counter for OOBI okt drops";
    }
    leaf counter_slice9_ifg_mac_pool80_tx_oobi_pkt_drop_counter4_tx_oobi_pkt_drop {
      type oc-yang:counter64;
      description
        "counter for OOBI okt drops";
    }
    leaf counter_slice9_ifg_mac_pool80_tx_oobi_pkt_drop_counter5_tx_oobi_pkt_drop {
      type oc-yang:counter64;
      description
        "counter for OOBI okt drops";
    }
    leaf counter_slice9_ifg_mac_pool80_tx_oobi_pkt_drop_counter6_tx_oobi_pkt_drop {
      type oc-yang:counter64;
      description
        "counter for OOBI okt drops";
    }
    leaf counter_slice9_ifg_mac_pool80_tx_oobi_pkt_drop_counter7_tx_oobi_pkt_drop {
      type oc-yang:counter64;
      description
        "counter for OOBI okt drops";
    }
    leaf counter_slice9_ifg_mac_pool81_tx_oobi_pkt_drop_counter0_tx_oobi_pkt_drop {
      type oc-yang:counter64;
      description
        "counter for OOBI okt drops";
    }
    leaf counter_slice9_ifg_mac_pool81_tx_oobi_pkt_drop_counter1_tx_oobi_pkt_drop {
      type oc-yang:counter64;
      description
        "counter for OOBI okt drops";
    }
    leaf counter_slice9_ifg_mac_pool81_tx_oobi_pkt_drop_counter2_tx_oobi_pkt_drop {
      type oc-yang:counter64;
      description
        "counter for OOBI okt drops";
    }
    leaf counter_slice9_ifg_mac_pool81_tx_oobi_pkt_drop_counter3_tx_oobi_pkt_drop {
      type oc-yang:counter64;
      description
        "counter for OOBI okt drops";
    }
    leaf counter_slice9_ifg_mac_pool81_tx_oobi_pkt_drop_counter4_tx_oobi_pkt_drop {
      type oc-yang:counter64;
      description
        "counter for OOBI okt drops";
    }
    leaf counter_slice9_ifg_mac_pool81_tx_oobi_pkt_drop_counter5_tx_oobi_pkt_drop {
      type oc-yang:counter64;
      description
        "counter for OOBI okt drops";
    }
    leaf counter_slice9_ifg_mac_pool81_tx_oobi_pkt_drop_counter6_tx_oobi_pkt_drop {
      type oc-yang:counter64;
      description
        "counter for OOBI okt drops";
    }
    leaf counter_slice9_ifg_mac_pool81_tx_oobi_pkt_drop_counter7_tx_oobi_pkt_drop {
      type oc-yang:counter64;
      description
        "counter for OOBI okt drops";
    }
    leaf counter_slice9_ifg_mac_pool82_tx_oobi_pkt_drop_counter0_tx_oobi_pkt_drop {
      type oc-yang:counter64;
      description
        "counter for OOBI okt drops";
    }
    leaf counter_slice9_ifg_mac_pool82_tx_oobi_pkt_drop_counter1_tx_oobi_pkt_drop {
      type oc-yang:counter64;
      description
        "counter for OOBI okt drops";
    }
    leaf counter_slice9_ifg_mac_pool82_tx_oobi_pkt_drop_counter2_tx_oobi_pkt_drop {
      type oc-yang:counter64;
      description
        "counter for OOBI okt drops";
    }
    leaf counter_slice9_ifg_mac_pool82_tx_oobi_pkt_drop_counter3_tx_oobi_pkt_drop {
      type oc-yang:counter64;
      description
        "counter for OOBI okt drops";
    }
    leaf counter_slice9_ifg_mac_pool82_tx_oobi_pkt_drop_counter4_tx_oobi_pkt_drop {
      type oc-yang:counter64;
      description
        "counter for OOBI okt drops";
    }
    leaf counter_slice9_ifg_mac_pool82_tx_oobi_pkt_drop_counter5_tx_oobi_pkt_drop {
      type oc-yang:counter64;
      description
        "counter for OOBI okt drops";
    }
    leaf counter_slice9_ifg_mac_pool82_tx_oobi_pkt_drop_counter6_tx_oobi_pkt_drop {
      type oc-yang:counter64;
      description
        "counter for OOBI okt drops";
    }
    leaf counter_slice9_ifg_mac_pool82_tx_oobi_pkt_drop_counter7_tx_oobi_pkt_drop {
      type oc-yang:counter64;
      description
        "counter for OOBI okt drops";
    }
    leaf counter_slice9_ifg_mac_pool83_tx_oobi_pkt_drop_counter0_tx_oobi_pkt_drop {
      type oc-yang:counter64;
      description
        "counter for OOBI okt drops";
    }
    leaf counter_slice9_ifg_mac_pool83_tx_oobi_pkt_drop_counter1_tx_oobi_pkt_drop {
      type oc-yang:counter64;
      description
        "counter for OOBI okt drops";
    }
    leaf counter_slice9_ifg_mac_pool83_tx_oobi_pkt_drop_counter2_tx_oobi_pkt_drop {
      type oc-yang:counter64;
      description
        "counter for OOBI okt drops";
    }
    leaf counter_slice9_ifg_mac_pool83_tx_oobi_pkt_drop_counter3_tx_oobi_pkt_drop {
      type oc-yang:counter64;
      description
        "counter for OOBI okt drops";
    }
    leaf counter_slice9_ifg_mac_pool83_tx_oobi_pkt_drop_counter4_tx_oobi_pkt_drop {
      type oc-yang:counter64;
      description
        "counter for OOBI okt drops";
    }
    leaf counter_slice9_ifg_mac_pool83_tx_oobi_pkt_drop_counter5_tx_oobi_pkt_drop {
      type oc-yang:counter64;
      description
        "counter for OOBI okt drops";
    }
    leaf counter_slice9_ifg_mac_pool83_tx_oobi_pkt_drop_counter6_tx_oobi_pkt_drop {
      type oc-yang:counter64;
      description
        "counter for OOBI okt drops";
    }
    leaf counter_slice9_ifg_mac_pool83_tx_oobi_pkt_drop_counter7_tx_oobi_pkt_drop {
      type oc-yang:counter64;
      description
        "counter for OOBI okt drops";
    }
    leaf counter_slice9_ifg_mac_pool84_tx_oobi_pkt_drop_counter0_tx_oobi_pkt_drop {
      type oc-yang:counter64;
      description
        "counter for OOBI okt drops";
    }
    leaf counter_slice9_ifg_mac_pool84_tx_oobi_pkt_drop_counter1_tx_oobi_pkt_drop {
      type oc-yang:counter64;
      description
        "counter for OOBI okt drops";
    }
    leaf counter_slice9_ifg_mac_pool84_tx_oobi_pkt_drop_counter2_tx_oobi_pkt_drop {
      type oc-yang:counter64;
      description
        "counter for OOBI okt drops";
    }
    leaf counter_slice9_ifg_mac_pool84_tx_oobi_pkt_drop_counter3_tx_oobi_pkt_drop {
      type oc-yang:counter64;
      description
        "counter for OOBI okt drops";
    }
    leaf counter_slice9_ifg_mac_pool84_tx_oobi_pkt_drop_counter4_tx_oobi_pkt_drop {
      type oc-yang:counter64;
      description
        "counter for OOBI okt drops";
    }
    leaf counter_slice9_ifg_mac_pool84_tx_oobi_pkt_drop_counter5_tx_oobi_pkt_drop {
      type oc-yang:counter64;
      description
        "counter for OOBI okt drops";
    }
    leaf counter_slice9_ifg_mac_pool84_tx_oobi_pkt_drop_counter6_tx_oobi_pkt_drop {
      type oc-yang:counter64;
      description
        "counter for OOBI okt drops";
    }
    leaf counter_slice9_ifg_mac_pool84_tx_oobi_pkt_drop_counter7_tx_oobi_pkt_drop {
      type oc-yang:counter64;
      description
        "counter for OOBI okt drops";
    }
    leaf counter_slice9_ifg_mac_pool85_tx_oobi_pkt_drop_counter0_tx_oobi_pkt_drop {
      type oc-yang:counter64;
      description
        "counter for OOBI okt drops";
    }
    leaf counter_slice9_ifg_mac_pool85_tx_oobi_pkt_drop_counter1_tx_oobi_pkt_drop {
      type oc-yang:counter64;
      description
        "counter for OOBI okt drops";
    }
    leaf counter_slice9_ifg_mac_pool85_tx_oobi_pkt_drop_counter2_tx_oobi_pkt_drop {
      type oc-yang:counter64;
      description
        "counter for OOBI okt drops";
    }
    leaf counter_slice9_ifg_mac_pool85_tx_oobi_pkt_drop_counter3_tx_oobi_pkt_drop {
      type oc-yang:counter64;
      description
        "counter for OOBI okt drops";
    }
    leaf counter_slice9_ifg_mac_pool85_tx_oobi_pkt_drop_counter4_tx_oobi_pkt_drop {
      type oc-yang:counter64;
      description
        "counter for OOBI okt drops";
    }
    leaf counter_slice9_ifg_mac_pool85_tx_oobi_pkt_drop_counter5_tx_oobi_pkt_drop {
      type oc-yang:counter64;
      description
        "counter for OOBI okt drops";
    }
    leaf counter_slice9_ifg_mac_pool85_tx_oobi_pkt_drop_counter6_tx_oobi_pkt_drop {
      type oc-yang:counter64;
      description
        "counter for OOBI okt drops";
    }
    leaf counter_slice9_ifg_mac_pool85_tx_oobi_pkt_drop_counter7_tx_oobi_pkt_drop {
      type oc-yang:counter64;
      description
        "counter for OOBI okt drops";
    }
    leaf counter_slice9_ifg_mac_pool86_tx_oobi_pkt_drop_counter0_tx_oobi_pkt_drop {
      type oc-yang:counter64;
      description
        "counter for OOBI okt drops";
    }
    leaf counter_slice9_ifg_mac_pool86_tx_oobi_pkt_drop_counter1_tx_oobi_pkt_drop {
      type oc-yang:counter64;
      description
        "counter for OOBI okt drops";
    }
    leaf counter_slice9_ifg_mac_pool86_tx_oobi_pkt_drop_counter2_tx_oobi_pkt_drop {
      type oc-yang:counter64;
      description
        "counter for OOBI okt drops";
    }
    leaf counter_slice9_ifg_mac_pool86_tx_oobi_pkt_drop_counter3_tx_oobi_pkt_drop {
      type oc-yang:counter64;
      description
        "counter for OOBI okt drops";
    }
    leaf counter_slice9_ifg_mac_pool86_tx_oobi_pkt_drop_counter4_tx_oobi_pkt_drop {
      type oc-yang:counter64;
      description
        "counter for OOBI okt drops";
    }
    leaf counter_slice9_ifg_mac_pool86_tx_oobi_pkt_drop_counter5_tx_oobi_pkt_drop {
      type oc-yang:counter64;
      description
        "counter for OOBI okt drops";
    }
    leaf counter_slice9_ifg_mac_pool86_tx_oobi_pkt_drop_counter6_tx_oobi_pkt_drop {
      type oc-yang:counter64;
      description
        "counter for OOBI okt drops";
    }
    leaf counter_slice9_ifg_mac_pool86_tx_oobi_pkt_drop_counter7_tx_oobi_pkt_drop {
      type oc-yang:counter64;
      description
        "counter for OOBI okt drops";
    }
    leaf counter_slice9_ifg_mac_pool87_tx_oobi_pkt_drop_counter0_tx_oobi_pkt_drop {
      type oc-yang:counter64;
      description
        "counter for OOBI okt drops";
    }
    leaf counter_slice9_ifg_mac_pool87_tx_oobi_pkt_drop_counter1_tx_oobi_pkt_drop {
      type oc-yang:counter64;
      description
        "counter for OOBI okt drops";
    }
    leaf counter_slice9_ifg_mac_pool87_tx_oobi_pkt_drop_counter2_tx_oobi_pkt_drop {
      type oc-yang:counter64;
      description
        "counter for OOBI okt drops";
    }
    leaf counter_slice9_ifg_mac_pool87_tx_oobi_pkt_drop_counter3_tx_oobi_pkt_drop {
      type oc-yang:counter64;
      description
        "counter for OOBI okt drops";
    }
    leaf counter_slice9_ifg_mac_pool87_tx_oobi_pkt_drop_counter4_tx_oobi_pkt_drop {
      type oc-yang:counter64;
      description
        "counter for OOBI okt drops";
    }
    leaf counter_slice9_ifg_mac_pool87_tx_oobi_pkt_drop_counter5_tx_oobi_pkt_drop {
      type oc-yang:counter64;
      description
        "counter for OOBI okt drops";
    }
    leaf counter_slice9_ifg_mac_pool87_tx_oobi_pkt_drop_counter6_tx_oobi_pkt_drop {
      type oc-yang:counter64;
      description
        "counter for OOBI okt drops";
    }
    leaf counter_slice9_ifg_mac_pool87_tx_oobi_pkt_drop_counter7_tx_oobi_pkt_drop {
      type oc-yang:counter64;
      description
        "counter for OOBI okt drops";
    }
    leaf counter_slice10_ifg_mac_pool80_tx_oobi_pkt_drop_counter0_tx_oobi_pkt_drop {
      type oc-yang:counter64;
      description
        "counter for OOBI okt drops";
    }
    leaf counter_slice10_ifg_mac_pool80_tx_oobi_pkt_drop_counter1_tx_oobi_pkt_drop {
      type oc-yang:counter64;
      description
        "counter for OOBI okt drops";
    }
    leaf counter_slice10_ifg_mac_pool80_tx_oobi_pkt_drop_counter2_tx_oobi_pkt_drop {
      type oc-yang:counter64;
      description
        "counter for OOBI okt drops";
    }
    leaf counter_slice10_ifg_mac_pool80_tx_oobi_pkt_drop_counter3_tx_oobi_pkt_drop {
      type oc-yang:counter64;
      description
        "counter for OOBI okt drops";
    }
    leaf counter_slice10_ifg_mac_pool80_tx_oobi_pkt_drop_counter4_tx_oobi_pkt_drop {
      type oc-yang:counter64;
      description
        "counter for OOBI okt drops";
    }
    leaf counter_slice10_ifg_mac_pool80_tx_oobi_pkt_drop_counter5_tx_oobi_pkt_drop {
      type oc-yang:counter64;
      description
        "counter for OOBI okt drops";
    }
    leaf counter_slice10_ifg_mac_pool80_tx_oobi_pkt_drop_counter6_tx_oobi_pkt_drop {
      type oc-yang:counter64;
      description
        "counter for OOBI okt drops";
    }
    leaf counter_slice10_ifg_mac_pool80_tx_oobi_pkt_drop_counter7_tx_oobi_pkt_drop {
      type oc-yang:counter64;
      description
        "counter for OOBI okt drops";
    }
    leaf counter_slice10_ifg_mac_pool81_tx_oobi_pkt_drop_counter0_tx_oobi_pkt_drop {
      type oc-yang:counter64;
      description
        "counter for OOBI okt drops";
    }
    leaf counter_slice10_ifg_mac_pool81_tx_oobi_pkt_drop_counter1_tx_oobi_pkt_drop {
      type oc-yang:counter64;
      description
        "counter for OOBI okt drops";
    }
    leaf counter_slice10_ifg_mac_pool81_tx_oobi_pkt_drop_counter2_tx_oobi_pkt_drop {
      type oc-yang:counter64;
      description
        "counter for OOBI okt drops";
    }
    leaf counter_slice10_ifg_mac_pool81_tx_oobi_pkt_drop_counter3_tx_oobi_pkt_drop {
      type oc-yang:counter64;
      description
        "counter for OOBI okt drops";
    }
    leaf counter_slice10_ifg_mac_pool81_tx_oobi_pkt_drop_counter4_tx_oobi_pkt_drop {
      type oc-yang:counter64;
      description
        "counter for OOBI okt drops";
    }
    leaf counter_slice10_ifg_mac_pool81_tx_oobi_pkt_drop_counter5_tx_oobi_pkt_drop {
      type oc-yang:counter64;
      description
        "counter for OOBI okt drops";
    }
    leaf counter_slice10_ifg_mac_pool81_tx_oobi_pkt_drop_counter6_tx_oobi_pkt_drop {
      type oc-yang:counter64;
      description
        "counter for OOBI okt drops";
    }
    leaf counter_slice10_ifg_mac_pool81_tx_oobi_pkt_drop_counter7_tx_oobi_pkt_drop {
      type oc-yang:counter64;
      description
        "counter for OOBI okt drops";
    }
    leaf counter_slice10_ifg_mac_pool82_tx_oobi_pkt_drop_counter0_tx_oobi_pkt_drop {
      type oc-yang:counter64;
      description
        "counter for OOBI okt drops";
    }
    leaf counter_slice10_ifg_mac_pool82_tx_oobi_pkt_drop_counter1_tx_oobi_pkt_drop {
      type oc-yang:counter64;
      description
        "counter for OOBI okt drops";
    }
    leaf counter_slice10_ifg_mac_pool82_tx_oobi_pkt_drop_counter2_tx_oobi_pkt_drop {
      type oc-yang:counter64;
      description
        "counter for OOBI okt drops";
    }
    leaf counter_slice10_ifg_mac_pool82_tx_oobi_pkt_drop_counter3_tx_oobi_pkt_drop {
      type oc-yang:counter64;
      description
        "counter for OOBI okt drops";
    }
    leaf counter_slice10_ifg_mac_pool82_tx_oobi_pkt_drop_counter4_tx_oobi_pkt_drop {
      type oc-yang:counter64;
      description
        "counter for OOBI okt drops";
    }
    leaf counter_slice10_ifg_mac_pool82_tx_oobi_pkt_drop_counter5_tx_oobi_pkt_drop {
      type oc-yang:counter64;
      description
        "counter for OOBI okt drops";
    }
    leaf counter_slice10_ifg_mac_pool82_tx_oobi_pkt_drop_counter6_tx_oobi_pkt_drop {
      type oc-yang:counter64;
      description
        "counter for OOBI okt drops";
    }
    leaf counter_slice10_ifg_mac_pool82_tx_oobi_pkt_drop_counter7_tx_oobi_pkt_drop {
      type oc-yang:counter64;
      description
        "counter for OOBI okt drops";
    }
    leaf counter_slice10_ifg_mac_pool83_tx_oobi_pkt_drop_counter0_tx_oobi_pkt_drop {
      type oc-yang:counter64;
      description
        "counter for OOBI okt drops";
    }
    leaf counter_slice10_ifg_mac_pool83_tx_oobi_pkt_drop_counter1_tx_oobi_pkt_drop {
      type oc-yang:counter64;
      description
        "counter for OOBI okt drops";
    }
    leaf counter_slice10_ifg_mac_pool83_tx_oobi_pkt_drop_counter2_tx_oobi_pkt_drop {
      type oc-yang:counter64;
      description
        "counter for OOBI okt drops";
    }
    leaf counter_slice10_ifg_mac_pool83_tx_oobi_pkt_drop_counter3_tx_oobi_pkt_drop {
      type oc-yang:counter64;
      description
        "counter for OOBI okt drops";
    }
    leaf counter_slice10_ifg_mac_pool83_tx_oobi_pkt_drop_counter4_tx_oobi_pkt_drop {
      type oc-yang:counter64;
      description
        "counter for OOBI okt drops";
    }
    leaf counter_slice10_ifg_mac_pool83_tx_oobi_pkt_drop_counter5_tx_oobi_pkt_drop {
      type oc-yang:counter64;
      description
        "counter for OOBI okt drops";
    }
    leaf counter_slice10_ifg_mac_pool83_tx_oobi_pkt_drop_counter6_tx_oobi_pkt_drop {
      type oc-yang:counter64;
      description
        "counter for OOBI okt drops";
    }
    leaf counter_slice10_ifg_mac_pool83_tx_oobi_pkt_drop_counter7_tx_oobi_pkt_drop {
      type oc-yang:counter64;
      description
        "counter for OOBI okt drops";
    }
    leaf counter_slice10_ifg_mac_pool84_tx_oobi_pkt_drop_counter0_tx_oobi_pkt_drop {
      type oc-yang:counter64;
      description
        "counter for OOBI okt drops";
    }
    leaf counter_slice10_ifg_mac_pool84_tx_oobi_pkt_drop_counter1_tx_oobi_pkt_drop {
      type oc-yang:counter64;
      description
        "counter for OOBI okt drops";
    }
    leaf counter_slice10_ifg_mac_pool84_tx_oobi_pkt_drop_counter2_tx_oobi_pkt_drop {
      type oc-yang:counter64;
      description
        "counter for OOBI okt drops";
    }
    leaf counter_slice10_ifg_mac_pool84_tx_oobi_pkt_drop_counter3_tx_oobi_pkt_drop {
      type oc-yang:counter64;
      description
        "counter for OOBI okt drops";
    }
    leaf counter_slice10_ifg_mac_pool84_tx_oobi_pkt_drop_counter4_tx_oobi_pkt_drop {
      type oc-yang:counter64;
      description
        "counter for OOBI okt drops";
    }
    leaf counter_slice10_ifg_mac_pool84_tx_oobi_pkt_drop_counter5_tx_oobi_pkt_drop {
      type oc-yang:counter64;
      description
        "counter for OOBI okt drops";
    }
    leaf counter_slice10_ifg_mac_pool84_tx_oobi_pkt_drop_counter6_tx_oobi_pkt_drop {
      type oc-yang:counter64;
      description
        "counter for OOBI okt drops";
    }
    leaf counter_slice10_ifg_mac_pool84_tx_oobi_pkt_drop_counter7_tx_oobi_pkt_drop {
      type oc-yang:counter64;
      description
        "counter for OOBI okt drops";
    }
    leaf counter_slice10_ifg_mac_pool85_tx_oobi_pkt_drop_counter0_tx_oobi_pkt_drop {
      type oc-yang:counter64;
      description
        "counter for OOBI okt drops";
    }
    leaf counter_slice10_ifg_mac_pool85_tx_oobi_pkt_drop_counter1_tx_oobi_pkt_drop {
      type oc-yang:counter64;
      description
        "counter for OOBI okt drops";
    }
    leaf counter_slice10_ifg_mac_pool85_tx_oobi_pkt_drop_counter2_tx_oobi_pkt_drop {
      type oc-yang:counter64;
      description
        "counter for OOBI okt drops";
    }
    leaf counter_slice10_ifg_mac_pool85_tx_oobi_pkt_drop_counter3_tx_oobi_pkt_drop {
      type oc-yang:counter64;
      description
        "counter for OOBI okt drops";
    }
    leaf counter_slice10_ifg_mac_pool85_tx_oobi_pkt_drop_counter4_tx_oobi_pkt_drop {
      type oc-yang:counter64;
      description
        "counter for OOBI okt drops";
    }
    leaf counter_slice10_ifg_mac_pool85_tx_oobi_pkt_drop_counter5_tx_oobi_pkt_drop {
      type oc-yang:counter64;
      description
        "counter for OOBI okt drops";
    }
    leaf counter_slice10_ifg_mac_pool85_tx_oobi_pkt_drop_counter6_tx_oobi_pkt_drop {
      type oc-yang:counter64;
      description
        "counter for OOBI okt drops";
    }
    leaf counter_slice10_ifg_mac_pool85_tx_oobi_pkt_drop_counter7_tx_oobi_pkt_drop {
      type oc-yang:counter64;
      description
        "counter for OOBI okt drops";
    }
    leaf counter_slice10_ifg_mac_pool86_tx_oobi_pkt_drop_counter0_tx_oobi_pkt_drop {
      type oc-yang:counter64;
      description
        "counter for OOBI okt drops";
    }
    leaf counter_slice10_ifg_mac_pool86_tx_oobi_pkt_drop_counter1_tx_oobi_pkt_drop {
      type oc-yang:counter64;
      description
        "counter for OOBI okt drops";
    }
    leaf counter_slice10_ifg_mac_pool86_tx_oobi_pkt_drop_counter2_tx_oobi_pkt_drop {
      type oc-yang:counter64;
      description
        "counter for OOBI okt drops";
    }
    leaf counter_slice10_ifg_mac_pool86_tx_oobi_pkt_drop_counter3_tx_oobi_pkt_drop {
      type oc-yang:counter64;
      description
        "counter for OOBI okt drops";
    }
    leaf counter_slice10_ifg_mac_pool86_tx_oobi_pkt_drop_counter4_tx_oobi_pkt_drop {
      type oc-yang:counter64;
      description
        "counter for OOBI okt drops";
    }
    leaf counter_slice10_ifg_mac_pool86_tx_oobi_pkt_drop_counter5_tx_oobi_pkt_drop {
      type oc-yang:counter64;
      description
        "counter for OOBI okt drops";
    }
    leaf counter_slice10_ifg_mac_pool86_tx_oobi_pkt_drop_counter6_tx_oobi_pkt_drop {
      type oc-yang:counter64;
      description
        "counter for OOBI okt drops";
    }
    leaf counter_slice10_ifg_mac_pool86_tx_oobi_pkt_drop_counter7_tx_oobi_pkt_drop {
      type oc-yang:counter64;
      description
        "counter for OOBI okt drops";
    }
    leaf counter_slice10_ifg_mac_pool87_tx_oobi_pkt_drop_counter0_tx_oobi_pkt_drop {
      type oc-yang:counter64;
      description
        "counter for OOBI okt drops";
    }
    leaf counter_slice10_ifg_mac_pool87_tx_oobi_pkt_drop_counter1_tx_oobi_pkt_drop {
      type oc-yang:counter64;
      description
        "counter for OOBI okt drops";
    }
    leaf counter_slice10_ifg_mac_pool87_tx_oobi_pkt_drop_counter2_tx_oobi_pkt_drop {
      type oc-yang:counter64;
      description
        "counter for OOBI okt drops";
    }
    leaf counter_slice10_ifg_mac_pool87_tx_oobi_pkt_drop_counter3_tx_oobi_pkt_drop {
      type oc-yang:counter64;
      description
        "counter for OOBI okt drops";
    }
    leaf counter_slice10_ifg_mac_pool87_tx_oobi_pkt_drop_counter4_tx_oobi_pkt_drop {
      type oc-yang:counter64;
      description
        "counter for OOBI okt drops";
    }
    leaf counter_slice10_ifg_mac_pool87_tx_oobi_pkt_drop_counter5_tx_oobi_pkt_drop {
      type oc-yang:counter64;
      description
        "counter for OOBI okt drops";
    }
    leaf counter_slice10_ifg_mac_pool87_tx_oobi_pkt_drop_counter6_tx_oobi_pkt_drop {
      type oc-yang:counter64;
      description
        "counter for OOBI okt drops";
    }
    leaf counter_slice10_ifg_mac_pool87_tx_oobi_pkt_drop_counter7_tx_oobi_pkt_drop {
      type oc-yang:counter64;
      description
        "counter for OOBI okt drops";
    }
    leaf counter_slice11_ifg_mac_pool80_tx_oobi_pkt_drop_counter0_tx_oobi_pkt_drop {
      type oc-yang:counter64;
      description
        "counter for OOBI okt drops";
    }
    leaf counter_slice11_ifg_mac_pool80_tx_oobi_pkt_drop_counter1_tx_oobi_pkt_drop {
      type oc-yang:counter64;
      description
        "counter for OOBI okt drops";
    }
    leaf counter_slice11_ifg_mac_pool80_tx_oobi_pkt_drop_counter2_tx_oobi_pkt_drop {
      type oc-yang:counter64;
      description
        "counter for OOBI okt drops";
    }
    leaf counter_slice11_ifg_mac_pool80_tx_oobi_pkt_drop_counter3_tx_oobi_pkt_drop {
      type oc-yang:counter64;
      description
        "counter for OOBI okt drops";
    }
    leaf counter_slice11_ifg_mac_pool80_tx_oobi_pkt_drop_counter4_tx_oobi_pkt_drop {
      type oc-yang:counter64;
      description
        "counter for OOBI okt drops";
    }
    leaf counter_slice11_ifg_mac_pool80_tx_oobi_pkt_drop_counter5_tx_oobi_pkt_drop {
      type oc-yang:counter64;
      description
        "counter for OOBI okt drops";
    }
    leaf counter_slice11_ifg_mac_pool80_tx_oobi_pkt_drop_counter6_tx_oobi_pkt_drop {
      type oc-yang:counter64;
      description
        "counter for OOBI okt drops";
    }
    leaf counter_slice11_ifg_mac_pool80_tx_oobi_pkt_drop_counter7_tx_oobi_pkt_drop {
      type oc-yang:counter64;
      description
        "counter for OOBI okt drops";
    }
    leaf counter_slice11_ifg_mac_pool81_tx_oobi_pkt_drop_counter0_tx_oobi_pkt_drop {
      type oc-yang:counter64;
      description
        "counter for OOBI okt drops";
    }
    leaf counter_slice11_ifg_mac_pool81_tx_oobi_pkt_drop_counter1_tx_oobi_pkt_drop {
      type oc-yang:counter64;
      description
        "counter for OOBI okt drops";
    }
    leaf counter_slice11_ifg_mac_pool81_tx_oobi_pkt_drop_counter2_tx_oobi_pkt_drop {
      type oc-yang:counter64;
      description
        "counter for OOBI okt drops";
    }
    leaf counter_slice11_ifg_mac_pool81_tx_oobi_pkt_drop_counter3_tx_oobi_pkt_drop {
      type oc-yang:counter64;
      description
        "counter for OOBI okt drops";
    }
    leaf counter_slice11_ifg_mac_pool81_tx_oobi_pkt_drop_counter4_tx_oobi_pkt_drop {
      type oc-yang:counter64;
      description
        "counter for OOBI okt drops";
    }
    leaf counter_slice11_ifg_mac_pool81_tx_oobi_pkt_drop_counter5_tx_oobi_pkt_drop {
      type oc-yang:counter64;
      description
        "counter for OOBI okt drops";
    }
    leaf counter_slice11_ifg_mac_pool81_tx_oobi_pkt_drop_counter6_tx_oobi_pkt_drop {
      type oc-yang:counter64;
      description
        "counter for OOBI okt drops";
    }
    leaf counter_slice11_ifg_mac_pool81_tx_oobi_pkt_drop_counter7_tx_oobi_pkt_drop {
      type oc-yang:counter64;
      description
        "counter for OOBI okt drops";
    }
    leaf counter_slice11_ifg_mac_pool82_tx_oobi_pkt_drop_counter0_tx_oobi_pkt_drop {
      type oc-yang:counter64;
      description
        "counter for OOBI okt drops";
    }
    leaf counter_slice11_ifg_mac_pool82_tx_oobi_pkt_drop_counter1_tx_oobi_pkt_drop {
      type oc-yang:counter64;
      description
        "counter for OOBI okt drops";
    }
    leaf counter_slice11_ifg_mac_pool82_tx_oobi_pkt_drop_counter2_tx_oobi_pkt_drop {
      type oc-yang:counter64;
      description
        "counter for OOBI okt drops";
    }
    leaf counter_slice11_ifg_mac_pool82_tx_oobi_pkt_drop_counter3_tx_oobi_pkt_drop {
      type oc-yang:counter64;
      description
        "counter for OOBI okt drops";
    }
    leaf counter_slice11_ifg_mac_pool82_tx_oobi_pkt_drop_counter4_tx_oobi_pkt_drop {
      type oc-yang:counter64;
      description
        "counter for OOBI okt drops";
    }
    leaf counter_slice11_ifg_mac_pool82_tx_oobi_pkt_drop_counter5_tx_oobi_pkt_drop {
      type oc-yang:counter64;
      description
        "counter for OOBI okt drops";
    }
    leaf counter_slice11_ifg_mac_pool82_tx_oobi_pkt_drop_counter6_tx_oobi_pkt_drop {
      type oc-yang:counter64;
      description
        "counter for OOBI okt drops";
    }
    leaf counter_slice11_ifg_mac_pool82_tx_oobi_pkt_drop_counter7_tx_oobi_pkt_drop {
      type oc-yang:counter64;
      description
        "counter for OOBI okt drops";
    }
    leaf counter_slice11_ifg_mac_pool83_tx_oobi_pkt_drop_counter0_tx_oobi_pkt_drop {
      type oc-yang:counter64;
      description
        "counter for OOBI okt drops";
    }
    leaf counter_slice11_ifg_mac_pool83_tx_oobi_pkt_drop_counter1_tx_oobi_pkt_drop {
      type oc-yang:counter64;
      description
        "counter for OOBI okt drops";
    }
    leaf counter_slice11_ifg_mac_pool83_tx_oobi_pkt_drop_counter2_tx_oobi_pkt_drop {
      type oc-yang:counter64;
      description
        "counter for OOBI okt drops";
    }
    leaf counter_slice11_ifg_mac_pool83_tx_oobi_pkt_drop_counter3_tx_oobi_pkt_drop {
      type oc-yang:counter64;
      description
        "counter for OOBI okt drops";
    }
    leaf counter_slice11_ifg_mac_pool83_tx_oobi_pkt_drop_counter4_tx_oobi_pkt_drop {
      type oc-yang:counter64;
      description
        "counter for OOBI okt drops";
    }
    leaf counter_slice11_ifg_mac_pool83_tx_oobi_pkt_drop_counter5_tx_oobi_pkt_drop {
      type oc-yang:counter64;
      description
        "counter for OOBI okt drops";
    }
    leaf counter_slice11_ifg_mac_pool83_tx_oobi_pkt_drop_counter6_tx_oobi_pkt_drop {
      type oc-yang:counter64;
      description
        "counter for OOBI okt drops";
    }
    leaf counter_slice11_ifg_mac_pool83_tx_oobi_pkt_drop_counter7_tx_oobi_pkt_drop {
      type oc-yang:counter64;
      description
        "counter for OOBI okt drops";
    }
    leaf counter_slice11_ifg_mac_pool84_tx_oobi_pkt_drop_counter0_tx_oobi_pkt_drop {
      type oc-yang:counter64;
      description
        "counter for OOBI okt drops";
    }
    leaf counter_slice11_ifg_mac_pool84_tx_oobi_pkt_drop_counter1_tx_oobi_pkt_drop {
      type oc-yang:counter64;
      description
        "counter for OOBI okt drops";
    }
    leaf counter_slice11_ifg_mac_pool84_tx_oobi_pkt_drop_counter2_tx_oobi_pkt_drop {
      type oc-yang:counter64;
      description
        "counter for OOBI okt drops";
    }
    leaf counter_slice11_ifg_mac_pool84_tx_oobi_pkt_drop_counter3_tx_oobi_pkt_drop {
      type oc-yang:counter64;
      description
        "counter for OOBI okt drops";
    }
    leaf counter_slice11_ifg_mac_pool84_tx_oobi_pkt_drop_counter4_tx_oobi_pkt_drop {
      type oc-yang:counter64;
      description
        "counter for OOBI okt drops";
    }
    leaf counter_slice11_ifg_mac_pool84_tx_oobi_pkt_drop_counter5_tx_oobi_pkt_drop {
      type oc-yang:counter64;
      description
        "counter for OOBI okt drops";
    }
    leaf counter_slice11_ifg_mac_pool84_tx_oobi_pkt_drop_counter6_tx_oobi_pkt_drop {
      type oc-yang:counter64;
      description
        "counter for OOBI okt drops";
    }
    leaf counter_slice11_ifg_mac_pool84_tx_oobi_pkt_drop_counter7_tx_oobi_pkt_drop {
      type oc-yang:counter64;
      description
        "counter for OOBI okt drops";
    }
    leaf counter_slice11_ifg_mac_pool85_tx_oobi_pkt_drop_counter0_tx_oobi_pkt_drop {
      type oc-yang:counter64;
      description
        "counter for OOBI okt drops";
    }
    leaf counter_slice11_ifg_mac_pool85_tx_oobi_pkt_drop_counter1_tx_oobi_pkt_drop {
      type oc-yang:counter64;
      description
        "counter for OOBI okt drops";
    }
    leaf counter_slice11_ifg_mac_pool85_tx_oobi_pkt_drop_counter2_tx_oobi_pkt_drop {
      type oc-yang:counter64;
      description
        "counter for OOBI okt drops";
    }
    leaf counter_slice11_ifg_mac_pool85_tx_oobi_pkt_drop_counter3_tx_oobi_pkt_drop {
      type oc-yang:counter64;
      description
        "counter for OOBI okt drops";
    }
    leaf counter_slice11_ifg_mac_pool85_tx_oobi_pkt_drop_counter4_tx_oobi_pkt_drop {
      type oc-yang:counter64;
      description
        "counter for OOBI okt drops";
    }
    leaf counter_slice11_ifg_mac_pool85_tx_oobi_pkt_drop_counter5_tx_oobi_pkt_drop {
      type oc-yang:counter64;
      description
        "counter for OOBI okt drops";
    }
    leaf counter_slice11_ifg_mac_pool85_tx_oobi_pkt_drop_counter6_tx_oobi_pkt_drop {
      type oc-yang:counter64;
      description
        "counter for OOBI okt drops";
    }
    leaf counter_slice11_ifg_mac_pool85_tx_oobi_pkt_drop_counter7_tx_oobi_pkt_drop {
      type oc-yang:counter64;
      description
        "counter for OOBI okt drops";
    }
    leaf counter_slice11_ifg_mac_pool86_tx_oobi_pkt_drop_counter0_tx_oobi_pkt_drop {
      type oc-yang:counter64;
      description
        "counter for OOBI okt drops";
    }
    leaf counter_slice11_ifg_mac_pool86_tx_oobi_pkt_drop_counter1_tx_oobi_pkt_drop {
      type oc-yang:counter64;
      description
        "counter for OOBI okt drops";
    }
    leaf counter_slice11_ifg_mac_pool86_tx_oobi_pkt_drop_counter2_tx_oobi_pkt_drop {
      type oc-yang:counter64;
      description
        "counter for OOBI okt drops";
    }
    leaf counter_slice11_ifg_mac_pool86_tx_oobi_pkt_drop_counter3_tx_oobi_pkt_drop {
      type oc-yang:counter64;
      description
        "counter for OOBI okt drops";
    }
    leaf counter_slice11_ifg_mac_pool86_tx_oobi_pkt_drop_counter4_tx_oobi_pkt_drop {
      type oc-yang:counter64;
      description
        "counter for OOBI okt drops";
    }
    leaf counter_slice11_ifg_mac_pool86_tx_oobi_pkt_drop_counter5_tx_oobi_pkt_drop {
      type oc-yang:counter64;
      description
        "counter for OOBI okt drops";
    }
    leaf counter_slice11_ifg_mac_pool86_tx_oobi_pkt_drop_counter6_tx_oobi_pkt_drop {
      type oc-yang:counter64;
      description
        "counter for OOBI okt drops";
    }
    leaf counter_slice11_ifg_mac_pool86_tx_oobi_pkt_drop_counter7_tx_oobi_pkt_drop {
      type oc-yang:counter64;
      description
        "counter for OOBI okt drops";
    }
    leaf counter_slice11_ifg_mac_pool87_tx_oobi_pkt_drop_counter0_tx_oobi_pkt_drop {
      type oc-yang:counter64;
      description
        "counter for OOBI okt drops";
    }
    leaf counter_slice11_ifg_mac_pool87_tx_oobi_pkt_drop_counter1_tx_oobi_pkt_drop {
      type oc-yang:counter64;
      description
        "counter for OOBI okt drops";
    }
    leaf counter_slice11_ifg_mac_pool87_tx_oobi_pkt_drop_counter2_tx_oobi_pkt_drop {
      type oc-yang:counter64;
      description
        "counter for OOBI okt drops";
    }
    leaf counter_slice11_ifg_mac_pool87_tx_oobi_pkt_drop_counter3_tx_oobi_pkt_drop {
      type oc-yang:counter64;
      description
        "counter for OOBI okt drops";
    }
    leaf counter_slice11_ifg_mac_pool87_tx_oobi_pkt_drop_counter4_tx_oobi_pkt_drop {
      type oc-yang:counter64;
      description
        "counter for OOBI okt drops";
    }
    leaf counter_slice11_ifg_mac_pool87_tx_oobi_pkt_drop_counter5_tx_oobi_pkt_drop {
      type oc-yang:counter64;
      description
        "counter for OOBI okt drops";
    }
    leaf counter_slice11_ifg_mac_pool87_tx_oobi_pkt_drop_counter6_tx_oobi_pkt_drop {
      type oc-yang:counter64;
      description
        "counter for OOBI okt drops";
    }
    leaf counter_slice11_ifg_mac_pool87_tx_oobi_pkt_drop_counter7_tx_oobi_pkt_drop {
      type oc-yang:counter64;
      description
        "counter for OOBI okt drops";
    }
    leaf counter_slice12_ifg_mac_pool80_tx_oobi_pkt_drop_counter0_tx_oobi_pkt_drop {
      type oc-yang:counter64;
      description
        "counter for OOBI okt drops";
    }
    leaf counter_slice12_ifg_mac_pool80_tx_oobi_pkt_drop_counter1_tx_oobi_pkt_drop {
      type oc-yang:counter64;
      description
        "counter for OOBI okt drops";
    }
    leaf counter_slice12_ifg_mac_pool80_tx_oobi_pkt_drop_counter2_tx_oobi_pkt_drop {
      type oc-yang:counter64;
      description
        "counter for OOBI okt drops";
    }
    leaf counter_slice12_ifg_mac_pool80_tx_oobi_pkt_drop_counter3_tx_oobi_pkt_drop {
      type oc-yang:counter64;
      description
        "counter for OOBI okt drops";
    }
    leaf counter_slice12_ifg_mac_pool80_tx_oobi_pkt_drop_counter4_tx_oobi_pkt_drop {
      type oc-yang:counter64;
      description
        "counter for OOBI okt drops";
    }
    leaf counter_slice12_ifg_mac_pool80_tx_oobi_pkt_drop_counter5_tx_oobi_pkt_drop {
      type oc-yang:counter64;
      description
        "counter for OOBI okt drops";
    }
    leaf counter_slice12_ifg_mac_pool80_tx_oobi_pkt_drop_counter6_tx_oobi_pkt_drop {
      type oc-yang:counter64;
      description
        "counter for OOBI okt drops";
    }
    leaf counter_slice12_ifg_mac_pool80_tx_oobi_pkt_drop_counter7_tx_oobi_pkt_drop {
      type oc-yang:counter64;
      description
        "counter for OOBI okt drops";
    }
    leaf counter_slice12_ifg_mac_pool81_tx_oobi_pkt_drop_counter0_tx_oobi_pkt_drop {
      type oc-yang:counter64;
      description
        "counter for OOBI okt drops";
    }
    leaf counter_slice12_ifg_mac_pool81_tx_oobi_pkt_drop_counter1_tx_oobi_pkt_drop {
      type oc-yang:counter64;
      description
        "counter for OOBI okt drops";
    }
    leaf counter_slice12_ifg_mac_pool81_tx_oobi_pkt_drop_counter2_tx_oobi_pkt_drop {
      type oc-yang:counter64;
      description
        "counter for OOBI okt drops";
    }
    leaf counter_slice12_ifg_mac_pool81_tx_oobi_pkt_drop_counter3_tx_oobi_pkt_drop {
      type oc-yang:counter64;
      description
        "counter for OOBI okt drops";
    }
    leaf counter_slice12_ifg_mac_pool81_tx_oobi_pkt_drop_counter4_tx_oobi_pkt_drop {
      type oc-yang:counter64;
      description
        "counter for OOBI okt drops";
    }
    leaf counter_slice12_ifg_mac_pool81_tx_oobi_pkt_drop_counter5_tx_oobi_pkt_drop {
      type oc-yang:counter64;
      description
        "counter for OOBI okt drops";
    }
    leaf counter_slice12_ifg_mac_pool81_tx_oobi_pkt_drop_counter6_tx_oobi_pkt_drop {
      type oc-yang:counter64;
      description
        "counter for OOBI okt drops";
    }
    leaf counter_slice12_ifg_mac_pool81_tx_oobi_pkt_drop_counter7_tx_oobi_pkt_drop {
      type oc-yang:counter64;
      description
        "counter for OOBI okt drops";
    }
    leaf counter_slice12_ifg_mac_pool82_tx_oobi_pkt_drop_counter0_tx_oobi_pkt_drop {
      type oc-yang:counter64;
      description
        "counter for OOBI okt drops";
    }
    leaf counter_slice12_ifg_mac_pool82_tx_oobi_pkt_drop_counter1_tx_oobi_pkt_drop {
      type oc-yang:counter64;
      description
        "counter for OOBI okt drops";
    }
    leaf counter_slice12_ifg_mac_pool82_tx_oobi_pkt_drop_counter2_tx_oobi_pkt_drop {
      type oc-yang:counter64;
      description
        "counter for OOBI okt drops";
    }
    leaf counter_slice12_ifg_mac_pool82_tx_oobi_pkt_drop_counter3_tx_oobi_pkt_drop {
      type oc-yang:counter64;
      description
        "counter for OOBI okt drops";
    }
    leaf counter_slice12_ifg_mac_pool82_tx_oobi_pkt_drop_counter4_tx_oobi_pkt_drop {
      type oc-yang:counter64;
      description
        "counter for OOBI okt drops";
    }
    leaf counter_slice12_ifg_mac_pool82_tx_oobi_pkt_drop_counter5_tx_oobi_pkt_drop {
      type oc-yang:counter64;
      description
        "counter for OOBI okt drops";
    }
    leaf counter_slice12_ifg_mac_pool82_tx_oobi_pkt_drop_counter6_tx_oobi_pkt_drop {
      type oc-yang:counter64;
      description
        "counter for OOBI okt drops";
    }
    leaf counter_slice12_ifg_mac_pool82_tx_oobi_pkt_drop_counter7_tx_oobi_pkt_drop {
      type oc-yang:counter64;
      description
        "counter for OOBI okt drops";
    }
    leaf counter_slice12_ifg_mac_pool83_tx_oobi_pkt_drop_counter0_tx_oobi_pkt_drop {
      type oc-yang:counter64;
      description
        "counter for OOBI okt drops";
    }
    leaf counter_slice12_ifg_mac_pool83_tx_oobi_pkt_drop_counter1_tx_oobi_pkt_drop {
      type oc-yang:counter64;
      description
        "counter for OOBI okt drops";
    }
    leaf counter_slice12_ifg_mac_pool83_tx_oobi_pkt_drop_counter2_tx_oobi_pkt_drop {
      type oc-yang:counter64;
      description
        "counter for OOBI okt drops";
    }
    leaf counter_slice12_ifg_mac_pool83_tx_oobi_pkt_drop_counter3_tx_oobi_pkt_drop {
      type oc-yang:counter64;
      description
        "counter for OOBI okt drops";
    }
    leaf counter_slice12_ifg_mac_pool83_tx_oobi_pkt_drop_counter4_tx_oobi_pkt_drop {
      type oc-yang:counter64;
      description
        "counter for OOBI okt drops";
    }
    leaf counter_slice12_ifg_mac_pool83_tx_oobi_pkt_drop_counter5_tx_oobi_pkt_drop {
      type oc-yang:counter64;
      description
        "counter for OOBI okt drops";
    }
    leaf counter_slice12_ifg_mac_pool83_tx_oobi_pkt_drop_counter6_tx_oobi_pkt_drop {
      type oc-yang:counter64;
      description
        "counter for OOBI okt drops";
    }
    leaf counter_slice12_ifg_mac_pool83_tx_oobi_pkt_drop_counter7_tx_oobi_pkt_drop {
      type oc-yang:counter64;
      description
        "counter for OOBI okt drops";
    }
    leaf counter_slice12_ifg_mac_pool84_tx_oobi_pkt_drop_counter0_tx_oobi_pkt_drop {
      type oc-yang:counter64;
      description
        "counter for OOBI okt drops";
    }
    leaf counter_slice12_ifg_mac_pool84_tx_oobi_pkt_drop_counter1_tx_oobi_pkt_drop {
      type oc-yang:counter64;
      description
        "counter for OOBI okt drops";
    }
    leaf counter_slice12_ifg_mac_pool84_tx_oobi_pkt_drop_counter2_tx_oobi_pkt_drop {
      type oc-yang:counter64;
      description
        "counter for OOBI okt drops";
    }
    leaf counter_slice12_ifg_mac_pool84_tx_oobi_pkt_drop_counter3_tx_oobi_pkt_drop {
      type oc-yang:counter64;
      description
        "counter for OOBI okt drops";
    }
    leaf counter_slice12_ifg_mac_pool84_tx_oobi_pkt_drop_counter4_tx_oobi_pkt_drop {
      type oc-yang:counter64;
      description
        "counter for OOBI okt drops";
    }
    leaf counter_slice12_ifg_mac_pool84_tx_oobi_pkt_drop_counter5_tx_oobi_pkt_drop {
      type oc-yang:counter64;
      description
        "counter for OOBI okt drops";
    }
    leaf counter_slice12_ifg_mac_pool84_tx_oobi_pkt_drop_counter6_tx_oobi_pkt_drop {
      type oc-yang:counter64;
      description
        "counter for OOBI okt drops";
    }
    leaf counter_slice12_ifg_mac_pool84_tx_oobi_pkt_drop_counter7_tx_oobi_pkt_drop {
      type oc-yang:counter64;
      description
        "counter for OOBI okt drops";
    }
    leaf counter_slice12_ifg_mac_pool85_tx_oobi_pkt_drop_counter0_tx_oobi_pkt_drop {
      type oc-yang:counter64;
      description
        "counter for OOBI okt drops";
    }
    leaf counter_slice12_ifg_mac_pool85_tx_oobi_pkt_drop_counter1_tx_oobi_pkt_drop {
      type oc-yang:counter64;
      description
        "counter for OOBI okt drops";
    }
    leaf counter_slice12_ifg_mac_pool85_tx_oobi_pkt_drop_counter2_tx_oobi_pkt_drop {
      type oc-yang:counter64;
      description
        "counter for OOBI okt drops";
    }
    leaf counter_slice12_ifg_mac_pool85_tx_oobi_pkt_drop_counter3_tx_oobi_pkt_drop {
      type oc-yang:counter64;
      description
        "counter for OOBI okt drops";
    }
    leaf counter_slice12_ifg_mac_pool85_tx_oobi_pkt_drop_counter4_tx_oobi_pkt_drop {
      type oc-yang:counter64;
      description
        "counter for OOBI okt drops";
    }
    leaf counter_slice12_ifg_mac_pool85_tx_oobi_pkt_drop_counter5_tx_oobi_pkt_drop {
      type oc-yang:counter64;
      description
        "counter for OOBI okt drops";
    }
    leaf counter_slice12_ifg_mac_pool85_tx_oobi_pkt_drop_counter6_tx_oobi_pkt_drop {
      type oc-yang:counter64;
      description
        "counter for OOBI okt drops";
    }
    leaf counter_slice12_ifg_mac_pool85_tx_oobi_pkt_drop_counter7_tx_oobi_pkt_drop {
      type oc-yang:counter64;
      description
        "counter for OOBI okt drops";
    }
    leaf counter_slice12_ifg_mac_pool86_tx_oobi_pkt_drop_counter0_tx_oobi_pkt_drop {
      type oc-yang:counter64;
      description
        "counter for OOBI okt drops";
    }
    leaf counter_slice12_ifg_mac_pool86_tx_oobi_pkt_drop_counter1_tx_oobi_pkt_drop {
      type oc-yang:counter64;
      description
        "counter for OOBI okt drops";
    }
    leaf counter_slice12_ifg_mac_pool86_tx_oobi_pkt_drop_counter2_tx_oobi_pkt_drop {
      type oc-yang:counter64;
      description
        "counter for OOBI okt drops";
    }
    leaf counter_slice12_ifg_mac_pool86_tx_oobi_pkt_drop_counter3_tx_oobi_pkt_drop {
      type oc-yang:counter64;
      description
        "counter for OOBI okt drops";
    }
    leaf counter_slice12_ifg_mac_pool86_tx_oobi_pkt_drop_counter4_tx_oobi_pkt_drop {
      type oc-yang:counter64;
      description
        "counter for OOBI okt drops";
    }
    leaf counter_slice12_ifg_mac_pool86_tx_oobi_pkt_drop_counter5_tx_oobi_pkt_drop {
      type oc-yang:counter64;
      description
        "counter for OOBI okt drops";
    }
    leaf counter_slice12_ifg_mac_pool86_tx_oobi_pkt_drop_counter6_tx_oobi_pkt_drop {
      type oc-yang:counter64;
      description
        "counter for OOBI okt drops";
    }
    leaf counter_slice12_ifg_mac_pool86_tx_oobi_pkt_drop_counter7_tx_oobi_pkt_drop {
      type oc-yang:counter64;
      description
        "counter for OOBI okt drops";
    }
    leaf counter_slice12_ifg_mac_pool87_tx_oobi_pkt_drop_counter0_tx_oobi_pkt_drop {
      type oc-yang:counter64;
      description
        "counter for OOBI okt drops";
    }
    leaf counter_slice12_ifg_mac_pool87_tx_oobi_pkt_drop_counter1_tx_oobi_pkt_drop {
      type oc-yang:counter64;
      description
        "counter for OOBI okt drops";
    }
    leaf counter_slice12_ifg_mac_pool87_tx_oobi_pkt_drop_counter2_tx_oobi_pkt_drop {
      type oc-yang:counter64;
      description
        "counter for OOBI okt drops";
    }
    leaf counter_slice12_ifg_mac_pool87_tx_oobi_pkt_drop_counter3_tx_oobi_pkt_drop {
      type oc-yang:counter64;
      description
        "counter for OOBI okt drops";
    }
    leaf counter_slice12_ifg_mac_pool87_tx_oobi_pkt_drop_counter4_tx_oobi_pkt_drop {
      type oc-yang:counter64;
      description
        "counter for OOBI okt drops";
    }
    leaf counter_slice12_ifg_mac_pool87_tx_oobi_pkt_drop_counter5_tx_oobi_pkt_drop {
      type oc-yang:counter64;
      description
        "counter for OOBI okt drops";
    }
    leaf counter_slice12_ifg_mac_pool87_tx_oobi_pkt_drop_counter6_tx_oobi_pkt_drop {
      type oc-yang:counter64;
      description
        "counter for OOBI okt drops";
    }
    leaf counter_slice12_ifg_mac_pool87_tx_oobi_pkt_drop_counter7_tx_oobi_pkt_drop {
      type oc-yang:counter64;
      description
        "counter for OOBI okt drops";
    }
    leaf counter_slice13_ifg_mac_pool80_tx_oobi_pkt_drop_counter0_tx_oobi_pkt_drop {
      type oc-yang:counter64;
      description
        "counter for OOBI okt drops";
    }
    leaf counter_slice13_ifg_mac_pool80_tx_oobi_pkt_drop_counter1_tx_oobi_pkt_drop {
      type oc-yang:counter64;
      description
        "counter for OOBI okt drops";
    }
    leaf counter_slice13_ifg_mac_pool80_tx_oobi_pkt_drop_counter2_tx_oobi_pkt_drop {
      type oc-yang:counter64;
      description
        "counter for OOBI okt drops";
    }
    leaf counter_slice13_ifg_mac_pool80_tx_oobi_pkt_drop_counter3_tx_oobi_pkt_drop {
      type oc-yang:counter64;
      description
        "counter for OOBI okt drops";
    }
    leaf counter_slice13_ifg_mac_pool80_tx_oobi_pkt_drop_counter4_tx_oobi_pkt_drop {
      type oc-yang:counter64;
      description
        "counter for OOBI okt drops";
    }
    leaf counter_slice13_ifg_mac_pool80_tx_oobi_pkt_drop_counter5_tx_oobi_pkt_drop {
      type oc-yang:counter64;
      description
        "counter for OOBI okt drops";
    }
    leaf counter_slice13_ifg_mac_pool80_tx_oobi_pkt_drop_counter6_tx_oobi_pkt_drop {
      type oc-yang:counter64;
      description
        "counter for OOBI okt drops";
    }
    leaf counter_slice13_ifg_mac_pool80_tx_oobi_pkt_drop_counter7_tx_oobi_pkt_drop {
      type oc-yang:counter64;
      description
        "counter for OOBI okt drops";
    }
    leaf counter_slice13_ifg_mac_pool81_tx_oobi_pkt_drop_counter0_tx_oobi_pkt_drop {
      type oc-yang:counter64;
      description
        "counter for OOBI okt drops";
    }
    leaf counter_slice13_ifg_mac_pool81_tx_oobi_pkt_drop_counter1_tx_oobi_pkt_drop {
      type oc-yang:counter64;
      description
        "counter for OOBI okt drops";
    }
    leaf counter_slice13_ifg_mac_pool81_tx_oobi_pkt_drop_counter2_tx_oobi_pkt_drop {
      type oc-yang:counter64;
      description
        "counter for OOBI okt drops";
    }
    leaf counter_slice13_ifg_mac_pool81_tx_oobi_pkt_drop_counter3_tx_oobi_pkt_drop {
      type oc-yang:counter64;
      description
        "counter for OOBI okt drops";
    }
    leaf counter_slice13_ifg_mac_pool81_tx_oobi_pkt_drop_counter4_tx_oobi_pkt_drop {
      type oc-yang:counter64;
      description
        "counter for OOBI okt drops";
    }
    leaf counter_slice13_ifg_mac_pool81_tx_oobi_pkt_drop_counter5_tx_oobi_pkt_drop {
      type oc-yang:counter64;
      description
        "counter for OOBI okt drops";
    }
    leaf counter_slice13_ifg_mac_pool81_tx_oobi_pkt_drop_counter6_tx_oobi_pkt_drop {
      type oc-yang:counter64;
      description
        "counter for OOBI okt drops";
    }
    leaf counter_slice13_ifg_mac_pool81_tx_oobi_pkt_drop_counter7_tx_oobi_pkt_drop {
      type oc-yang:counter64;
      description
        "counter for OOBI okt drops";
    }
    leaf counter_slice13_ifg_mac_pool82_tx_oobi_pkt_drop_counter0_tx_oobi_pkt_drop {
      type oc-yang:counter64;
      description
        "counter for OOBI okt drops";
    }
    leaf counter_slice13_ifg_mac_pool82_tx_oobi_pkt_drop_counter1_tx_oobi_pkt_drop {
      type oc-yang:counter64;
      description
        "counter for OOBI okt drops";
    }
    leaf counter_slice13_ifg_mac_pool82_tx_oobi_pkt_drop_counter2_tx_oobi_pkt_drop {
      type oc-yang:counter64;
      description
        "counter for OOBI okt drops";
    }
    leaf counter_slice13_ifg_mac_pool82_tx_oobi_pkt_drop_counter3_tx_oobi_pkt_drop {
      type oc-yang:counter64;
      description
        "counter for OOBI okt drops";
    }
    leaf counter_slice13_ifg_mac_pool82_tx_oobi_pkt_drop_counter4_tx_oobi_pkt_drop {
      type oc-yang:counter64;
      description
        "counter for OOBI okt drops";
    }
    leaf counter_slice13_ifg_mac_pool82_tx_oobi_pkt_drop_counter5_tx_oobi_pkt_drop {
      type oc-yang:counter64;
      description
        "counter for OOBI okt drops";
    }
    leaf counter_slice13_ifg_mac_pool82_tx_oobi_pkt_drop_counter6_tx_oobi_pkt_drop {
      type oc-yang:counter64;
      description
        "counter for OOBI okt drops";
    }
    leaf counter_slice13_ifg_mac_pool82_tx_oobi_pkt_drop_counter7_tx_oobi_pkt_drop {
      type oc-yang:counter64;
      description
        "counter for OOBI okt drops";
    }
    leaf counter_slice13_ifg_mac_pool83_tx_oobi_pkt_drop_counter0_tx_oobi_pkt_drop {
      type oc-yang:counter64;
      description
        "counter for OOBI okt drops";
    }
    leaf counter_slice13_ifg_mac_pool83_tx_oobi_pkt_drop_counter1_tx_oobi_pkt_drop {
      type oc-yang:counter64;
      description
        "counter for OOBI okt drops";
    }
    leaf counter_slice13_ifg_mac_pool83_tx_oobi_pkt_drop_counter2_tx_oobi_pkt_drop {
      type oc-yang:counter64;
      description
        "counter for OOBI okt drops";
    }
    leaf counter_slice13_ifg_mac_pool83_tx_oobi_pkt_drop_counter3_tx_oobi_pkt_drop {
      type oc-yang:counter64;
      description
        "counter for OOBI okt drops";
    }
    leaf counter_slice13_ifg_mac_pool83_tx_oobi_pkt_drop_counter4_tx_oobi_pkt_drop {
      type oc-yang:counter64;
      description
        "counter for OOBI okt drops";
    }
    leaf counter_slice13_ifg_mac_pool83_tx_oobi_pkt_drop_counter5_tx_oobi_pkt_drop {
      type oc-yang:counter64;
      description
        "counter for OOBI okt drops";
    }
    leaf counter_slice13_ifg_mac_pool83_tx_oobi_pkt_drop_counter6_tx_oobi_pkt_drop {
      type oc-yang:counter64;
      description
        "counter for OOBI okt drops";
    }
    leaf counter_slice13_ifg_mac_pool83_tx_oobi_pkt_drop_counter7_tx_oobi_pkt_drop {
      type oc-yang:counter64;
      description
        "counter for OOBI okt drops";
    }
    leaf counter_slice13_ifg_mac_pool84_tx_oobi_pkt_drop_counter0_tx_oobi_pkt_drop {
      type oc-yang:counter64;
      description
        "counter for OOBI okt drops";
    }
    leaf counter_slice13_ifg_mac_pool84_tx_oobi_pkt_drop_counter1_tx_oobi_pkt_drop {
      type oc-yang:counter64;
      description
        "counter for OOBI okt drops";
    }
    leaf counter_slice13_ifg_mac_pool84_tx_oobi_pkt_drop_counter2_tx_oobi_pkt_drop {
      type oc-yang:counter64;
      description
        "counter for OOBI okt drops";
    }
    leaf counter_slice13_ifg_mac_pool84_tx_oobi_pkt_drop_counter3_tx_oobi_pkt_drop {
      type oc-yang:counter64;
      description
        "counter for OOBI okt drops";
    }
    leaf counter_slice13_ifg_mac_pool84_tx_oobi_pkt_drop_counter4_tx_oobi_pkt_drop {
      type oc-yang:counter64;
      description
        "counter for OOBI okt drops";
    }
    leaf counter_slice13_ifg_mac_pool84_tx_oobi_pkt_drop_counter5_tx_oobi_pkt_drop {
      type oc-yang:counter64;
      description
        "counter for OOBI okt drops";
    }
    leaf counter_slice13_ifg_mac_pool84_tx_oobi_pkt_drop_counter6_tx_oobi_pkt_drop {
      type oc-yang:counter64;
      description
        "counter for OOBI okt drops";
    }
    leaf counter_slice13_ifg_mac_pool84_tx_oobi_pkt_drop_counter7_tx_oobi_pkt_drop {
      type oc-yang:counter64;
      description
        "counter for OOBI okt drops";
    }
    leaf counter_slice13_ifg_mac_pool85_tx_oobi_pkt_drop_counter0_tx_oobi_pkt_drop {
      type oc-yang:counter64;
      description
        "counter for OOBI okt drops";
    }
    leaf counter_slice13_ifg_mac_pool85_tx_oobi_pkt_drop_counter1_tx_oobi_pkt_drop {
      type oc-yang:counter64;
      description
        "counter for OOBI okt drops";
    }
    leaf counter_slice13_ifg_mac_pool85_tx_oobi_pkt_drop_counter2_tx_oobi_pkt_drop {
      type oc-yang:counter64;
      description
        "counter for OOBI okt drops";
    }
    leaf counter_slice13_ifg_mac_pool85_tx_oobi_pkt_drop_counter3_tx_oobi_pkt_drop {
      type oc-yang:counter64;
      description
        "counter for OOBI okt drops";
    }
    leaf counter_slice13_ifg_mac_pool85_tx_oobi_pkt_drop_counter4_tx_oobi_pkt_drop {
      type oc-yang:counter64;
      description
        "counter for OOBI okt drops";
    }
    leaf counter_slice13_ifg_mac_pool85_tx_oobi_pkt_drop_counter5_tx_oobi_pkt_drop {
      type oc-yang:counter64;
      description
        "counter for OOBI okt drops";
    }
    leaf counter_slice13_ifg_mac_pool85_tx_oobi_pkt_drop_counter6_tx_oobi_pkt_drop {
      type oc-yang:counter64;
      description
        "counter for OOBI okt drops";
    }
    leaf counter_slice13_ifg_mac_pool85_tx_oobi_pkt_drop_counter7_tx_oobi_pkt_drop {
      type oc-yang:counter64;
      description
        "counter for OOBI okt drops";
    }
    leaf counter_slice13_ifg_mac_pool86_tx_oobi_pkt_drop_counter0_tx_oobi_pkt_drop {
      type oc-yang:counter64;
      description
        "counter for OOBI okt drops";
    }
    leaf counter_slice13_ifg_mac_pool86_tx_oobi_pkt_drop_counter1_tx_oobi_pkt_drop {
      type oc-yang:counter64;
      description
        "counter for OOBI okt drops";
    }
    leaf counter_slice13_ifg_mac_pool86_tx_oobi_pkt_drop_counter2_tx_oobi_pkt_drop {
      type oc-yang:counter64;
      description
        "counter for OOBI okt drops";
    }
    leaf counter_slice13_ifg_mac_pool86_tx_oobi_pkt_drop_counter3_tx_oobi_pkt_drop {
      type oc-yang:counter64;
      description
        "counter for OOBI okt drops";
    }
    leaf counter_slice13_ifg_mac_pool86_tx_oobi_pkt_drop_counter4_tx_oobi_pkt_drop {
      type oc-yang:counter64;
      description
        "counter for OOBI okt drops";
    }
    leaf counter_slice13_ifg_mac_pool86_tx_oobi_pkt_drop_counter5_tx_oobi_pkt_drop {
      type oc-yang:counter64;
      description
        "counter for OOBI okt drops";
    }
    leaf counter_slice13_ifg_mac_pool86_tx_oobi_pkt_drop_counter6_tx_oobi_pkt_drop {
      type oc-yang:counter64;
      description
        "counter for OOBI okt drops";
    }
    leaf counter_slice13_ifg_mac_pool86_tx_oobi_pkt_drop_counter7_tx_oobi_pkt_drop {
      type oc-yang:counter64;
      description
        "counter for OOBI okt drops";
    }
    leaf counter_slice13_ifg_mac_pool87_tx_oobi_pkt_drop_counter0_tx_oobi_pkt_drop {
      type oc-yang:counter64;
      description
        "counter for OOBI okt drops";
    }
    leaf counter_slice13_ifg_mac_pool87_tx_oobi_pkt_drop_counter1_tx_oobi_pkt_drop {
      type oc-yang:counter64;
      description
        "counter for OOBI okt drops";
    }
    leaf counter_slice13_ifg_mac_pool87_tx_oobi_pkt_drop_counter2_tx_oobi_pkt_drop {
      type oc-yang:counter64;
      description
        "counter for OOBI okt drops";
    }
    leaf counter_slice13_ifg_mac_pool87_tx_oobi_pkt_drop_counter3_tx_oobi_pkt_drop {
      type oc-yang:counter64;
      description
        "counter for OOBI okt drops";
    }
    leaf counter_slice13_ifg_mac_pool87_tx_oobi_pkt_drop_counter4_tx_oobi_pkt_drop {
      type oc-yang:counter64;
      description
        "counter for OOBI okt drops";
    }
    leaf counter_slice13_ifg_mac_pool87_tx_oobi_pkt_drop_counter5_tx_oobi_pkt_drop {
      type oc-yang:counter64;
      description
        "counter for OOBI okt drops";
    }
    leaf counter_slice13_ifg_mac_pool87_tx_oobi_pkt_drop_counter6_tx_oobi_pkt_drop {
      type oc-yang:counter64;
      description
        "counter for OOBI okt drops";
    }
    leaf counter_slice13_ifg_mac_pool87_tx_oobi_pkt_drop_counter7_tx_oobi_pkt_drop {
      type oc-yang:counter64;
      description
        "counter for OOBI okt drops";
    }
    leaf counter_slice14_ifg_mac_pool80_tx_oobi_pkt_drop_counter0_tx_oobi_pkt_drop {
      type oc-yang:counter64;
      description
        "counter for OOBI okt drops";
    }
    leaf counter_slice14_ifg_mac_pool80_tx_oobi_pkt_drop_counter1_tx_oobi_pkt_drop {
      type oc-yang:counter64;
      description
        "counter for OOBI okt drops";
    }
    leaf counter_slice14_ifg_mac_pool80_tx_oobi_pkt_drop_counter2_tx_oobi_pkt_drop {
      type oc-yang:counter64;
      description
        "counter for OOBI okt drops";
    }
    leaf counter_slice14_ifg_mac_pool80_tx_oobi_pkt_drop_counter3_tx_oobi_pkt_drop {
      type oc-yang:counter64;
      description
        "counter for OOBI okt drops";
    }
    leaf counter_slice14_ifg_mac_pool80_tx_oobi_pkt_drop_counter4_tx_oobi_pkt_drop {
      type oc-yang:counter64;
      description
        "counter for OOBI okt drops";
    }
    leaf counter_slice14_ifg_mac_pool80_tx_oobi_pkt_drop_counter5_tx_oobi_pkt_drop {
      type oc-yang:counter64;
      description
        "counter for OOBI okt drops";
    }
    leaf counter_slice14_ifg_mac_pool80_tx_oobi_pkt_drop_counter6_tx_oobi_pkt_drop {
      type oc-yang:counter64;
      description
        "counter for OOBI okt drops";
    }
    leaf counter_slice14_ifg_mac_pool80_tx_oobi_pkt_drop_counter7_tx_oobi_pkt_drop {
      type oc-yang:counter64;
      description
        "counter for OOBI okt drops";
    }
    leaf counter_slice14_ifg_mac_pool81_tx_oobi_pkt_drop_counter0_tx_oobi_pkt_drop {
      type oc-yang:counter64;
      description
        "counter for OOBI okt drops";
    }
    leaf counter_slice14_ifg_mac_pool81_tx_oobi_pkt_drop_counter1_tx_oobi_pkt_drop {
      type oc-yang:counter64;
      description
        "counter for OOBI okt drops";
    }
    leaf counter_slice14_ifg_mac_pool81_tx_oobi_pkt_drop_counter2_tx_oobi_pkt_drop {
      type oc-yang:counter64;
      description
        "counter for OOBI okt drops";
    }
    leaf counter_slice14_ifg_mac_pool81_tx_oobi_pkt_drop_counter3_tx_oobi_pkt_drop {
      type oc-yang:counter64;
      description
        "counter for OOBI okt drops";
    }
    leaf counter_slice14_ifg_mac_pool81_tx_oobi_pkt_drop_counter4_tx_oobi_pkt_drop {
      type oc-yang:counter64;
      description
        "counter for OOBI okt drops";
    }
    leaf counter_slice14_ifg_mac_pool81_tx_oobi_pkt_drop_counter5_tx_oobi_pkt_drop {
      type oc-yang:counter64;
      description
        "counter for OOBI okt drops";
    }
    leaf counter_slice14_ifg_mac_pool81_tx_oobi_pkt_drop_counter6_tx_oobi_pkt_drop {
      type oc-yang:counter64;
      description
        "counter for OOBI okt drops";
    }
    leaf counter_slice14_ifg_mac_pool81_tx_oobi_pkt_drop_counter7_tx_oobi_pkt_drop {
      type oc-yang:counter64;
      description
        "counter for OOBI okt drops";
    }
    leaf counter_slice14_ifg_mac_pool82_tx_oobi_pkt_drop_counter0_tx_oobi_pkt_drop {
      type oc-yang:counter64;
      description
        "counter for OOBI okt drops";
    }
    leaf counter_slice14_ifg_mac_pool82_tx_oobi_pkt_drop_counter1_tx_oobi_pkt_drop {
      type oc-yang:counter64;
      description
        "counter for OOBI okt drops";
    }
    leaf counter_slice14_ifg_mac_pool82_tx_oobi_pkt_drop_counter2_tx_oobi_pkt_drop {
      type oc-yang:counter64;
      description
        "counter for OOBI okt drops";
    }
    leaf counter_slice14_ifg_mac_pool82_tx_oobi_pkt_drop_counter3_tx_oobi_pkt_drop {
      type oc-yang:counter64;
      description
        "counter for OOBI okt drops";
    }
    leaf counter_slice14_ifg_mac_pool82_tx_oobi_pkt_drop_counter4_tx_oobi_pkt_drop {
      type oc-yang:counter64;
      description
        "counter for OOBI okt drops";
    }
    leaf counter_slice14_ifg_mac_pool82_tx_oobi_pkt_drop_counter5_tx_oobi_pkt_drop {
      type oc-yang:counter64;
      description
        "counter for OOBI okt drops";
    }
    leaf counter_slice14_ifg_mac_pool82_tx_oobi_pkt_drop_counter6_tx_oobi_pkt_drop {
      type oc-yang:counter64;
      description
        "counter for OOBI okt drops";
    }
    leaf counter_slice14_ifg_mac_pool82_tx_oobi_pkt_drop_counter7_tx_oobi_pkt_drop {
      type oc-yang:counter64;
      description
        "counter for OOBI okt drops";
    }
    leaf counter_slice14_ifg_mac_pool83_tx_oobi_pkt_drop_counter0_tx_oobi_pkt_drop {
      type oc-yang:counter64;
      description
        "counter for OOBI okt drops";
    }
    leaf counter_slice14_ifg_mac_pool83_tx_oobi_pkt_drop_counter1_tx_oobi_pkt_drop {
      type oc-yang:counter64;
      description
        "counter for OOBI okt drops";
    }
    leaf counter_slice14_ifg_mac_pool83_tx_oobi_pkt_drop_counter2_tx_oobi_pkt_drop {
      type oc-yang:counter64;
      description
        "counter for OOBI okt drops";
    }
    leaf counter_slice14_ifg_mac_pool83_tx_oobi_pkt_drop_counter3_tx_oobi_pkt_drop {
      type oc-yang:counter64;
      description
        "counter for OOBI okt drops";
    }
    leaf counter_slice14_ifg_mac_pool83_tx_oobi_pkt_drop_counter4_tx_oobi_pkt_drop {
      type oc-yang:counter64;
      description
        "counter for OOBI okt drops";
    }
    leaf counter_slice14_ifg_mac_pool83_tx_oobi_pkt_drop_counter5_tx_oobi_pkt_drop {
      type oc-yang:counter64;
      description
        "counter for OOBI okt drops";
    }
    leaf counter_slice14_ifg_mac_pool83_tx_oobi_pkt_drop_counter6_tx_oobi_pkt_drop {
      type oc-yang:counter64;
      description
        "counter for OOBI okt drops";
    }
    leaf counter_slice14_ifg_mac_pool83_tx_oobi_pkt_drop_counter7_tx_oobi_pkt_drop {
      type oc-yang:counter64;
      description
        "counter for OOBI okt drops";
    }
    leaf counter_slice14_ifg_mac_pool84_tx_oobi_pkt_drop_counter0_tx_oobi_pkt_drop {
      type oc-yang:counter64;
      description
        "counter for OOBI okt drops";
    }
    leaf counter_slice14_ifg_mac_pool84_tx_oobi_pkt_drop_counter1_tx_oobi_pkt_drop {
      type oc-yang:counter64;
      description
        "counter for OOBI okt drops";
    }
    leaf counter_slice14_ifg_mac_pool84_tx_oobi_pkt_drop_counter2_tx_oobi_pkt_drop {
      type oc-yang:counter64;
      description
        "counter for OOBI okt drops";
    }
    leaf counter_slice14_ifg_mac_pool84_tx_oobi_pkt_drop_counter3_tx_oobi_pkt_drop {
      type oc-yang:counter64;
      description
        "counter for OOBI okt drops";
    }
    leaf counter_slice14_ifg_mac_pool84_tx_oobi_pkt_drop_counter4_tx_oobi_pkt_drop {
      type oc-yang:counter64;
      description
        "counter for OOBI okt drops";
    }
    leaf counter_slice14_ifg_mac_pool84_tx_oobi_pkt_drop_counter5_tx_oobi_pkt_drop {
      type oc-yang:counter64;
      description
        "counter for OOBI okt drops";
    }
    leaf counter_slice14_ifg_mac_pool84_tx_oobi_pkt_drop_counter6_tx_oobi_pkt_drop {
      type oc-yang:counter64;
      description
        "counter for OOBI okt drops";
    }
    leaf counter_slice14_ifg_mac_pool84_tx_oobi_pkt_drop_counter7_tx_oobi_pkt_drop {
      type oc-yang:counter64;
      description
        "counter for OOBI okt drops";
    }
    leaf counter_slice14_ifg_mac_pool85_tx_oobi_pkt_drop_counter0_tx_oobi_pkt_drop {
      type oc-yang:counter64;
      description
        "counter for OOBI okt drops";
    }
    leaf counter_slice14_ifg_mac_pool85_tx_oobi_pkt_drop_counter1_tx_oobi_pkt_drop {
      type oc-yang:counter64;
      description
        "counter for OOBI okt drops";
    }
    leaf counter_slice14_ifg_mac_pool85_tx_oobi_pkt_drop_counter2_tx_oobi_pkt_drop {
      type oc-yang:counter64;
      description
        "counter for OOBI okt drops";
    }
    leaf counter_slice14_ifg_mac_pool85_tx_oobi_pkt_drop_counter3_tx_oobi_pkt_drop {
      type oc-yang:counter64;
      description
        "counter for OOBI okt drops";
    }
    leaf counter_slice14_ifg_mac_pool85_tx_oobi_pkt_drop_counter4_tx_oobi_pkt_drop {
      type oc-yang:counter64;
      description
        "counter for OOBI okt drops";
    }
    leaf counter_slice14_ifg_mac_pool85_tx_oobi_pkt_drop_counter5_tx_oobi_pkt_drop {
      type oc-yang:counter64;
      description
        "counter for OOBI okt drops";
    }
    leaf counter_slice14_ifg_mac_pool85_tx_oobi_pkt_drop_counter6_tx_oobi_pkt_drop {
      type oc-yang:counter64;
      description
        "counter for OOBI okt drops";
    }
    leaf counter_slice14_ifg_mac_pool85_tx_oobi_pkt_drop_counter7_tx_oobi_pkt_drop {
      type oc-yang:counter64;
      description
        "counter for OOBI okt drops";
    }
    leaf counter_slice14_ifg_mac_pool86_tx_oobi_pkt_drop_counter0_tx_oobi_pkt_drop {
      type oc-yang:counter64;
      description
        "counter for OOBI okt drops";
    }
    leaf counter_slice14_ifg_mac_pool86_tx_oobi_pkt_drop_counter1_tx_oobi_pkt_drop {
      type oc-yang:counter64;
      description
        "counter for OOBI okt drops";
    }
    leaf counter_slice14_ifg_mac_pool86_tx_oobi_pkt_drop_counter2_tx_oobi_pkt_drop {
      type oc-yang:counter64;
      description
        "counter for OOBI okt drops";
    }
    leaf counter_slice14_ifg_mac_pool86_tx_oobi_pkt_drop_counter3_tx_oobi_pkt_drop {
      type oc-yang:counter64;
      description
        "counter for OOBI okt drops";
    }
    leaf counter_slice14_ifg_mac_pool86_tx_oobi_pkt_drop_counter4_tx_oobi_pkt_drop {
      type oc-yang:counter64;
      description
        "counter for OOBI okt drops";
    }
    leaf counter_slice14_ifg_mac_pool86_tx_oobi_pkt_drop_counter5_tx_oobi_pkt_drop {
      type oc-yang:counter64;
      description
        "counter for OOBI okt drops";
    }
    leaf counter_slice14_ifg_mac_pool86_tx_oobi_pkt_drop_counter6_tx_oobi_pkt_drop {
      type oc-yang:counter64;
      description
        "counter for OOBI okt drops";
    }
    leaf counter_slice14_ifg_mac_pool86_tx_oobi_pkt_drop_counter7_tx_oobi_pkt_drop {
      type oc-yang:counter64;
      description
        "counter for OOBI okt drops";
    }
    leaf counter_slice14_ifg_mac_pool87_tx_oobi_pkt_drop_counter0_tx_oobi_pkt_drop {
      type oc-yang:counter64;
      description
        "counter for OOBI okt drops";
    }
    leaf counter_slice14_ifg_mac_pool87_tx_oobi_pkt_drop_counter1_tx_oobi_pkt_drop {
      type oc-yang:counter64;
      description
        "counter for OOBI okt drops";
    }
    leaf counter_slice14_ifg_mac_pool87_tx_oobi_pkt_drop_counter2_tx_oobi_pkt_drop {
      type oc-yang:counter64;
      description
        "counter for OOBI okt drops";
    }
    leaf counter_slice14_ifg_mac_pool87_tx_oobi_pkt_drop_counter3_tx_oobi_pkt_drop {
      type oc-yang:counter64;
      description
        "counter for OOBI okt drops";
    }
    leaf counter_slice14_ifg_mac_pool87_tx_oobi_pkt_drop_counter4_tx_oobi_pkt_drop {
      type oc-yang:counter64;
      description
        "counter for OOBI okt drops";
    }
    leaf counter_slice14_ifg_mac_pool87_tx_oobi_pkt_drop_counter5_tx_oobi_pkt_drop {
      type oc-yang:counter64;
      description
        "counter for OOBI okt drops";
    }
    leaf counter_slice14_ifg_mac_pool87_tx_oobi_pkt_drop_counter6_tx_oobi_pkt_drop {
      type oc-yang:counter64;
      description
        "counter for OOBI okt drops";
    }
    leaf counter_slice14_ifg_mac_pool87_tx_oobi_pkt_drop_counter7_tx_oobi_pkt_drop {
      type oc-yang:counter64;
      description
        "counter for OOBI okt drops";
    }
    leaf counter_slice15_ifg_mac_pool80_tx_oobi_pkt_drop_counter0_tx_oobi_pkt_drop {
      type oc-yang:counter64;
      description
        "counter for OOBI okt drops";
    }
    leaf counter_slice15_ifg_mac_pool80_tx_oobi_pkt_drop_counter1_tx_oobi_pkt_drop {
      type oc-yang:counter64;
      description
        "counter for OOBI okt drops";
    }
    leaf counter_slice15_ifg_mac_pool80_tx_oobi_pkt_drop_counter2_tx_oobi_pkt_drop {
      type oc-yang:counter64;
      description
        "counter for OOBI okt drops";
    }
    leaf counter_slice15_ifg_mac_pool80_tx_oobi_pkt_drop_counter3_tx_oobi_pkt_drop {
      type oc-yang:counter64;
      description
        "counter for OOBI okt drops";
    }
    leaf counter_slice15_ifg_mac_pool80_tx_oobi_pkt_drop_counter4_tx_oobi_pkt_drop {
      type oc-yang:counter64;
      description
        "counter for OOBI okt drops";
    }
    leaf counter_slice15_ifg_mac_pool80_tx_oobi_pkt_drop_counter5_tx_oobi_pkt_drop {
      type oc-yang:counter64;
      description
        "counter for OOBI okt drops";
    }
    leaf counter_slice15_ifg_mac_pool80_tx_oobi_pkt_drop_counter6_tx_oobi_pkt_drop {
      type oc-yang:counter64;
      description
        "counter for OOBI okt drops";
    }
    leaf counter_slice15_ifg_mac_pool80_tx_oobi_pkt_drop_counter7_tx_oobi_pkt_drop {
      type oc-yang:counter64;
      description
        "counter for OOBI okt drops";
    }
    leaf counter_slice15_ifg_mac_pool81_tx_oobi_pkt_drop_counter0_tx_oobi_pkt_drop {
      type oc-yang:counter64;
      description
        "counter for OOBI okt drops";
    }
    leaf counter_slice15_ifg_mac_pool81_tx_oobi_pkt_drop_counter1_tx_oobi_pkt_drop {
      type oc-yang:counter64;
      description
        "counter for OOBI okt drops";
    }
    leaf counter_slice15_ifg_mac_pool81_tx_oobi_pkt_drop_counter2_tx_oobi_pkt_drop {
      type oc-yang:counter64;
      description
        "counter for OOBI okt drops";
    }
    leaf counter_slice15_ifg_mac_pool81_tx_oobi_pkt_drop_counter3_tx_oobi_pkt_drop {
      type oc-yang:counter64;
      description
        "counter for OOBI okt drops";
    }
    leaf counter_slice15_ifg_mac_pool81_tx_oobi_pkt_drop_counter4_tx_oobi_pkt_drop {
      type oc-yang:counter64;
      description
        "counter for OOBI okt drops";
    }
    leaf counter_slice15_ifg_mac_pool81_tx_oobi_pkt_drop_counter5_tx_oobi_pkt_drop {
      type oc-yang:counter64;
      description
        "counter for OOBI okt drops";
    }
    leaf counter_slice15_ifg_mac_pool81_tx_oobi_pkt_drop_counter6_tx_oobi_pkt_drop {
      type oc-yang:counter64;
      description
        "counter for OOBI okt drops";
    }
    leaf counter_slice15_ifg_mac_pool81_tx_oobi_pkt_drop_counter7_tx_oobi_pkt_drop {
      type oc-yang:counter64;
      description
        "counter for OOBI okt drops";
    }
    leaf counter_slice15_ifg_mac_pool82_tx_oobi_pkt_drop_counter0_tx_oobi_pkt_drop {
      type oc-yang:counter64;
      description
        "counter for OOBI okt drops";
    }
    leaf counter_slice15_ifg_mac_pool82_tx_oobi_pkt_drop_counter1_tx_oobi_pkt_drop {
      type oc-yang:counter64;
      description
        "counter for OOBI okt drops";
    }
    leaf counter_slice15_ifg_mac_pool82_tx_oobi_pkt_drop_counter2_tx_oobi_pkt_drop {
      type oc-yang:counter64;
      description
        "counter for OOBI okt drops";
    }
    leaf counter_slice15_ifg_mac_pool82_tx_oobi_pkt_drop_counter3_tx_oobi_pkt_drop {
      type oc-yang:counter64;
      description
        "counter for OOBI okt drops";
    }
    leaf counter_slice15_ifg_mac_pool82_tx_oobi_pkt_drop_counter4_tx_oobi_pkt_drop {
      type oc-yang:counter64;
      description
        "counter for OOBI okt drops";
    }
    leaf counter_slice15_ifg_mac_pool82_tx_oobi_pkt_drop_counter5_tx_oobi_pkt_drop {
      type oc-yang:counter64;
      description
        "counter for OOBI okt drops";
    }
    leaf counter_slice15_ifg_mac_pool82_tx_oobi_pkt_drop_counter6_tx_oobi_pkt_drop {
      type oc-yang:counter64;
      description
        "counter for OOBI okt drops";
    }
    leaf counter_slice15_ifg_mac_pool82_tx_oobi_pkt_drop_counter7_tx_oobi_pkt_drop {
      type oc-yang:counter64;
      description
        "counter for OOBI okt drops";
    }
    leaf counter_slice15_ifg_mac_pool83_tx_oobi_pkt_drop_counter0_tx_oobi_pkt_drop {
      type oc-yang:counter64;
      description
        "counter for OOBI okt drops";
    }
    leaf counter_slice15_ifg_mac_pool83_tx_oobi_pkt_drop_counter1_tx_oobi_pkt_drop {
      type oc-yang:counter64;
      description
        "counter for OOBI okt drops";
    }
    leaf counter_slice15_ifg_mac_pool83_tx_oobi_pkt_drop_counter2_tx_oobi_pkt_drop {
      type oc-yang:counter64;
      description
        "counter for OOBI okt drops";
    }
    leaf counter_slice15_ifg_mac_pool83_tx_oobi_pkt_drop_counter3_tx_oobi_pkt_drop {
      type oc-yang:counter64;
      description
        "counter for OOBI okt drops";
    }
    leaf counter_slice15_ifg_mac_pool83_tx_oobi_pkt_drop_counter4_tx_oobi_pkt_drop {
      type oc-yang:counter64;
      description
        "counter for OOBI okt drops";
    }
    leaf counter_slice15_ifg_mac_pool83_tx_oobi_pkt_drop_counter5_tx_oobi_pkt_drop {
      type oc-yang:counter64;
      description
        "counter for OOBI okt drops";
    }
    leaf counter_slice15_ifg_mac_pool83_tx_oobi_pkt_drop_counter6_tx_oobi_pkt_drop {
      type oc-yang:counter64;
      description
        "counter for OOBI okt drops";
    }
    leaf counter_slice15_ifg_mac_pool83_tx_oobi_pkt_drop_counter7_tx_oobi_pkt_drop {
      type oc-yang:counter64;
      description
        "counter for OOBI okt drops";
    }
    leaf counter_slice15_ifg_mac_pool84_tx_oobi_pkt_drop_counter0_tx_oobi_pkt_drop {
      type oc-yang:counter64;
      description
        "counter for OOBI okt drops";
    }
    leaf counter_slice15_ifg_mac_pool84_tx_oobi_pkt_drop_counter1_tx_oobi_pkt_drop {
      type oc-yang:counter64;
      description
        "counter for OOBI okt drops";
    }
    leaf counter_slice15_ifg_mac_pool84_tx_oobi_pkt_drop_counter2_tx_oobi_pkt_drop {
      type oc-yang:counter64;
      description
        "counter for OOBI okt drops";
    }
    leaf counter_slice15_ifg_mac_pool84_tx_oobi_pkt_drop_counter3_tx_oobi_pkt_drop {
      type oc-yang:counter64;
      description
        "counter for OOBI okt drops";
    }
    leaf counter_slice15_ifg_mac_pool84_tx_oobi_pkt_drop_counter4_tx_oobi_pkt_drop {
      type oc-yang:counter64;
      description
        "counter for OOBI okt drops";
    }
    leaf counter_slice15_ifg_mac_pool84_tx_oobi_pkt_drop_counter5_tx_oobi_pkt_drop {
      type oc-yang:counter64;
      description
        "counter for OOBI okt drops";
    }
    leaf counter_slice15_ifg_mac_pool84_tx_oobi_pkt_drop_counter6_tx_oobi_pkt_drop {
      type oc-yang:counter64;
      description
        "counter for OOBI okt drops";
    }
    leaf counter_slice15_ifg_mac_pool84_tx_oobi_pkt_drop_counter7_tx_oobi_pkt_drop {
      type oc-yang:counter64;
      description
        "counter for OOBI okt drops";
    }
    leaf counter_slice15_ifg_mac_pool85_tx_oobi_pkt_drop_counter0_tx_oobi_pkt_drop {
      type oc-yang:counter64;
      description
        "counter for OOBI okt drops";
    }
    leaf counter_slice15_ifg_mac_pool85_tx_oobi_pkt_drop_counter1_tx_oobi_pkt_drop {
      type oc-yang:counter64;
      description
        "counter for OOBI okt drops";
    }
    leaf counter_slice15_ifg_mac_pool85_tx_oobi_pkt_drop_counter2_tx_oobi_pkt_drop {
      type oc-yang:counter64;
      description
        "counter for OOBI okt drops";
    }
    leaf counter_slice15_ifg_mac_pool85_tx_oobi_pkt_drop_counter3_tx_oobi_pkt_drop {
      type oc-yang:counter64;
      description
        "counter for OOBI okt drops";
    }
    leaf counter_slice15_ifg_mac_pool85_tx_oobi_pkt_drop_counter4_tx_oobi_pkt_drop {
      type oc-yang:counter64;
      description
        "counter for OOBI okt drops";
    }
    leaf counter_slice15_ifg_mac_pool85_tx_oobi_pkt_drop_counter5_tx_oobi_pkt_drop {
      type oc-yang:counter64;
      description
        "counter for OOBI okt drops";
    }
    leaf counter_slice15_ifg_mac_pool85_tx_oobi_pkt_drop_counter6_tx_oobi_pkt_drop {
      type oc-yang:counter64;
      description
        "counter for OOBI okt drops";
    }
    leaf counter_slice15_ifg_mac_pool85_tx_oobi_pkt_drop_counter7_tx_oobi_pkt_drop {
      type oc-yang:counter64;
      description
        "counter for OOBI okt drops";
    }
    leaf counter_slice15_ifg_mac_pool86_tx_oobi_pkt_drop_counter0_tx_oobi_pkt_drop {
      type oc-yang:counter64;
      description
        "counter for OOBI okt drops";
    }
    leaf counter_slice15_ifg_mac_pool86_tx_oobi_pkt_drop_counter1_tx_oobi_pkt_drop {
      type oc-yang:counter64;
      description
        "counter for OOBI okt drops";
    }
    leaf counter_slice15_ifg_mac_pool86_tx_oobi_pkt_drop_counter2_tx_oobi_pkt_drop {
      type oc-yang:counter64;
      description
        "counter for OOBI okt drops";
    }
    leaf counter_slice15_ifg_mac_pool86_tx_oobi_pkt_drop_counter3_tx_oobi_pkt_drop {
      type oc-yang:counter64;
      description
        "counter for OOBI okt drops";
    }
    leaf counter_slice15_ifg_mac_pool86_tx_oobi_pkt_drop_counter4_tx_oobi_pkt_drop {
      type oc-yang:counter64;
      description
        "counter for OOBI okt drops";
    }
    leaf counter_slice15_ifg_mac_pool86_tx_oobi_pkt_drop_counter5_tx_oobi_pkt_drop {
      type oc-yang:counter64;
      description
        "counter for OOBI okt drops";
    }
    leaf counter_slice15_ifg_mac_pool86_tx_oobi_pkt_drop_counter6_tx_oobi_pkt_drop {
      type oc-yang:counter64;
      description
        "counter for OOBI okt drops";
    }
    leaf counter_slice15_ifg_mac_pool86_tx_oobi_pkt_drop_counter7_tx_oobi_pkt_drop {
      type oc-yang:counter64;
      description
        "counter for OOBI okt drops";
    }
    leaf counter_slice15_ifg_mac_pool87_tx_oobi_pkt_drop_counter0_tx_oobi_pkt_drop {
      type oc-yang:counter64;
      description
        "counter for OOBI okt drops";
    }
    leaf counter_slice15_ifg_mac_pool87_tx_oobi_pkt_drop_counter1_tx_oobi_pkt_drop {
      type oc-yang:counter64;
      description
        "counter for OOBI okt drops";
    }
    leaf counter_slice15_ifg_mac_pool87_tx_oobi_pkt_drop_counter2_tx_oobi_pkt_drop {
      type oc-yang:counter64;
      description
        "counter for OOBI okt drops";
    }
    leaf counter_slice15_ifg_mac_pool87_tx_oobi_pkt_drop_counter3_tx_oobi_pkt_drop {
      type oc-yang:counter64;
      description
        "counter for OOBI okt drops";
    }
    leaf counter_slice15_ifg_mac_pool87_tx_oobi_pkt_drop_counter4_tx_oobi_pkt_drop {
      type oc-yang:counter64;
      description
        "counter for OOBI okt drops";
    }
    leaf counter_slice15_ifg_mac_pool87_tx_oobi_pkt_drop_counter5_tx_oobi_pkt_drop {
      type oc-yang:counter64;
      description
        "counter for OOBI okt drops";
    }
    leaf counter_slice15_ifg_mac_pool87_tx_oobi_pkt_drop_counter6_tx_oobi_pkt_drop {
      type oc-yang:counter64;
      description
        "counter for OOBI okt drops";
    }
    leaf counter_slice15_ifg_mac_pool87_tx_oobi_pkt_drop_counter7_tx_oobi_pkt_drop {
      type oc-yang:counter64;
      description
        "counter for OOBI okt drops";
    }
    leaf counter_mmu_error_counters_any_err_dram_pkts_read {
      type oc-yang:counter64;
      description
        "DRAM packets that are read from HBM with any of the following errors set: ECC or 128b line CRC, HBM I/F Parity, gen_err or drop_dbd.";
    }
    leaf counter_mmu_error_counters_dram_crc_err_counter {
      type oc-yang:counter64;
      description
        "DRAM CRC Error Counter";
    }
    leaf counter_mmu_error_counters_drop_dbd_dram_pkts_read {
      type oc-yang:counter64;
      description
        "DRAM packets that are read from HBM for which drop bit was set in dics2mmu command.";
    }
    leaf counter_mmu_error_counters_drop_dbd_rcvd {
      type oc-yang:counter64;
      description
        "Count DBD with drop bit set";
    }
    leaf counter_mmu_error_counters_dummy_pkt_counter {
      type oc-yang:counter64;
      description
        "Counter of dummy packets sent by MMU to SMS";
    }
    leaf counter_mmu_error_counters_error_buffer_counter {
      type oc-yang:counter64;
      description
        "Counter of number of DRAM buffers taken out of use since has an error. Does not account for those buffers added back by CPU";
    }
    leaf counter_mmu_error_counters_error_pkt_counter {
      type oc-yang:counter64;
      description
        "Counter of error packets sent by MMU to SMS";
    }
    leaf counter_mmu_error_counters_gen_err_dram_pkts_read {
      type oc-yang:counter64;
      description
        "DRAM packets that are read from HBM with gen_error set.";
    }
    leaf counter_mmu_error_counters_lpm_error_counter {
      type oc-yang:counter64;
      description
        "Counter of LPM lookups returned with errors, shared counter for both LPM interfaces";
    }
    leaf counter_mmu_error_counters_mmu_monitor_error_counter {
      type oc-yang:counter64;
      description
        "Number of errors logged by MMU monitor logic";
    }
    leaf counter_mmu_error_counters_size_error_counter {
      type oc-yang:counter64;
      description
        "Number of size errors logged by MMU monitor logic";
    }
    leaf counter_mmu_buff_error_counters_drop_pkt_counter_sms0 {
      type oc-yang:counter64;
      description
        "Counter of invert_crc cycles received by MMU from SMS if 0";
    }
    leaf counter_mmu_buff_error_counters_drop_pkt_counter_sms1 {
      type oc-yang:counter64;
      description
        "Counter of invert_crc cycles received by MMU from SMS if 1";
    }
    leaf counter_mmu_buff_error_counters_drop_pkt_counter_sms2 {
      type oc-yang:counter64;
      description
        "Counter of invert_crc cycles received by MMU from SMS if 2";
    }
    leaf counter_mmu_buff_error_counters_drop_pkt_counter_sms3 {
      type oc-yang:counter64;
      description
        "Counter of invert_crc cycles received by MMU from SMS if 3";
    }
    leaf counter_mmu_buff_error_counters_gen_err_dram_pkts_write {
      type oc-yang:counter64;
      description
        "DRAM packets that are written to HBM with gen_error set.";
    }
    leaf counter_slice0_oib_oobi_drop_pkt_cnt_oobi_csms_drop_pkt_cnt {
      type oc-yang:counter64;
      description
        "Injected CSMS pkt drop cnt across all links.";
    }
    leaf counter_slice1_oib_oobi_drop_pkt_cnt_oobi_csms_drop_pkt_cnt {
      type oc-yang:counter64;
      description
        "Injected CSMS pkt drop cnt across all links.";
    }
    leaf counter_slice2_oib_oobi_drop_pkt_cnt_oobi_csms_drop_pkt_cnt {
      type oc-yang:counter64;
      description
        "Injected CSMS pkt drop cnt across all links.";
    }
    leaf counter_slice3_oib_oobi_drop_pkt_cnt_oobi_csms_drop_pkt_cnt {
      type oc-yang:counter64;
      description
        "Injected CSMS pkt drop cnt across all links.";
    }
    leaf counter_slice4_oib_oobi_drop_pkt_cnt_oobi_csms_drop_pkt_cnt {
      type oc-yang:counter64;
      description
        "Injected CSMS pkt drop cnt across all links.";
    }
    leaf counter_slice5_oib_oobi_drop_pkt_cnt_oobi_csms_drop_pkt_cnt {
      type oc-yang:counter64;
      description
        "Injected CSMS pkt drop cnt across all links.";
    }
    leaf counter_slice6_oib_oobi_drop_pkt_cnt_oobi_csms_drop_pkt_cnt {
      type oc-yang:counter64;
      description
        "Injected CSMS pkt drop cnt across all links.";
    }
    leaf counter_slice7_oib_oobi_drop_pkt_cnt_oobi_csms_drop_pkt_cnt {
      type oc-yang:counter64;
      description
        "Injected CSMS pkt drop cnt across all links.";
    }
    leaf counter_slice8_oib_oobi_drop_pkt_cnt_oobi_csms_drop_pkt_cnt {
      type oc-yang:counter64;
      description
        "Injected CSMS pkt drop cnt across all links.";
    }
    leaf counter_slice9_oib_oobi_drop_pkt_cnt_oobi_csms_drop_pkt_cnt {
      type oc-yang:counter64;
      description
        "Injected CSMS pkt drop cnt across all links.";
    }
    leaf counter_slice10_oib_oobi_drop_pkt_cnt_oobi_csms_drop_pkt_cnt {
      type oc-yang:counter64;
      description
        "Injected CSMS pkt drop cnt across all links.";
    }
    leaf counter_slice11_oib_oobi_drop_pkt_cnt_oobi_csms_drop_pkt_cnt {
      type oc-yang:counter64;
      description
        "Injected CSMS pkt drop cnt across all links.";
    }
    leaf counter_slice12_oib_oobi_drop_pkt_cnt_oobi_csms_drop_pkt_cnt {
      type oc-yang:counter64;
      description
        "Injected CSMS pkt drop cnt across all links.";
    }
    leaf counter_slice13_oib_oobi_drop_pkt_cnt_oobi_csms_drop_pkt_cnt {
      type oc-yang:counter64;
      description
        "Injected CSMS pkt drop cnt across all links.";
    }
    leaf counter_slice14_oib_oobi_drop_pkt_cnt_oobi_csms_drop_pkt_cnt {
      type oc-yang:counter64;
      description
        "Injected CSMS pkt drop cnt across all links.";
    }
    leaf counter_slice15_oib_oobi_drop_pkt_cnt_oobi_csms_drop_pkt_cnt {
      type oc-yang:counter64;
      description
        "Injected CSMS pkt drop cnt across all links.";
    }
    leaf counter_slice0_oib_oobi_drop_pkt_cnt_oobi_frm_drop_pkt_cnt {
      type oc-yang:counter64;
      description
        "Injected FRM pkt drop cnt across all links";
    }
    leaf counter_slice1_oib_oobi_drop_pkt_cnt_oobi_frm_drop_pkt_cnt {
      type oc-yang:counter64;
      description
        "Injected FRM pkt drop cnt across all links";
    }
    leaf counter_slice2_oib_oobi_drop_pkt_cnt_oobi_frm_drop_pkt_cnt {
      type oc-yang:counter64;
      description
        "Injected FRM pkt drop cnt across all links";
    }
    leaf counter_slice3_oib_oobi_drop_pkt_cnt_oobi_frm_drop_pkt_cnt {
      type oc-yang:counter64;
      description
        "Injected FRM pkt drop cnt across all links";
    }
    leaf counter_slice4_oib_oobi_drop_pkt_cnt_oobi_frm_drop_pkt_cnt {
      type oc-yang:counter64;
      description
        "Injected FRM pkt drop cnt across all links";
    }
    leaf counter_slice5_oib_oobi_drop_pkt_cnt_oobi_frm_drop_pkt_cnt {
      type oc-yang:counter64;
      description
        "Injected FRM pkt drop cnt across all links";
    }
    leaf counter_slice6_oib_oobi_drop_pkt_cnt_oobi_frm_drop_pkt_cnt {
      type oc-yang:counter64;
      description
        "Injected FRM pkt drop cnt across all links";
    }
    leaf counter_slice7_oib_oobi_drop_pkt_cnt_oobi_frm_drop_pkt_cnt {
      type oc-yang:counter64;
      description
        "Injected FRM pkt drop cnt across all links";
    }
    leaf counter_slice8_oib_oobi_drop_pkt_cnt_oobi_frm_drop_pkt_cnt {
      type oc-yang:counter64;
      description
        "Injected FRM pkt drop cnt across all links";
    }
    leaf counter_slice9_oib_oobi_drop_pkt_cnt_oobi_frm_drop_pkt_cnt {
      type oc-yang:counter64;
      description
        "Injected FRM pkt drop cnt across all links";
    }
    leaf counter_slice10_oib_oobi_drop_pkt_cnt_oobi_frm_drop_pkt_cnt {
      type oc-yang:counter64;
      description
        "Injected FRM pkt drop cnt across all links";
    }
    leaf counter_slice11_oib_oobi_drop_pkt_cnt_oobi_frm_drop_pkt_cnt {
      type oc-yang:counter64;
      description
        "Injected FRM pkt drop cnt across all links";
    }
    leaf counter_slice12_oib_oobi_drop_pkt_cnt_oobi_frm_drop_pkt_cnt {
      type oc-yang:counter64;
      description
        "Injected FRM pkt drop cnt across all links";
    }
    leaf counter_slice13_oib_oobi_drop_pkt_cnt_oobi_frm_drop_pkt_cnt {
      type oc-yang:counter64;
      description
        "Injected FRM pkt drop cnt across all links";
    }
    leaf counter_slice14_oib_oobi_drop_pkt_cnt_oobi_frm_drop_pkt_cnt {
      type oc-yang:counter64;
      description
        "Injected FRM pkt drop cnt across all links";
    }
    leaf counter_slice15_oib_oobi_drop_pkt_cnt_oobi_frm_drop_pkt_cnt {
      type oc-yang:counter64;
      description
        "Injected FRM pkt drop cnt across all links";
    }
    leaf counter_slice0_oib_oobi_drop_pkt_cnt_oobi_fte_fts_drop_pkt_cnt {
      type oc-yang:counter64;
      description
        "Injected FTE Fabric Time Sync pkt drop cnt across all links";
    }
    leaf counter_slice1_oib_oobi_drop_pkt_cnt_oobi_fte_fts_drop_pkt_cnt {
      type oc-yang:counter64;
      description
        "Injected FTE Fabric Time Sync pkt drop cnt across all links";
    }
    leaf counter_slice2_oib_oobi_drop_pkt_cnt_oobi_fte_fts_drop_pkt_cnt {
      type oc-yang:counter64;
      description
        "Injected FTE Fabric Time Sync pkt drop cnt across all links";
    }
    leaf counter_slice3_oib_oobi_drop_pkt_cnt_oobi_fte_fts_drop_pkt_cnt {
      type oc-yang:counter64;
      description
        "Injected FTE Fabric Time Sync pkt drop cnt across all links";
    }
    leaf counter_slice4_oib_oobi_drop_pkt_cnt_oobi_fte_fts_drop_pkt_cnt {
      type oc-yang:counter64;
      description
        "Injected FTE Fabric Time Sync pkt drop cnt across all links";
    }
    leaf counter_slice5_oib_oobi_drop_pkt_cnt_oobi_fte_fts_drop_pkt_cnt {
      type oc-yang:counter64;
      description
        "Injected FTE Fabric Time Sync pkt drop cnt across all links";
    }
    leaf counter_slice6_oib_oobi_drop_pkt_cnt_oobi_fte_fts_drop_pkt_cnt {
      type oc-yang:counter64;
      description
        "Injected FTE Fabric Time Sync pkt drop cnt across all links";
    }
    leaf counter_slice7_oib_oobi_drop_pkt_cnt_oobi_fte_fts_drop_pkt_cnt {
      type oc-yang:counter64;
      description
        "Injected FTE Fabric Time Sync pkt drop cnt across all links";
    }
    leaf counter_slice8_oib_oobi_drop_pkt_cnt_oobi_fte_fts_drop_pkt_cnt {
      type oc-yang:counter64;
      description
        "Injected FTE Fabric Time Sync pkt drop cnt across all links";
    }
    leaf counter_slice9_oib_oobi_drop_pkt_cnt_oobi_fte_fts_drop_pkt_cnt {
      type oc-yang:counter64;
      description
        "Injected FTE Fabric Time Sync pkt drop cnt across all links";
    }
    leaf counter_slice10_oib_oobi_drop_pkt_cnt_oobi_fte_fts_drop_pkt_cnt {
      type oc-yang:counter64;
      description
        "Injected FTE Fabric Time Sync pkt drop cnt across all links";
    }
    leaf counter_slice11_oib_oobi_drop_pkt_cnt_oobi_fte_fts_drop_pkt_cnt {
      type oc-yang:counter64;
      description
        "Injected FTE Fabric Time Sync pkt drop cnt across all links";
    }
    leaf counter_slice12_oib_oobi_drop_pkt_cnt_oobi_fte_fts_drop_pkt_cnt {
      type oc-yang:counter64;
      description
        "Injected FTE Fabric Time Sync pkt drop cnt across all links";
    }
    leaf counter_slice13_oib_oobi_drop_pkt_cnt_oobi_fte_fts_drop_pkt_cnt {
      type oc-yang:counter64;
      description
        "Injected FTE Fabric Time Sync pkt drop cnt across all links";
    }
    leaf counter_slice14_oib_oobi_drop_pkt_cnt_oobi_fte_fts_drop_pkt_cnt {
      type oc-yang:counter64;
      description
        "Injected FTE Fabric Time Sync pkt drop cnt across all links";
    }
    leaf counter_slice15_oib_oobi_drop_pkt_cnt_oobi_fte_fts_drop_pkt_cnt {
      type oc-yang:counter64;
      description
        "Injected FTE Fabric Time Sync pkt drop cnt across all links";
    }
    leaf counter_slice0_oib_oobi_drop_pkt_cnt_oobi_fte_pd_req_drop_pkt_cnt {
      type oc-yang:counter64;
      description
        "Injected FTE Peer Delay Request pkt drop cnt across all links.";
    }
    leaf counter_slice1_oib_oobi_drop_pkt_cnt_oobi_fte_pd_req_drop_pkt_cnt {
      type oc-yang:counter64;
      description
        "Injected FTE Peer Delay Request pkt drop cnt across all links.";
    }
    leaf counter_slice2_oib_oobi_drop_pkt_cnt_oobi_fte_pd_req_drop_pkt_cnt {
      type oc-yang:counter64;
      description
        "Injected FTE Peer Delay Request pkt drop cnt across all links.";
    }
    leaf counter_slice3_oib_oobi_drop_pkt_cnt_oobi_fte_pd_req_drop_pkt_cnt {
      type oc-yang:counter64;
      description
        "Injected FTE Peer Delay Request pkt drop cnt across all links.";
    }
    leaf counter_slice4_oib_oobi_drop_pkt_cnt_oobi_fte_pd_req_drop_pkt_cnt {
      type oc-yang:counter64;
      description
        "Injected FTE Peer Delay Request pkt drop cnt across all links.";
    }
    leaf counter_slice5_oib_oobi_drop_pkt_cnt_oobi_fte_pd_req_drop_pkt_cnt {
      type oc-yang:counter64;
      description
        "Injected FTE Peer Delay Request pkt drop cnt across all links.";
    }
    leaf counter_slice6_oib_oobi_drop_pkt_cnt_oobi_fte_pd_req_drop_pkt_cnt {
      type oc-yang:counter64;
      description
        "Injected FTE Peer Delay Request pkt drop cnt across all links.";
    }
    leaf counter_slice7_oib_oobi_drop_pkt_cnt_oobi_fte_pd_req_drop_pkt_cnt {
      type oc-yang:counter64;
      description
        "Injected FTE Peer Delay Request pkt drop cnt across all links.";
    }
    leaf counter_slice8_oib_oobi_drop_pkt_cnt_oobi_fte_pd_req_drop_pkt_cnt {
      type oc-yang:counter64;
      description
        "Injected FTE Peer Delay Request pkt drop cnt across all links.";
    }
    leaf counter_slice9_oib_oobi_drop_pkt_cnt_oobi_fte_pd_req_drop_pkt_cnt {
      type oc-yang:counter64;
      description
        "Injected FTE Peer Delay Request pkt drop cnt across all links.";
    }
    leaf counter_slice10_oib_oobi_drop_pkt_cnt_oobi_fte_pd_req_drop_pkt_cnt {
      type oc-yang:counter64;
      description
        "Injected FTE Peer Delay Request pkt drop cnt across all links.";
    }
    leaf counter_slice11_oib_oobi_drop_pkt_cnt_oobi_fte_pd_req_drop_pkt_cnt {
      type oc-yang:counter64;
      description
        "Injected FTE Peer Delay Request pkt drop cnt across all links.";
    }
    leaf counter_slice12_oib_oobi_drop_pkt_cnt_oobi_fte_pd_req_drop_pkt_cnt {
      type oc-yang:counter64;
      description
        "Injected FTE Peer Delay Request pkt drop cnt across all links.";
    }
    leaf counter_slice13_oib_oobi_drop_pkt_cnt_oobi_fte_pd_req_drop_pkt_cnt {
      type oc-yang:counter64;
      description
        "Injected FTE Peer Delay Request pkt drop cnt across all links.";
    }
    leaf counter_slice14_oib_oobi_drop_pkt_cnt_oobi_fte_pd_req_drop_pkt_cnt {
      type oc-yang:counter64;
      description
        "Injected FTE Peer Delay Request pkt drop cnt across all links.";
    }
    leaf counter_slice15_oib_oobi_drop_pkt_cnt_oobi_fte_pd_req_drop_pkt_cnt {
      type oc-yang:counter64;
      description
        "Injected FTE Peer Delay Request pkt drop cnt across all links.";
    }
    leaf counter_slice0_oib_oobi_drop_pkt_cnt_oobi_fte_pd_res_drop_pkt_cnt {
      type oc-yang:counter64;
      description
        "Injected FTE Peer Delay Response pkt drop cnt across all links";
    }
    leaf counter_slice1_oib_oobi_drop_pkt_cnt_oobi_fte_pd_res_drop_pkt_cnt {
      type oc-yang:counter64;
      description
        "Injected FTE Peer Delay Response pkt drop cnt across all links";
    }
    leaf counter_slice2_oib_oobi_drop_pkt_cnt_oobi_fte_pd_res_drop_pkt_cnt {
      type oc-yang:counter64;
      description
        "Injected FTE Peer Delay Response pkt drop cnt across all links";
    }
    leaf counter_slice3_oib_oobi_drop_pkt_cnt_oobi_fte_pd_res_drop_pkt_cnt {
      type oc-yang:counter64;
      description
        "Injected FTE Peer Delay Response pkt drop cnt across all links";
    }
    leaf counter_slice4_oib_oobi_drop_pkt_cnt_oobi_fte_pd_res_drop_pkt_cnt {
      type oc-yang:counter64;
      description
        "Injected FTE Peer Delay Response pkt drop cnt across all links";
    }
    leaf counter_slice5_oib_oobi_drop_pkt_cnt_oobi_fte_pd_res_drop_pkt_cnt {
      type oc-yang:counter64;
      description
        "Injected FTE Peer Delay Response pkt drop cnt across all links";
    }
    leaf counter_slice6_oib_oobi_drop_pkt_cnt_oobi_fte_pd_res_drop_pkt_cnt {
      type oc-yang:counter64;
      description
        "Injected FTE Peer Delay Response pkt drop cnt across all links";
    }
    leaf counter_slice7_oib_oobi_drop_pkt_cnt_oobi_fte_pd_res_drop_pkt_cnt {
      type oc-yang:counter64;
      description
        "Injected FTE Peer Delay Response pkt drop cnt across all links";
    }
    leaf counter_slice8_oib_oobi_drop_pkt_cnt_oobi_fte_pd_res_drop_pkt_cnt {
      type oc-yang:counter64;
      description
        "Injected FTE Peer Delay Response pkt drop cnt across all links";
    }
    leaf counter_slice9_oib_oobi_drop_pkt_cnt_oobi_fte_pd_res_drop_pkt_cnt {
      type oc-yang:counter64;
      description
        "Injected FTE Peer Delay Response pkt drop cnt across all links";
    }
    leaf counter_slice10_oib_oobi_drop_pkt_cnt_oobi_fte_pd_res_drop_pkt_cnt {
      type oc-yang:counter64;
      description
        "Injected FTE Peer Delay Response pkt drop cnt across all links";
    }
    leaf counter_slice11_oib_oobi_drop_pkt_cnt_oobi_fte_pd_res_drop_pkt_cnt {
      type oc-yang:counter64;
      description
        "Injected FTE Peer Delay Response pkt drop cnt across all links";
    }
    leaf counter_slice12_oib_oobi_drop_pkt_cnt_oobi_fte_pd_res_drop_pkt_cnt {
      type oc-yang:counter64;
      description
        "Injected FTE Peer Delay Response pkt drop cnt across all links";
    }
    leaf counter_slice13_oib_oobi_drop_pkt_cnt_oobi_fte_pd_res_drop_pkt_cnt {
      type oc-yang:counter64;
      description
        "Injected FTE Peer Delay Response pkt drop cnt across all links";
    }
    leaf counter_slice14_oib_oobi_drop_pkt_cnt_oobi_fte_pd_res_drop_pkt_cnt {
      type oc-yang:counter64;
      description
        "Injected FTE Peer Delay Response pkt drop cnt across all links";
    }
    leaf counter_slice15_oib_oobi_drop_pkt_cnt_oobi_fte_pd_res_drop_pkt_cnt {
      type oc-yang:counter64;
      description
        "Injected FTE Peer Delay Response pkt drop cnt across all links";
    }
    leaf counter_slice0_oib_oobi_drop_pkt_cnt_oobi_illegal_drop_pkt_cnt {
      type oc-yang:counter64;
      description
        "Injected Illegal pkt drop cnt across all links";
    }
    leaf counter_slice1_oib_oobi_drop_pkt_cnt_oobi_illegal_drop_pkt_cnt {
      type oc-yang:counter64;
      description
        "Injected Illegal pkt drop cnt across all links";
    }
    leaf counter_slice2_oib_oobi_drop_pkt_cnt_oobi_illegal_drop_pkt_cnt {
      type oc-yang:counter64;
      description
        "Injected Illegal pkt drop cnt across all links";
    }
    leaf counter_slice3_oib_oobi_drop_pkt_cnt_oobi_illegal_drop_pkt_cnt {
      type oc-yang:counter64;
      description
        "Injected Illegal pkt drop cnt across all links";
    }
    leaf counter_slice4_oib_oobi_drop_pkt_cnt_oobi_illegal_drop_pkt_cnt {
      type oc-yang:counter64;
      description
        "Injected Illegal pkt drop cnt across all links";
    }
    leaf counter_slice5_oib_oobi_drop_pkt_cnt_oobi_illegal_drop_pkt_cnt {
      type oc-yang:counter64;
      description
        "Injected Illegal pkt drop cnt across all links";
    }
    leaf counter_slice6_oib_oobi_drop_pkt_cnt_oobi_illegal_drop_pkt_cnt {
      type oc-yang:counter64;
      description
        "Injected Illegal pkt drop cnt across all links";
    }
    leaf counter_slice7_oib_oobi_drop_pkt_cnt_oobi_illegal_drop_pkt_cnt {
      type oc-yang:counter64;
      description
        "Injected Illegal pkt drop cnt across all links";
    }
    leaf counter_slice8_oib_oobi_drop_pkt_cnt_oobi_illegal_drop_pkt_cnt {
      type oc-yang:counter64;
      description
        "Injected Illegal pkt drop cnt across all links";
    }
    leaf counter_slice9_oib_oobi_drop_pkt_cnt_oobi_illegal_drop_pkt_cnt {
      type oc-yang:counter64;
      description
        "Injected Illegal pkt drop cnt across all links";
    }
    leaf counter_slice10_oib_oobi_drop_pkt_cnt_oobi_illegal_drop_pkt_cnt {
      type oc-yang:counter64;
      description
        "Injected Illegal pkt drop cnt across all links";
    }
    leaf counter_slice11_oib_oobi_drop_pkt_cnt_oobi_illegal_drop_pkt_cnt {
      type oc-yang:counter64;
      description
        "Injected Illegal pkt drop cnt across all links";
    }
    leaf counter_slice12_oib_oobi_drop_pkt_cnt_oobi_illegal_drop_pkt_cnt {
      type oc-yang:counter64;
      description
        "Injected Illegal pkt drop cnt across all links";
    }
    leaf counter_slice13_oib_oobi_drop_pkt_cnt_oobi_illegal_drop_pkt_cnt {
      type oc-yang:counter64;
      description
        "Injected Illegal pkt drop cnt across all links";
    }
    leaf counter_slice14_oib_oobi_drop_pkt_cnt_oobi_illegal_drop_pkt_cnt {
      type oc-yang:counter64;
      description
        "Injected Illegal pkt drop cnt across all links";
    }
    leaf counter_slice15_oib_oobi_drop_pkt_cnt_oobi_illegal_drop_pkt_cnt {
      type oc-yang:counter64;
      description
        "Injected Illegal pkt drop cnt across all links";
    }
    leaf counter_info_pool0_pib0_inbe_err_pkt_cnt_inbe_nph_err_pkt_cnt {
      type oc-yang:counter64;
      description
        "Bad Packet Count for inbe NPU Host";
    }
    leaf counter_info_pool0_pib1_inbe_err_pkt_cnt_inbe_nph_err_pkt_cnt {
      type oc-yang:counter64;
      description
        "Bad Packet Count for inbe NPU Host";
    }
    leaf counter_info_pool0_pib2_inbe_err_pkt_cnt_inbe_nph_err_pkt_cnt {
      type oc-yang:counter64;
      description
        "Bad Packet Count for inbe NPU Host";
    }
    leaf counter_info_pool0_pib3_inbe_err_pkt_cnt_inbe_nph_err_pkt_cnt {
      type oc-yang:counter64;
      description
        "Bad Packet Count for inbe NPU Host";
    }
    leaf counter_info_pool1_pib0_inbe_err_pkt_cnt_inbe_nph_err_pkt_cnt {
      type oc-yang:counter64;
      description
        "Bad Packet Count for inbe NPU Host";
    }
    leaf counter_info_pool1_pib1_inbe_err_pkt_cnt_inbe_nph_err_pkt_cnt {
      type oc-yang:counter64;
      description
        "Bad Packet Count for inbe NPU Host";
    }
    leaf counter_info_pool1_pib2_inbe_err_pkt_cnt_inbe_nph_err_pkt_cnt {
      type oc-yang:counter64;
      description
        "Bad Packet Count for inbe NPU Host";
    }
    leaf counter_info_pool1_pib3_inbe_err_pkt_cnt_inbe_nph_err_pkt_cnt {
      type oc-yang:counter64;
      description
        "Bad Packet Count for inbe NPU Host";
    }
    leaf counter_info_pool2_pib0_inbe_err_pkt_cnt_inbe_nph_err_pkt_cnt {
      type oc-yang:counter64;
      description
        "Bad Packet Count for inbe NPU Host";
    }
    leaf counter_info_pool2_pib1_inbe_err_pkt_cnt_inbe_nph_err_pkt_cnt {
      type oc-yang:counter64;
      description
        "Bad Packet Count for inbe NPU Host";
    }
    leaf counter_info_pool2_pib2_inbe_err_pkt_cnt_inbe_nph_err_pkt_cnt {
      type oc-yang:counter64;
      description
        "Bad Packet Count for inbe NPU Host";
    }
    leaf counter_info_pool2_pib3_inbe_err_pkt_cnt_inbe_nph_err_pkt_cnt {
      type oc-yang:counter64;
      description
        "Bad Packet Count for inbe NPU Host";
    }
    leaf counter_info_pool3_pib0_inbe_err_pkt_cnt_inbe_nph_err_pkt_cnt {
      type oc-yang:counter64;
      description
        "Bad Packet Count for inbe NPU Host";
    }
    leaf counter_info_pool3_pib1_inbe_err_pkt_cnt_inbe_nph_err_pkt_cnt {
      type oc-yang:counter64;
      description
        "Bad Packet Count for inbe NPU Host";
    }
    leaf counter_info_pool3_pib2_inbe_err_pkt_cnt_inbe_nph_err_pkt_cnt {
      type oc-yang:counter64;
      description
        "Bad Packet Count for inbe NPU Host";
    }
    leaf counter_info_pool3_pib3_inbe_err_pkt_cnt_inbe_nph_err_pkt_cnt {
      type oc-yang:counter64;
      description
        "Bad Packet Count for inbe NPU Host";
    }
    leaf counter_info_pool0_pib0_inbe_err_pkt_cnt_inbe_pdm_err_pkt_cnt {
      type oc-yang:counter64;
      description
        "Bad Packet Count for inbe Pkt DMA";
    }
    leaf counter_info_pool0_pib1_inbe_err_pkt_cnt_inbe_pdm_err_pkt_cnt {
      type oc-yang:counter64;
      description
        "Bad Packet Count for inbe Pkt DMA";
    }
    leaf counter_info_pool0_pib2_inbe_err_pkt_cnt_inbe_pdm_err_pkt_cnt {
      type oc-yang:counter64;
      description
        "Bad Packet Count for inbe Pkt DMA";
    }
    leaf counter_info_pool0_pib3_inbe_err_pkt_cnt_inbe_pdm_err_pkt_cnt {
      type oc-yang:counter64;
      description
        "Bad Packet Count for inbe Pkt DMA";
    }
    leaf counter_info_pool1_pib0_inbe_err_pkt_cnt_inbe_pdm_err_pkt_cnt {
      type oc-yang:counter64;
      description
        "Bad Packet Count for inbe Pkt DMA";
    }
    leaf counter_info_pool1_pib1_inbe_err_pkt_cnt_inbe_pdm_err_pkt_cnt {
      type oc-yang:counter64;
      description
        "Bad Packet Count for inbe Pkt DMA";
    }
    leaf counter_info_pool1_pib2_inbe_err_pkt_cnt_inbe_pdm_err_pkt_cnt {
      type oc-yang:counter64;
      description
        "Bad Packet Count for inbe Pkt DMA";
    }
    leaf counter_info_pool1_pib3_inbe_err_pkt_cnt_inbe_pdm_err_pkt_cnt {
      type oc-yang:counter64;
      description
        "Bad Packet Count for inbe Pkt DMA";
    }
    leaf counter_info_pool2_pib0_inbe_err_pkt_cnt_inbe_pdm_err_pkt_cnt {
      type oc-yang:counter64;
      description
        "Bad Packet Count for inbe Pkt DMA";
    }
    leaf counter_info_pool2_pib1_inbe_err_pkt_cnt_inbe_pdm_err_pkt_cnt {
      type oc-yang:counter64;
      description
        "Bad Packet Count for inbe Pkt DMA";
    }
    leaf counter_info_pool2_pib2_inbe_err_pkt_cnt_inbe_pdm_err_pkt_cnt {
      type oc-yang:counter64;
      description
        "Bad Packet Count for inbe Pkt DMA";
    }
    leaf counter_info_pool2_pib3_inbe_err_pkt_cnt_inbe_pdm_err_pkt_cnt {
      type oc-yang:counter64;
      description
        "Bad Packet Count for inbe Pkt DMA";
    }
    leaf counter_info_pool3_pib0_inbe_err_pkt_cnt_inbe_pdm_err_pkt_cnt {
      type oc-yang:counter64;
      description
        "Bad Packet Count for inbe Pkt DMA";
    }
    leaf counter_info_pool3_pib1_inbe_err_pkt_cnt_inbe_pdm_err_pkt_cnt {
      type oc-yang:counter64;
      description
        "Bad Packet Count for inbe Pkt DMA";
    }
    leaf counter_info_pool3_pib2_inbe_err_pkt_cnt_inbe_pdm_err_pkt_cnt {
      type oc-yang:counter64;
      description
        "Bad Packet Count for inbe Pkt DMA";
    }
    leaf counter_info_pool3_pib3_inbe_err_pkt_cnt_inbe_pdm_err_pkt_cnt {
      type oc-yang:counter64;
      description
        "Bad Packet Count for inbe Pkt DMA";
    }
    leaf counter_info_pool0_pib0_inbi_err_pkt_cnt_inbi_nph_err_pkt_cnt {
      type oc-yang:counter64;
      description
        "Bad NPU Host packet injected by CSS";
    }
    leaf counter_info_pool0_pib1_inbi_err_pkt_cnt_inbi_nph_err_pkt_cnt {
      type oc-yang:counter64;
      description
        "Bad NPU Host packet injected by CSS";
    }
    leaf counter_info_pool0_pib2_inbi_err_pkt_cnt_inbi_nph_err_pkt_cnt {
      type oc-yang:counter64;
      description
        "Bad NPU Host packet injected by CSS";
    }
    leaf counter_info_pool0_pib3_inbi_err_pkt_cnt_inbi_nph_err_pkt_cnt {
      type oc-yang:counter64;
      description
        "Bad NPU Host packet injected by CSS";
    }
    leaf counter_info_pool1_pib0_inbi_err_pkt_cnt_inbi_nph_err_pkt_cnt {
      type oc-yang:counter64;
      description
        "Bad NPU Host packet injected by CSS";
    }
    leaf counter_info_pool1_pib1_inbi_err_pkt_cnt_inbi_nph_err_pkt_cnt {
      type oc-yang:counter64;
      description
        "Bad NPU Host packet injected by CSS";
    }
    leaf counter_info_pool1_pib2_inbi_err_pkt_cnt_inbi_nph_err_pkt_cnt {
      type oc-yang:counter64;
      description
        "Bad NPU Host packet injected by CSS";
    }
    leaf counter_info_pool1_pib3_inbi_err_pkt_cnt_inbi_nph_err_pkt_cnt {
      type oc-yang:counter64;
      description
        "Bad NPU Host packet injected by CSS";
    }
    leaf counter_info_pool2_pib0_inbi_err_pkt_cnt_inbi_nph_err_pkt_cnt {
      type oc-yang:counter64;
      description
        "Bad NPU Host packet injected by CSS";
    }
    leaf counter_info_pool2_pib1_inbi_err_pkt_cnt_inbi_nph_err_pkt_cnt {
      type oc-yang:counter64;
      description
        "Bad NPU Host packet injected by CSS";
    }
    leaf counter_info_pool2_pib2_inbi_err_pkt_cnt_inbi_nph_err_pkt_cnt {
      type oc-yang:counter64;
      description
        "Bad NPU Host packet injected by CSS";
    }
    leaf counter_info_pool2_pib3_inbi_err_pkt_cnt_inbi_nph_err_pkt_cnt {
      type oc-yang:counter64;
      description
        "Bad NPU Host packet injected by CSS";
    }
    leaf counter_info_pool3_pib0_inbi_err_pkt_cnt_inbi_nph_err_pkt_cnt {
      type oc-yang:counter64;
      description
        "Bad NPU Host packet injected by CSS";
    }
    leaf counter_info_pool3_pib1_inbi_err_pkt_cnt_inbi_nph_err_pkt_cnt {
      type oc-yang:counter64;
      description
        "Bad NPU Host packet injected by CSS";
    }
    leaf counter_info_pool3_pib2_inbi_err_pkt_cnt_inbi_nph_err_pkt_cnt {
      type oc-yang:counter64;
      description
        "Bad NPU Host packet injected by CSS";
    }
    leaf counter_info_pool3_pib3_inbi_err_pkt_cnt_inbi_nph_err_pkt_cnt {
      type oc-yang:counter64;
      description
        "Bad NPU Host packet injected by CSS";
    }
    leaf counter_info_pool0_pib0_inbi_err_pkt_cnt_inbi_pdm_err_pkt_cnt {
      type oc-yang:counter64;
      description
        "Bad Packet DMA pkt  injected by CSS";
    }
    leaf counter_info_pool0_pib1_inbi_err_pkt_cnt_inbi_pdm_err_pkt_cnt {
      type oc-yang:counter64;
      description
        "Bad Packet DMA pkt  injected by CSS";
    }
    leaf counter_info_pool0_pib2_inbi_err_pkt_cnt_inbi_pdm_err_pkt_cnt {
      type oc-yang:counter64;
      description
        "Bad Packet DMA pkt  injected by CSS";
    }
    leaf counter_info_pool0_pib3_inbi_err_pkt_cnt_inbi_pdm_err_pkt_cnt {
      type oc-yang:counter64;
      description
        "Bad Packet DMA pkt  injected by CSS";
    }
    leaf counter_info_pool1_pib0_inbi_err_pkt_cnt_inbi_pdm_err_pkt_cnt {
      type oc-yang:counter64;
      description
        "Bad Packet DMA pkt  injected by CSS";
    }
    leaf counter_info_pool1_pib1_inbi_err_pkt_cnt_inbi_pdm_err_pkt_cnt {
      type oc-yang:counter64;
      description
        "Bad Packet DMA pkt  injected by CSS";
    }
    leaf counter_info_pool1_pib2_inbi_err_pkt_cnt_inbi_pdm_err_pkt_cnt {
      type oc-yang:counter64;
      description
        "Bad Packet DMA pkt  injected by CSS";
    }
    leaf counter_info_pool1_pib3_inbi_err_pkt_cnt_inbi_pdm_err_pkt_cnt {
      type oc-yang:counter64;
      description
        "Bad Packet DMA pkt  injected by CSS";
    }
    leaf counter_info_pool2_pib0_inbi_err_pkt_cnt_inbi_pdm_err_pkt_cnt {
      type oc-yang:counter64;
      description
        "Bad Packet DMA pkt  injected by CSS";
    }
    leaf counter_info_pool2_pib1_inbi_err_pkt_cnt_inbi_pdm_err_pkt_cnt {
      type oc-yang:counter64;
      description
        "Bad Packet DMA pkt  injected by CSS";
    }
    leaf counter_info_pool2_pib2_inbi_err_pkt_cnt_inbi_pdm_err_pkt_cnt {
      type oc-yang:counter64;
      description
        "Bad Packet DMA pkt  injected by CSS";
    }
    leaf counter_info_pool2_pib3_inbi_err_pkt_cnt_inbi_pdm_err_pkt_cnt {
      type oc-yang:counter64;
      description
        "Bad Packet DMA pkt  injected by CSS";
    }
    leaf counter_info_pool3_pib0_inbi_err_pkt_cnt_inbi_pdm_err_pkt_cnt {
      type oc-yang:counter64;
      description
        "Bad Packet DMA pkt  injected by CSS";
    }
    leaf counter_info_pool3_pib1_inbi_err_pkt_cnt_inbi_pdm_err_pkt_cnt {
      type oc-yang:counter64;
      description
        "Bad Packet DMA pkt  injected by CSS";
    }
    leaf counter_info_pool3_pib2_inbi_err_pkt_cnt_inbi_pdm_err_pkt_cnt {
      type oc-yang:counter64;
      description
        "Bad Packet DMA pkt  injected by CSS";
    }
    leaf counter_info_pool3_pib3_inbi_err_pkt_cnt_inbi_pdm_err_pkt_cnt {
      type oc-yang:counter64;
      description
        "Bad Packet DMA pkt  injected by CSS";
    }
    leaf counter_pie_mac_pool80_port_mib_counter0_rx_mac_code_err_cnt {
      type oc-yang:counter64;
      description
        "MAC RX code errors count.";
    }
    leaf counter_pie_mac_pool80_port_mib_counter1_rx_mac_code_err_cnt {
      type oc-yang:counter64;
      description
        "MAC RX code errors count.";
    }
    leaf counter_pie_mac_pool80_port_mib_counter2_rx_mac_code_err_cnt {
      type oc-yang:counter64;
      description
        "MAC RX code errors count.";
    }
    leaf counter_pie_mac_pool80_port_mib_counter3_rx_mac_code_err_cnt {
      type oc-yang:counter64;
      description
        "MAC RX code errors count.";
    }
    leaf counter_pie_mac_pool80_port_mib_counter4_rx_mac_code_err_cnt {
      type oc-yang:counter64;
      description
        "MAC RX code errors count.";
    }
    leaf counter_pie_mac_pool80_port_mib_counter5_rx_mac_code_err_cnt {
      type oc-yang:counter64;
      description
        "MAC RX code errors count.";
    }
    leaf counter_pie_mac_pool80_port_mib_counter6_rx_mac_code_err_cnt {
      type oc-yang:counter64;
      description
        "MAC RX code errors count.";
    }
    leaf counter_pie_mac_pool80_port_mib_counter7_rx_mac_code_err_cnt {
      type oc-yang:counter64;
      description
        "MAC RX code errors count.";
    }
    leaf counter_pie_mac_pool81_port_mib_counter0_rx_mac_code_err_cnt {
      type oc-yang:counter64;
      description
        "MAC RX code errors count.";
    }
    leaf counter_pie_mac_pool81_port_mib_counter1_rx_mac_code_err_cnt {
      type oc-yang:counter64;
      description
        "MAC RX code errors count.";
    }
    leaf counter_pie_mac_pool81_port_mib_counter2_rx_mac_code_err_cnt {
      type oc-yang:counter64;
      description
        "MAC RX code errors count.";
    }
    leaf counter_pie_mac_pool81_port_mib_counter3_rx_mac_code_err_cnt {
      type oc-yang:counter64;
      description
        "MAC RX code errors count.";
    }
    leaf counter_pie_mac_pool81_port_mib_counter4_rx_mac_code_err_cnt {
      type oc-yang:counter64;
      description
        "MAC RX code errors count.";
    }
    leaf counter_pie_mac_pool81_port_mib_counter5_rx_mac_code_err_cnt {
      type oc-yang:counter64;
      description
        "MAC RX code errors count.";
    }
    leaf counter_pie_mac_pool81_port_mib_counter6_rx_mac_code_err_cnt {
      type oc-yang:counter64;
      description
        "MAC RX code errors count.";
    }
    leaf counter_pie_mac_pool81_port_mib_counter7_rx_mac_code_err_cnt {
      type oc-yang:counter64;
      description
        "MAC RX code errors count.";
    }
    leaf counter_pie_mac_pool80_port_mib_counter0_rx_mac_crc_err_cnt {
      type oc-yang:counter64;
      description
        "MAC RX CRC errors count aFrameCheckSequenceErrors.";
    }
    leaf counter_pie_mac_pool80_port_mib_counter1_rx_mac_crc_err_cnt {
      type oc-yang:counter64;
      description
        "MAC RX CRC errors count aFrameCheckSequenceErrors.";
    }
    leaf counter_pie_mac_pool80_port_mib_counter2_rx_mac_crc_err_cnt {
      type oc-yang:counter64;
      description
        "MAC RX CRC errors count aFrameCheckSequenceErrors.";
    }
    leaf counter_pie_mac_pool80_port_mib_counter3_rx_mac_crc_err_cnt {
      type oc-yang:counter64;
      description
        "MAC RX CRC errors count aFrameCheckSequenceErrors.";
    }
    leaf counter_pie_mac_pool80_port_mib_counter4_rx_mac_crc_err_cnt {
      type oc-yang:counter64;
      description
        "MAC RX CRC errors count aFrameCheckSequenceErrors.";
    }
    leaf counter_pie_mac_pool80_port_mib_counter5_rx_mac_crc_err_cnt {
      type oc-yang:counter64;
      description
        "MAC RX CRC errors count aFrameCheckSequenceErrors.";
    }
    leaf counter_pie_mac_pool80_port_mib_counter6_rx_mac_crc_err_cnt {
      type oc-yang:counter64;
      description
        "MAC RX CRC errors count aFrameCheckSequenceErrors.";
    }
    leaf counter_pie_mac_pool80_port_mib_counter7_rx_mac_crc_err_cnt {
      type oc-yang:counter64;
      description
        "MAC RX CRC errors count aFrameCheckSequenceErrors.";
    }
    leaf counter_pie_mac_pool81_port_mib_counter0_rx_mac_crc_err_cnt {
      type oc-yang:counter64;
      description
        "MAC RX CRC errors count aFrameCheckSequenceErrors.";
    }
    leaf counter_pie_mac_pool81_port_mib_counter1_rx_mac_crc_err_cnt {
      type oc-yang:counter64;
      description
        "MAC RX CRC errors count aFrameCheckSequenceErrors.";
    }
    leaf counter_pie_mac_pool81_port_mib_counter2_rx_mac_crc_err_cnt {
      type oc-yang:counter64;
      description
        "MAC RX CRC errors count aFrameCheckSequenceErrors.";
    }
    leaf counter_pie_mac_pool81_port_mib_counter3_rx_mac_crc_err_cnt {
      type oc-yang:counter64;
      description
        "MAC RX CRC errors count aFrameCheckSequenceErrors.";
    }
    leaf counter_pie_mac_pool81_port_mib_counter4_rx_mac_crc_err_cnt {
      type oc-yang:counter64;
      description
        "MAC RX CRC errors count aFrameCheckSequenceErrors.";
    }
    leaf counter_pie_mac_pool81_port_mib_counter5_rx_mac_crc_err_cnt {
      type oc-yang:counter64;
      description
        "MAC RX CRC errors count aFrameCheckSequenceErrors.";
    }
    leaf counter_pie_mac_pool81_port_mib_counter6_rx_mac_crc_err_cnt {
      type oc-yang:counter64;
      description
        "MAC RX CRC errors count aFrameCheckSequenceErrors.";
    }
    leaf counter_pie_mac_pool81_port_mib_counter7_rx_mac_crc_err_cnt {
      type oc-yang:counter64;
      description
        "MAC RX CRC errors count aFrameCheckSequenceErrors.";
    }
    leaf counter_pie_mac_pool80_port_mib_counter0_rx_mac_fc_frames_err_cnt {
      type oc-yang:counter64;
      description
        "MAC RX received flow control errored packet count";
    }
    leaf counter_pie_mac_pool80_port_mib_counter1_rx_mac_fc_frames_err_cnt {
      type oc-yang:counter64;
      description
        "MAC RX received flow control errored packet count";
    }
    leaf counter_pie_mac_pool80_port_mib_counter2_rx_mac_fc_frames_err_cnt {
      type oc-yang:counter64;
      description
        "MAC RX received flow control errored packet count";
    }
    leaf counter_pie_mac_pool80_port_mib_counter3_rx_mac_fc_frames_err_cnt {
      type oc-yang:counter64;
      description
        "MAC RX received flow control errored packet count";
    }
    leaf counter_pie_mac_pool80_port_mib_counter4_rx_mac_fc_frames_err_cnt {
      type oc-yang:counter64;
      description
        "MAC RX received flow control errored packet count";
    }
    leaf counter_pie_mac_pool80_port_mib_counter5_rx_mac_fc_frames_err_cnt {
      type oc-yang:counter64;
      description
        "MAC RX received flow control errored packet count";
    }
    leaf counter_pie_mac_pool80_port_mib_counter6_rx_mac_fc_frames_err_cnt {
      type oc-yang:counter64;
      description
        "MAC RX received flow control errored packet count";
    }
    leaf counter_pie_mac_pool80_port_mib_counter7_rx_mac_fc_frames_err_cnt {
      type oc-yang:counter64;
      description
        "MAC RX received flow control errored packet count";
    }
    leaf counter_pie_mac_pool81_port_mib_counter0_rx_mac_fc_frames_err_cnt {
      type oc-yang:counter64;
      description
        "MAC RX received flow control errored packet count";
    }
    leaf counter_pie_mac_pool81_port_mib_counter1_rx_mac_fc_frames_err_cnt {
      type oc-yang:counter64;
      description
        "MAC RX received flow control errored packet count";
    }
    leaf counter_pie_mac_pool81_port_mib_counter2_rx_mac_fc_frames_err_cnt {
      type oc-yang:counter64;
      description
        "MAC RX received flow control errored packet count";
    }
    leaf counter_pie_mac_pool81_port_mib_counter3_rx_mac_fc_frames_err_cnt {
      type oc-yang:counter64;
      description
        "MAC RX received flow control errored packet count";
    }
    leaf counter_pie_mac_pool81_port_mib_counter4_rx_mac_fc_frames_err_cnt {
      type oc-yang:counter64;
      description
        "MAC RX received flow control errored packet count";
    }
    leaf counter_pie_mac_pool81_port_mib_counter5_rx_mac_fc_frames_err_cnt {
      type oc-yang:counter64;
      description
        "MAC RX received flow control errored packet count";
    }
    leaf counter_pie_mac_pool81_port_mib_counter6_rx_mac_fc_frames_err_cnt {
      type oc-yang:counter64;
      description
        "MAC RX received flow control errored packet count";
    }
    leaf counter_pie_mac_pool81_port_mib_counter7_rx_mac_fc_frames_err_cnt {
      type oc-yang:counter64;
      description
        "MAC RX received flow control errored packet count";
    }
    leaf counter_pie_mac_pool80_port_mib_counter0_rx_mac_invert_crc_cnt {
      type oc-yang:counter64;
      description
        "MAC RX inverted CRC count packets with CRC result = 32'hFFFFFFFF.";
    }
    leaf counter_pie_mac_pool80_port_mib_counter1_rx_mac_invert_crc_cnt {
      type oc-yang:counter64;
      description
        "MAC RX inverted CRC count packets with CRC result = 32'hFFFFFFFF.";
    }
    leaf counter_pie_mac_pool80_port_mib_counter2_rx_mac_invert_crc_cnt {
      type oc-yang:counter64;
      description
        "MAC RX inverted CRC count packets with CRC result = 32'hFFFFFFFF.";
    }
    leaf counter_pie_mac_pool80_port_mib_counter3_rx_mac_invert_crc_cnt {
      type oc-yang:counter64;
      description
        "MAC RX inverted CRC count packets with CRC result = 32'hFFFFFFFF.";
    }
    leaf counter_pie_mac_pool80_port_mib_counter4_rx_mac_invert_crc_cnt {
      type oc-yang:counter64;
      description
        "MAC RX inverted CRC count packets with CRC result = 32'hFFFFFFFF.";
    }
    leaf counter_pie_mac_pool80_port_mib_counter5_rx_mac_invert_crc_cnt {
      type oc-yang:counter64;
      description
        "MAC RX inverted CRC count packets with CRC result = 32'hFFFFFFFF.";
    }
    leaf counter_pie_mac_pool80_port_mib_counter6_rx_mac_invert_crc_cnt {
      type oc-yang:counter64;
      description
        "MAC RX inverted CRC count packets with CRC result = 32'hFFFFFFFF.";
    }
    leaf counter_pie_mac_pool80_port_mib_counter7_rx_mac_invert_crc_cnt {
      type oc-yang:counter64;
      description
        "MAC RX inverted CRC count packets with CRC result = 32'hFFFFFFFF.";
    }
    leaf counter_pie_mac_pool81_port_mib_counter0_rx_mac_invert_crc_cnt {
      type oc-yang:counter64;
      description
        "MAC RX inverted CRC count packets with CRC result = 32'hFFFFFFFF.";
    }
    leaf counter_pie_mac_pool81_port_mib_counter1_rx_mac_invert_crc_cnt {
      type oc-yang:counter64;
      description
        "MAC RX inverted CRC count packets with CRC result = 32'hFFFFFFFF.";
    }
    leaf counter_pie_mac_pool81_port_mib_counter2_rx_mac_invert_crc_cnt {
      type oc-yang:counter64;
      description
        "MAC RX inverted CRC count packets with CRC result = 32'hFFFFFFFF.";
    }
    leaf counter_pie_mac_pool81_port_mib_counter3_rx_mac_invert_crc_cnt {
      type oc-yang:counter64;
      description
        "MAC RX inverted CRC count packets with CRC result = 32'hFFFFFFFF.";
    }
    leaf counter_pie_mac_pool81_port_mib_counter4_rx_mac_invert_crc_cnt {
      type oc-yang:counter64;
      description
        "MAC RX inverted CRC count packets with CRC result = 32'hFFFFFFFF.";
    }
    leaf counter_pie_mac_pool81_port_mib_counter5_rx_mac_invert_crc_cnt {
      type oc-yang:counter64;
      description
        "MAC RX inverted CRC count packets with CRC result = 32'hFFFFFFFF.";
    }
    leaf counter_pie_mac_pool81_port_mib_counter6_rx_mac_invert_crc_cnt {
      type oc-yang:counter64;
      description
        "MAC RX inverted CRC count packets with CRC result = 32'hFFFFFFFF.";
    }
    leaf counter_pie_mac_pool81_port_mib_counter7_rx_mac_invert_crc_cnt {
      type oc-yang:counter64;
      description
        "MAC RX inverted CRC count packets with CRC result = 32'hFFFFFFFF.";
    }
    leaf counter_pie_mac_pool80_port_mib_counter0_rx_mac_oversize_err_cnt {
      type oc-yang:counter64;
      description
        "MAC RX undersize errors count.";
    }
    leaf counter_pie_mac_pool80_port_mib_counter1_rx_mac_oversize_err_cnt {
      type oc-yang:counter64;
      description
        "MAC RX undersize errors count.";
    }
    leaf counter_pie_mac_pool80_port_mib_counter2_rx_mac_oversize_err_cnt {
      type oc-yang:counter64;
      description
        "MAC RX undersize errors count.";
    }
    leaf counter_pie_mac_pool80_port_mib_counter3_rx_mac_oversize_err_cnt {
      type oc-yang:counter64;
      description
        "MAC RX undersize errors count.";
    }
    leaf counter_pie_mac_pool80_port_mib_counter4_rx_mac_oversize_err_cnt {
      type oc-yang:counter64;
      description
        "MAC RX undersize errors count.";
    }
    leaf counter_pie_mac_pool80_port_mib_counter5_rx_mac_oversize_err_cnt {
      type oc-yang:counter64;
      description
        "MAC RX undersize errors count.";
    }
    leaf counter_pie_mac_pool80_port_mib_counter6_rx_mac_oversize_err_cnt {
      type oc-yang:counter64;
      description
        "MAC RX undersize errors count.";
    }
    leaf counter_pie_mac_pool80_port_mib_counter7_rx_mac_oversize_err_cnt {
      type oc-yang:counter64;
      description
        "MAC RX undersize errors count.";
    }
    leaf counter_pie_mac_pool81_port_mib_counter0_rx_mac_oversize_err_cnt {
      type oc-yang:counter64;
      description
        "MAC RX undersize errors count.";
    }
    leaf counter_pie_mac_pool81_port_mib_counter1_rx_mac_oversize_err_cnt {
      type oc-yang:counter64;
      description
        "MAC RX undersize errors count.";
    }
    leaf counter_pie_mac_pool81_port_mib_counter2_rx_mac_oversize_err_cnt {
      type oc-yang:counter64;
      description
        "MAC RX undersize errors count.";
    }
    leaf counter_pie_mac_pool81_port_mib_counter3_rx_mac_oversize_err_cnt {
      type oc-yang:counter64;
      description
        "MAC RX undersize errors count.";
    }
    leaf counter_pie_mac_pool81_port_mib_counter4_rx_mac_oversize_err_cnt {
      type oc-yang:counter64;
      description
        "MAC RX undersize errors count.";
    }
    leaf counter_pie_mac_pool81_port_mib_counter5_rx_mac_oversize_err_cnt {
      type oc-yang:counter64;
      description
        "MAC RX undersize errors count.";
    }
    leaf counter_pie_mac_pool81_port_mib_counter6_rx_mac_oversize_err_cnt {
      type oc-yang:counter64;
      description
        "MAC RX undersize errors count.";
    }
    leaf counter_pie_mac_pool81_port_mib_counter7_rx_mac_oversize_err_cnt {
      type oc-yang:counter64;
      description
        "MAC RX undersize errors count.";
    }
    leaf counter_pie_mac_pool80_port_mib_counter0_rx_mac_undersize_err_cnt {
      type oc-yang:counter64;
      description
        "MAC RX oversize errors count.";
    }
    leaf counter_pie_mac_pool80_port_mib_counter1_rx_mac_undersize_err_cnt {
      type oc-yang:counter64;
      description
        "MAC RX oversize errors count.";
    }
    leaf counter_pie_mac_pool80_port_mib_counter2_rx_mac_undersize_err_cnt {
      type oc-yang:counter64;
      description
        "MAC RX oversize errors count.";
    }
    leaf counter_pie_mac_pool80_port_mib_counter3_rx_mac_undersize_err_cnt {
      type oc-yang:counter64;
      description
        "MAC RX oversize errors count.";
    }
    leaf counter_pie_mac_pool80_port_mib_counter4_rx_mac_undersize_err_cnt {
      type oc-yang:counter64;
      description
        "MAC RX oversize errors count.";
    }
    leaf counter_pie_mac_pool80_port_mib_counter5_rx_mac_undersize_err_cnt {
      type oc-yang:counter64;
      description
        "MAC RX oversize errors count.";
    }
    leaf counter_pie_mac_pool80_port_mib_counter6_rx_mac_undersize_err_cnt {
      type oc-yang:counter64;
      description
        "MAC RX oversize errors count.";
    }
    leaf counter_pie_mac_pool80_port_mib_counter7_rx_mac_undersize_err_cnt {
      type oc-yang:counter64;
      description
        "MAC RX oversize errors count.";
    }
    leaf counter_pie_mac_pool81_port_mib_counter0_rx_mac_undersize_err_cnt {
      type oc-yang:counter64;
      description
        "MAC RX oversize errors count.";
    }
    leaf counter_pie_mac_pool81_port_mib_counter1_rx_mac_undersize_err_cnt {
      type oc-yang:counter64;
      description
        "MAC RX oversize errors count.";
    }
    leaf counter_pie_mac_pool81_port_mib_counter2_rx_mac_undersize_err_cnt {
      type oc-yang:counter64;
      description
        "MAC RX oversize errors count.";
    }
    leaf counter_pie_mac_pool81_port_mib_counter3_rx_mac_undersize_err_cnt {
      type oc-yang:counter64;
      description
        "MAC RX oversize errors count.";
    }
    leaf counter_pie_mac_pool81_port_mib_counter4_rx_mac_undersize_err_cnt {
      type oc-yang:counter64;
      description
        "MAC RX oversize errors count.";
    }
    leaf counter_pie_mac_pool81_port_mib_counter5_rx_mac_undersize_err_cnt {
      type oc-yang:counter64;
      description
        "MAC RX oversize errors count.";
    }
    leaf counter_pie_mac_pool81_port_mib_counter6_rx_mac_undersize_err_cnt {
      type oc-yang:counter64;
      description
        "MAC RX oversize errors count.";
    }
    leaf counter_pie_mac_pool81_port_mib_counter7_rx_mac_undersize_err_cnt {
      type oc-yang:counter64;
      description
        "MAC RX oversize errors count.";
    }
    leaf counter_pie_mac_pool80_port_mib_counter0_rx_oob_mac_code_err_cnt {
      type oc-yang:counter64;
      description
        "MAC RX code errors count for interleaved out of band fabric control packets.";
    }
    leaf counter_pie_mac_pool80_port_mib_counter1_rx_oob_mac_code_err_cnt {
      type oc-yang:counter64;
      description
        "MAC RX code errors count for interleaved out of band fabric control packets.";
    }
    leaf counter_pie_mac_pool80_port_mib_counter2_rx_oob_mac_code_err_cnt {
      type oc-yang:counter64;
      description
        "MAC RX code errors count for interleaved out of band fabric control packets.";
    }
    leaf counter_pie_mac_pool80_port_mib_counter3_rx_oob_mac_code_err_cnt {
      type oc-yang:counter64;
      description
        "MAC RX code errors count for interleaved out of band fabric control packets.";
    }
    leaf counter_pie_mac_pool80_port_mib_counter4_rx_oob_mac_code_err_cnt {
      type oc-yang:counter64;
      description
        "MAC RX code errors count for interleaved out of band fabric control packets.";
    }
    leaf counter_pie_mac_pool80_port_mib_counter5_rx_oob_mac_code_err_cnt {
      type oc-yang:counter64;
      description
        "MAC RX code errors count for interleaved out of band fabric control packets.";
    }
    leaf counter_pie_mac_pool80_port_mib_counter6_rx_oob_mac_code_err_cnt {
      type oc-yang:counter64;
      description
        "MAC RX code errors count for interleaved out of band fabric control packets.";
    }
    leaf counter_pie_mac_pool80_port_mib_counter7_rx_oob_mac_code_err_cnt {
      type oc-yang:counter64;
      description
        "MAC RX code errors count for interleaved out of band fabric control packets.";
    }
    leaf counter_pie_mac_pool81_port_mib_counter0_rx_oob_mac_code_err_cnt {
      type oc-yang:counter64;
      description
        "MAC RX code errors count for interleaved out of band fabric control packets.";
    }
    leaf counter_pie_mac_pool81_port_mib_counter1_rx_oob_mac_code_err_cnt {
      type oc-yang:counter64;
      description
        "MAC RX code errors count for interleaved out of band fabric control packets.";
    }
    leaf counter_pie_mac_pool81_port_mib_counter2_rx_oob_mac_code_err_cnt {
      type oc-yang:counter64;
      description
        "MAC RX code errors count for interleaved out of band fabric control packets.";
    }
    leaf counter_pie_mac_pool81_port_mib_counter3_rx_oob_mac_code_err_cnt {
      type oc-yang:counter64;
      description
        "MAC RX code errors count for interleaved out of band fabric control packets.";
    }
    leaf counter_pie_mac_pool81_port_mib_counter4_rx_oob_mac_code_err_cnt {
      type oc-yang:counter64;
      description
        "MAC RX code errors count for interleaved out of band fabric control packets.";
    }
    leaf counter_pie_mac_pool81_port_mib_counter5_rx_oob_mac_code_err_cnt {
      type oc-yang:counter64;
      description
        "MAC RX code errors count for interleaved out of band fabric control packets.";
    }
    leaf counter_pie_mac_pool81_port_mib_counter6_rx_oob_mac_code_err_cnt {
      type oc-yang:counter64;
      description
        "MAC RX code errors count for interleaved out of band fabric control packets.";
    }
    leaf counter_pie_mac_pool81_port_mib_counter7_rx_oob_mac_code_err_cnt {
      type oc-yang:counter64;
      description
        "MAC RX code errors count for interleaved out of band fabric control packets.";
    }
    leaf counter_pie_mac_pool80_port_mib_counter0_tx_mac_crc_err_cnt {
      type oc-yang:counter64;
      description
        "MAC TX CRC errors count drop commands from core.";
    }
    leaf counter_pie_mac_pool80_port_mib_counter1_tx_mac_crc_err_cnt {
      type oc-yang:counter64;
      description
        "MAC TX CRC errors count drop commands from core.";
    }
    leaf counter_pie_mac_pool80_port_mib_counter2_tx_mac_crc_err_cnt {
      type oc-yang:counter64;
      description
        "MAC TX CRC errors count drop commands from core.";
    }
    leaf counter_pie_mac_pool80_port_mib_counter3_tx_mac_crc_err_cnt {
      type oc-yang:counter64;
      description
        "MAC TX CRC errors count drop commands from core.";
    }
    leaf counter_pie_mac_pool80_port_mib_counter4_tx_mac_crc_err_cnt {
      type oc-yang:counter64;
      description
        "MAC TX CRC errors count drop commands from core.";
    }
    leaf counter_pie_mac_pool80_port_mib_counter5_tx_mac_crc_err_cnt {
      type oc-yang:counter64;
      description
        "MAC TX CRC errors count drop commands from core.";
    }
    leaf counter_pie_mac_pool80_port_mib_counter6_tx_mac_crc_err_cnt {
      type oc-yang:counter64;
      description
        "MAC TX CRC errors count drop commands from core.";
    }
    leaf counter_pie_mac_pool80_port_mib_counter7_tx_mac_crc_err_cnt {
      type oc-yang:counter64;
      description
        "MAC TX CRC errors count drop commands from core.";
    }
    leaf counter_pie_mac_pool81_port_mib_counter0_tx_mac_crc_err_cnt {
      type oc-yang:counter64;
      description
        "MAC TX CRC errors count drop commands from core.";
    }
    leaf counter_pie_mac_pool81_port_mib_counter1_tx_mac_crc_err_cnt {
      type oc-yang:counter64;
      description
        "MAC TX CRC errors count drop commands from core.";
    }
    leaf counter_pie_mac_pool81_port_mib_counter2_tx_mac_crc_err_cnt {
      type oc-yang:counter64;
      description
        "MAC TX CRC errors count drop commands from core.";
    }
    leaf counter_pie_mac_pool81_port_mib_counter3_tx_mac_crc_err_cnt {
      type oc-yang:counter64;
      description
        "MAC TX CRC errors count drop commands from core.";
    }
    leaf counter_pie_mac_pool81_port_mib_counter4_tx_mac_crc_err_cnt {
      type oc-yang:counter64;
      description
        "MAC TX CRC errors count drop commands from core.";
    }
    leaf counter_pie_mac_pool81_port_mib_counter5_tx_mac_crc_err_cnt {
      type oc-yang:counter64;
      description
        "MAC TX CRC errors count drop commands from core.";
    }
    leaf counter_pie_mac_pool81_port_mib_counter6_tx_mac_crc_err_cnt {
      type oc-yang:counter64;
      description
        "MAC TX CRC errors count drop commands from core.";
    }
    leaf counter_pie_mac_pool81_port_mib_counter7_tx_mac_crc_err_cnt {
      type oc-yang:counter64;
      description
        "MAC TX CRC errors count drop commands from core.";
    }
    leaf counter_pie_mac_pool80_port_mib_counter0_tx_mac_missing_eop_err_cnt {
      type oc-yang:counter64;
      description
        "MAC TX missing eop errors count.";
    }
    leaf counter_pie_mac_pool80_port_mib_counter1_tx_mac_missing_eop_err_cnt {
      type oc-yang:counter64;
      description
        "MAC TX missing eop errors count.";
    }
    leaf counter_pie_mac_pool80_port_mib_counter2_tx_mac_missing_eop_err_cnt {
      type oc-yang:counter64;
      description
        "MAC TX missing eop errors count.";
    }
    leaf counter_pie_mac_pool80_port_mib_counter3_tx_mac_missing_eop_err_cnt {
      type oc-yang:counter64;
      description
        "MAC TX missing eop errors count.";
    }
    leaf counter_pie_mac_pool80_port_mib_counter4_tx_mac_missing_eop_err_cnt {
      type oc-yang:counter64;
      description
        "MAC TX missing eop errors count.";
    }
    leaf counter_pie_mac_pool80_port_mib_counter5_tx_mac_missing_eop_err_cnt {
      type oc-yang:counter64;
      description
        "MAC TX missing eop errors count.";
    }
    leaf counter_pie_mac_pool80_port_mib_counter6_tx_mac_missing_eop_err_cnt {
      type oc-yang:counter64;
      description
        "MAC TX missing eop errors count.";
    }
    leaf counter_pie_mac_pool80_port_mib_counter7_tx_mac_missing_eop_err_cnt {
      type oc-yang:counter64;
      description
        "MAC TX missing eop errors count.";
    }
    leaf counter_pie_mac_pool81_port_mib_counter0_tx_mac_missing_eop_err_cnt {
      type oc-yang:counter64;
      description
        "MAC TX missing eop errors count.";
    }
    leaf counter_pie_mac_pool81_port_mib_counter1_tx_mac_missing_eop_err_cnt {
      type oc-yang:counter64;
      description
        "MAC TX missing eop errors count.";
    }
    leaf counter_pie_mac_pool81_port_mib_counter2_tx_mac_missing_eop_err_cnt {
      type oc-yang:counter64;
      description
        "MAC TX missing eop errors count.";
    }
    leaf counter_pie_mac_pool81_port_mib_counter3_tx_mac_missing_eop_err_cnt {
      type oc-yang:counter64;
      description
        "MAC TX missing eop errors count.";
    }
    leaf counter_pie_mac_pool81_port_mib_counter4_tx_mac_missing_eop_err_cnt {
      type oc-yang:counter64;
      description
        "MAC TX missing eop errors count.";
    }
    leaf counter_pie_mac_pool81_port_mib_counter5_tx_mac_missing_eop_err_cnt {
      type oc-yang:counter64;
      description
        "MAC TX missing eop errors count.";
    }
    leaf counter_pie_mac_pool81_port_mib_counter6_tx_mac_missing_eop_err_cnt {
      type oc-yang:counter64;
      description
        "MAC TX missing eop errors count.";
    }
    leaf counter_pie_mac_pool81_port_mib_counter7_tx_mac_missing_eop_err_cnt {
      type oc-yang:counter64;
      description
        "MAC TX missing eop errors count.";
    }
    leaf counter_pie_mac_pool80_port_mib_counter0_tx_mac_underrun_err_cnt {
      type oc-yang:counter64;
      description
        "MAC TX underrun errors count.";
    }
    leaf counter_pie_mac_pool80_port_mib_counter1_tx_mac_underrun_err_cnt {
      type oc-yang:counter64;
      description
        "MAC TX underrun errors count.";
    }
    leaf counter_pie_mac_pool80_port_mib_counter2_tx_mac_underrun_err_cnt {
      type oc-yang:counter64;
      description
        "MAC TX underrun errors count.";
    }
    leaf counter_pie_mac_pool80_port_mib_counter3_tx_mac_underrun_err_cnt {
      type oc-yang:counter64;
      description
        "MAC TX underrun errors count.";
    }
    leaf counter_pie_mac_pool80_port_mib_counter4_tx_mac_underrun_err_cnt {
      type oc-yang:counter64;
      description
        "MAC TX underrun errors count.";
    }
    leaf counter_pie_mac_pool80_port_mib_counter5_tx_mac_underrun_err_cnt {
      type oc-yang:counter64;
      description
        "MAC TX underrun errors count.";
    }
    leaf counter_pie_mac_pool80_port_mib_counter6_tx_mac_underrun_err_cnt {
      type oc-yang:counter64;
      description
        "MAC TX underrun errors count.";
    }
    leaf counter_pie_mac_pool80_port_mib_counter7_tx_mac_underrun_err_cnt {
      type oc-yang:counter64;
      description
        "MAC TX underrun errors count.";
    }
    leaf counter_pie_mac_pool81_port_mib_counter0_tx_mac_underrun_err_cnt {
      type oc-yang:counter64;
      description
        "MAC TX underrun errors count.";
    }
    leaf counter_pie_mac_pool81_port_mib_counter1_tx_mac_underrun_err_cnt {
      type oc-yang:counter64;
      description
        "MAC TX underrun errors count.";
    }
    leaf counter_pie_mac_pool81_port_mib_counter2_tx_mac_underrun_err_cnt {
      type oc-yang:counter64;
      description
        "MAC TX underrun errors count.";
    }
    leaf counter_pie_mac_pool81_port_mib_counter3_tx_mac_underrun_err_cnt {
      type oc-yang:counter64;
      description
        "MAC TX underrun errors count.";
    }
    leaf counter_pie_mac_pool81_port_mib_counter4_tx_mac_underrun_err_cnt {
      type oc-yang:counter64;
      description
        "MAC TX underrun errors count.";
    }
    leaf counter_pie_mac_pool81_port_mib_counter5_tx_mac_underrun_err_cnt {
      type oc-yang:counter64;
      description
        "MAC TX underrun errors count.";
    }
    leaf counter_pie_mac_pool81_port_mib_counter6_tx_mac_underrun_err_cnt {
      type oc-yang:counter64;
      description
        "MAC TX underrun errors count.";
    }
    leaf counter_pie_mac_pool81_port_mib_counter7_tx_mac_underrun_err_cnt {
      type oc-yang:counter64;
      description
        "MAC TX underrun errors count.";
    }
    leaf counter_pie_mac_pool80_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg0_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg1_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg2_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg3_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg4_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg5_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg6_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool81_rx_mac_filt_cnt_reg7_rx_mac_filt_cnt {
      type oc-yang:counter64;
      description
        "Counts two kinds of packet drops in the MAC RX: 1. When RxDataEn is 0 - counts dropped packets due to isolation. 2. When RxDataEn is 1 and in fabric mode with OOB interleaving - counts number of packets dropped due to type error.";
    }
    leaf counter_pie_mac_pool80_rx_mac_partial1_invert_crc_cnt_reg0_rx_mac_partial1_invert_crc_cnt {
      type oc-yang:counter64;
      description
        "Counts the number of received packets with partial CRC type 1.";
    }
    leaf counter_pie_mac_pool80_rx_mac_partial1_invert_crc_cnt_reg1_rx_mac_partial1_invert_crc_cnt {
      type oc-yang:counter64;
      description
        "Counts the number of received packets with partial CRC type 1.";
    }
    leaf counter_pie_mac_pool80_rx_mac_partial1_invert_crc_cnt_reg2_rx_mac_partial1_invert_crc_cnt {
      type oc-yang:counter64;
      description
        "Counts the number of received packets with partial CRC type 1.";
    }
    leaf counter_pie_mac_pool80_rx_mac_partial1_invert_crc_cnt_reg3_rx_mac_partial1_invert_crc_cnt {
      type oc-yang:counter64;
      description
        "Counts the number of received packets with partial CRC type 1.";
    }
    leaf counter_pie_mac_pool80_rx_mac_partial1_invert_crc_cnt_reg4_rx_mac_partial1_invert_crc_cnt {
      type oc-yang:counter64;
      description
        "Counts the number of received packets with partial CRC type 1.";
    }
    leaf counter_pie_mac_pool80_rx_mac_partial1_invert_crc_cnt_reg5_rx_mac_partial1_invert_crc_cnt {
      type oc-yang:counter64;
      description
        "Counts the number of received packets with partial CRC type 1.";
    }
    leaf counter_pie_mac_pool80_rx_mac_partial1_invert_crc_cnt_reg6_rx_mac_partial1_invert_crc_cnt {
      type oc-yang:counter64;
      description
        "Counts the number of received packets with partial CRC type 1.";
    }
    leaf counter_pie_mac_pool80_rx_mac_partial1_invert_crc_cnt_reg7_rx_mac_partial1_invert_crc_cnt {
      type oc-yang:counter64;
      description
        "Counts the number of received packets with partial CRC type 1.";
    }
    leaf counter_pie_mac_pool81_rx_mac_partial1_invert_crc_cnt_reg0_rx_mac_partial1_invert_crc_cnt {
      type oc-yang:counter64;
      description
        "Counts the number of received packets with partial CRC type 1.";
    }
    leaf counter_pie_mac_pool81_rx_mac_partial1_invert_crc_cnt_reg1_rx_mac_partial1_invert_crc_cnt {
      type oc-yang:counter64;
      description
        "Counts the number of received packets with partial CRC type 1.";
    }
    leaf counter_pie_mac_pool81_rx_mac_partial1_invert_crc_cnt_reg2_rx_mac_partial1_invert_crc_cnt {
      type oc-yang:counter64;
      description
        "Counts the number of received packets with partial CRC type 1.";
    }
    leaf counter_pie_mac_pool81_rx_mac_partial1_invert_crc_cnt_reg3_rx_mac_partial1_invert_crc_cnt {
      type oc-yang:counter64;
      description
        "Counts the number of received packets with partial CRC type 1.";
    }
    leaf counter_pie_mac_pool81_rx_mac_partial1_invert_crc_cnt_reg4_rx_mac_partial1_invert_crc_cnt {
      type oc-yang:counter64;
      description
        "Counts the number of received packets with partial CRC type 1.";
    }
    leaf counter_pie_mac_pool81_rx_mac_partial1_invert_crc_cnt_reg5_rx_mac_partial1_invert_crc_cnt {
      type oc-yang:counter64;
      description
        "Counts the number of received packets with partial CRC type 1.";
    }
    leaf counter_pie_mac_pool81_rx_mac_partial1_invert_crc_cnt_reg6_rx_mac_partial1_invert_crc_cnt {
      type oc-yang:counter64;
      description
        "Counts the number of received packets with partial CRC type 1.";
    }
    leaf counter_pie_mac_pool81_rx_mac_partial1_invert_crc_cnt_reg7_rx_mac_partial1_invert_crc_cnt {
      type oc-yang:counter64;
      description
        "Counts the number of received packets with partial CRC type 1.";
    }
    leaf counter_pie_mac_pool80_rx_mac_partial2_invert_crc_cnt_reg0_rx_mac_partial2_invert_crc_cnt {
      type oc-yang:counter64;
      description
        "Counts the number of received packets with partial CRC type 2.";
    }
    leaf counter_pie_mac_pool80_rx_mac_partial2_invert_crc_cnt_reg1_rx_mac_partial2_invert_crc_cnt {
      type oc-yang:counter64;
      description
        "Counts the number of received packets with partial CRC type 2.";
    }
    leaf counter_pie_mac_pool80_rx_mac_partial2_invert_crc_cnt_reg2_rx_mac_partial2_invert_crc_cnt {
      type oc-yang:counter64;
      description
        "Counts the number of received packets with partial CRC type 2.";
    }
    leaf counter_pie_mac_pool80_rx_mac_partial2_invert_crc_cnt_reg3_rx_mac_partial2_invert_crc_cnt {
      type oc-yang:counter64;
      description
        "Counts the number of received packets with partial CRC type 2.";
    }
    leaf counter_pie_mac_pool80_rx_mac_partial2_invert_crc_cnt_reg4_rx_mac_partial2_invert_crc_cnt {
      type oc-yang:counter64;
      description
        "Counts the number of received packets with partial CRC type 2.";
    }
    leaf counter_pie_mac_pool80_rx_mac_partial2_invert_crc_cnt_reg5_rx_mac_partial2_invert_crc_cnt {
      type oc-yang:counter64;
      description
        "Counts the number of received packets with partial CRC type 2.";
    }
    leaf counter_pie_mac_pool80_rx_mac_partial2_invert_crc_cnt_reg6_rx_mac_partial2_invert_crc_cnt {
      type oc-yang:counter64;
      description
        "Counts the number of received packets with partial CRC type 2.";
    }
    leaf counter_pie_mac_pool80_rx_mac_partial2_invert_crc_cnt_reg7_rx_mac_partial2_invert_crc_cnt {
      type oc-yang:counter64;
      description
        "Counts the number of received packets with partial CRC type 2.";
    }
    leaf counter_pie_mac_pool81_rx_mac_partial2_invert_crc_cnt_reg0_rx_mac_partial2_invert_crc_cnt {
      type oc-yang:counter64;
      description
        "Counts the number of received packets with partial CRC type 2.";
    }
    leaf counter_pie_mac_pool81_rx_mac_partial2_invert_crc_cnt_reg1_rx_mac_partial2_invert_crc_cnt {
      type oc-yang:counter64;
      description
        "Counts the number of received packets with partial CRC type 2.";
    }
    leaf counter_pie_mac_pool81_rx_mac_partial2_invert_crc_cnt_reg2_rx_mac_partial2_invert_crc_cnt {
      type oc-yang:counter64;
      description
        "Counts the number of received packets with partial CRC type 2.";
    }
    leaf counter_pie_mac_pool81_rx_mac_partial2_invert_crc_cnt_reg3_rx_mac_partial2_invert_crc_cnt {
      type oc-yang:counter64;
      description
        "Counts the number of received packets with partial CRC type 2.";
    }
    leaf counter_pie_mac_pool81_rx_mac_partial2_invert_crc_cnt_reg4_rx_mac_partial2_invert_crc_cnt {
      type oc-yang:counter64;
      description
        "Counts the number of received packets with partial CRC type 2.";
    }
    leaf counter_pie_mac_pool81_rx_mac_partial2_invert_crc_cnt_reg5_rx_mac_partial2_invert_crc_cnt {
      type oc-yang:counter64;
      description
        "Counts the number of received packets with partial CRC type 2.";
    }
    leaf counter_pie_mac_pool81_rx_mac_partial2_invert_crc_cnt_reg6_rx_mac_partial2_invert_crc_cnt {
      type oc-yang:counter64;
      description
        "Counts the number of received packets with partial CRC type 2.";
    }
    leaf counter_pie_mac_pool81_rx_mac_partial2_invert_crc_cnt_reg7_rx_mac_partial2_invert_crc_cnt {
      type oc-yang:counter64;
      description
        "Counts the number of received packets with partial CRC type 2.";
    }
    leaf counter_pie_mac_pool80_rx_oob_mac_type_err_cnt_reg0_rx_oob_mac_type_err_cnt {
      type oc-yang:counter64;
      description
        "Counts in interleaving mode OOB packets that are received with none OOB packet type. Those are dropped when RxOobIntrlvTypeFiltEn is set.";
    }
    leaf counter_pie_mac_pool80_rx_oob_mac_type_err_cnt_reg1_rx_oob_mac_type_err_cnt {
      type oc-yang:counter64;
      description
        "Counts in interleaving mode OOB packets that are received with none OOB packet type. Those are dropped when RxOobIntrlvTypeFiltEn is set.";
    }
    leaf counter_pie_mac_pool80_rx_oob_mac_type_err_cnt_reg2_rx_oob_mac_type_err_cnt {
      type oc-yang:counter64;
      description
        "Counts in interleaving mode OOB packets that are received with none OOB packet type. Those are dropped when RxOobIntrlvTypeFiltEn is set.";
    }
    leaf counter_pie_mac_pool80_rx_oob_mac_type_err_cnt_reg3_rx_oob_mac_type_err_cnt {
      type oc-yang:counter64;
      description
        "Counts in interleaving mode OOB packets that are received with none OOB packet type. Those are dropped when RxOobIntrlvTypeFiltEn is set.";
    }
    leaf counter_pie_mac_pool81_rx_oob_mac_type_err_cnt_reg0_rx_oob_mac_type_err_cnt {
      type oc-yang:counter64;
      description
        "Counts in interleaving mode OOB packets that are received with none OOB packet type. Those are dropped when RxOobIntrlvTypeFiltEn is set.";
    }
    leaf counter_pie_mac_pool81_rx_oob_mac_type_err_cnt_reg1_rx_oob_mac_type_err_cnt {
      type oc-yang:counter64;
      description
        "Counts in interleaving mode OOB packets that are received with none OOB packet type. Those are dropped when RxOobIntrlvTypeFiltEn is set.";
    }
    leaf counter_pie_mac_pool81_rx_oob_mac_type_err_cnt_reg2_rx_oob_mac_type_err_cnt {
      type oc-yang:counter64;
      description
        "Counts in interleaving mode OOB packets that are received with none OOB packet type. Those are dropped when RxOobIntrlvTypeFiltEn is set.";
    }
    leaf counter_pie_mac_pool81_rx_oob_mac_type_err_cnt_reg3_rx_oob_mac_type_err_cnt {
      type oc-yang:counter64;
      description
        "Counts in interleaving mode OOB packets that are received with none OOB packet type. Those are dropped when RxOobIntrlvTypeFiltEn is set.";
    }
    leaf counter_pie_mac_pool80_tx_drained_pkt_cnt_reg0_tx_drained_pkt_cnt {
      type oc-yang:counter64;
      description
        "Count number of packets that are transmitted by mac and dropped by the RS layer because the link is in fault state.";
    }
    leaf counter_pie_mac_pool80_tx_drained_pkt_cnt_reg1_tx_drained_pkt_cnt {
      type oc-yang:counter64;
      description
        "Count number of packets that are transmitted by mac and dropped by the RS layer because the link is in fault state.";
    }
    leaf counter_pie_mac_pool80_tx_drained_pkt_cnt_reg2_tx_drained_pkt_cnt {
      type oc-yang:counter64;
      description
        "Count number of packets that are transmitted by mac and dropped by the RS layer because the link is in fault state.";
    }
    leaf counter_pie_mac_pool80_tx_drained_pkt_cnt_reg3_tx_drained_pkt_cnt {
      type oc-yang:counter64;
      description
        "Count number of packets that are transmitted by mac and dropped by the RS layer because the link is in fault state.";
    }
    leaf counter_pie_mac_pool80_tx_drained_pkt_cnt_reg4_tx_drained_pkt_cnt {
      type oc-yang:counter64;
      description
        "Count number of packets that are transmitted by mac and dropped by the RS layer because the link is in fault state.";
    }
    leaf counter_pie_mac_pool80_tx_drained_pkt_cnt_reg5_tx_drained_pkt_cnt {
      type oc-yang:counter64;
      description
        "Count number of packets that are transmitted by mac and dropped by the RS layer because the link is in fault state.";
    }
    leaf counter_pie_mac_pool80_tx_drained_pkt_cnt_reg6_tx_drained_pkt_cnt {
      type oc-yang:counter64;
      description
        "Count number of packets that are transmitted by mac and dropped by the RS layer because the link is in fault state.";
    }
    leaf counter_pie_mac_pool80_tx_drained_pkt_cnt_reg7_tx_drained_pkt_cnt {
      type oc-yang:counter64;
      description
        "Count number of packets that are transmitted by mac and dropped by the RS layer because the link is in fault state.";
    }
    leaf counter_pie_mac_pool81_tx_drained_pkt_cnt_reg0_tx_drained_pkt_cnt {
      type oc-yang:counter64;
      description
        "Count number of packets that are transmitted by mac and dropped by the RS layer because the link is in fault state.";
    }
    leaf counter_pie_mac_pool81_tx_drained_pkt_cnt_reg1_tx_drained_pkt_cnt {
      type oc-yang:counter64;
      description
        "Count number of packets that are transmitted by mac and dropped by the RS layer because the link is in fault state.";
    }
    leaf counter_pie_mac_pool81_tx_drained_pkt_cnt_reg2_tx_drained_pkt_cnt {
      type oc-yang:counter64;
      description
        "Count number of packets that are transmitted by mac and dropped by the RS layer because the link is in fault state.";
    }
    leaf counter_pie_mac_pool81_tx_drained_pkt_cnt_reg3_tx_drained_pkt_cnt {
      type oc-yang:counter64;
      description
        "Count number of packets that are transmitted by mac and dropped by the RS layer because the link is in fault state.";
    }
    leaf counter_pie_mac_pool81_tx_drained_pkt_cnt_reg4_tx_drained_pkt_cnt {
      type oc-yang:counter64;
      description
        "Count number of packets that are transmitted by mac and dropped by the RS layer because the link is in fault state.";
    }
    leaf counter_pie_mac_pool81_tx_drained_pkt_cnt_reg5_tx_drained_pkt_cnt {
      type oc-yang:counter64;
      description
        "Count number of packets that are transmitted by mac and dropped by the RS layer because the link is in fault state.";
    }
    leaf counter_pie_mac_pool81_tx_drained_pkt_cnt_reg6_tx_drained_pkt_cnt {
      type oc-yang:counter64;
      description
        "Count number of packets that are transmitted by mac and dropped by the RS layer because the link is in fault state.";
    }
    leaf counter_pie_mac_pool81_tx_drained_pkt_cnt_reg7_tx_drained_pkt_cnt {
      type oc-yang:counter64;
      description
        "Count number of packets that are transmitted by mac and dropped by the RS layer because the link is in fault state.";
    }
    leaf counter_pie_mac_pool80_tx_mac_partial1_invert_crc_cnt_reg0_tx_mac_partial1_invert_crc_cnt {
      type oc-yang:counter64;
      description
        "Counts the number of transmitted packets with partial CRC type 1.";
    }
    leaf counter_pie_mac_pool80_tx_mac_partial1_invert_crc_cnt_reg1_tx_mac_partial1_invert_crc_cnt {
      type oc-yang:counter64;
      description
        "Counts the number of transmitted packets with partial CRC type 1.";
    }
    leaf counter_pie_mac_pool80_tx_mac_partial1_invert_crc_cnt_reg2_tx_mac_partial1_invert_crc_cnt {
      type oc-yang:counter64;
      description
        "Counts the number of transmitted packets with partial CRC type 1.";
    }
    leaf counter_pie_mac_pool80_tx_mac_partial1_invert_crc_cnt_reg3_tx_mac_partial1_invert_crc_cnt {
      type oc-yang:counter64;
      description
        "Counts the number of transmitted packets with partial CRC type 1.";
    }
    leaf counter_pie_mac_pool80_tx_mac_partial1_invert_crc_cnt_reg4_tx_mac_partial1_invert_crc_cnt {
      type oc-yang:counter64;
      description
        "Counts the number of transmitted packets with partial CRC type 1.";
    }
    leaf counter_pie_mac_pool80_tx_mac_partial1_invert_crc_cnt_reg5_tx_mac_partial1_invert_crc_cnt {
      type oc-yang:counter64;
      description
        "Counts the number of transmitted packets with partial CRC type 1.";
    }
    leaf counter_pie_mac_pool80_tx_mac_partial1_invert_crc_cnt_reg6_tx_mac_partial1_invert_crc_cnt {
      type oc-yang:counter64;
      description
        "Counts the number of transmitted packets with partial CRC type 1.";
    }
    leaf counter_pie_mac_pool80_tx_mac_partial1_invert_crc_cnt_reg7_tx_mac_partial1_invert_crc_cnt {
      type oc-yang:counter64;
      description
        "Counts the number of transmitted packets with partial CRC type 1.";
    }
    leaf counter_pie_mac_pool81_tx_mac_partial1_invert_crc_cnt_reg0_tx_mac_partial1_invert_crc_cnt {
      type oc-yang:counter64;
      description
        "Counts the number of transmitted packets with partial CRC type 1.";
    }
    leaf counter_pie_mac_pool81_tx_mac_partial1_invert_crc_cnt_reg1_tx_mac_partial1_invert_crc_cnt {
      type oc-yang:counter64;
      description
        "Counts the number of transmitted packets with partial CRC type 1.";
    }
    leaf counter_pie_mac_pool81_tx_mac_partial1_invert_crc_cnt_reg2_tx_mac_partial1_invert_crc_cnt {
      type oc-yang:counter64;
      description
        "Counts the number of transmitted packets with partial CRC type 1.";
    }
    leaf counter_pie_mac_pool81_tx_mac_partial1_invert_crc_cnt_reg3_tx_mac_partial1_invert_crc_cnt {
      type oc-yang:counter64;
      description
        "Counts the number of transmitted packets with partial CRC type 1.";
    }
    leaf counter_pie_mac_pool81_tx_mac_partial1_invert_crc_cnt_reg4_tx_mac_partial1_invert_crc_cnt {
      type oc-yang:counter64;
      description
        "Counts the number of transmitted packets with partial CRC type 1.";
    }
    leaf counter_pie_mac_pool81_tx_mac_partial1_invert_crc_cnt_reg5_tx_mac_partial1_invert_crc_cnt {
      type oc-yang:counter64;
      description
        "Counts the number of transmitted packets with partial CRC type 1.";
    }
    leaf counter_pie_mac_pool81_tx_mac_partial1_invert_crc_cnt_reg6_tx_mac_partial1_invert_crc_cnt {
      type oc-yang:counter64;
      description
        "Counts the number of transmitted packets with partial CRC type 1.";
    }
    leaf counter_pie_mac_pool81_tx_mac_partial1_invert_crc_cnt_reg7_tx_mac_partial1_invert_crc_cnt {
      type oc-yang:counter64;
      description
        "Counts the number of transmitted packets with partial CRC type 1.";
    }
    leaf counter_pie_mac_pool80_tx_mac_partial2_invert_crc_cnt_reg0_tx_mac_partial2_invert_crc_cnt {
      type oc-yang:counter64;
      description
        "Counts the number of transmitted packets with partial CRC type 2.";
    }
    leaf counter_pie_mac_pool80_tx_mac_partial2_invert_crc_cnt_reg1_tx_mac_partial2_invert_crc_cnt {
      type oc-yang:counter64;
      description
        "Counts the number of transmitted packets with partial CRC type 2.";
    }
    leaf counter_pie_mac_pool80_tx_mac_partial2_invert_crc_cnt_reg2_tx_mac_partial2_invert_crc_cnt {
      type oc-yang:counter64;
      description
        "Counts the number of transmitted packets with partial CRC type 2.";
    }
    leaf counter_pie_mac_pool80_tx_mac_partial2_invert_crc_cnt_reg3_tx_mac_partial2_invert_crc_cnt {
      type oc-yang:counter64;
      description
        "Counts the number of transmitted packets with partial CRC type 2.";
    }
    leaf counter_pie_mac_pool80_tx_mac_partial2_invert_crc_cnt_reg4_tx_mac_partial2_invert_crc_cnt {
      type oc-yang:counter64;
      description
        "Counts the number of transmitted packets with partial CRC type 2.";
    }
    leaf counter_pie_mac_pool80_tx_mac_partial2_invert_crc_cnt_reg5_tx_mac_partial2_invert_crc_cnt {
      type oc-yang:counter64;
      description
        "Counts the number of transmitted packets with partial CRC type 2.";
    }
    leaf counter_pie_mac_pool80_tx_mac_partial2_invert_crc_cnt_reg6_tx_mac_partial2_invert_crc_cnt {
      type oc-yang:counter64;
      description
        "Counts the number of transmitted packets with partial CRC type 2.";
    }
    leaf counter_pie_mac_pool80_tx_mac_partial2_invert_crc_cnt_reg7_tx_mac_partial2_invert_crc_cnt {
      type oc-yang:counter64;
      description
        "Counts the number of transmitted packets with partial CRC type 2.";
    }
    leaf counter_pie_mac_pool81_tx_mac_partial2_invert_crc_cnt_reg0_tx_mac_partial2_invert_crc_cnt {
      type oc-yang:counter64;
      description
        "Counts the number of transmitted packets with partial CRC type 2.";
    }
    leaf counter_pie_mac_pool81_tx_mac_partial2_invert_crc_cnt_reg1_tx_mac_partial2_invert_crc_cnt {
      type oc-yang:counter64;
      description
        "Counts the number of transmitted packets with partial CRC type 2.";
    }
    leaf counter_pie_mac_pool81_tx_mac_partial2_invert_crc_cnt_reg2_tx_mac_partial2_invert_crc_cnt {
      type oc-yang:counter64;
      description
        "Counts the number of transmitted packets with partial CRC type 2.";
    }
    leaf counter_pie_mac_pool81_tx_mac_partial2_invert_crc_cnt_reg3_tx_mac_partial2_invert_crc_cnt {
      type oc-yang:counter64;
      description
        "Counts the number of transmitted packets with partial CRC type 2.";
    }
    leaf counter_pie_mac_pool81_tx_mac_partial2_invert_crc_cnt_reg4_tx_mac_partial2_invert_crc_cnt {
      type oc-yang:counter64;
      description
        "Counts the number of transmitted packets with partial CRC type 2.";
    }
    leaf counter_pie_mac_pool81_tx_mac_partial2_invert_crc_cnt_reg5_tx_mac_partial2_invert_crc_cnt {
      type oc-yang:counter64;
      description
        "Counts the number of transmitted packets with partial CRC type 2.";
    }
    leaf counter_pie_mac_pool81_tx_mac_partial2_invert_crc_cnt_reg6_tx_mac_partial2_invert_crc_cnt {
      type oc-yang:counter64;
      description
        "Counts the number of transmitted packets with partial CRC type 2.";
    }
    leaf counter_pie_mac_pool81_tx_mac_partial2_invert_crc_cnt_reg7_tx_mac_partial2_invert_crc_cnt {
      type oc-yang:counter64;
      description
        "Counts the number of transmitted packets with partial CRC type 2.";
    }
    leaf counter_pie_mac_pool80_tx_oobi_pkt_drop_counter0_tx_oobi_pkt_drop {
      type oc-yang:counter64;
      description
        "counter for OOBI okt drops";
    }
    leaf counter_pie_mac_pool80_tx_oobi_pkt_drop_counter1_tx_oobi_pkt_drop {
      type oc-yang:counter64;
      description
        "counter for OOBI okt drops";
    }
    leaf counter_pie_mac_pool80_tx_oobi_pkt_drop_counter2_tx_oobi_pkt_drop {
      type oc-yang:counter64;
      description
        "counter for OOBI okt drops";
    }
    leaf counter_pie_mac_pool80_tx_oobi_pkt_drop_counter3_tx_oobi_pkt_drop {
      type oc-yang:counter64;
      description
        "counter for OOBI okt drops";
    }
    leaf counter_pie_mac_pool80_tx_oobi_pkt_drop_counter4_tx_oobi_pkt_drop {
      type oc-yang:counter64;
      description
        "counter for OOBI okt drops";
    }
    leaf counter_pie_mac_pool80_tx_oobi_pkt_drop_counter5_tx_oobi_pkt_drop {
      type oc-yang:counter64;
      description
        "counter for OOBI okt drops";
    }
    leaf counter_pie_mac_pool80_tx_oobi_pkt_drop_counter6_tx_oobi_pkt_drop {
      type oc-yang:counter64;
      description
        "counter for OOBI okt drops";
    }
    leaf counter_pie_mac_pool80_tx_oobi_pkt_drop_counter7_tx_oobi_pkt_drop {
      type oc-yang:counter64;
      description
        "counter for OOBI okt drops";
    }
    leaf counter_pie_mac_pool81_tx_oobi_pkt_drop_counter0_tx_oobi_pkt_drop {
      type oc-yang:counter64;
      description
        "counter for OOBI okt drops";
    }
    leaf counter_pie_mac_pool81_tx_oobi_pkt_drop_counter1_tx_oobi_pkt_drop {
      type oc-yang:counter64;
      description
        "counter for OOBI okt drops";
    }
    leaf counter_pie_mac_pool81_tx_oobi_pkt_drop_counter2_tx_oobi_pkt_drop {
      type oc-yang:counter64;
      description
        "counter for OOBI okt drops";
    }
    leaf counter_pie_mac_pool81_tx_oobi_pkt_drop_counter3_tx_oobi_pkt_drop {
      type oc-yang:counter64;
      description
        "counter for OOBI okt drops";
    }
    leaf counter_pie_mac_pool81_tx_oobi_pkt_drop_counter4_tx_oobi_pkt_drop {
      type oc-yang:counter64;
      description
        "counter for OOBI okt drops";
    }
    leaf counter_pie_mac_pool81_tx_oobi_pkt_drop_counter5_tx_oobi_pkt_drop {
      type oc-yang:counter64;
      description
        "counter for OOBI okt drops";
    }
    leaf counter_pie_mac_pool81_tx_oobi_pkt_drop_counter6_tx_oobi_pkt_drop {
      type oc-yang:counter64;
      description
        "counter for OOBI okt drops";
    }
    leaf counter_pie_mac_pool81_tx_oobi_pkt_drop_counter7_tx_oobi_pkt_drop {
      type oc-yang:counter64;
      description
        "counter for OOBI okt drops";
    }
    leaf counter_sbif_ext_dma_drop_cnt_reg0_ext_dma_drop_cnt {
      type oc-yang:counter64;
      description
        "nan";
    }
    leaf counter_sbif_ext_dma_drop_cnt_reg1_ext_dma_drop_cnt {
      type oc-yang:counter64;
      description
        "nan";
    }
    leaf counter_sbif_ext_dma_drop_cnt_reg2_ext_dma_drop_cnt {
      type oc-yang:counter64;
      description
        "nan";
    }
    leaf counter_sbif_ext_dma_drop_cnt_reg3_ext_dma_drop_cnt {
      type oc-yang:counter64;
      description
        "nan";
    }
    leaf counter_sbif_ext_dma_drop_cnt_reg4_ext_dma_drop_cnt {
      type oc-yang:counter64;
      description
        "nan";
    }
    leaf counter_sbif_ext_dma_drop_cnt_reg5_ext_dma_drop_cnt {
      type oc-yang:counter64;
      description
        "nan";
    }
    leaf counter_sbif_ext_dma_drop_cnt_reg6_ext_dma_drop_cnt {
      type oc-yang:counter64;
      description
        "nan";
    }
    leaf counter_sbif_ext_dma_drop_cnt_reg7_ext_dma_drop_cnt {
      type oc-yang:counter64;
      description
        "nan";
    }
    leaf counter_sbif_ext_dma_drop_cnt_reg8_ext_dma_drop_cnt {
      type oc-yang:counter64;
      description
        "nan";
    }
    leaf counter_sbif_ext_dma_drop_cnt_reg9_ext_dma_drop_cnt {
      type oc-yang:counter64;
      description
        "nan";
    }
    leaf counter_sbif_ext_dma_drop_cnt_reg10_ext_dma_drop_cnt {
      type oc-yang:counter64;
      description
        "nan";
    }
    leaf counter_sbif_ext_dma_drop_cnt_reg11_ext_dma_drop_cnt {
      type oc-yang:counter64;
      description
        "nan";
    }
    leaf counter_sbif_ext_dma_drop_cnt_reg12_ext_dma_drop_cnt {
      type oc-yang:counter64;
      description
        "nan";
    }
    leaf counter_sbif_ext_dma_drop_cnt_reg13_ext_dma_drop_cnt {
      type oc-yang:counter64;
      description
        "nan";
    }
    leaf counter_sbif_ext_dma_drop_cnt_reg14_ext_dma_drop_cnt {
      type oc-yang:counter64;
      description
        "nan";
    }
    leaf counter_sbif_ext_dma_drop_cnt_reg15_ext_dma_drop_cnt {
      type oc-yang:counter64;
      description
        "nan";
    }
    leaf counter_sbif_ext_dma_drop_cnt_reg16_ext_dma_drop_cnt {
      type oc-yang:counter64;
      description
        "nan";
    }
    leaf counter_sbif_ext_dma_drop_cnt_reg17_ext_dma_drop_cnt {
      type oc-yang:counter64;
      description
        "nan";
    }
    leaf counter_sbif_ext_dma_drop_cnt_reg18_ext_dma_drop_cnt {
      type oc-yang:counter64;
      description
        "nan";
    }
    leaf counter_sbif_ext_dma_drop_cnt_reg19_ext_dma_drop_cnt {
      type oc-yang:counter64;
      description
        "nan";
    }
    leaf counter_sbif_ext_dma_drop_cnt_reg20_ext_dma_drop_cnt {
      type oc-yang:counter64;
      description
        "nan";
    }
    leaf counter_sbif_ext_dma_drop_cnt_reg21_ext_dma_drop_cnt {
      type oc-yang:counter64;
      description
        "nan";
    }
    leaf counter_sbif_ext_dma_drop_cnt_reg22_ext_dma_drop_cnt {
      type oc-yang:counter64;
      description
        "nan";
    }
    leaf counter_sbif_ext_dma_drop_cnt_reg23_ext_dma_drop_cnt {
      type oc-yang:counter64;
      description
        "nan";
    }
    leaf counter_sbif_ext_dma_drop_cnt_reg24_ext_dma_drop_cnt {
      type oc-yang:counter64;
      description
        "nan";
    }
    leaf counter_sbif_ext_dma_drop_cnt_reg25_ext_dma_drop_cnt {
      type oc-yang:counter64;
      description
        "nan";
    }
    leaf counter_sbif_ext_dma_drop_cnt_reg26_ext_dma_drop_cnt {
      type oc-yang:counter64;
      description
        "nan";
    }
    leaf counter_sbif_ext_dma_drop_cnt_reg27_ext_dma_drop_cnt {
      type oc-yang:counter64;
      description
        "nan";
    }
    leaf counter_sbif_ext_dma_drop_cnt_reg28_ext_dma_drop_cnt {
      type oc-yang:counter64;
      description
        "nan";
    }
    leaf counter_sbif_ext_dma_drop_cnt_reg29_ext_dma_drop_cnt {
      type oc-yang:counter64;
      description
        "nan";
    }
    leaf counter_sbif_ext_dma_drop_cnt_reg30_ext_dma_drop_cnt {
      type oc-yang:counter64;
      description
        "nan";
    }
    leaf counter_sbif_ext_dma_drop_cnt_reg31_ext_dma_drop_cnt {
      type oc-yang:counter64;
      description
        "nan";
    }
    leaf counter_sbif_ext_dma_drop_cnt_reg32_ext_dma_drop_cnt {
      type oc-yang:counter64;
      description
        "nan";
    }
    leaf counter_sbif_ext_dma_drop_cnt_reg33_ext_dma_drop_cnt {
      type oc-yang:counter64;
      description
        "nan";
    }
    leaf counter_sbif_ext_dma_drop_cnt_reg34_ext_dma_drop_cnt {
      type oc-yang:counter64;
      description
        "nan";
    }
    leaf counter_sbif_ext_dma_drop_cnt_reg35_ext_dma_drop_cnt {
      type oc-yang:counter64;
      description
        "nan";
    }
    leaf counter_sbif_ext_dma_drop_cnt_reg36_ext_dma_drop_cnt {
      type oc-yang:counter64;
      description
        "nan";
    }
    leaf counter_sbif_ext_dma_drop_cnt_reg37_ext_dma_drop_cnt {
      type oc-yang:counter64;
      description
        "nan";
    }
    leaf counter_sbif_ext_dma_drop_cnt_reg38_ext_dma_drop_cnt {
      type oc-yang:counter64;
      description
        "nan";
    }
    leaf counter_sbif_ext_dma_drop_cnt_reg39_ext_dma_drop_cnt {
      type oc-yang:counter64;
      description
        "nan";
    }
    leaf counter_sbif_ext_dma_drop_cnt_reg40_ext_dma_drop_cnt {
      type oc-yang:counter64;
      description
        "nan";
    }
    leaf counter_sbif_ext_dma_drop_cnt_reg41_ext_dma_drop_cnt {
      type oc-yang:counter64;
      description
        "nan";
    }
    leaf counter_sbif_ext_dma_drop_cnt_reg42_ext_dma_drop_cnt {
      type oc-yang:counter64;
      description
        "nan";
    }
    leaf counter_sbif_ext_dma_drop_cnt_reg43_ext_dma_drop_cnt {
      type oc-yang:counter64;
      description
        "nan";
    }
    leaf counter_sbif_ext_dma_drop_cnt_reg44_ext_dma_drop_cnt {
      type oc-yang:counter64;
      description
        "nan";
    }
    leaf counter_sbif_ext_dma_drop_cnt_reg45_ext_dma_drop_cnt {
      type oc-yang:counter64;
      description
        "nan";
    }
    leaf counter_sbif_ext_dma_drop_cnt_reg46_ext_dma_drop_cnt {
      type oc-yang:counter64;
      description
        "nan";
    }
    leaf counter_sbif_ext_dma_drop_cnt_reg47_ext_dma_drop_cnt {
      type oc-yang:counter64;
      description
        "nan";
    }
    leaf counter_sbif_ext_dma_drop_cnt_reg48_ext_dma_drop_cnt {
      type oc-yang:counter64;
      description
        "nan";
    }
    leaf counter_sbif_ext_dma_drop_cnt_reg49_ext_dma_drop_cnt {
      type oc-yang:counter64;
      description
        "nan";
    }
    leaf counter_sbif_ext_dma_drop_cnt_reg50_ext_dma_drop_cnt {
      type oc-yang:counter64;
      description
        "nan";
    }
    leaf counter_sbif_ext_dma_drop_cnt_reg51_ext_dma_drop_cnt {
      type oc-yang:counter64;
      description
        "nan";
    }
    leaf counter_sbif_ext_dma_drop_cnt_reg52_ext_dma_drop_cnt {
      type oc-yang:counter64;
      description
        "nan";
    }
    leaf counter_sbif_ext_dma_drop_cnt_reg53_ext_dma_drop_cnt {
      type oc-yang:counter64;
      description
        "nan";
    }
    leaf counter_sbif_ext_dma_drop_cnt_reg54_ext_dma_drop_cnt {
      type oc-yang:counter64;
      description
        "nan";
    }
    leaf counter_sbif_ext_dma_drop_cnt_reg55_ext_dma_drop_cnt {
      type oc-yang:counter64;
      description
        "nan";
    }
    leaf counter_sbif_ext_dma_drop_cnt_reg56_ext_dma_drop_cnt {
      type oc-yang:counter64;
      description
        "nan";
    }
    leaf counter_sbif_ext_dma_drop_cnt_reg57_ext_dma_drop_cnt {
      type oc-yang:counter64;
      description
        "nan";
    }
    leaf counter_sbif_ext_dma_drop_cnt_reg58_ext_dma_drop_cnt {
      type oc-yang:counter64;
      description
        "nan";
    }
    leaf counter_sbif_ext_dma_drop_cnt_reg59_ext_dma_drop_cnt {
      type oc-yang:counter64;
      description
        "nan";
    }
    leaf counter_sbif_ext_dma_drop_cnt_reg60_ext_dma_drop_cnt {
      type oc-yang:counter64;
      description
        "nan";
    }
    leaf counter_sbif_ext_dma_drop_cnt_reg61_ext_dma_drop_cnt {
      type oc-yang:counter64;
      description
        "nan";
    }
    leaf counter_sbif_ext_dma_drop_cnt_reg62_ext_dma_drop_cnt {
      type oc-yang:counter64;
      description
        "nan";
    }
    leaf counter_sbif_ext_dma_drop_cnt_reg63_ext_dma_drop_cnt {
      type oc-yang:counter64;
      description
        "nan";
    }
  }

  grouping cisco-p200-congestion-drop-counters {
    description
      "Congestion Drop leafs grouping for the p200 asic";
    leaf exact_meter_packet_got_dropped_due_to_exact_meter {
      type oc-yang:counter64;
      description
        " Packet got dropped due to exact meter";
    }
    leaf statistical_meter_packet_got_dropped_due_to_statistical_meter {
      type oc-yang:counter64;
      description
        "Packet got dropped due to statistical metering";
    }
    leaf counter_slice0_filb_dbg_pd_drop_cnt_pd_drop_cnt {
      type oc-yang:counter64;
      description
        "Number of dropped PDs due to FILB no eligible link selected";
    }
    leaf counter_slice1_filb_dbg_pd_drop_cnt_pd_drop_cnt {
      type oc-yang:counter64;
      description
        "Number of dropped PDs due to FILB no eligible link selected";
    }
    leaf counter_slice2_filb_dbg_pd_drop_cnt_pd_drop_cnt {
      type oc-yang:counter64;
      description
        "Number of dropped PDs due to FILB no eligible link selected";
    }
    leaf counter_slice3_filb_dbg_pd_drop_cnt_pd_drop_cnt {
      type oc-yang:counter64;
      description
        "Number of dropped PDs due to FILB no eligible link selected";
    }
    leaf counter_slice4_filb_dbg_pd_drop_cnt_pd_drop_cnt {
      type oc-yang:counter64;
      description
        "Number of dropped PDs due to FILB no eligible link selected";
    }
    leaf counter_slice5_filb_dbg_pd_drop_cnt_pd_drop_cnt {
      type oc-yang:counter64;
      description
        "Number of dropped PDs due to FILB no eligible link selected";
    }
    leaf counter_slice6_filb_dbg_pd_drop_cnt_pd_drop_cnt {
      type oc-yang:counter64;
      description
        "Number of dropped PDs due to FILB no eligible link selected";
    }
    leaf counter_slice7_filb_dbg_pd_drop_cnt_pd_drop_cnt {
      type oc-yang:counter64;
      description
        "Number of dropped PDs due to FILB no eligible link selected";
    }
    leaf counter_slice8_filb_dbg_pd_drop_cnt_pd_drop_cnt {
      type oc-yang:counter64;
      description
        "Number of dropped PDs due to FILB no eligible link selected";
    }
    leaf counter_slice9_filb_dbg_pd_drop_cnt_pd_drop_cnt {
      type oc-yang:counter64;
      description
        "Number of dropped PDs due to FILB no eligible link selected";
    }
    leaf counter_slice10_filb_dbg_pd_drop_cnt_pd_drop_cnt {
      type oc-yang:counter64;
      description
        "Number of dropped PDs due to FILB no eligible link selected";
    }
    leaf counter_slice11_filb_dbg_pd_drop_cnt_pd_drop_cnt {
      type oc-yang:counter64;
      description
        "Number of dropped PDs due to FILB no eligible link selected";
    }
    leaf counter_slice12_filb_dbg_pd_drop_cnt_pd_drop_cnt {
      type oc-yang:counter64;
      description
        "Number of dropped PDs due to FILB no eligible link selected";
    }
    leaf counter_slice13_filb_dbg_pd_drop_cnt_pd_drop_cnt {
      type oc-yang:counter64;
      description
        "Number of dropped PDs due to FILB no eligible link selected";
    }
    leaf counter_slice14_filb_dbg_pd_drop_cnt_pd_drop_cnt {
      type oc-yang:counter64;
      description
        "Number of dropped PDs due to FILB no eligible link selected";
    }
    leaf counter_slice15_filb_dbg_pd_drop_cnt_pd_drop_cnt {
      type oc-yang:counter64;
      description
        "Number of dropped PDs due to FILB no eligible link selected";
    }
    leaf counter_slice0_filb_dbg_ts_invalid_pd_drop_cnt_ts_invalid_pd_drop_cnt {
      type oc-yang:counter64;
      description
        "Number of dropped PDs due to fabric time not valid in FILB";
    }
    leaf counter_slice1_filb_dbg_ts_invalid_pd_drop_cnt_ts_invalid_pd_drop_cnt {
      type oc-yang:counter64;
      description
        "Number of dropped PDs due to fabric time not valid in FILB";
    }
    leaf counter_slice2_filb_dbg_ts_invalid_pd_drop_cnt_ts_invalid_pd_drop_cnt {
      type oc-yang:counter64;
      description
        "Number of dropped PDs due to fabric time not valid in FILB";
    }
    leaf counter_slice3_filb_dbg_ts_invalid_pd_drop_cnt_ts_invalid_pd_drop_cnt {
      type oc-yang:counter64;
      description
        "Number of dropped PDs due to fabric time not valid in FILB";
    }
    leaf counter_slice4_filb_dbg_ts_invalid_pd_drop_cnt_ts_invalid_pd_drop_cnt {
      type oc-yang:counter64;
      description
        "Number of dropped PDs due to fabric time not valid in FILB";
    }
    leaf counter_slice5_filb_dbg_ts_invalid_pd_drop_cnt_ts_invalid_pd_drop_cnt {
      type oc-yang:counter64;
      description
        "Number of dropped PDs due to fabric time not valid in FILB";
    }
    leaf counter_slice6_filb_dbg_ts_invalid_pd_drop_cnt_ts_invalid_pd_drop_cnt {
      type oc-yang:counter64;
      description
        "Number of dropped PDs due to fabric time not valid in FILB";
    }
    leaf counter_slice7_filb_dbg_ts_invalid_pd_drop_cnt_ts_invalid_pd_drop_cnt {
      type oc-yang:counter64;
      description
        "Number of dropped PDs due to fabric time not valid in FILB";
    }
    leaf counter_slice8_filb_dbg_ts_invalid_pd_drop_cnt_ts_invalid_pd_drop_cnt {
      type oc-yang:counter64;
      description
        "Number of dropped PDs due to fabric time not valid in FILB";
    }
    leaf counter_slice9_filb_dbg_ts_invalid_pd_drop_cnt_ts_invalid_pd_drop_cnt {
      type oc-yang:counter64;
      description
        "Number of dropped PDs due to fabric time not valid in FILB";
    }
    leaf counter_slice10_filb_dbg_ts_invalid_pd_drop_cnt_ts_invalid_pd_drop_cnt {
      type oc-yang:counter64;
      description
        "Number of dropped PDs due to fabric time not valid in FILB";
    }
    leaf counter_slice11_filb_dbg_ts_invalid_pd_drop_cnt_ts_invalid_pd_drop_cnt {
      type oc-yang:counter64;
      description
        "Number of dropped PDs due to fabric time not valid in FILB";
    }
    leaf counter_slice12_filb_dbg_ts_invalid_pd_drop_cnt_ts_invalid_pd_drop_cnt {
      type oc-yang:counter64;
      description
        "Number of dropped PDs due to fabric time not valid in FILB";
    }
    leaf counter_slice13_filb_dbg_ts_invalid_pd_drop_cnt_ts_invalid_pd_drop_cnt {
      type oc-yang:counter64;
      description
        "Number of dropped PDs due to fabric time not valid in FILB";
    }
    leaf counter_slice14_filb_dbg_ts_invalid_pd_drop_cnt_ts_invalid_pd_drop_cnt {
      type oc-yang:counter64;
      description
        "Number of dropped PDs due to fabric time not valid in FILB";
    }
    leaf counter_slice15_filb_dbg_ts_invalid_pd_drop_cnt_ts_invalid_pd_drop_cnt {
      type oc-yang:counter64;
      description
        "Number of dropped PDs due to fabric time not valid in FILB";
    }
    leaf counter_slice0_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice0_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice1_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice2_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice3_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice4_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice5_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice6_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice7_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice8_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice9_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice10_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice11_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice12_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice13_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice14_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter0_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter1_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter2_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter3_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter4_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter5_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter6_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter7_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter8_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter9_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter10_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter11_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter12_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter13_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter14_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter15_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter16_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter17_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter18_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter19_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter20_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter21_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter22_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter23_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter24_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter25_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter26_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter27_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter28_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter29_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter30_rx_port_cgm_tc0_drop_cnt {
      type oc-yang:counter64;
      description
        "RX port cgm ostc0 drops counter. Counts packets that were totally dropped and will not be seen on RX side.";
    }
    leaf counter_slice15_ifg_ifgbe_ra_rx_port_cgm_tc0_drop_counter31_rx_port_cgm_tc0_drop_cnt {
      type oc-yang:counter64;
      description
        "RX port cgm ostc0 drops counter. Counts packets that were totally dropped and will not be seen on RX side.";
    }
    leaf counter_slice0_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice0_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice1_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice2_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice3_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice4_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice5_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice6_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice7_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice8_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice9_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice10_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice11_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice12_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice13_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice14_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter0_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter1_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter2_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter3_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter4_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter5_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter6_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter7_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter8_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter9_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter10_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter11_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter12_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter13_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter14_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter15_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter16_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter17_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter18_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter19_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter20_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter21_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter22_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter23_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter24_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter25_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter26_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter27_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter28_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter29_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter30_rx_port_cgm_tc0_partial_drop_cnt {
      type oc-yang:counter64;
      description
        "RX port cgm ostc0 partial drops counter. Counts packets that were partially dropped and will be seen on RX side.";
    }
    leaf counter_slice15_ifg_ifgbe_ra_rx_port_cgm_tc0_partial_drop_counter31_rx_port_cgm_tc0_partial_drop_cnt {
      type oc-yang:counter64;
      description
        "RX port cgm ostc0 partial drops counter. Counts packets that were partially dropped and will be seen on RX side.";
    }
    leaf counter_slice0_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice0_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice1_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice2_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice3_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice4_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice5_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice6_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice7_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice8_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice9_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice10_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice11_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice12_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice13_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice14_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter0_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter1_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter2_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter3_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter4_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter5_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter6_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter7_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter8_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter9_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter10_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter11_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter12_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter13_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter14_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter15_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter16_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter17_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter18_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter19_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter20_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter21_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter22_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter23_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter24_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter25_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter26_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter27_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter28_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter29_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter30_rx_port_cgm_tc1_drop_cnt {
      type oc-yang:counter64;
      description
        "RX port cgm ostc1 drops counter. Counts packets that were totally dropped and will not be seen on RX side.";
    }
    leaf counter_slice15_ifg_ifgbe_ra_rx_port_cgm_tc1_drop_counter31_rx_port_cgm_tc1_drop_cnt {
      type oc-yang:counter64;
      description
        "RX port cgm ostc1 drops counter. Counts packets that were totally dropped and will not be seen on RX side.";
    }
    leaf counter_slice0_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice0_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice1_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice2_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice3_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice4_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice5_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice6_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice7_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice8_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice9_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice10_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice11_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice12_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice13_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice14_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter0_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter1_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter2_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter3_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter4_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter5_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter6_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter7_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter8_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter9_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter10_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter11_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter12_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter13_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter14_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter15_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter16_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter17_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter18_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter19_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter20_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter21_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter22_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter23_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter24_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter25_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter26_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter27_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter28_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter29_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter30_rx_port_cgm_tc1_partial_drop_cnt {
      type oc-yang:counter64;
      description
        "RX port cgm ostc1 partial drops counter. Counts packets that were partially dropped and will be seen on RX side.";
    }
    leaf counter_slice15_ifg_ifgbe_ra_rx_port_cgm_tc1_partial_drop_counter31_rx_port_cgm_tc1_partial_drop_cnt {
      type oc-yang:counter64;
      description
        "RX port cgm ostc1 partial drops counter. Counts packets that were partially dropped and will be seen on RX side.";
    }
    leaf counter_slice0_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice0_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice1_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice2_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice3_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice4_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice5_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice6_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice7_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice8_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice9_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice10_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice11_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice12_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice13_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice14_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter0_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter1_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter2_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter3_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter4_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter5_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter6_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter7_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter8_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter9_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter10_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter11_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter12_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter13_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter14_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter15_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter16_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter17_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter18_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter19_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter20_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter21_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter22_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter23_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter24_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter25_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter26_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter27_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter28_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter29_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter30_rx_port_cgm_tc2_drop_cnt {
      type oc-yang:counter64;
      description
        "RX port cgm ostc2 drops counter. Counts packets that were totally dropped and will not be seen on RX side.";
    }
    leaf counter_slice15_ifg_ifgbe_ra_rx_port_cgm_tc2_drop_counter31_rx_port_cgm_tc2_drop_cnt {
      type oc-yang:counter64;
      description
        "RX port cgm ostc2 drops counter. Counts packets that were totally dropped and will not be seen on RX side.";
    }
    leaf counter_slice0_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice0_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice1_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice2_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice3_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice4_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice5_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice6_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice7_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice8_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice9_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice10_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice11_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice12_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice13_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice14_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter0_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter1_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter2_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter3_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter4_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter5_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter6_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter7_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter8_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter9_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter10_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter11_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter12_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter13_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter14_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter15_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter16_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter17_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter18_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter19_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter20_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter21_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter22_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter23_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter24_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter25_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter26_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter27_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter28_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter29_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter30_rx_port_cgm_tc2_partial_drop_cnt {
      type oc-yang:counter64;
      description
        "RX port cgm ostc2 partial drops counter. Counts packets that were partially dropped and will be seen on RX side.";
    }
    leaf counter_slice15_ifg_ifgbe_ra_rx_port_cgm_tc2_partial_drop_counter31_rx_port_cgm_tc2_partial_drop_cnt {
      type oc-yang:counter64;
      description
        "RX port cgm ostc2 partial drops counter. Counts packets that were partially dropped and will be seen on RX side.";
    }
    leaf counter_slice0_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice0_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice1_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice2_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice3_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice4_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice5_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice6_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice7_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice8_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice9_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice10_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice11_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice12_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice13_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice14_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter0_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter1_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter2_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter3_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter4_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter5_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter6_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter7_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter8_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter9_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter10_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter11_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter12_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter13_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter14_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter15_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter16_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter17_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter18_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter19_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter20_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter21_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter22_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter23_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter24_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter25_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter26_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter27_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter28_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter29_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter30_rx_port_cgm_tc3_drop_cnt {
      type oc-yang:counter64;
      description
        "RX port cgm ostc3 drops counter. Counts packets that were totally dropped and will not be seen on RX side.";
    }
    leaf counter_slice15_ifg_ifgbe_ra_rx_port_cgm_tc3_drop_counter31_rx_port_cgm_tc3_drop_cnt {
      type oc-yang:counter64;
      description
        "RX port cgm ostc3 drops counter. Counts packets that were totally dropped and will not be seen on RX side.";
    }
    leaf counter_slice0_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice0_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice1_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice2_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice3_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice4_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice5_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice6_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice7_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice8_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice9_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice10_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice11_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice12_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice13_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice14_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter0_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter1_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter2_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter3_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter4_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter5_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter6_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter7_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter8_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter9_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter10_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter11_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter12_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter13_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter14_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter15_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter16_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter17_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter18_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter19_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter20_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter21_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter22_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter23_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter24_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter25_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter26_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter27_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter28_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter29_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter30_rx_port_cgm_tc3_partial_drop_cnt {
      type oc-yang:counter64;
      description
        "RX port cgm ostc3 partial drops counter. Counts packets that were partially dropped and will be seen on RX side.";
    }
    leaf counter_slice15_ifg_ifgbe_ra_rx_port_cgm_tc3_partial_drop_counter31_rx_port_cgm_tc3_partial_drop_cnt {
      type oc-yang:counter64;
      description
        "RX port cgm ostc3 partial drops counter. Counts packets that were partially dropped and will be seen on RX side.";
    }
    leaf counter_pdvoq_shared_mem0_voq_counters0_dropped_bytes {
      type oc-yang:counter64;
      description
        "nan";
    }
    leaf counter_pdvoq_shared_mem0_voq_counters1_dropped_bytes {
      type oc-yang:counter64;
      description
        "nan";
    }
    leaf counter_pdvoq_shared_mem0_voq_counters2_dropped_bytes {
      type oc-yang:counter64;
      description
        "nan";
    }
    leaf counter_pdvoq_shared_mem0_voq_counters3_dropped_bytes {
      type oc-yang:counter64;
      description
        "nan";
    }
    leaf counter_pdvoq_shared_mem0_voq_counters4_dropped_bytes {
      type oc-yang:counter64;
      description
        "nan";
    }
    leaf counter_pdvoq_shared_mem0_voq_counters5_dropped_bytes {
      type oc-yang:counter64;
      description
        "nan";
    }
    leaf counter_pdvoq_shared_mem0_voq_counters6_dropped_bytes {
      type oc-yang:counter64;
      description
        "nan";
    }
    leaf counter_pdvoq_shared_mem0_voq_counters7_dropped_bytes {
      type oc-yang:counter64;
      description
        "nan";
    }
    leaf counter_pdvoq_shared_mem0_voq_counters8_dropped_bytes {
      type oc-yang:counter64;
      description
        "nan";
    }
    leaf counter_pdvoq_shared_mem0_voq_counters9_dropped_bytes {
      type oc-yang:counter64;
      description
        "nan";
    }
    leaf counter_pdvoq_shared_mem0_voq_counters10_dropped_bytes {
      type oc-yang:counter64;
      description
        "nan";
    }
    leaf counter_pdvoq_shared_mem0_voq_counters11_dropped_bytes {
      type oc-yang:counter64;
      description
        "nan";
    }
    leaf counter_pdvoq_shared_mem0_voq_counters12_dropped_bytes {
      type oc-yang:counter64;
      description
        "nan";
    }
    leaf counter_pdvoq_shared_mem0_voq_counters13_dropped_bytes {
      type oc-yang:counter64;
      description
        "nan";
    }
    leaf counter_pdvoq_shared_mem0_voq_counters14_dropped_bytes {
      type oc-yang:counter64;
      description
        "nan";
    }
    leaf counter_pdvoq_shared_mem0_voq_counters15_dropped_bytes {
      type oc-yang:counter64;
      description
        "nan";
    }
    leaf counter_pdvoq_shared_mem0_voq_counters16_dropped_bytes {
      type oc-yang:counter64;
      description
        "nan";
    }
    leaf counter_pdvoq_shared_mem0_voq_counters17_dropped_bytes {
      type oc-yang:counter64;
      description
        "nan";
    }
    leaf counter_pdvoq_shared_mem0_voq_counters18_dropped_bytes {
      type oc-yang:counter64;
      description
        "nan";
    }
    leaf counter_pdvoq_shared_mem0_voq_counters19_dropped_bytes {
      type oc-yang:counter64;
      description
        "nan";
    }
    leaf counter_pdvoq_shared_mem0_voq_counters20_dropped_bytes {
      type oc-yang:counter64;
      description
        "nan";
    }
    leaf counter_pdvoq_shared_mem0_voq_counters21_dropped_bytes {
      type oc-yang:counter64;
      description
        "nan";
    }
    leaf counter_pdvoq_shared_mem0_voq_counters22_dropped_bytes {
      type oc-yang:counter64;
      description
        "nan";
    }
    leaf counter_pdvoq_shared_mem0_voq_counters23_dropped_bytes {
      type oc-yang:counter64;
      description
        "nan";
    }
    leaf counter_pdvoq_shared_mem0_voq_counters24_dropped_bytes {
      type oc-yang:counter64;
      description
        "nan";
    }
    leaf counter_pdvoq_shared_mem0_voq_counters25_dropped_bytes {
      type oc-yang:counter64;
      description
        "nan";
    }
    leaf counter_pdvoq_shared_mem0_voq_counters26_dropped_bytes {
      type oc-yang:counter64;
      description
        "nan";
    }
    leaf counter_pdvoq_shared_mem0_voq_counters27_dropped_bytes {
      type oc-yang:counter64;
      description
        "nan";
    }
    leaf counter_pdvoq_shared_mem0_voq_counters28_dropped_bytes {
      type oc-yang:counter64;
      description
        "nan";
    }
    leaf counter_pdvoq_shared_mem0_voq_counters29_dropped_bytes {
      type oc-yang:counter64;
      description
        "nan";
    }
    leaf counter_pdvoq_shared_mem0_voq_counters30_dropped_bytes {
      type oc-yang:counter64;
      description
        "nan";
    }
    leaf counter_pdvoq_shared_mem0_voq_counters31_dropped_bytes {
      type oc-yang:counter64;
      description
        "nan";
    }
    leaf counter_pdvoq_shared_mem1_voq_counters0_dropped_bytes {
      type oc-yang:counter64;
      description
        "nan";
    }
    leaf counter_pdvoq_shared_mem1_voq_counters1_dropped_bytes {
      type oc-yang:counter64;
      description
        "nan";
    }
    leaf counter_pdvoq_shared_mem1_voq_counters2_dropped_bytes {
      type oc-yang:counter64;
      description
        "nan";
    }
    leaf counter_pdvoq_shared_mem1_voq_counters3_dropped_bytes {
      type oc-yang:counter64;
      description
        "nan";
    }
    leaf counter_pdvoq_shared_mem1_voq_counters4_dropped_bytes {
      type oc-yang:counter64;
      description
        "nan";
    }
    leaf counter_pdvoq_shared_mem1_voq_counters5_dropped_bytes {
      type oc-yang:counter64;
      description
        "nan";
    }
    leaf counter_pdvoq_shared_mem1_voq_counters6_dropped_bytes {
      type oc-yang:counter64;
      description
        "nan";
    }
    leaf counter_pdvoq_shared_mem1_voq_counters7_dropped_bytes {
      type oc-yang:counter64;
      description
        "nan";
    }
    leaf counter_pdvoq_shared_mem1_voq_counters8_dropped_bytes {
      type oc-yang:counter64;
      description
        "nan";
    }
    leaf counter_pdvoq_shared_mem1_voq_counters9_dropped_bytes {
      type oc-yang:counter64;
      description
        "nan";
    }
    leaf counter_pdvoq_shared_mem1_voq_counters10_dropped_bytes {
      type oc-yang:counter64;
      description
        "nan";
    }
    leaf counter_pdvoq_shared_mem1_voq_counters11_dropped_bytes {
      type oc-yang:counter64;
      description
        "nan";
    }
    leaf counter_pdvoq_shared_mem1_voq_counters12_dropped_bytes {
      type oc-yang:counter64;
      description
        "nan";
    }
    leaf counter_pdvoq_shared_mem1_voq_counters13_dropped_bytes {
      type oc-yang:counter64;
      description
        "nan";
    }
    leaf counter_pdvoq_shared_mem1_voq_counters14_dropped_bytes {
      type oc-yang:counter64;
      description
        "nan";
    }
    leaf counter_pdvoq_shared_mem1_voq_counters15_dropped_bytes {
      type oc-yang:counter64;
      description
        "nan";
    }
    leaf counter_pdvoq_shared_mem1_voq_counters16_dropped_bytes {
      type oc-yang:counter64;
      description
        "nan";
    }
    leaf counter_pdvoq_shared_mem1_voq_counters17_dropped_bytes {
      type oc-yang:counter64;
      description
        "nan";
    }
    leaf counter_pdvoq_shared_mem1_voq_counters18_dropped_bytes {
      type oc-yang:counter64;
      description
        "nan";
    }
    leaf counter_pdvoq_shared_mem1_voq_counters19_dropped_bytes {
      type oc-yang:counter64;
      description
        "nan";
    }
    leaf counter_pdvoq_shared_mem1_voq_counters20_dropped_bytes {
      type oc-yang:counter64;
      description
        "nan";
    }
    leaf counter_pdvoq_shared_mem1_voq_counters21_dropped_bytes {
      type oc-yang:counter64;
      description
        "nan";
    }
    leaf counter_pdvoq_shared_mem1_voq_counters22_dropped_bytes {
      type oc-yang:counter64;
      description
        "nan";
    }
    leaf counter_pdvoq_shared_mem1_voq_counters23_dropped_bytes {
      type oc-yang:counter64;
      description
        "nan";
    }
    leaf counter_pdvoq_shared_mem1_voq_counters24_dropped_bytes {
      type oc-yang:counter64;
      description
        "nan";
    }
    leaf counter_pdvoq_shared_mem1_voq_counters25_dropped_bytes {
      type oc-yang:counter64;
      description
        "nan";
    }
    leaf counter_pdvoq_shared_mem1_voq_counters26_dropped_bytes {
      type oc-yang:counter64;
      description
        "nan";
    }
    leaf counter_pdvoq_shared_mem1_voq_counters27_dropped_bytes {
      type oc-yang:counter64;
      description
        "nan";
    }
    leaf counter_pdvoq_shared_mem1_voq_counters28_dropped_bytes {
      type oc-yang:counter64;
      description
        "nan";
    }
    leaf counter_pdvoq_shared_mem1_voq_counters29_dropped_bytes {
      type oc-yang:counter64;
      description
        "nan";
    }
    leaf counter_pdvoq_shared_mem1_voq_counters30_dropped_bytes {
      type oc-yang:counter64;
      description
        "nan";
    }
    leaf counter_pdvoq_shared_mem1_voq_counters31_dropped_bytes {
      type oc-yang:counter64;
      description
        "nan";
    }
    leaf counter_pdvoq_shared_mem0_voq_counters0_dropped_packets {
      type oc-yang:counter64;
      description
        "nan";
    }
    leaf counter_pdvoq_shared_mem0_voq_counters1_dropped_packets {
      type oc-yang:counter64;
      description
        "nan";
    }
    leaf counter_pdvoq_shared_mem0_voq_counters2_dropped_packets {
      type oc-yang:counter64;
      description
        "nan";
    }
    leaf counter_pdvoq_shared_mem0_voq_counters3_dropped_packets {
      type oc-yang:counter64;
      description
        "nan";
    }
    leaf counter_pdvoq_shared_mem0_voq_counters4_dropped_packets {
      type oc-yang:counter64;
      description
        "nan";
    }
    leaf counter_pdvoq_shared_mem0_voq_counters5_dropped_packets {
      type oc-yang:counter64;
      description
        "nan";
    }
    leaf counter_pdvoq_shared_mem0_voq_counters6_dropped_packets {
      type oc-yang:counter64;
      description
        "nan";
    }
    leaf counter_pdvoq_shared_mem0_voq_counters7_dropped_packets {
      type oc-yang:counter64;
      description
        "nan";
    }
    leaf counter_pdvoq_shared_mem0_voq_counters8_dropped_packets {
      type oc-yang:counter64;
      description
        "nan";
    }
    leaf counter_pdvoq_shared_mem0_voq_counters9_dropped_packets {
      type oc-yang:counter64;
      description
        "nan";
    }
    leaf counter_pdvoq_shared_mem0_voq_counters10_dropped_packets {
      type oc-yang:counter64;
      description
        "nan";
    }
    leaf counter_pdvoq_shared_mem0_voq_counters11_dropped_packets {
      type oc-yang:counter64;
      description
        "nan";
    }
    leaf counter_pdvoq_shared_mem0_voq_counters12_dropped_packets {
      type oc-yang:counter64;
      description
        "nan";
    }
    leaf counter_pdvoq_shared_mem0_voq_counters13_dropped_packets {
      type oc-yang:counter64;
      description
        "nan";
    }
    leaf counter_pdvoq_shared_mem0_voq_counters14_dropped_packets {
      type oc-yang:counter64;
      description
        "nan";
    }
    leaf counter_pdvoq_shared_mem0_voq_counters15_dropped_packets {
      type oc-yang:counter64;
      description
        "nan";
    }
    leaf counter_pdvoq_shared_mem0_voq_counters16_dropped_packets {
      type oc-yang:counter64;
      description
        "nan";
    }
    leaf counter_pdvoq_shared_mem0_voq_counters17_dropped_packets {
      type oc-yang:counter64;
      description
        "nan";
    }
    leaf counter_pdvoq_shared_mem0_voq_counters18_dropped_packets {
      type oc-yang:counter64;
      description
        "nan";
    }
    leaf counter_pdvoq_shared_mem0_voq_counters19_dropped_packets {
      type oc-yang:counter64;
      description
        "nan";
    }
    leaf counter_pdvoq_shared_mem0_voq_counters20_dropped_packets {
      type oc-yang:counter64;
      description
        "nan";
    }
    leaf counter_pdvoq_shared_mem0_voq_counters21_dropped_packets {
      type oc-yang:counter64;
      description
        "nan";
    }
    leaf counter_pdvoq_shared_mem0_voq_counters22_dropped_packets {
      type oc-yang:counter64;
      description
        "nan";
    }
    leaf counter_pdvoq_shared_mem0_voq_counters23_dropped_packets {
      type oc-yang:counter64;
      description
        "nan";
    }
    leaf counter_pdvoq_shared_mem0_voq_counters24_dropped_packets {
      type oc-yang:counter64;
      description
        "nan";
    }
    leaf counter_pdvoq_shared_mem0_voq_counters25_dropped_packets {
      type oc-yang:counter64;
      description
        "nan";
    }
    leaf counter_pdvoq_shared_mem0_voq_counters26_dropped_packets {
      type oc-yang:counter64;
      description
        "nan";
    }
    leaf counter_pdvoq_shared_mem0_voq_counters27_dropped_packets {
      type oc-yang:counter64;
      description
        "nan";
    }
    leaf counter_pdvoq_shared_mem0_voq_counters28_dropped_packets {
      type oc-yang:counter64;
      description
        "nan";
    }
    leaf counter_pdvoq_shared_mem0_voq_counters29_dropped_packets {
      type oc-yang:counter64;
      description
        "nan";
    }
    leaf counter_pdvoq_shared_mem0_voq_counters30_dropped_packets {
      type oc-yang:counter64;
      description
        "nan";
    }
    leaf counter_pdvoq_shared_mem0_voq_counters31_dropped_packets {
      type oc-yang:counter64;
      description
        "nan";
    }
    leaf counter_pdvoq_shared_mem1_voq_counters0_dropped_packets {
      type oc-yang:counter64;
      description
        "nan";
    }
    leaf counter_pdvoq_shared_mem1_voq_counters1_dropped_packets {
      type oc-yang:counter64;
      description
        "nan";
    }
    leaf counter_pdvoq_shared_mem1_voq_counters2_dropped_packets {
      type oc-yang:counter64;
      description
        "nan";
    }
    leaf counter_pdvoq_shared_mem1_voq_counters3_dropped_packets {
      type oc-yang:counter64;
      description
        "nan";
    }
    leaf counter_pdvoq_shared_mem1_voq_counters4_dropped_packets {
      type oc-yang:counter64;
      description
        "nan";
    }
    leaf counter_pdvoq_shared_mem1_voq_counters5_dropped_packets {
      type oc-yang:counter64;
      description
        "nan";
    }
    leaf counter_pdvoq_shared_mem1_voq_counters6_dropped_packets {
      type oc-yang:counter64;
      description
        "nan";
    }
    leaf counter_pdvoq_shared_mem1_voq_counters7_dropped_packets {
      type oc-yang:counter64;
      description
        "nan";
    }
    leaf counter_pdvoq_shared_mem1_voq_counters8_dropped_packets {
      type oc-yang:counter64;
      description
        "nan";
    }
    leaf counter_pdvoq_shared_mem1_voq_counters9_dropped_packets {
      type oc-yang:counter64;
      description
        "nan";
    }
    leaf counter_pdvoq_shared_mem1_voq_counters10_dropped_packets {
      type oc-yang:counter64;
      description
        "nan";
    }
    leaf counter_pdvoq_shared_mem1_voq_counters11_dropped_packets {
      type oc-yang:counter64;
      description
        "nan";
    }
    leaf counter_pdvoq_shared_mem1_voq_counters12_dropped_packets {
      type oc-yang:counter64;
      description
        "nan";
    }
    leaf counter_pdvoq_shared_mem1_voq_counters13_dropped_packets {
      type oc-yang:counter64;
      description
        "nan";
    }
    leaf counter_pdvoq_shared_mem1_voq_counters14_dropped_packets {
      type oc-yang:counter64;
      description
        "nan";
    }
    leaf counter_pdvoq_shared_mem1_voq_counters15_dropped_packets {
      type oc-yang:counter64;
      description
        "nan";
    }
    leaf counter_pdvoq_shared_mem1_voq_counters16_dropped_packets {
      type oc-yang:counter64;
      description
        "nan";
    }
    leaf counter_pdvoq_shared_mem1_voq_counters17_dropped_packets {
      type oc-yang:counter64;
      description
        "nan";
    }
    leaf counter_pdvoq_shared_mem1_voq_counters18_dropped_packets {
      type oc-yang:counter64;
      description
        "nan";
    }
    leaf counter_pdvoq_shared_mem1_voq_counters19_dropped_packets {
      type oc-yang:counter64;
      description
        "nan";
    }
    leaf counter_pdvoq_shared_mem1_voq_counters20_dropped_packets {
      type oc-yang:counter64;
      description
        "nan";
    }
    leaf counter_pdvoq_shared_mem1_voq_counters21_dropped_packets {
      type oc-yang:counter64;
      description
        "nan";
    }
    leaf counter_pdvoq_shared_mem1_voq_counters22_dropped_packets {
      type oc-yang:counter64;
      description
        "nan";
    }
    leaf counter_pdvoq_shared_mem1_voq_counters23_dropped_packets {
      type oc-yang:counter64;
      description
        "nan";
    }
    leaf counter_pdvoq_shared_mem1_voq_counters24_dropped_packets {
      type oc-yang:counter64;
      description
        "nan";
    }
    leaf counter_pdvoq_shared_mem1_voq_counters25_dropped_packets {
      type oc-yang:counter64;
      description
        "nan";
    }
    leaf counter_pdvoq_shared_mem1_voq_counters26_dropped_packets {
      type oc-yang:counter64;
      description
        "nan";
    }
    leaf counter_pdvoq_shared_mem1_voq_counters27_dropped_packets {
      type oc-yang:counter64;
      description
        "nan";
    }
    leaf counter_pdvoq_shared_mem1_voq_counters28_dropped_packets {
      type oc-yang:counter64;
      description
        "nan";
    }
    leaf counter_pdvoq_shared_mem1_voq_counters29_dropped_packets {
      type oc-yang:counter64;
      description
        "nan";
    }
    leaf counter_pdvoq_shared_mem1_voq_counters30_dropped_packets {
      type oc-yang:counter64;
      description
        "nan";
    }
    leaf counter_pdvoq_shared_mem1_voq_counters31_dropped_packets {
      type oc-yang:counter64;
      description
        "nan";
    }
    leaf counter_pdvoq_shared_mem0_voq_drop_counters_voq_cgm_cant_evict_to_dram_drop {
      type oc-yang:counter64;
      description
        "nan";
    }
    leaf counter_pdvoq_shared_mem1_voq_drop_counters_voq_cgm_cant_evict_to_dram_drop {
      type oc-yang:counter64;
      description
        "nan";
    }
    leaf counter_pdvoq_shared_mem0_voq_drop_counters_voq_cgm_cgm_meter_drop {
      type oc-yang:counter64;
      description
        "nan";
    }
    leaf counter_pdvoq_shared_mem1_voq_drop_counters_voq_cgm_cgm_meter_drop {
      type oc-yang:counter64;
      description
        "nan";
    }
    leaf counter_pdvoq_shared_mem0_voq_drop_counters_voq_cgm_context_unavailable_drop {
      type oc-yang:counter64;
      description
        "nan";
    }
    leaf counter_pdvoq_shared_mem1_voq_drop_counters_voq_cgm_context_unavailable_drop {
      type oc-yang:counter64;
      description
        "nan";
    }
    leaf counter_pdvoq_shared_mem0_voq_drop_counters_voq_cgm_dram_buffers_ect_pkt_drop {
      type oc-yang:counter64;
      description
        "nan";
    }
    leaf counter_pdvoq_shared_mem1_voq_drop_counters_voq_cgm_dram_buffers_ect_pkt_drop {
      type oc-yang:counter64;
      description
        "nan";
    }
    leaf counter_pdvoq_shared_mem0_voq_drop_counters_voq_cgm_dram_buffers_green_drop {
      type oc-yang:counter64;
      description
        "nan";
    }
    leaf counter_pdvoq_shared_mem1_voq_drop_counters_voq_cgm_dram_buffers_green_drop {
      type oc-yang:counter64;
      description
        "nan";
    }
    leaf counter_pdvoq_shared_mem0_voq_drop_counters_voq_cgm_dram_buffers_red_drop {
      type oc-yang:counter64;
      description
        "nan";
    }
    leaf counter_pdvoq_shared_mem1_voq_drop_counters_voq_cgm_dram_buffers_red_drop {
      type oc-yang:counter64;
      description
        "nan";
    }
    leaf counter_pdvoq_shared_mem0_voq_drop_counters_voq_cgm_dram_buffers_yellow_drop {
      type oc-yang:counter64;
      description
        "nan";
    }
    leaf counter_pdvoq_shared_mem1_voq_drop_counters_voq_cgm_dram_buffers_yellow_drop {
      type oc-yang:counter64;
      description
        "nan";
    }
    leaf counter_pdvoq_shared_mem0_voq_drop_counters_voq_cgm_dram_wred_drop {
      type oc-yang:counter64;
      description
        "nan";
    }
    leaf counter_pdvoq_shared_mem1_voq_drop_counters_voq_cgm_dram_wred_drop {
      type oc-yang:counter64;
      description
        "nan";
    }
    leaf counter_pdvoq_shared_mem0_voq_drop_counters_voq_cgm_dram_wred_ect_pkt_drop {
      type oc-yang:counter64;
      description
        "nan";
    }
    leaf counter_pdvoq_shared_mem1_voq_drop_counters_voq_cgm_dram_wred_ect_pkt_drop {
      type oc-yang:counter64;
      description
        "nan";
    }
    leaf counter_pdvoq_shared_mem0_voq_drop_counters_voq_cgm_non_min_guarantee_drop {
      type oc-yang:counter64;
      description
        "nan";
    }
    leaf counter_pdvoq_shared_mem1_voq_drop_counters_voq_cgm_non_min_guarantee_drop {
      type oc-yang:counter64;
      description
        "nan";
    }
    leaf counter_pdvoq_shared_mem0_voq_drop_counters_voq_cgm_pd_counters_overflow_drop {
      type oc-yang:counter64;
      description
        "nan";
    }
    leaf counter_pdvoq_shared_mem1_voq_drop_counters_voq_cgm_pd_counters_overflow_drop {
      type oc-yang:counter64;
      description
        "nan";
    }
    leaf counter_pdvoq_shared_mem0_voq_drop_counters_voq_cgm_queue_flush_drop {
      type oc-yang:counter64;
      description
        "nan";
    }
    leaf counter_pdvoq_shared_mem1_voq_drop_counters_voq_cgm_queue_flush_drop {
      type oc-yang:counter64;
      description
        "nan";
    }
    leaf counter_pdvoq_shared_mem0_voq_drop_counters_voq_cgm_sms_buffers_ect_pkt_drop {
      type oc-yang:counter64;
      description
        "nan";
    }
    leaf counter_pdvoq_shared_mem1_voq_drop_counters_voq_cgm_sms_buffers_ect_pkt_drop {
      type oc-yang:counter64;
      description
        "nan";
    }
    leaf counter_pdvoq_shared_mem0_voq_drop_counters_voq_cgm_sms_pds_ect_pkt_drop {
      type oc-yang:counter64;
      description
        "nan";
    }
    leaf counter_pdvoq_shared_mem1_voq_drop_counters_voq_cgm_sms_pds_ect_pkt_drop {
      type oc-yang:counter64;
      description
        "nan";
    }
    leaf counter_pdvoq_shared_mem0_voq_drop_counters_voq_cgm_sms_pds_green_drop {
      type oc-yang:counter64;
      description
        "nan";
    }
    leaf counter_pdvoq_shared_mem1_voq_drop_counters_voq_cgm_sms_pds_green_drop {
      type oc-yang:counter64;
      description
        "nan";
    }
    leaf counter_pdvoq_shared_mem0_voq_drop_counters_voq_cgm_sms_pds_red_drop {
      type oc-yang:counter64;
      description
        "nan";
    }
    leaf counter_pdvoq_shared_mem1_voq_drop_counters_voq_cgm_sms_pds_red_drop {
      type oc-yang:counter64;
      description
        "nan";
    }
    leaf counter_pdvoq_shared_mem0_voq_drop_counters_voq_cgm_sms_pds_yellow_drop {
      type oc-yang:counter64;
      description
        "nan";
    }
    leaf counter_pdvoq_shared_mem1_voq_drop_counters_voq_cgm_sms_pds_yellow_drop {
      type oc-yang:counter64;
      description
        "nan";
    }
    leaf counter_pdvoq_shared_mem0_voq_drop_counters_voq_cgm_sms_wred_buffers_drop {
      type oc-yang:counter64;
      description
        "nan";
    }
    leaf counter_pdvoq_shared_mem1_voq_drop_counters_voq_cgm_sms_wred_buffers_drop {
      type oc-yang:counter64;
      description
        "nan";
    }
    leaf counter_pdvoq_shared_mem0_voq_drop_counters_voq_cgm_total_evicted_buffers_green_drop {
      type oc-yang:counter64;
      description
        "nan";
    }
    leaf counter_pdvoq_shared_mem1_voq_drop_counters_voq_cgm_total_evicted_buffers_green_drop {
      type oc-yang:counter64;
      description
        "nan";
    }
    leaf counter_pdvoq_shared_mem0_voq_drop_counters_voq_cgm_total_evicted_buffers_red_drop {
      type oc-yang:counter64;
      description
        "nan";
    }
    leaf counter_pdvoq_shared_mem1_voq_drop_counters_voq_cgm_total_evicted_buffers_red_drop {
      type oc-yang:counter64;
      description
        "nan";
    }
    leaf counter_pdvoq_shared_mem0_voq_drop_counters_voq_cgm_total_evicted_buffers_yellow_drop {
      type oc-yang:counter64;
      description
        "nan";
    }
    leaf counter_pdvoq_shared_mem1_voq_drop_counters_voq_cgm_total_evicted_buffers_yellow_drop {
      type oc-yang:counter64;
      description
        "nan";
    }
    leaf counter_slice0_pdvoq_pd_pool_drop_counters_pd_pool_mc_drop_count {
      type oc-yang:counter64;
      description
        "Counts number of packets dropped in this slice because of exceeding the global PD Pool Mc drop threshold";
    }
    leaf counter_slice1_pdvoq_pd_pool_drop_counters_pd_pool_mc_drop_count {
      type oc-yang:counter64;
      description
        "Counts number of packets dropped in this slice because of exceeding the global PD Pool Mc drop threshold";
    }
    leaf counter_slice2_pdvoq_pd_pool_drop_counters_pd_pool_mc_drop_count {
      type oc-yang:counter64;
      description
        "Counts number of packets dropped in this slice because of exceeding the global PD Pool Mc drop threshold";
    }
    leaf counter_slice3_pdvoq_pd_pool_drop_counters_pd_pool_mc_drop_count {
      type oc-yang:counter64;
      description
        "Counts number of packets dropped in this slice because of exceeding the global PD Pool Mc drop threshold";
    }
    leaf counter_slice4_pdvoq_pd_pool_drop_counters_pd_pool_mc_drop_count {
      type oc-yang:counter64;
      description
        "Counts number of packets dropped in this slice because of exceeding the global PD Pool Mc drop threshold";
    }
    leaf counter_slice5_pdvoq_pd_pool_drop_counters_pd_pool_mc_drop_count {
      type oc-yang:counter64;
      description
        "Counts number of packets dropped in this slice because of exceeding the global PD Pool Mc drop threshold";
    }
    leaf counter_slice6_pdvoq_pd_pool_drop_counters_pd_pool_mc_drop_count {
      type oc-yang:counter64;
      description
        "Counts number of packets dropped in this slice because of exceeding the global PD Pool Mc drop threshold";
    }
    leaf counter_slice7_pdvoq_pd_pool_drop_counters_pd_pool_mc_drop_count {
      type oc-yang:counter64;
      description
        "Counts number of packets dropped in this slice because of exceeding the global PD Pool Mc drop threshold";
    }
    leaf counter_slice8_pdvoq_pd_pool_drop_counters_pd_pool_mc_drop_count {
      type oc-yang:counter64;
      description
        "Counts number of packets dropped in this slice because of exceeding the global PD Pool Mc drop threshold";
    }
    leaf counter_slice9_pdvoq_pd_pool_drop_counters_pd_pool_mc_drop_count {
      type oc-yang:counter64;
      description
        "Counts number of packets dropped in this slice because of exceeding the global PD Pool Mc drop threshold";
    }
    leaf counter_slice10_pdvoq_pd_pool_drop_counters_pd_pool_mc_drop_count {
      type oc-yang:counter64;
      description
        "Counts number of packets dropped in this slice because of exceeding the global PD Pool Mc drop threshold";
    }
    leaf counter_slice11_pdvoq_pd_pool_drop_counters_pd_pool_mc_drop_count {
      type oc-yang:counter64;
      description
        "Counts number of packets dropped in this slice because of exceeding the global PD Pool Mc drop threshold";
    }
    leaf counter_slice12_pdvoq_pd_pool_drop_counters_pd_pool_mc_drop_count {
      type oc-yang:counter64;
      description
        "Counts number of packets dropped in this slice because of exceeding the global PD Pool Mc drop threshold";
    }
    leaf counter_slice13_pdvoq_pd_pool_drop_counters_pd_pool_mc_drop_count {
      type oc-yang:counter64;
      description
        "Counts number of packets dropped in this slice because of exceeding the global PD Pool Mc drop threshold";
    }
    leaf counter_slice14_pdvoq_pd_pool_drop_counters_pd_pool_mc_drop_count {
      type oc-yang:counter64;
      description
        "Counts number of packets dropped in this slice because of exceeding the global PD Pool Mc drop threshold";
    }
    leaf counter_slice15_pdvoq_pd_pool_drop_counters_pd_pool_mc_drop_count {
      type oc-yang:counter64;
      description
        "Counts number of packets dropped in this slice because of exceeding the global PD Pool Mc drop threshold";
    }
    leaf counter_slice0_pdvoq_pd_pool_drop_counters_pd_pool_ms_mc_drop_count {
      type oc-yang:counter64;
      description
        "Counts number of packets dropped in this slice because of exceeding the global PD Pool MsMc drop threshold";
    }
    leaf counter_slice1_pdvoq_pd_pool_drop_counters_pd_pool_ms_mc_drop_count {
      type oc-yang:counter64;
      description
        "Counts number of packets dropped in this slice because of exceeding the global PD Pool MsMc drop threshold";
    }
    leaf counter_slice2_pdvoq_pd_pool_drop_counters_pd_pool_ms_mc_drop_count {
      type oc-yang:counter64;
      description
        "Counts number of packets dropped in this slice because of exceeding the global PD Pool MsMc drop threshold";
    }
    leaf counter_slice3_pdvoq_pd_pool_drop_counters_pd_pool_ms_mc_drop_count {
      type oc-yang:counter64;
      description
        "Counts number of packets dropped in this slice because of exceeding the global PD Pool MsMc drop threshold";
    }
    leaf counter_slice4_pdvoq_pd_pool_drop_counters_pd_pool_ms_mc_drop_count {
      type oc-yang:counter64;
      description
        "Counts number of packets dropped in this slice because of exceeding the global PD Pool MsMc drop threshold";
    }
    leaf counter_slice5_pdvoq_pd_pool_drop_counters_pd_pool_ms_mc_drop_count {
      type oc-yang:counter64;
      description
        "Counts number of packets dropped in this slice because of exceeding the global PD Pool MsMc drop threshold";
    }
    leaf counter_slice6_pdvoq_pd_pool_drop_counters_pd_pool_ms_mc_drop_count {
      type oc-yang:counter64;
      description
        "Counts number of packets dropped in this slice because of exceeding the global PD Pool MsMc drop threshold";
    }
    leaf counter_slice7_pdvoq_pd_pool_drop_counters_pd_pool_ms_mc_drop_count {
      type oc-yang:counter64;
      description
        "Counts number of packets dropped in this slice because of exceeding the global PD Pool MsMc drop threshold";
    }
    leaf counter_slice8_pdvoq_pd_pool_drop_counters_pd_pool_ms_mc_drop_count {
      type oc-yang:counter64;
      description
        "Counts number of packets dropped in this slice because of exceeding the global PD Pool MsMc drop threshold";
    }
    leaf counter_slice9_pdvoq_pd_pool_drop_counters_pd_pool_ms_mc_drop_count {
      type oc-yang:counter64;
      description
        "Counts number of packets dropped in this slice because of exceeding the global PD Pool MsMc drop threshold";
    }
    leaf counter_slice10_pdvoq_pd_pool_drop_counters_pd_pool_ms_mc_drop_count {
      type oc-yang:counter64;
      description
        "Counts number of packets dropped in this slice because of exceeding the global PD Pool MsMc drop threshold";
    }
    leaf counter_slice11_pdvoq_pd_pool_drop_counters_pd_pool_ms_mc_drop_count {
      type oc-yang:counter64;
      description
        "Counts number of packets dropped in this slice because of exceeding the global PD Pool MsMc drop threshold";
    }
    leaf counter_slice12_pdvoq_pd_pool_drop_counters_pd_pool_ms_mc_drop_count {
      type oc-yang:counter64;
      description
        "Counts number of packets dropped in this slice because of exceeding the global PD Pool MsMc drop threshold";
    }
    leaf counter_slice13_pdvoq_pd_pool_drop_counters_pd_pool_ms_mc_drop_count {
      type oc-yang:counter64;
      description
        "Counts number of packets dropped in this slice because of exceeding the global PD Pool MsMc drop threshold";
    }
    leaf counter_slice14_pdvoq_pd_pool_drop_counters_pd_pool_ms_mc_drop_count {
      type oc-yang:counter64;
      description
        "Counts number of packets dropped in this slice because of exceeding the global PD Pool MsMc drop threshold";
    }
    leaf counter_slice15_pdvoq_pd_pool_drop_counters_pd_pool_ms_mc_drop_count {
      type oc-yang:counter64;
      description
        "Counts number of packets dropped in this slice because of exceeding the global PD Pool MsMc drop threshold";
    }
    leaf counter_slice0_pdvoq_pd_pool_drop_counters_pd_pool_ms_uc_drop_count {
      type oc-yang:counter64;
      description
        "Counts number of packets dropped in this slice because of exceeding the global PD Pool MsUc drop threshold";
    }
    leaf counter_slice1_pdvoq_pd_pool_drop_counters_pd_pool_ms_uc_drop_count {
      type oc-yang:counter64;
      description
        "Counts number of packets dropped in this slice because of exceeding the global PD Pool MsUc drop threshold";
    }
    leaf counter_slice2_pdvoq_pd_pool_drop_counters_pd_pool_ms_uc_drop_count {
      type oc-yang:counter64;
      description
        "Counts number of packets dropped in this slice because of exceeding the global PD Pool MsUc drop threshold";
    }
    leaf counter_slice3_pdvoq_pd_pool_drop_counters_pd_pool_ms_uc_drop_count {
      type oc-yang:counter64;
      description
        "Counts number of packets dropped in this slice because of exceeding the global PD Pool MsUc drop threshold";
    }
    leaf counter_slice4_pdvoq_pd_pool_drop_counters_pd_pool_ms_uc_drop_count {
      type oc-yang:counter64;
      description
        "Counts number of packets dropped in this slice because of exceeding the global PD Pool MsUc drop threshold";
    }
    leaf counter_slice5_pdvoq_pd_pool_drop_counters_pd_pool_ms_uc_drop_count {
      type oc-yang:counter64;
      description
        "Counts number of packets dropped in this slice because of exceeding the global PD Pool MsUc drop threshold";
    }
    leaf counter_slice6_pdvoq_pd_pool_drop_counters_pd_pool_ms_uc_drop_count {
      type oc-yang:counter64;
      description
        "Counts number of packets dropped in this slice because of exceeding the global PD Pool MsUc drop threshold";
    }
    leaf counter_slice7_pdvoq_pd_pool_drop_counters_pd_pool_ms_uc_drop_count {
      type oc-yang:counter64;
      description
        "Counts number of packets dropped in this slice because of exceeding the global PD Pool MsUc drop threshold";
    }
    leaf counter_slice8_pdvoq_pd_pool_drop_counters_pd_pool_ms_uc_drop_count {
      type oc-yang:counter64;
      description
        "Counts number of packets dropped in this slice because of exceeding the global PD Pool MsUc drop threshold";
    }
    leaf counter_slice9_pdvoq_pd_pool_drop_counters_pd_pool_ms_uc_drop_count {
      type oc-yang:counter64;
      description
        "Counts number of packets dropped in this slice because of exceeding the global PD Pool MsUc drop threshold";
    }
    leaf counter_slice10_pdvoq_pd_pool_drop_counters_pd_pool_ms_uc_drop_count {
      type oc-yang:counter64;
      description
        "Counts number of packets dropped in this slice because of exceeding the global PD Pool MsUc drop threshold";
    }
    leaf counter_slice11_pdvoq_pd_pool_drop_counters_pd_pool_ms_uc_drop_count {
      type oc-yang:counter64;
      description
        "Counts number of packets dropped in this slice because of exceeding the global PD Pool MsUc drop threshold";
    }
    leaf counter_slice12_pdvoq_pd_pool_drop_counters_pd_pool_ms_uc_drop_count {
      type oc-yang:counter64;
      description
        "Counts number of packets dropped in this slice because of exceeding the global PD Pool MsUc drop threshold";
    }
    leaf counter_slice13_pdvoq_pd_pool_drop_counters_pd_pool_ms_uc_drop_count {
      type oc-yang:counter64;
      description
        "Counts number of packets dropped in this slice because of exceeding the global PD Pool MsUc drop threshold";
    }
    leaf counter_slice14_pdvoq_pd_pool_drop_counters_pd_pool_ms_uc_drop_count {
      type oc-yang:counter64;
      description
        "Counts number of packets dropped in this slice because of exceeding the global PD Pool MsUc drop threshold";
    }
    leaf counter_slice15_pdvoq_pd_pool_drop_counters_pd_pool_ms_uc_drop_count {
      type oc-yang:counter64;
      description
        "Counts number of packets dropped in this slice because of exceeding the global PD Pool MsUc drop threshold";
    }
    leaf counter_slice0_pdvoq_pd_pool_drop_counters_pd_pool_uc_drop_count {
      type oc-yang:counter64;
      description
        "Counts number of packets dropped in this slice because of exceeding the global PD Pool Uc drop threshold";
    }
    leaf counter_slice1_pdvoq_pd_pool_drop_counters_pd_pool_uc_drop_count {
      type oc-yang:counter64;
      description
        "Counts number of packets dropped in this slice because of exceeding the global PD Pool Uc drop threshold";
    }
    leaf counter_slice2_pdvoq_pd_pool_drop_counters_pd_pool_uc_drop_count {
      type oc-yang:counter64;
      description
        "Counts number of packets dropped in this slice because of exceeding the global PD Pool Uc drop threshold";
    }
    leaf counter_slice3_pdvoq_pd_pool_drop_counters_pd_pool_uc_drop_count {
      type oc-yang:counter64;
      description
        "Counts number of packets dropped in this slice because of exceeding the global PD Pool Uc drop threshold";
    }
    leaf counter_slice4_pdvoq_pd_pool_drop_counters_pd_pool_uc_drop_count {
      type oc-yang:counter64;
      description
        "Counts number of packets dropped in this slice because of exceeding the global PD Pool Uc drop threshold";
    }
    leaf counter_slice5_pdvoq_pd_pool_drop_counters_pd_pool_uc_drop_count {
      type oc-yang:counter64;
      description
        "Counts number of packets dropped in this slice because of exceeding the global PD Pool Uc drop threshold";
    }
    leaf counter_slice6_pdvoq_pd_pool_drop_counters_pd_pool_uc_drop_count {
      type oc-yang:counter64;
      description
        "Counts number of packets dropped in this slice because of exceeding the global PD Pool Uc drop threshold";
    }
    leaf counter_slice7_pdvoq_pd_pool_drop_counters_pd_pool_uc_drop_count {
      type oc-yang:counter64;
      description
        "Counts number of packets dropped in this slice because of exceeding the global PD Pool Uc drop threshold";
    }
    leaf counter_slice8_pdvoq_pd_pool_drop_counters_pd_pool_uc_drop_count {
      type oc-yang:counter64;
      description
        "Counts number of packets dropped in this slice because of exceeding the global PD Pool Uc drop threshold";
    }
    leaf counter_slice9_pdvoq_pd_pool_drop_counters_pd_pool_uc_drop_count {
      type oc-yang:counter64;
      description
        "Counts number of packets dropped in this slice because of exceeding the global PD Pool Uc drop threshold";
    }
    leaf counter_slice10_pdvoq_pd_pool_drop_counters_pd_pool_uc_drop_count {
      type oc-yang:counter64;
      description
        "Counts number of packets dropped in this slice because of exceeding the global PD Pool Uc drop threshold";
    }
    leaf counter_slice11_pdvoq_pd_pool_drop_counters_pd_pool_uc_drop_count {
      type oc-yang:counter64;
      description
        "Counts number of packets dropped in this slice because of exceeding the global PD Pool Uc drop threshold";
    }
    leaf counter_slice12_pdvoq_pd_pool_drop_counters_pd_pool_uc_drop_count {
      type oc-yang:counter64;
      description
        "Counts number of packets dropped in this slice because of exceeding the global PD Pool Uc drop threshold";
    }
    leaf counter_slice13_pdvoq_pd_pool_drop_counters_pd_pool_uc_drop_count {
      type oc-yang:counter64;
      description
        "Counts number of packets dropped in this slice because of exceeding the global PD Pool Uc drop threshold";
    }
    leaf counter_slice14_pdvoq_pd_pool_drop_counters_pd_pool_uc_drop_count {
      type oc-yang:counter64;
      description
        "Counts number of packets dropped in this slice because of exceeding the global PD Pool Uc drop threshold";
    }
    leaf counter_slice15_pdvoq_pd_pool_drop_counters_pd_pool_uc_drop_count {
      type oc-yang:counter64;
      description
        "Counts number of packets dropped in this slice because of exceeding the global PD Pool Uc drop threshold";
    }
    leaf counter_pie_ifgb_rx_buf_ovfl_drop_byte_cnt0_ovfl_drop_byte_cnt {
      type oc-yang:counter64;
      description
        "Counts bytes dropped by PIE to avoid RX buffer overflow";
    }
    leaf counter_pie_ifgb_rx_buf_ovfl_drop_byte_cnt1_ovfl_drop_byte_cnt {
      type oc-yang:counter64;
      description
        "Counts bytes dropped by PIE to avoid RX buffer overflow";
    }
    leaf counter_pie_ifgb_rx_buf_ovfl_drop_pkt_cnt0_ovfl_drop_pkt_cnt {
      type oc-yang:counter64;
      description
        "Counts packets dropped by PIE to avoid RX buffer overflow";
    }
    leaf counter_pie_ifgb_rx_buf_ovfl_drop_pkt_cnt1_ovfl_drop_pkt_cnt {
      type oc-yang:counter64;
      description
        "Counts packets dropped by PIE to avoid RX buffer overflow";
    }
    leaf counter_rx_cgm_rx_cgm_drop_counters10_sq_drop_counter {
      type oc-yang:counter64;
      description
        "Counts the number of packets that were dropped by either SQ or SQG or HR";
    }
    leaf counter_rx_cgm_rx_cgm_drop_counters11_sq_drop_counter {
      type oc-yang:counter64;
      description
        "Counts the number of packets that were dropped by either SQ or SQG or HR";
    }
    leaf counter_rx_cgm_rx_cgm_drop_counters12_sq_drop_counter {
      type oc-yang:counter64;
      description
        "Counts the number of packets that were dropped by either SQ or SQG or HR";
    }
    leaf counter_rx_cgm_rx_cgm_drop_counters13_sq_drop_counter {
      type oc-yang:counter64;
      description
        "Counts the number of packets that were dropped by either SQ or SQG or HR";
    }
    leaf counter_rx_cgm_rx_cgm_drop_counters14_sq_drop_counter {
      type oc-yang:counter64;
      description
        "Counts the number of packets that were dropped by either SQ or SQG or HR";
    }
    leaf counter_rx_cgm_rx_cgm_drop_counters15_sq_drop_counter {
      type oc-yang:counter64;
      description
        "Counts the number of packets that were dropped by either SQ or SQG or HR";
    }
    leaf counter_rx_cgm_rx_cgm_drop_counters16_sq_drop_counter {
      type oc-yang:counter64;
      description
        "Counts the number of packets that were dropped by either SQ or SQG or HR";
    }
    leaf counter_rx_cgm_rx_cgm_drop_counters17_sq_drop_counter {
      type oc-yang:counter64;
      description
        "Counts the number of packets that were dropped by either SQ or SQG or HR";
    }
    leaf counter_rx_cgm_rx_cgm_drop_counters18_sq_drop_counter {
      type oc-yang:counter64;
      description
        "Counts the number of packets that were dropped by either SQ or SQG or HR";
    }
    leaf counter_rx_cgm_rx_cgm_drop_counters19_sq_drop_counter {
      type oc-yang:counter64;
      description
        "Counts the number of packets that were dropped by either SQ or SQG or HR";
    }
    leaf counter_rx_cgm_rx_cgm_drop_counters110_sq_drop_counter {
      type oc-yang:counter64;
      description
        "Counts the number of packets that were dropped by either SQ or SQG or HR";
    }
    leaf counter_rx_cgm_rx_cgm_drop_counters111_sq_drop_counter {
      type oc-yang:counter64;
      description
        "Counts the number of packets that were dropped by either SQ or SQG or HR";
    }
    leaf counter_rx_cgm_rx_cgm_drop_counters112_sq_drop_counter {
      type oc-yang:counter64;
      description
        "Counts the number of packets that were dropped by either SQ or SQG or HR";
    }
    leaf counter_rx_cgm_rx_cgm_drop_counters113_sq_drop_counter {
      type oc-yang:counter64;
      description
        "Counts the number of packets that were dropped by either SQ or SQG or HR";
    }
    leaf counter_rx_cgm_rx_cgm_drop_counters114_sq_drop_counter {
      type oc-yang:counter64;
      description
        "Counts the number of packets that were dropped by either SQ or SQG or HR";
    }
    leaf counter_rx_cgm_rx_cgm_drop_counters115_sq_drop_counter {
      type oc-yang:counter64;
      description
        "Counts the number of packets that were dropped by either SQ or SQG or HR";
    }
    leaf counter_slice_pair0_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair0_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair1_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair1_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair2_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair2_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair3_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair3_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair4_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair4_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair5_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair5_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair6_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair6_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair7_rx_meter_rx_meter_debug_cnt0_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair7_rx_meter_rx_meter_debug_cnt1_slice_drop_pkts_counter {
      type oc-yang:counter64;
      description
        "When bypass_meter==1, drop_pkts_counter=0. When bypass_meter==0 and meter_en==0 and non-fabric mode and ignore_npu_drop==0, drop_pkts_counter includes npu drops VN=-1. When bypass_meter==0 and meter_en==0 and non-fabric mode and ignore_npu_drop==1, drop_pkts_counter=0. When bypass_meter==0 and meter_en==1 and non-fabric mode and ignore_npu_drop==0, drop_pkts_counter includes npu drops VN=-1 and meter/rate_limiter drops. When bypass_meter==0 and meter_en==1 and non-fabric mode and ignore_npu_drop==1, drop_pkts_counter includes meter/rate_limiter drops. When bypass_meter==0 and fabric mode and ignore_npu_drop==0, drop_pkts_counter includes npu drops VN=-1 and keepalive. When bypass_meter==0 and fabric mode and ignore_npu_drop==1, drop_pkts_counter includes keepalive.";
    }
    leaf counter_slice_pair0_rx_pdr_rxpdr_cgm_drop_counter_reg0_slice_counter_a_drop_counter {
      type oc-yang:counter64;
      description
        "Number of packets dropped due to CGM counter A";
    }
    leaf counter_slice_pair0_rx_pdr_rxpdr_cgm_drop_counter_reg1_slice_counter_a_drop_counter {
      type oc-yang:counter64;
      description
        "Number of packets dropped due to CGM counter A";
    }
    leaf counter_slice_pair1_rx_pdr_rxpdr_cgm_drop_counter_reg0_slice_counter_a_drop_counter {
      type oc-yang:counter64;
      description
        "Number of packets dropped due to CGM counter A";
    }
    leaf counter_slice_pair1_rx_pdr_rxpdr_cgm_drop_counter_reg1_slice_counter_a_drop_counter {
      type oc-yang:counter64;
      description
        "Number of packets dropped due to CGM counter A";
    }
    leaf counter_slice_pair2_rx_pdr_rxpdr_cgm_drop_counter_reg0_slice_counter_a_drop_counter {
      type oc-yang:counter64;
      description
        "Number of packets dropped due to CGM counter A";
    }
    leaf counter_slice_pair2_rx_pdr_rxpdr_cgm_drop_counter_reg1_slice_counter_a_drop_counter {
      type oc-yang:counter64;
      description
        "Number of packets dropped due to CGM counter A";
    }
    leaf counter_slice_pair3_rx_pdr_rxpdr_cgm_drop_counter_reg0_slice_counter_a_drop_counter {
      type oc-yang:counter64;
      description
        "Number of packets dropped due to CGM counter A";
    }
    leaf counter_slice_pair3_rx_pdr_rxpdr_cgm_drop_counter_reg1_slice_counter_a_drop_counter {
      type oc-yang:counter64;
      description
        "Number of packets dropped due to CGM counter A";
    }
    leaf counter_slice_pair4_rx_pdr_rxpdr_cgm_drop_counter_reg0_slice_counter_a_drop_counter {
      type oc-yang:counter64;
      description
        "Number of packets dropped due to CGM counter A";
    }
    leaf counter_slice_pair4_rx_pdr_rxpdr_cgm_drop_counter_reg1_slice_counter_a_drop_counter {
      type oc-yang:counter64;
      description
        "Number of packets dropped due to CGM counter A";
    }
    leaf counter_slice_pair5_rx_pdr_rxpdr_cgm_drop_counter_reg0_slice_counter_a_drop_counter {
      type oc-yang:counter64;
      description
        "Number of packets dropped due to CGM counter A";
    }
    leaf counter_slice_pair5_rx_pdr_rxpdr_cgm_drop_counter_reg1_slice_counter_a_drop_counter {
      type oc-yang:counter64;
      description
        "Number of packets dropped due to CGM counter A";
    }
    leaf counter_slice_pair6_rx_pdr_rxpdr_cgm_drop_counter_reg0_slice_counter_a_drop_counter {
      type oc-yang:counter64;
      description
        "Number of packets dropped due to CGM counter A";
    }
    leaf counter_slice_pair6_rx_pdr_rxpdr_cgm_drop_counter_reg1_slice_counter_a_drop_counter {
      type oc-yang:counter64;
      description
        "Number of packets dropped due to CGM counter A";
    }
    leaf counter_slice_pair7_rx_pdr_rxpdr_cgm_drop_counter_reg0_slice_counter_a_drop_counter {
      type oc-yang:counter64;
      description
        "Number of packets dropped due to CGM counter A";
    }
    leaf counter_slice_pair7_rx_pdr_rxpdr_cgm_drop_counter_reg1_slice_counter_a_drop_counter {
      type oc-yang:counter64;
      description
        "Number of packets dropped due to CGM counter A";
    }
    leaf counter_slice_pair0_rx_pdr_rxpdr_cgm_drop_counter_reg0_slice_counter_b_drop_counter {
      type oc-yang:counter64;
      description
        "Number of packets dropped due to CGM counter B";
    }
    leaf counter_slice_pair0_rx_pdr_rxpdr_cgm_drop_counter_reg1_slice_counter_b_drop_counter {
      type oc-yang:counter64;
      description
        "Number of packets dropped due to CGM counter B";
    }
    leaf counter_slice_pair1_rx_pdr_rxpdr_cgm_drop_counter_reg0_slice_counter_b_drop_counter {
      type oc-yang:counter64;
      description
        "Number of packets dropped due to CGM counter B";
    }
    leaf counter_slice_pair1_rx_pdr_rxpdr_cgm_drop_counter_reg1_slice_counter_b_drop_counter {
      type oc-yang:counter64;
      description
        "Number of packets dropped due to CGM counter B";
    }
    leaf counter_slice_pair2_rx_pdr_rxpdr_cgm_drop_counter_reg0_slice_counter_b_drop_counter {
      type oc-yang:counter64;
      description
        "Number of packets dropped due to CGM counter B";
    }
    leaf counter_slice_pair2_rx_pdr_rxpdr_cgm_drop_counter_reg1_slice_counter_b_drop_counter {
      type oc-yang:counter64;
      description
        "Number of packets dropped due to CGM counter B";
    }
    leaf counter_slice_pair3_rx_pdr_rxpdr_cgm_drop_counter_reg0_slice_counter_b_drop_counter {
      type oc-yang:counter64;
      description
        "Number of packets dropped due to CGM counter B";
    }
    leaf counter_slice_pair3_rx_pdr_rxpdr_cgm_drop_counter_reg1_slice_counter_b_drop_counter {
      type oc-yang:counter64;
      description
        "Number of packets dropped due to CGM counter B";
    }
    leaf counter_slice_pair4_rx_pdr_rxpdr_cgm_drop_counter_reg0_slice_counter_b_drop_counter {
      type oc-yang:counter64;
      description
        "Number of packets dropped due to CGM counter B";
    }
    leaf counter_slice_pair4_rx_pdr_rxpdr_cgm_drop_counter_reg1_slice_counter_b_drop_counter {
      type oc-yang:counter64;
      description
        "Number of packets dropped due to CGM counter B";
    }
    leaf counter_slice_pair5_rx_pdr_rxpdr_cgm_drop_counter_reg0_slice_counter_b_drop_counter {
      type oc-yang:counter64;
      description
        "Number of packets dropped due to CGM counter B";
    }
    leaf counter_slice_pair5_rx_pdr_rxpdr_cgm_drop_counter_reg1_slice_counter_b_drop_counter {
      type oc-yang:counter64;
      description
        "Number of packets dropped due to CGM counter B";
    }
    leaf counter_slice_pair6_rx_pdr_rxpdr_cgm_drop_counter_reg0_slice_counter_b_drop_counter {
      type oc-yang:counter64;
      description
        "Number of packets dropped due to CGM counter B";
    }
    leaf counter_slice_pair6_rx_pdr_rxpdr_cgm_drop_counter_reg1_slice_counter_b_drop_counter {
      type oc-yang:counter64;
      description
        "Number of packets dropped due to CGM counter B";
    }
    leaf counter_slice_pair7_rx_pdr_rxpdr_cgm_drop_counter_reg0_slice_counter_b_drop_counter {
      type oc-yang:counter64;
      description
        "Number of packets dropped due to CGM counter B";
    }
    leaf counter_slice_pair7_rx_pdr_rxpdr_cgm_drop_counter_reg1_slice_counter_b_drop_counter {
      type oc-yang:counter64;
      description
        "Number of packets dropped due to CGM counter B";
    }
    leaf counter_slice_pair0_rx_pdr_rxpdr_cgm_drop_counter_reg0_slice_counter_e_drop_counter {
      type oc-yang:counter64;
      description
        "Number of packets dropped due to CGM counter E";
    }
    leaf counter_slice_pair0_rx_pdr_rxpdr_cgm_drop_counter_reg1_slice_counter_e_drop_counter {
      type oc-yang:counter64;
      description
        "Number of packets dropped due to CGM counter E";
    }
    leaf counter_slice_pair1_rx_pdr_rxpdr_cgm_drop_counter_reg0_slice_counter_e_drop_counter {
      type oc-yang:counter64;
      description
        "Number of packets dropped due to CGM counter E";
    }
    leaf counter_slice_pair1_rx_pdr_rxpdr_cgm_drop_counter_reg1_slice_counter_e_drop_counter {
      type oc-yang:counter64;
      description
        "Number of packets dropped due to CGM counter E";
    }
    leaf counter_slice_pair2_rx_pdr_rxpdr_cgm_drop_counter_reg0_slice_counter_e_drop_counter {
      type oc-yang:counter64;
      description
        "Number of packets dropped due to CGM counter E";
    }
    leaf counter_slice_pair2_rx_pdr_rxpdr_cgm_drop_counter_reg1_slice_counter_e_drop_counter {
      type oc-yang:counter64;
      description
        "Number of packets dropped due to CGM counter E";
    }
    leaf counter_slice_pair3_rx_pdr_rxpdr_cgm_drop_counter_reg0_slice_counter_e_drop_counter {
      type oc-yang:counter64;
      description
        "Number of packets dropped due to CGM counter E";
    }
    leaf counter_slice_pair3_rx_pdr_rxpdr_cgm_drop_counter_reg1_slice_counter_e_drop_counter {
      type oc-yang:counter64;
      description
        "Number of packets dropped due to CGM counter E";
    }
    leaf counter_slice_pair4_rx_pdr_rxpdr_cgm_drop_counter_reg0_slice_counter_e_drop_counter {
      type oc-yang:counter64;
      description
        "Number of packets dropped due to CGM counter E";
    }
    leaf counter_slice_pair4_rx_pdr_rxpdr_cgm_drop_counter_reg1_slice_counter_e_drop_counter {
      type oc-yang:counter64;
      description
        "Number of packets dropped due to CGM counter E";
    }
    leaf counter_slice_pair5_rx_pdr_rxpdr_cgm_drop_counter_reg0_slice_counter_e_drop_counter {
      type oc-yang:counter64;
      description
        "Number of packets dropped due to CGM counter E";
    }
    leaf counter_slice_pair5_rx_pdr_rxpdr_cgm_drop_counter_reg1_slice_counter_e_drop_counter {
      type oc-yang:counter64;
      description
        "Number of packets dropped due to CGM counter E";
    }
    leaf counter_slice_pair6_rx_pdr_rxpdr_cgm_drop_counter_reg0_slice_counter_e_drop_counter {
      type oc-yang:counter64;
      description
        "Number of packets dropped due to CGM counter E";
    }
    leaf counter_slice_pair6_rx_pdr_rxpdr_cgm_drop_counter_reg1_slice_counter_e_drop_counter {
      type oc-yang:counter64;
      description
        "Number of packets dropped due to CGM counter E";
    }
    leaf counter_slice_pair7_rx_pdr_rxpdr_cgm_drop_counter_reg0_slice_counter_e_drop_counter {
      type oc-yang:counter64;
      description
        "Number of packets dropped due to CGM counter E";
    }
    leaf counter_slice_pair7_rx_pdr_rxpdr_cgm_drop_counter_reg1_slice_counter_e_drop_counter {
      type oc-yang:counter64;
      description
        "Number of packets dropped due to CGM counter E";
    }
    leaf counter_slice_pair0_rx_pdr_rxpdr_cgm_drop_counter_reg0_slice_counter_j_drop_counter {
      type oc-yang:counter64;
      description
        "Number of packets whose mirror copies were dropped due to CGM counter J";
    }
    leaf counter_slice_pair0_rx_pdr_rxpdr_cgm_drop_counter_reg1_slice_counter_j_drop_counter {
      type oc-yang:counter64;
      description
        "Number of packets whose mirror copies were dropped due to CGM counter J";
    }
    leaf counter_slice_pair1_rx_pdr_rxpdr_cgm_drop_counter_reg0_slice_counter_j_drop_counter {
      type oc-yang:counter64;
      description
        "Number of packets whose mirror copies were dropped due to CGM counter J";
    }
    leaf counter_slice_pair1_rx_pdr_rxpdr_cgm_drop_counter_reg1_slice_counter_j_drop_counter {
      type oc-yang:counter64;
      description
        "Number of packets whose mirror copies were dropped due to CGM counter J";
    }
    leaf counter_slice_pair2_rx_pdr_rxpdr_cgm_drop_counter_reg0_slice_counter_j_drop_counter {
      type oc-yang:counter64;
      description
        "Number of packets whose mirror copies were dropped due to CGM counter J";
    }
    leaf counter_slice_pair2_rx_pdr_rxpdr_cgm_drop_counter_reg1_slice_counter_j_drop_counter {
      type oc-yang:counter64;
      description
        "Number of packets whose mirror copies were dropped due to CGM counter J";
    }
    leaf counter_slice_pair3_rx_pdr_rxpdr_cgm_drop_counter_reg0_slice_counter_j_drop_counter {
      type oc-yang:counter64;
      description
        "Number of packets whose mirror copies were dropped due to CGM counter J";
    }
    leaf counter_slice_pair3_rx_pdr_rxpdr_cgm_drop_counter_reg1_slice_counter_j_drop_counter {
      type oc-yang:counter64;
      description
        "Number of packets whose mirror copies were dropped due to CGM counter J";
    }
    leaf counter_slice_pair4_rx_pdr_rxpdr_cgm_drop_counter_reg0_slice_counter_j_drop_counter {
      type oc-yang:counter64;
      description
        "Number of packets whose mirror copies were dropped due to CGM counter J";
    }
    leaf counter_slice_pair4_rx_pdr_rxpdr_cgm_drop_counter_reg1_slice_counter_j_drop_counter {
      type oc-yang:counter64;
      description
        "Number of packets whose mirror copies were dropped due to CGM counter J";
    }
    leaf counter_slice_pair5_rx_pdr_rxpdr_cgm_drop_counter_reg0_slice_counter_j_drop_counter {
      type oc-yang:counter64;
      description
        "Number of packets whose mirror copies were dropped due to CGM counter J";
    }
    leaf counter_slice_pair5_rx_pdr_rxpdr_cgm_drop_counter_reg1_slice_counter_j_drop_counter {
      type oc-yang:counter64;
      description
        "Number of packets whose mirror copies were dropped due to CGM counter J";
    }
    leaf counter_slice_pair6_rx_pdr_rxpdr_cgm_drop_counter_reg0_slice_counter_j_drop_counter {
      type oc-yang:counter64;
      description
        "Number of packets whose mirror copies were dropped due to CGM counter J";
    }
    leaf counter_slice_pair6_rx_pdr_rxpdr_cgm_drop_counter_reg1_slice_counter_j_drop_counter {
      type oc-yang:counter64;
      description
        "Number of packets whose mirror copies were dropped due to CGM counter J";
    }
    leaf counter_slice_pair7_rx_pdr_rxpdr_cgm_drop_counter_reg0_slice_counter_j_drop_counter {
      type oc-yang:counter64;
      description
        "Number of packets whose mirror copies were dropped due to CGM counter J";
    }
    leaf counter_slice_pair7_rx_pdr_rxpdr_cgm_drop_counter_reg1_slice_counter_j_drop_counter {
      type oc-yang:counter64;
      description
        "Number of packets whose mirror copies were dropped due to CGM counter J";
    }
    leaf counter_slice_pair0_rx_pdr_rxpdr_cgm_drop_counter_reg0_slice_deq_cgm_ibm_counter_bg_drop_counter {
      type oc-yang:counter64;
      description
        "Number of mirror packets dropped due to CGM counter G for packets belonging to counter B.";
    }
    leaf counter_slice_pair0_rx_pdr_rxpdr_cgm_drop_counter_reg1_slice_deq_cgm_ibm_counter_bg_drop_counter {
      type oc-yang:counter64;
      description
        "Number of mirror packets dropped due to CGM counter G for packets belonging to counter B.";
    }
    leaf counter_slice_pair1_rx_pdr_rxpdr_cgm_drop_counter_reg0_slice_deq_cgm_ibm_counter_bg_drop_counter {
      type oc-yang:counter64;
      description
        "Number of mirror packets dropped due to CGM counter G for packets belonging to counter B.";
    }
    leaf counter_slice_pair1_rx_pdr_rxpdr_cgm_drop_counter_reg1_slice_deq_cgm_ibm_counter_bg_drop_counter {
      type oc-yang:counter64;
      description
        "Number of mirror packets dropped due to CGM counter G for packets belonging to counter B.";
    }
    leaf counter_slice_pair2_rx_pdr_rxpdr_cgm_drop_counter_reg0_slice_deq_cgm_ibm_counter_bg_drop_counter {
      type oc-yang:counter64;
      description
        "Number of mirror packets dropped due to CGM counter G for packets belonging to counter B.";
    }
    leaf counter_slice_pair2_rx_pdr_rxpdr_cgm_drop_counter_reg1_slice_deq_cgm_ibm_counter_bg_drop_counter {
      type oc-yang:counter64;
      description
        "Number of mirror packets dropped due to CGM counter G for packets belonging to counter B.";
    }
    leaf counter_slice_pair3_rx_pdr_rxpdr_cgm_drop_counter_reg0_slice_deq_cgm_ibm_counter_bg_drop_counter {
      type oc-yang:counter64;
      description
        "Number of mirror packets dropped due to CGM counter G for packets belonging to counter B.";
    }
    leaf counter_slice_pair3_rx_pdr_rxpdr_cgm_drop_counter_reg1_slice_deq_cgm_ibm_counter_bg_drop_counter {
      type oc-yang:counter64;
      description
        "Number of mirror packets dropped due to CGM counter G for packets belonging to counter B.";
    }
    leaf counter_slice_pair4_rx_pdr_rxpdr_cgm_drop_counter_reg0_slice_deq_cgm_ibm_counter_bg_drop_counter {
      type oc-yang:counter64;
      description
        "Number of mirror packets dropped due to CGM counter G for packets belonging to counter B.";
    }
    leaf counter_slice_pair4_rx_pdr_rxpdr_cgm_drop_counter_reg1_slice_deq_cgm_ibm_counter_bg_drop_counter {
      type oc-yang:counter64;
      description
        "Number of mirror packets dropped due to CGM counter G for packets belonging to counter B.";
    }
    leaf counter_slice_pair5_rx_pdr_rxpdr_cgm_drop_counter_reg0_slice_deq_cgm_ibm_counter_bg_drop_counter {
      type oc-yang:counter64;
      description
        "Number of mirror packets dropped due to CGM counter G for packets belonging to counter B.";
    }
    leaf counter_slice_pair5_rx_pdr_rxpdr_cgm_drop_counter_reg1_slice_deq_cgm_ibm_counter_bg_drop_counter {
      type oc-yang:counter64;
      description
        "Number of mirror packets dropped due to CGM counter G for packets belonging to counter B.";
    }
    leaf counter_slice_pair6_rx_pdr_rxpdr_cgm_drop_counter_reg0_slice_deq_cgm_ibm_counter_bg_drop_counter {
      type oc-yang:counter64;
      description
        "Number of mirror packets dropped due to CGM counter G for packets belonging to counter B.";
    }
    leaf counter_slice_pair6_rx_pdr_rxpdr_cgm_drop_counter_reg1_slice_deq_cgm_ibm_counter_bg_drop_counter {
      type oc-yang:counter64;
      description
        "Number of mirror packets dropped due to CGM counter G for packets belonging to counter B.";
    }
    leaf counter_slice_pair7_rx_pdr_rxpdr_cgm_drop_counter_reg0_slice_deq_cgm_ibm_counter_bg_drop_counter {
      type oc-yang:counter64;
      description
        "Number of mirror packets dropped due to CGM counter G for packets belonging to counter B.";
    }
    leaf counter_slice_pair7_rx_pdr_rxpdr_cgm_drop_counter_reg1_slice_deq_cgm_ibm_counter_bg_drop_counter {
      type oc-yang:counter64;
      description
        "Number of mirror packets dropped due to CGM counter G for packets belonging to counter B.";
    }
    leaf counter_slice_pair0_rx_pdr_rxpdr_cgm_drop_counter_reg0_slice_deq_cgm_ibm_counter_g_drop_counter {
      type oc-yang:counter64;
      description
        "Number of mirror packets dropped due to CGM counter G for packets belonging to counter A.";
    }
    leaf counter_slice_pair0_rx_pdr_rxpdr_cgm_drop_counter_reg1_slice_deq_cgm_ibm_counter_g_drop_counter {
      type oc-yang:counter64;
      description
        "Number of mirror packets dropped due to CGM counter G for packets belonging to counter A.";
    }
    leaf counter_slice_pair1_rx_pdr_rxpdr_cgm_drop_counter_reg0_slice_deq_cgm_ibm_counter_g_drop_counter {
      type oc-yang:counter64;
      description
        "Number of mirror packets dropped due to CGM counter G for packets belonging to counter A.";
    }
    leaf counter_slice_pair1_rx_pdr_rxpdr_cgm_drop_counter_reg1_slice_deq_cgm_ibm_counter_g_drop_counter {
      type oc-yang:counter64;
      description
        "Number of mirror packets dropped due to CGM counter G for packets belonging to counter A.";
    }
    leaf counter_slice_pair2_rx_pdr_rxpdr_cgm_drop_counter_reg0_slice_deq_cgm_ibm_counter_g_drop_counter {
      type oc-yang:counter64;
      description
        "Number of mirror packets dropped due to CGM counter G for packets belonging to counter A.";
    }
    leaf counter_slice_pair2_rx_pdr_rxpdr_cgm_drop_counter_reg1_slice_deq_cgm_ibm_counter_g_drop_counter {
      type oc-yang:counter64;
      description
        "Number of mirror packets dropped due to CGM counter G for packets belonging to counter A.";
    }
    leaf counter_slice_pair3_rx_pdr_rxpdr_cgm_drop_counter_reg0_slice_deq_cgm_ibm_counter_g_drop_counter {
      type oc-yang:counter64;
      description
        "Number of mirror packets dropped due to CGM counter G for packets belonging to counter A.";
    }
    leaf counter_slice_pair3_rx_pdr_rxpdr_cgm_drop_counter_reg1_slice_deq_cgm_ibm_counter_g_drop_counter {
      type oc-yang:counter64;
      description
        "Number of mirror packets dropped due to CGM counter G for packets belonging to counter A.";
    }
    leaf counter_slice_pair4_rx_pdr_rxpdr_cgm_drop_counter_reg0_slice_deq_cgm_ibm_counter_g_drop_counter {
      type oc-yang:counter64;
      description
        "Number of mirror packets dropped due to CGM counter G for packets belonging to counter A.";
    }
    leaf counter_slice_pair4_rx_pdr_rxpdr_cgm_drop_counter_reg1_slice_deq_cgm_ibm_counter_g_drop_counter {
      type oc-yang:counter64;
      description
        "Number of mirror packets dropped due to CGM counter G for packets belonging to counter A.";
    }
    leaf counter_slice_pair5_rx_pdr_rxpdr_cgm_drop_counter_reg0_slice_deq_cgm_ibm_counter_g_drop_counter {
      type oc-yang:counter64;
      description
        "Number of mirror packets dropped due to CGM counter G for packets belonging to counter A.";
    }
    leaf counter_slice_pair5_rx_pdr_rxpdr_cgm_drop_counter_reg1_slice_deq_cgm_ibm_counter_g_drop_counter {
      type oc-yang:counter64;
      description
        "Number of mirror packets dropped due to CGM counter G for packets belonging to counter A.";
    }
    leaf counter_slice_pair6_rx_pdr_rxpdr_cgm_drop_counter_reg0_slice_deq_cgm_ibm_counter_g_drop_counter {
      type oc-yang:counter64;
      description
        "Number of mirror packets dropped due to CGM counter G for packets belonging to counter A.";
    }
    leaf counter_slice_pair6_rx_pdr_rxpdr_cgm_drop_counter_reg1_slice_deq_cgm_ibm_counter_g_drop_counter {
      type oc-yang:counter64;
      description
        "Number of mirror packets dropped due to CGM counter G for packets belonging to counter A.";
    }
    leaf counter_slice_pair7_rx_pdr_rxpdr_cgm_drop_counter_reg0_slice_deq_cgm_ibm_counter_g_drop_counter {
      type oc-yang:counter64;
      description
        "Number of mirror packets dropped due to CGM counter G for packets belonging to counter A.";
    }
    leaf counter_slice_pair7_rx_pdr_rxpdr_cgm_drop_counter_reg1_slice_deq_cgm_ibm_counter_g_drop_counter {
      type oc-yang:counter64;
      description
        "Number of mirror packets dropped due to CGM counter G for packets belonging to counter A.";
    }
    leaf counter_slice_pair0_rx_pdr_rxpdr_cgm_drop_counter_reg0_slice_deq_cgm_ibm_drop_counter {
      type oc-yang:counter64;
      description
        "Number of mirror packets dropped due to Rxrq DEQ-CGM.";
    }
    leaf counter_slice_pair0_rx_pdr_rxpdr_cgm_drop_counter_reg1_slice_deq_cgm_ibm_drop_counter {
      type oc-yang:counter64;
      description
        "Number of mirror packets dropped due to Rxrq DEQ-CGM.";
    }
    leaf counter_slice_pair1_rx_pdr_rxpdr_cgm_drop_counter_reg0_slice_deq_cgm_ibm_drop_counter {
      type oc-yang:counter64;
      description
        "Number of mirror packets dropped due to Rxrq DEQ-CGM.";
    }
    leaf counter_slice_pair1_rx_pdr_rxpdr_cgm_drop_counter_reg1_slice_deq_cgm_ibm_drop_counter {
      type oc-yang:counter64;
      description
        "Number of mirror packets dropped due to Rxrq DEQ-CGM.";
    }
    leaf counter_slice_pair2_rx_pdr_rxpdr_cgm_drop_counter_reg0_slice_deq_cgm_ibm_drop_counter {
      type oc-yang:counter64;
      description
        "Number of mirror packets dropped due to Rxrq DEQ-CGM.";
    }
    leaf counter_slice_pair2_rx_pdr_rxpdr_cgm_drop_counter_reg1_slice_deq_cgm_ibm_drop_counter {
      type oc-yang:counter64;
      description
        "Number of mirror packets dropped due to Rxrq DEQ-CGM.";
    }
    leaf counter_slice_pair3_rx_pdr_rxpdr_cgm_drop_counter_reg0_slice_deq_cgm_ibm_drop_counter {
      type oc-yang:counter64;
      description
        "Number of mirror packets dropped due to Rxrq DEQ-CGM.";
    }
    leaf counter_slice_pair3_rx_pdr_rxpdr_cgm_drop_counter_reg1_slice_deq_cgm_ibm_drop_counter {
      type oc-yang:counter64;
      description
        "Number of mirror packets dropped due to Rxrq DEQ-CGM.";
    }
    leaf counter_slice_pair4_rx_pdr_rxpdr_cgm_drop_counter_reg0_slice_deq_cgm_ibm_drop_counter {
      type oc-yang:counter64;
      description
        "Number of mirror packets dropped due to Rxrq DEQ-CGM.";
    }
    leaf counter_slice_pair4_rx_pdr_rxpdr_cgm_drop_counter_reg1_slice_deq_cgm_ibm_drop_counter {
      type oc-yang:counter64;
      description
        "Number of mirror packets dropped due to Rxrq DEQ-CGM.";
    }
    leaf counter_slice_pair5_rx_pdr_rxpdr_cgm_drop_counter_reg0_slice_deq_cgm_ibm_drop_counter {
      type oc-yang:counter64;
      description
        "Number of mirror packets dropped due to Rxrq DEQ-CGM.";
    }
    leaf counter_slice_pair5_rx_pdr_rxpdr_cgm_drop_counter_reg1_slice_deq_cgm_ibm_drop_counter {
      type oc-yang:counter64;
      description
        "Number of mirror packets dropped due to Rxrq DEQ-CGM.";
    }
    leaf counter_slice_pair6_rx_pdr_rxpdr_cgm_drop_counter_reg0_slice_deq_cgm_ibm_drop_counter {
      type oc-yang:counter64;
      description
        "Number of mirror packets dropped due to Rxrq DEQ-CGM.";
    }
    leaf counter_slice_pair6_rx_pdr_rxpdr_cgm_drop_counter_reg1_slice_deq_cgm_ibm_drop_counter {
      type oc-yang:counter64;
      description
        "Number of mirror packets dropped due to Rxrq DEQ-CGM.";
    }
    leaf counter_slice_pair7_rx_pdr_rxpdr_cgm_drop_counter_reg0_slice_deq_cgm_ibm_drop_counter {
      type oc-yang:counter64;
      description
        "Number of mirror packets dropped due to Rxrq DEQ-CGM.";
    }
    leaf counter_slice_pair7_rx_pdr_rxpdr_cgm_drop_counter_reg1_slice_deq_cgm_ibm_drop_counter {
      type oc-yang:counter64;
      description
        "Number of mirror packets dropped due to Rxrq DEQ-CGM.";
    }
    leaf counter_slice_pair0_rx_pdr_rxpdr_cgm_drop_counter_reg0_slice_deq_cgm_mc_drop_counter {
      type oc-yang:counter64;
      description
        "Number of multicast packets dropped due to Rxrq DEQ-CGM.";
    }
    leaf counter_slice_pair0_rx_pdr_rxpdr_cgm_drop_counter_reg1_slice_deq_cgm_mc_drop_counter {
      type oc-yang:counter64;
      description
        "Number of multicast packets dropped due to Rxrq DEQ-CGM.";
    }
    leaf counter_slice_pair1_rx_pdr_rxpdr_cgm_drop_counter_reg0_slice_deq_cgm_mc_drop_counter {
      type oc-yang:counter64;
      description
        "Number of multicast packets dropped due to Rxrq DEQ-CGM.";
    }
    leaf counter_slice_pair1_rx_pdr_rxpdr_cgm_drop_counter_reg1_slice_deq_cgm_mc_drop_counter {
      type oc-yang:counter64;
      description
        "Number of multicast packets dropped due to Rxrq DEQ-CGM.";
    }
    leaf counter_slice_pair2_rx_pdr_rxpdr_cgm_drop_counter_reg0_slice_deq_cgm_mc_drop_counter {
      type oc-yang:counter64;
      description
        "Number of multicast packets dropped due to Rxrq DEQ-CGM.";
    }
    leaf counter_slice_pair2_rx_pdr_rxpdr_cgm_drop_counter_reg1_slice_deq_cgm_mc_drop_counter {
      type oc-yang:counter64;
      description
        "Number of multicast packets dropped due to Rxrq DEQ-CGM.";
    }
    leaf counter_slice_pair3_rx_pdr_rxpdr_cgm_drop_counter_reg0_slice_deq_cgm_mc_drop_counter {
      type oc-yang:counter64;
      description
        "Number of multicast packets dropped due to Rxrq DEQ-CGM.";
    }
    leaf counter_slice_pair3_rx_pdr_rxpdr_cgm_drop_counter_reg1_slice_deq_cgm_mc_drop_counter {
      type oc-yang:counter64;
      description
        "Number of multicast packets dropped due to Rxrq DEQ-CGM.";
    }
    leaf counter_slice_pair4_rx_pdr_rxpdr_cgm_drop_counter_reg0_slice_deq_cgm_mc_drop_counter {
      type oc-yang:counter64;
      description
        "Number of multicast packets dropped due to Rxrq DEQ-CGM.";
    }
    leaf counter_slice_pair4_rx_pdr_rxpdr_cgm_drop_counter_reg1_slice_deq_cgm_mc_drop_counter {
      type oc-yang:counter64;
      description
        "Number of multicast packets dropped due to Rxrq DEQ-CGM.";
    }
    leaf counter_slice_pair5_rx_pdr_rxpdr_cgm_drop_counter_reg0_slice_deq_cgm_mc_drop_counter {
      type oc-yang:counter64;
      description
        "Number of multicast packets dropped due to Rxrq DEQ-CGM.";
    }
    leaf counter_slice_pair5_rx_pdr_rxpdr_cgm_drop_counter_reg1_slice_deq_cgm_mc_drop_counter {
      type oc-yang:counter64;
      description
        "Number of multicast packets dropped due to Rxrq DEQ-CGM.";
    }
    leaf counter_slice_pair6_rx_pdr_rxpdr_cgm_drop_counter_reg0_slice_deq_cgm_mc_drop_counter {
      type oc-yang:counter64;
      description
        "Number of multicast packets dropped due to Rxrq DEQ-CGM.";
    }
    leaf counter_slice_pair6_rx_pdr_rxpdr_cgm_drop_counter_reg1_slice_deq_cgm_mc_drop_counter {
      type oc-yang:counter64;
      description
        "Number of multicast packets dropped due to Rxrq DEQ-CGM.";
    }
    leaf counter_slice_pair7_rx_pdr_rxpdr_cgm_drop_counter_reg0_slice_deq_cgm_mc_drop_counter {
      type oc-yang:counter64;
      description
        "Number of multicast packets dropped due to Rxrq DEQ-CGM.";
    }
    leaf counter_slice_pair7_rx_pdr_rxpdr_cgm_drop_counter_reg1_slice_deq_cgm_mc_drop_counter {
      type oc-yang:counter64;
      description
        "Number of multicast packets dropped due to Rxrq DEQ-CGM.";
    }
    leaf counter_slice_pair0_rx_pdr_rxpdr_cgm_drop_counter_reg0_slice_enq_cgm_drop_counter {
      type oc-yang:counter64;
      description
        "Number of multicast packets dropped due to Rxrq ENQ-CGM.";
    }
    leaf counter_slice_pair0_rx_pdr_rxpdr_cgm_drop_counter_reg1_slice_enq_cgm_drop_counter {
      type oc-yang:counter64;
      description
        "Number of multicast packets dropped due to Rxrq ENQ-CGM.";
    }
    leaf counter_slice_pair1_rx_pdr_rxpdr_cgm_drop_counter_reg0_slice_enq_cgm_drop_counter {
      type oc-yang:counter64;
      description
        "Number of multicast packets dropped due to Rxrq ENQ-CGM.";
    }
    leaf counter_slice_pair1_rx_pdr_rxpdr_cgm_drop_counter_reg1_slice_enq_cgm_drop_counter {
      type oc-yang:counter64;
      description
        "Number of multicast packets dropped due to Rxrq ENQ-CGM.";
    }
    leaf counter_slice_pair2_rx_pdr_rxpdr_cgm_drop_counter_reg0_slice_enq_cgm_drop_counter {
      type oc-yang:counter64;
      description
        "Number of multicast packets dropped due to Rxrq ENQ-CGM.";
    }
    leaf counter_slice_pair2_rx_pdr_rxpdr_cgm_drop_counter_reg1_slice_enq_cgm_drop_counter {
      type oc-yang:counter64;
      description
        "Number of multicast packets dropped due to Rxrq ENQ-CGM.";
    }
    leaf counter_slice_pair3_rx_pdr_rxpdr_cgm_drop_counter_reg0_slice_enq_cgm_drop_counter {
      type oc-yang:counter64;
      description
        "Number of multicast packets dropped due to Rxrq ENQ-CGM.";
    }
    leaf counter_slice_pair3_rx_pdr_rxpdr_cgm_drop_counter_reg1_slice_enq_cgm_drop_counter {
      type oc-yang:counter64;
      description
        "Number of multicast packets dropped due to Rxrq ENQ-CGM.";
    }
    leaf counter_slice_pair4_rx_pdr_rxpdr_cgm_drop_counter_reg0_slice_enq_cgm_drop_counter {
      type oc-yang:counter64;
      description
        "Number of multicast packets dropped due to Rxrq ENQ-CGM.";
    }
    leaf counter_slice_pair4_rx_pdr_rxpdr_cgm_drop_counter_reg1_slice_enq_cgm_drop_counter {
      type oc-yang:counter64;
      description
        "Number of multicast packets dropped due to Rxrq ENQ-CGM.";
    }
    leaf counter_slice_pair5_rx_pdr_rxpdr_cgm_drop_counter_reg0_slice_enq_cgm_drop_counter {
      type oc-yang:counter64;
      description
        "Number of multicast packets dropped due to Rxrq ENQ-CGM.";
    }
    leaf counter_slice_pair5_rx_pdr_rxpdr_cgm_drop_counter_reg1_slice_enq_cgm_drop_counter {
      type oc-yang:counter64;
      description
        "Number of multicast packets dropped due to Rxrq ENQ-CGM.";
    }
    leaf counter_slice_pair6_rx_pdr_rxpdr_cgm_drop_counter_reg0_slice_enq_cgm_drop_counter {
      type oc-yang:counter64;
      description
        "Number of multicast packets dropped due to Rxrq ENQ-CGM.";
    }
    leaf counter_slice_pair6_rx_pdr_rxpdr_cgm_drop_counter_reg1_slice_enq_cgm_drop_counter {
      type oc-yang:counter64;
      description
        "Number of multicast packets dropped due to Rxrq ENQ-CGM.";
    }
    leaf counter_slice_pair7_rx_pdr_rxpdr_cgm_drop_counter_reg0_slice_enq_cgm_drop_counter {
      type oc-yang:counter64;
      description
        "Number of multicast packets dropped due to Rxrq ENQ-CGM.";
    }
    leaf counter_slice_pair7_rx_pdr_rxpdr_cgm_drop_counter_reg1_slice_enq_cgm_drop_counter {
      type oc-yang:counter64;
      description
        "Number of multicast packets dropped due to Rxrq ENQ-CGM.";
    }
    leaf counter_slice0_tx_cgm_local_sch_uc_buffers_drop_counter_local_sch_uc_buffer_drop_cnt {
      type oc-yang:counter64;
      description
        "Counts number of dropped packets by counter C";
    }
    leaf counter_slice1_tx_cgm_local_sch_uc_buffers_drop_counter_local_sch_uc_buffer_drop_cnt {
      type oc-yang:counter64;
      description
        "Counts number of dropped packets by counter C";
    }
    leaf counter_slice2_tx_cgm_local_sch_uc_buffers_drop_counter_local_sch_uc_buffer_drop_cnt {
      type oc-yang:counter64;
      description
        "Counts number of dropped packets by counter C";
    }
    leaf counter_slice3_tx_cgm_local_sch_uc_buffers_drop_counter_local_sch_uc_buffer_drop_cnt {
      type oc-yang:counter64;
      description
        "Counts number of dropped packets by counter C";
    }
    leaf counter_slice4_tx_cgm_local_sch_uc_buffers_drop_counter_local_sch_uc_buffer_drop_cnt {
      type oc-yang:counter64;
      description
        "Counts number of dropped packets by counter C";
    }
    leaf counter_slice5_tx_cgm_local_sch_uc_buffers_drop_counter_local_sch_uc_buffer_drop_cnt {
      type oc-yang:counter64;
      description
        "Counts number of dropped packets by counter C";
    }
    leaf counter_slice6_tx_cgm_local_sch_uc_buffers_drop_counter_local_sch_uc_buffer_drop_cnt {
      type oc-yang:counter64;
      description
        "Counts number of dropped packets by counter C";
    }
    leaf counter_slice7_tx_cgm_local_sch_uc_buffers_drop_counter_local_sch_uc_buffer_drop_cnt {
      type oc-yang:counter64;
      description
        "Counts number of dropped packets by counter C";
    }
    leaf counter_slice8_tx_cgm_local_sch_uc_buffers_drop_counter_local_sch_uc_buffer_drop_cnt {
      type oc-yang:counter64;
      description
        "Counts number of dropped packets by counter C";
    }
    leaf counter_slice9_tx_cgm_local_sch_uc_buffers_drop_counter_local_sch_uc_buffer_drop_cnt {
      type oc-yang:counter64;
      description
        "Counts number of dropped packets by counter C";
    }
    leaf counter_slice10_tx_cgm_local_sch_uc_buffers_drop_counter_local_sch_uc_buffer_drop_cnt {
      type oc-yang:counter64;
      description
        "Counts number of dropped packets by counter C";
    }
    leaf counter_slice11_tx_cgm_local_sch_uc_buffers_drop_counter_local_sch_uc_buffer_drop_cnt {
      type oc-yang:counter64;
      description
        "Counts number of dropped packets by counter C";
    }
    leaf counter_slice12_tx_cgm_local_sch_uc_buffers_drop_counter_local_sch_uc_buffer_drop_cnt {
      type oc-yang:counter64;
      description
        "Counts number of dropped packets by counter C";
    }
    leaf counter_slice13_tx_cgm_local_sch_uc_buffers_drop_counter_local_sch_uc_buffer_drop_cnt {
      type oc-yang:counter64;
      description
        "Counts number of dropped packets by counter C";
    }
    leaf counter_slice14_tx_cgm_local_sch_uc_buffers_drop_counter_local_sch_uc_buffer_drop_cnt {
      type oc-yang:counter64;
      description
        "Counts number of dropped packets by counter C";
    }
    leaf counter_slice15_tx_cgm_local_sch_uc_buffers_drop_counter_local_sch_uc_buffer_drop_cnt {
      type oc-yang:counter64;
      description
        "Counts number of dropped packets by counter C";
    }
    leaf counter_slice0_tx_cgm_max_allowed_qsize_drop_counter_max_allowed_qsize_drop_cnt {
      type oc-yang:counter64;
      description
        "Counts number of dropped packets by max allowed threshold";
    }
    leaf counter_slice1_tx_cgm_max_allowed_qsize_drop_counter_max_allowed_qsize_drop_cnt {
      type oc-yang:counter64;
      description
        "Counts number of dropped packets by max allowed threshold";
    }
    leaf counter_slice2_tx_cgm_max_allowed_qsize_drop_counter_max_allowed_qsize_drop_cnt {
      type oc-yang:counter64;
      description
        "Counts number of dropped packets by max allowed threshold";
    }
    leaf counter_slice3_tx_cgm_max_allowed_qsize_drop_counter_max_allowed_qsize_drop_cnt {
      type oc-yang:counter64;
      description
        "Counts number of dropped packets by max allowed threshold";
    }
    leaf counter_slice4_tx_cgm_max_allowed_qsize_drop_counter_max_allowed_qsize_drop_cnt {
      type oc-yang:counter64;
      description
        "Counts number of dropped packets by max allowed threshold";
    }
    leaf counter_slice5_tx_cgm_max_allowed_qsize_drop_counter_max_allowed_qsize_drop_cnt {
      type oc-yang:counter64;
      description
        "Counts number of dropped packets by max allowed threshold";
    }
    leaf counter_slice6_tx_cgm_max_allowed_qsize_drop_counter_max_allowed_qsize_drop_cnt {
      type oc-yang:counter64;
      description
        "Counts number of dropped packets by max allowed threshold";
    }
    leaf counter_slice7_tx_cgm_max_allowed_qsize_drop_counter_max_allowed_qsize_drop_cnt {
      type oc-yang:counter64;
      description
        "Counts number of dropped packets by max allowed threshold";
    }
    leaf counter_slice8_tx_cgm_max_allowed_qsize_drop_counter_max_allowed_qsize_drop_cnt {
      type oc-yang:counter64;
      description
        "Counts number of dropped packets by max allowed threshold";
    }
    leaf counter_slice9_tx_cgm_max_allowed_qsize_drop_counter_max_allowed_qsize_drop_cnt {
      type oc-yang:counter64;
      description
        "Counts number of dropped packets by max allowed threshold";
    }
    leaf counter_slice10_tx_cgm_max_allowed_qsize_drop_counter_max_allowed_qsize_drop_cnt {
      type oc-yang:counter64;
      description
        "Counts number of dropped packets by max allowed threshold";
    }
    leaf counter_slice11_tx_cgm_max_allowed_qsize_drop_counter_max_allowed_qsize_drop_cnt {
      type oc-yang:counter64;
      description
        "Counts number of dropped packets by max allowed threshold";
    }
    leaf counter_slice12_tx_cgm_max_allowed_qsize_drop_counter_max_allowed_qsize_drop_cnt {
      type oc-yang:counter64;
      description
        "Counts number of dropped packets by max allowed threshold";
    }
    leaf counter_slice13_tx_cgm_max_allowed_qsize_drop_counter_max_allowed_qsize_drop_cnt {
      type oc-yang:counter64;
      description
        "Counts number of dropped packets by max allowed threshold";
    }
    leaf counter_slice14_tx_cgm_max_allowed_qsize_drop_counter_max_allowed_qsize_drop_cnt {
      type oc-yang:counter64;
      description
        "Counts number of dropped packets by max allowed threshold";
    }
    leaf counter_slice15_tx_cgm_max_allowed_qsize_drop_counter_max_allowed_qsize_drop_cnt {
      type oc-yang:counter64;
      description
        "Counts number of dropped packets by max allowed threshold";
    }
    leaf counter_slice0_tx_cgm_mc_color_drop_counter0_mc_color_drop_cnt {
      type oc-yang:counter64;
      description
        "nan";
    }
    leaf counter_slice0_tx_cgm_mc_color_drop_counter1_mc_color_drop_cnt {
      type oc-yang:counter64;
      description
        "nan";
    }
    leaf counter_slice0_tx_cgm_mc_color_drop_counter2_mc_color_drop_cnt {
      type oc-yang:counter64;
      description
        "nan";
    }
    leaf counter_slice0_tx_cgm_mc_color_drop_counter3_mc_color_drop_cnt {
      type oc-yang:counter64;
      description
        "nan";
    }
    leaf counter_slice1_tx_cgm_mc_color_drop_counter0_mc_color_drop_cnt {
      type oc-yang:counter64;
      description
        "nan";
    }
    leaf counter_slice1_tx_cgm_mc_color_drop_counter1_mc_color_drop_cnt {
      type oc-yang:counter64;
      description
        "nan";
    }
    leaf counter_slice1_tx_cgm_mc_color_drop_counter2_mc_color_drop_cnt {
      type oc-yang:counter64;
      description
        "nan";
    }
    leaf counter_slice1_tx_cgm_mc_color_drop_counter3_mc_color_drop_cnt {
      type oc-yang:counter64;
      description
        "nan";
    }
    leaf counter_slice2_tx_cgm_mc_color_drop_counter0_mc_color_drop_cnt {
      type oc-yang:counter64;
      description
        "nan";
    }
    leaf counter_slice2_tx_cgm_mc_color_drop_counter1_mc_color_drop_cnt {
      type oc-yang:counter64;
      description
        "nan";
    }
    leaf counter_slice2_tx_cgm_mc_color_drop_counter2_mc_color_drop_cnt {
      type oc-yang:counter64;
      description
        "nan";
    }
    leaf counter_slice2_tx_cgm_mc_color_drop_counter3_mc_color_drop_cnt {
      type oc-yang:counter64;
      description
        "nan";
    }
    leaf counter_slice3_tx_cgm_mc_color_drop_counter0_mc_color_drop_cnt {
      type oc-yang:counter64;
      description
        "nan";
    }
    leaf counter_slice3_tx_cgm_mc_color_drop_counter1_mc_color_drop_cnt {
      type oc-yang:counter64;
      description
        "nan";
    }
    leaf counter_slice3_tx_cgm_mc_color_drop_counter2_mc_color_drop_cnt {
      type oc-yang:counter64;
      description
        "nan";
    }
    leaf counter_slice3_tx_cgm_mc_color_drop_counter3_mc_color_drop_cnt {
      type oc-yang:counter64;
      description
        "nan";
    }
    leaf counter_slice4_tx_cgm_mc_color_drop_counter0_mc_color_drop_cnt {
      type oc-yang:counter64;
      description
        "nan";
    }
    leaf counter_slice4_tx_cgm_mc_color_drop_counter1_mc_color_drop_cnt {
      type oc-yang:counter64;
      description
        "nan";
    }
    leaf counter_slice4_tx_cgm_mc_color_drop_counter2_mc_color_drop_cnt {
      type oc-yang:counter64;
      description
        "nan";
    }
    leaf counter_slice4_tx_cgm_mc_color_drop_counter3_mc_color_drop_cnt {
      type oc-yang:counter64;
      description
        "nan";
    }
    leaf counter_slice5_tx_cgm_mc_color_drop_counter0_mc_color_drop_cnt {
      type oc-yang:counter64;
      description
        "nan";
    }
    leaf counter_slice5_tx_cgm_mc_color_drop_counter1_mc_color_drop_cnt {
      type oc-yang:counter64;
      description
        "nan";
    }
    leaf counter_slice5_tx_cgm_mc_color_drop_counter2_mc_color_drop_cnt {
      type oc-yang:counter64;
      description
        "nan";
    }
    leaf counter_slice5_tx_cgm_mc_color_drop_counter3_mc_color_drop_cnt {
      type oc-yang:counter64;
      description
        "nan";
    }
    leaf counter_slice6_tx_cgm_mc_color_drop_counter0_mc_color_drop_cnt {
      type oc-yang:counter64;
      description
        "nan";
    }
    leaf counter_slice6_tx_cgm_mc_color_drop_counter1_mc_color_drop_cnt {
      type oc-yang:counter64;
      description
        "nan";
    }
    leaf counter_slice6_tx_cgm_mc_color_drop_counter2_mc_color_drop_cnt {
      type oc-yang:counter64;
      description
        "nan";
    }
    leaf counter_slice6_tx_cgm_mc_color_drop_counter3_mc_color_drop_cnt {
      type oc-yang:counter64;
      description
        "nan";
    }
    leaf counter_slice7_tx_cgm_mc_color_drop_counter0_mc_color_drop_cnt {
      type oc-yang:counter64;
      description
        "nan";
    }
    leaf counter_slice7_tx_cgm_mc_color_drop_counter1_mc_color_drop_cnt {
      type oc-yang:counter64;
      description
        "nan";
    }
    leaf counter_slice7_tx_cgm_mc_color_drop_counter2_mc_color_drop_cnt {
      type oc-yang:counter64;
      description
        "nan";
    }
    leaf counter_slice7_tx_cgm_mc_color_drop_counter3_mc_color_drop_cnt {
      type oc-yang:counter64;
      description
        "nan";
    }
    leaf counter_slice8_tx_cgm_mc_color_drop_counter0_mc_color_drop_cnt {
      type oc-yang:counter64;
      description
        "nan";
    }
    leaf counter_slice8_tx_cgm_mc_color_drop_counter1_mc_color_drop_cnt {
      type oc-yang:counter64;
      description
        "nan";
    }
    leaf counter_slice8_tx_cgm_mc_color_drop_counter2_mc_color_drop_cnt {
      type oc-yang:counter64;
      description
        "nan";
    }
    leaf counter_slice8_tx_cgm_mc_color_drop_counter3_mc_color_drop_cnt {
      type oc-yang:counter64;
      description
        "nan";
    }
    leaf counter_slice9_tx_cgm_mc_color_drop_counter0_mc_color_drop_cnt {
      type oc-yang:counter64;
      description
        "nan";
    }
    leaf counter_slice9_tx_cgm_mc_color_drop_counter1_mc_color_drop_cnt {
      type oc-yang:counter64;
      description
        "nan";
    }
    leaf counter_slice9_tx_cgm_mc_color_drop_counter2_mc_color_drop_cnt {
      type oc-yang:counter64;
      description
        "nan";
    }
    leaf counter_slice9_tx_cgm_mc_color_drop_counter3_mc_color_drop_cnt {
      type oc-yang:counter64;
      description
        "nan";
    }
    leaf counter_slice10_tx_cgm_mc_color_drop_counter0_mc_color_drop_cnt {
      type oc-yang:counter64;
      description
        "nan";
    }
    leaf counter_slice10_tx_cgm_mc_color_drop_counter1_mc_color_drop_cnt {
      type oc-yang:counter64;
      description
        "nan";
    }
    leaf counter_slice10_tx_cgm_mc_color_drop_counter2_mc_color_drop_cnt {
      type oc-yang:counter64;
      description
        "nan";
    }
    leaf counter_slice10_tx_cgm_mc_color_drop_counter3_mc_color_drop_cnt {
      type oc-yang:counter64;
      description
        "nan";
    }
    leaf counter_slice11_tx_cgm_mc_color_drop_counter0_mc_color_drop_cnt {
      type oc-yang:counter64;
      description
        "nan";
    }
    leaf counter_slice11_tx_cgm_mc_color_drop_counter1_mc_color_drop_cnt {
      type oc-yang:counter64;
      description
        "nan";
    }
    leaf counter_slice11_tx_cgm_mc_color_drop_counter2_mc_color_drop_cnt {
      type oc-yang:counter64;
      description
        "nan";
    }
    leaf counter_slice11_tx_cgm_mc_color_drop_counter3_mc_color_drop_cnt {
      type oc-yang:counter64;
      description
        "nan";
    }
    leaf counter_slice12_tx_cgm_mc_color_drop_counter0_mc_color_drop_cnt {
      type oc-yang:counter64;
      description
        "nan";
    }
    leaf counter_slice12_tx_cgm_mc_color_drop_counter1_mc_color_drop_cnt {
      type oc-yang:counter64;
      description
        "nan";
    }
    leaf counter_slice12_tx_cgm_mc_color_drop_counter2_mc_color_drop_cnt {
      type oc-yang:counter64;
      description
        "nan";
    }
    leaf counter_slice12_tx_cgm_mc_color_drop_counter3_mc_color_drop_cnt {
      type oc-yang:counter64;
      description
        "nan";
    }
    leaf counter_slice13_tx_cgm_mc_color_drop_counter0_mc_color_drop_cnt {
      type oc-yang:counter64;
      description
        "nan";
    }
    leaf counter_slice13_tx_cgm_mc_color_drop_counter1_mc_color_drop_cnt {
      type oc-yang:counter64;
      description
        "nan";
    }
    leaf counter_slice13_tx_cgm_mc_color_drop_counter2_mc_color_drop_cnt {
      type oc-yang:counter64;
      description
        "nan";
    }
    leaf counter_slice13_tx_cgm_mc_color_drop_counter3_mc_color_drop_cnt {
      type oc-yang:counter64;
      description
        "nan";
    }
    leaf counter_slice14_tx_cgm_mc_color_drop_counter0_mc_color_drop_cnt {
      type oc-yang:counter64;
      description
        "nan";
    }
    leaf counter_slice14_tx_cgm_mc_color_drop_counter1_mc_color_drop_cnt {
      type oc-yang:counter64;
      description
        "nan";
    }
    leaf counter_slice14_tx_cgm_mc_color_drop_counter2_mc_color_drop_cnt {
      type oc-yang:counter64;
      description
        "nan";
    }
    leaf counter_slice14_tx_cgm_mc_color_drop_counter3_mc_color_drop_cnt {
      type oc-yang:counter64;
      description
        "nan";
    }
    leaf counter_slice15_tx_cgm_mc_color_drop_counter0_mc_color_drop_cnt {
      type oc-yang:counter64;
      description
        "nan";
    }
    leaf counter_slice15_tx_cgm_mc_color_drop_counter1_mc_color_drop_cnt {
      type oc-yang:counter64;
      description
        "nan";
    }
    leaf counter_slice15_tx_cgm_mc_color_drop_counter2_mc_color_drop_cnt {
      type oc-yang:counter64;
      description
        "nan";
    }
    leaf counter_slice15_tx_cgm_mc_color_drop_counter3_mc_color_drop_cnt {
      type oc-yang:counter64;
      description
        "nan";
    }
    leaf counter_slice0_tx_cgm_mc_drop_hidden_counter_mc_drop_hidden_cnt {
      type oc-yang:counter64;
      description
        "Counter of dropped MC packets that were silently dropped";
    }
    leaf counter_slice1_tx_cgm_mc_drop_hidden_counter_mc_drop_hidden_cnt {
      type oc-yang:counter64;
      description
        "Counter of dropped MC packets that were silently dropped";
    }
    leaf counter_slice2_tx_cgm_mc_drop_hidden_counter_mc_drop_hidden_cnt {
      type oc-yang:counter64;
      description
        "Counter of dropped MC packets that were silently dropped";
    }
    leaf counter_slice3_tx_cgm_mc_drop_hidden_counter_mc_drop_hidden_cnt {
      type oc-yang:counter64;
      description
        "Counter of dropped MC packets that were silently dropped";
    }
    leaf counter_slice4_tx_cgm_mc_drop_hidden_counter_mc_drop_hidden_cnt {
      type oc-yang:counter64;
      description
        "Counter of dropped MC packets that were silently dropped";
    }
    leaf counter_slice5_tx_cgm_mc_drop_hidden_counter_mc_drop_hidden_cnt {
      type oc-yang:counter64;
      description
        "Counter of dropped MC packets that were silently dropped";
    }
    leaf counter_slice6_tx_cgm_mc_drop_hidden_counter_mc_drop_hidden_cnt {
      type oc-yang:counter64;
      description
        "Counter of dropped MC packets that were silently dropped";
    }
    leaf counter_slice7_tx_cgm_mc_drop_hidden_counter_mc_drop_hidden_cnt {
      type oc-yang:counter64;
      description
        "Counter of dropped MC packets that were silently dropped";
    }
    leaf counter_slice8_tx_cgm_mc_drop_hidden_counter_mc_drop_hidden_cnt {
      type oc-yang:counter64;
      description
        "Counter of dropped MC packets that were silently dropped";
    }
    leaf counter_slice9_tx_cgm_mc_drop_hidden_counter_mc_drop_hidden_cnt {
      type oc-yang:counter64;
      description
        "Counter of dropped MC packets that were silently dropped";
    }
    leaf counter_slice10_tx_cgm_mc_drop_hidden_counter_mc_drop_hidden_cnt {
      type oc-yang:counter64;
      description
        "Counter of dropped MC packets that were silently dropped";
    }
    leaf counter_slice11_tx_cgm_mc_drop_hidden_counter_mc_drop_hidden_cnt {
      type oc-yang:counter64;
      description
        "Counter of dropped MC packets that were silently dropped";
    }
    leaf counter_slice12_tx_cgm_mc_drop_hidden_counter_mc_drop_hidden_cnt {
      type oc-yang:counter64;
      description
        "Counter of dropped MC packets that were silently dropped";
    }
    leaf counter_slice13_tx_cgm_mc_drop_hidden_counter_mc_drop_hidden_cnt {
      type oc-yang:counter64;
      description
        "Counter of dropped MC packets that were silently dropped";
    }
    leaf counter_slice14_tx_cgm_mc_drop_hidden_counter_mc_drop_hidden_cnt {
      type oc-yang:counter64;
      description
        "Counter of dropped MC packets that were silently dropped";
    }
    leaf counter_slice15_tx_cgm_mc_drop_hidden_counter_mc_drop_hidden_cnt {
      type oc-yang:counter64;
      description
        "Counter of dropped MC packets that were silently dropped";
    }
    leaf counter_slice0_tx_cgm_oq_mc_byte_green_drop_counter_oq_mc_byte_green_drop_cnt {
      type oc-yang:counter64;
      description
        "Counts number of dropped packets by OQ MC green bytes test";
    }
    leaf counter_slice1_tx_cgm_oq_mc_byte_green_drop_counter_oq_mc_byte_green_drop_cnt {
      type oc-yang:counter64;
      description
        "Counts number of dropped packets by OQ MC green bytes test";
    }
    leaf counter_slice2_tx_cgm_oq_mc_byte_green_drop_counter_oq_mc_byte_green_drop_cnt {
      type oc-yang:counter64;
      description
        "Counts number of dropped packets by OQ MC green bytes test";
    }
    leaf counter_slice3_tx_cgm_oq_mc_byte_green_drop_counter_oq_mc_byte_green_drop_cnt {
      type oc-yang:counter64;
      description
        "Counts number of dropped packets by OQ MC green bytes test";
    }
    leaf counter_slice4_tx_cgm_oq_mc_byte_green_drop_counter_oq_mc_byte_green_drop_cnt {
      type oc-yang:counter64;
      description
        "Counts number of dropped packets by OQ MC green bytes test";
    }
    leaf counter_slice5_tx_cgm_oq_mc_byte_green_drop_counter_oq_mc_byte_green_drop_cnt {
      type oc-yang:counter64;
      description
        "Counts number of dropped packets by OQ MC green bytes test";
    }
    leaf counter_slice6_tx_cgm_oq_mc_byte_green_drop_counter_oq_mc_byte_green_drop_cnt {
      type oc-yang:counter64;
      description
        "Counts number of dropped packets by OQ MC green bytes test";
    }
    leaf counter_slice7_tx_cgm_oq_mc_byte_green_drop_counter_oq_mc_byte_green_drop_cnt {
      type oc-yang:counter64;
      description
        "Counts number of dropped packets by OQ MC green bytes test";
    }
    leaf counter_slice8_tx_cgm_oq_mc_byte_green_drop_counter_oq_mc_byte_green_drop_cnt {
      type oc-yang:counter64;
      description
        "Counts number of dropped packets by OQ MC green bytes test";
    }
    leaf counter_slice9_tx_cgm_oq_mc_byte_green_drop_counter_oq_mc_byte_green_drop_cnt {
      type oc-yang:counter64;
      description
        "Counts number of dropped packets by OQ MC green bytes test";
    }
    leaf counter_slice10_tx_cgm_oq_mc_byte_green_drop_counter_oq_mc_byte_green_drop_cnt {
      type oc-yang:counter64;
      description
        "Counts number of dropped packets by OQ MC green bytes test";
    }
    leaf counter_slice11_tx_cgm_oq_mc_byte_green_drop_counter_oq_mc_byte_green_drop_cnt {
      type oc-yang:counter64;
      description
        "Counts number of dropped packets by OQ MC green bytes test";
    }
    leaf counter_slice12_tx_cgm_oq_mc_byte_green_drop_counter_oq_mc_byte_green_drop_cnt {
      type oc-yang:counter64;
      description
        "Counts number of dropped packets by OQ MC green bytes test";
    }
    leaf counter_slice13_tx_cgm_oq_mc_byte_green_drop_counter_oq_mc_byte_green_drop_cnt {
      type oc-yang:counter64;
      description
        "Counts number of dropped packets by OQ MC green bytes test";
    }
    leaf counter_slice14_tx_cgm_oq_mc_byte_green_drop_counter_oq_mc_byte_green_drop_cnt {
      type oc-yang:counter64;
      description
        "Counts number of dropped packets by OQ MC green bytes test";
    }
    leaf counter_slice15_tx_cgm_oq_mc_byte_green_drop_counter_oq_mc_byte_green_drop_cnt {
      type oc-yang:counter64;
      description
        "Counts number of dropped packets by OQ MC green bytes test";
    }
    leaf counter_slice0_tx_cgm_oq_mc_byte_yellow_drop_counter_oq_mc_byte_yellow_drop_cnt {
      type oc-yang:counter64;
      description
        "Counts number of dropped packets by OQ MC yellow bytes test";
    }
    leaf counter_slice1_tx_cgm_oq_mc_byte_yellow_drop_counter_oq_mc_byte_yellow_drop_cnt {
      type oc-yang:counter64;
      description
        "Counts number of dropped packets by OQ MC yellow bytes test";
    }
    leaf counter_slice2_tx_cgm_oq_mc_byte_yellow_drop_counter_oq_mc_byte_yellow_drop_cnt {
      type oc-yang:counter64;
      description
        "Counts number of dropped packets by OQ MC yellow bytes test";
    }
    leaf counter_slice3_tx_cgm_oq_mc_byte_yellow_drop_counter_oq_mc_byte_yellow_drop_cnt {
      type oc-yang:counter64;
      description
        "Counts number of dropped packets by OQ MC yellow bytes test";
    }
    leaf counter_slice4_tx_cgm_oq_mc_byte_yellow_drop_counter_oq_mc_byte_yellow_drop_cnt {
      type oc-yang:counter64;
      description
        "Counts number of dropped packets by OQ MC yellow bytes test";
    }
    leaf counter_slice5_tx_cgm_oq_mc_byte_yellow_drop_counter_oq_mc_byte_yellow_drop_cnt {
      type oc-yang:counter64;
      description
        "Counts number of dropped packets by OQ MC yellow bytes test";
    }
    leaf counter_slice6_tx_cgm_oq_mc_byte_yellow_drop_counter_oq_mc_byte_yellow_drop_cnt {
      type oc-yang:counter64;
      description
        "Counts number of dropped packets by OQ MC yellow bytes test";
    }
    leaf counter_slice7_tx_cgm_oq_mc_byte_yellow_drop_counter_oq_mc_byte_yellow_drop_cnt {
      type oc-yang:counter64;
      description
        "Counts number of dropped packets by OQ MC yellow bytes test";
    }
    leaf counter_slice8_tx_cgm_oq_mc_byte_yellow_drop_counter_oq_mc_byte_yellow_drop_cnt {
      type oc-yang:counter64;
      description
        "Counts number of dropped packets by OQ MC yellow bytes test";
    }
    leaf counter_slice9_tx_cgm_oq_mc_byte_yellow_drop_counter_oq_mc_byte_yellow_drop_cnt {
      type oc-yang:counter64;
      description
        "Counts number of dropped packets by OQ MC yellow bytes test";
    }
    leaf counter_slice10_tx_cgm_oq_mc_byte_yellow_drop_counter_oq_mc_byte_yellow_drop_cnt {
      type oc-yang:counter64;
      description
        "Counts number of dropped packets by OQ MC yellow bytes test";
    }
    leaf counter_slice11_tx_cgm_oq_mc_byte_yellow_drop_counter_oq_mc_byte_yellow_drop_cnt {
      type oc-yang:counter64;
      description
        "Counts number of dropped packets by OQ MC yellow bytes test";
    }
    leaf counter_slice12_tx_cgm_oq_mc_byte_yellow_drop_counter_oq_mc_byte_yellow_drop_cnt {
      type oc-yang:counter64;
      description
        "Counts number of dropped packets by OQ MC yellow bytes test";
    }
    leaf counter_slice13_tx_cgm_oq_mc_byte_yellow_drop_counter_oq_mc_byte_yellow_drop_cnt {
      type oc-yang:counter64;
      description
        "Counts number of dropped packets by OQ MC yellow bytes test";
    }
    leaf counter_slice14_tx_cgm_oq_mc_byte_yellow_drop_counter_oq_mc_byte_yellow_drop_cnt {
      type oc-yang:counter64;
      description
        "Counts number of dropped packets by OQ MC yellow bytes test";
    }
    leaf counter_slice15_tx_cgm_oq_mc_byte_yellow_drop_counter_oq_mc_byte_yellow_drop_cnt {
      type oc-yang:counter64;
      description
        "Counts number of dropped packets by OQ MC yellow bytes test";
    }
    leaf counter_slice0_tx_cgm_oq_mc_pd_green_drop_counter_oq_mc_pd_green_drop_cnt {
      type oc-yang:counter64;
      description
        "Counts number of dropped packets by OQ MC green PDs test";
    }
    leaf counter_slice1_tx_cgm_oq_mc_pd_green_drop_counter_oq_mc_pd_green_drop_cnt {
      type oc-yang:counter64;
      description
        "Counts number of dropped packets by OQ MC green PDs test";
    }
    leaf counter_slice2_tx_cgm_oq_mc_pd_green_drop_counter_oq_mc_pd_green_drop_cnt {
      type oc-yang:counter64;
      description
        "Counts number of dropped packets by OQ MC green PDs test";
    }
    leaf counter_slice3_tx_cgm_oq_mc_pd_green_drop_counter_oq_mc_pd_green_drop_cnt {
      type oc-yang:counter64;
      description
        "Counts number of dropped packets by OQ MC green PDs test";
    }
    leaf counter_slice4_tx_cgm_oq_mc_pd_green_drop_counter_oq_mc_pd_green_drop_cnt {
      type oc-yang:counter64;
      description
        "Counts number of dropped packets by OQ MC green PDs test";
    }
    leaf counter_slice5_tx_cgm_oq_mc_pd_green_drop_counter_oq_mc_pd_green_drop_cnt {
      type oc-yang:counter64;
      description
        "Counts number of dropped packets by OQ MC green PDs test";
    }
    leaf counter_slice6_tx_cgm_oq_mc_pd_green_drop_counter_oq_mc_pd_green_drop_cnt {
      type oc-yang:counter64;
      description
        "Counts number of dropped packets by OQ MC green PDs test";
    }
    leaf counter_slice7_tx_cgm_oq_mc_pd_green_drop_counter_oq_mc_pd_green_drop_cnt {
      type oc-yang:counter64;
      description
        "Counts number of dropped packets by OQ MC green PDs test";
    }
    leaf counter_slice8_tx_cgm_oq_mc_pd_green_drop_counter_oq_mc_pd_green_drop_cnt {
      type oc-yang:counter64;
      description
        "Counts number of dropped packets by OQ MC green PDs test";
    }
    leaf counter_slice9_tx_cgm_oq_mc_pd_green_drop_counter_oq_mc_pd_green_drop_cnt {
      type oc-yang:counter64;
      description
        "Counts number of dropped packets by OQ MC green PDs test";
    }
    leaf counter_slice10_tx_cgm_oq_mc_pd_green_drop_counter_oq_mc_pd_green_drop_cnt {
      type oc-yang:counter64;
      description
        "Counts number of dropped packets by OQ MC green PDs test";
    }
    leaf counter_slice11_tx_cgm_oq_mc_pd_green_drop_counter_oq_mc_pd_green_drop_cnt {
      type oc-yang:counter64;
      description
        "Counts number of dropped packets by OQ MC green PDs test";
    }
    leaf counter_slice12_tx_cgm_oq_mc_pd_green_drop_counter_oq_mc_pd_green_drop_cnt {
      type oc-yang:counter64;
      description
        "Counts number of dropped packets by OQ MC green PDs test";
    }
    leaf counter_slice13_tx_cgm_oq_mc_pd_green_drop_counter_oq_mc_pd_green_drop_cnt {
      type oc-yang:counter64;
      description
        "Counts number of dropped packets by OQ MC green PDs test";
    }
    leaf counter_slice14_tx_cgm_oq_mc_pd_green_drop_counter_oq_mc_pd_green_drop_cnt {
      type oc-yang:counter64;
      description
        "Counts number of dropped packets by OQ MC green PDs test";
    }
    leaf counter_slice15_tx_cgm_oq_mc_pd_green_drop_counter_oq_mc_pd_green_drop_cnt {
      type oc-yang:counter64;
      description
        "Counts number of dropped packets by OQ MC green PDs test";
    }
    leaf counter_slice0_tx_cgm_oq_mc_pd_yellow_drop_counter_oq_mc_pd_yellow_drop_cnt {
      type oc-yang:counter64;
      description
        "Counts number of dropped packets by OQ MC yellow PDs test";
    }
    leaf counter_slice1_tx_cgm_oq_mc_pd_yellow_drop_counter_oq_mc_pd_yellow_drop_cnt {
      type oc-yang:counter64;
      description
        "Counts number of dropped packets by OQ MC yellow PDs test";
    }
    leaf counter_slice2_tx_cgm_oq_mc_pd_yellow_drop_counter_oq_mc_pd_yellow_drop_cnt {
      type oc-yang:counter64;
      description
        "Counts number of dropped packets by OQ MC yellow PDs test";
    }
    leaf counter_slice3_tx_cgm_oq_mc_pd_yellow_drop_counter_oq_mc_pd_yellow_drop_cnt {
      type oc-yang:counter64;
      description
        "Counts number of dropped packets by OQ MC yellow PDs test";
    }
    leaf counter_slice4_tx_cgm_oq_mc_pd_yellow_drop_counter_oq_mc_pd_yellow_drop_cnt {
      type oc-yang:counter64;
      description
        "Counts number of dropped packets by OQ MC yellow PDs test";
    }
    leaf counter_slice5_tx_cgm_oq_mc_pd_yellow_drop_counter_oq_mc_pd_yellow_drop_cnt {
      type oc-yang:counter64;
      description
        "Counts number of dropped packets by OQ MC yellow PDs test";
    }
    leaf counter_slice6_tx_cgm_oq_mc_pd_yellow_drop_counter_oq_mc_pd_yellow_drop_cnt {
      type oc-yang:counter64;
      description
        "Counts number of dropped packets by OQ MC yellow PDs test";
    }
    leaf counter_slice7_tx_cgm_oq_mc_pd_yellow_drop_counter_oq_mc_pd_yellow_drop_cnt {
      type oc-yang:counter64;
      description
        "Counts number of dropped packets by OQ MC yellow PDs test";
    }
    leaf counter_slice8_tx_cgm_oq_mc_pd_yellow_drop_counter_oq_mc_pd_yellow_drop_cnt {
      type oc-yang:counter64;
      description
        "Counts number of dropped packets by OQ MC yellow PDs test";
    }
    leaf counter_slice9_tx_cgm_oq_mc_pd_yellow_drop_counter_oq_mc_pd_yellow_drop_cnt {
      type oc-yang:counter64;
      description
        "Counts number of dropped packets by OQ MC yellow PDs test";
    }
    leaf counter_slice10_tx_cgm_oq_mc_pd_yellow_drop_counter_oq_mc_pd_yellow_drop_cnt {
      type oc-yang:counter64;
      description
        "Counts number of dropped packets by OQ MC yellow PDs test";
    }
    leaf counter_slice11_tx_cgm_oq_mc_pd_yellow_drop_counter_oq_mc_pd_yellow_drop_cnt {
      type oc-yang:counter64;
      description
        "Counts number of dropped packets by OQ MC yellow PDs test";
    }
    leaf counter_slice12_tx_cgm_oq_mc_pd_yellow_drop_counter_oq_mc_pd_yellow_drop_cnt {
      type oc-yang:counter64;
      description
        "Counts number of dropped packets by OQ MC yellow PDs test";
    }
    leaf counter_slice13_tx_cgm_oq_mc_pd_yellow_drop_counter_oq_mc_pd_yellow_drop_cnt {
      type oc-yang:counter64;
      description
        "Counts number of dropped packets by OQ MC yellow PDs test";
    }
    leaf counter_slice14_tx_cgm_oq_mc_pd_yellow_drop_counter_oq_mc_pd_yellow_drop_cnt {
      type oc-yang:counter64;
      description
        "Counts number of dropped packets by OQ MC yellow PDs test";
    }
    leaf counter_slice15_tx_cgm_oq_mc_pd_yellow_drop_counter_oq_mc_pd_yellow_drop_cnt {
      type oc-yang:counter64;
      description
        "Counts number of dropped packets by OQ MC yellow PDs test";
    }
    leaf counter_slice0_tx_cgm_oq_uc_drop_counter_oq_uc_drop_cnt {
      type oc-yang:counter64;
      description
        "Counts number of dropped by UC OQ test";
    }
    leaf counter_slice1_tx_cgm_oq_uc_drop_counter_oq_uc_drop_cnt {
      type oc-yang:counter64;
      description
        "Counts number of dropped by UC OQ test";
    }
    leaf counter_slice2_tx_cgm_oq_uc_drop_counter_oq_uc_drop_cnt {
      type oc-yang:counter64;
      description
        "Counts number of dropped by UC OQ test";
    }
    leaf counter_slice3_tx_cgm_oq_uc_drop_counter_oq_uc_drop_cnt {
      type oc-yang:counter64;
      description
        "Counts number of dropped by UC OQ test";
    }
    leaf counter_slice4_tx_cgm_oq_uc_drop_counter_oq_uc_drop_cnt {
      type oc-yang:counter64;
      description
        "Counts number of dropped by UC OQ test";
    }
    leaf counter_slice5_tx_cgm_oq_uc_drop_counter_oq_uc_drop_cnt {
      type oc-yang:counter64;
      description
        "Counts number of dropped by UC OQ test";
    }
    leaf counter_slice6_tx_cgm_oq_uc_drop_counter_oq_uc_drop_cnt {
      type oc-yang:counter64;
      description
        "Counts number of dropped by UC OQ test";
    }
    leaf counter_slice7_tx_cgm_oq_uc_drop_counter_oq_uc_drop_cnt {
      type oc-yang:counter64;
      description
        "Counts number of dropped by UC OQ test";
    }
    leaf counter_slice8_tx_cgm_oq_uc_drop_counter_oq_uc_drop_cnt {
      type oc-yang:counter64;
      description
        "Counts number of dropped by UC OQ test";
    }
    leaf counter_slice9_tx_cgm_oq_uc_drop_counter_oq_uc_drop_cnt {
      type oc-yang:counter64;
      description
        "Counts number of dropped by UC OQ test";
    }
    leaf counter_slice10_tx_cgm_oq_uc_drop_counter_oq_uc_drop_cnt {
      type oc-yang:counter64;
      description
        "Counts number of dropped by UC OQ test";
    }
    leaf counter_slice11_tx_cgm_oq_uc_drop_counter_oq_uc_drop_cnt {
      type oc-yang:counter64;
      description
        "Counts number of dropped by UC OQ test";
    }
    leaf counter_slice12_tx_cgm_oq_uc_drop_counter_oq_uc_drop_cnt {
      type oc-yang:counter64;
      description
        "Counts number of dropped by UC OQ test";
    }
    leaf counter_slice13_tx_cgm_oq_uc_drop_counter_oq_uc_drop_cnt {
      type oc-yang:counter64;
      description
        "Counts number of dropped by UC OQ test";
    }
    leaf counter_slice14_tx_cgm_oq_uc_drop_counter_oq_uc_drop_cnt {
      type oc-yang:counter64;
      description
        "Counts number of dropped by UC OQ test";
    }
    leaf counter_slice15_tx_cgm_oq_uc_drop_counter_oq_uc_drop_cnt {
      type oc-yang:counter64;
      description
        "Counts number of dropped by UC OQ test";
    }
    leaf counter_slice0_tx_cgm_oqg_uc_drop_counter_oqg_uc_drop_cnt {
      type oc-yang:counter64;
      description
        "Counts number of dropped by UC OQG test";
    }
    leaf counter_slice1_tx_cgm_oqg_uc_drop_counter_oqg_uc_drop_cnt {
      type oc-yang:counter64;
      description
        "Counts number of dropped by UC OQG test";
    }
    leaf counter_slice2_tx_cgm_oqg_uc_drop_counter_oqg_uc_drop_cnt {
      type oc-yang:counter64;
      description
        "Counts number of dropped by UC OQG test";
    }
    leaf counter_slice3_tx_cgm_oqg_uc_drop_counter_oqg_uc_drop_cnt {
      type oc-yang:counter64;
      description
        "Counts number of dropped by UC OQG test";
    }
    leaf counter_slice4_tx_cgm_oqg_uc_drop_counter_oqg_uc_drop_cnt {
      type oc-yang:counter64;
      description
        "Counts number of dropped by UC OQG test";
    }
    leaf counter_slice5_tx_cgm_oqg_uc_drop_counter_oqg_uc_drop_cnt {
      type oc-yang:counter64;
      description
        "Counts number of dropped by UC OQG test";
    }
    leaf counter_slice6_tx_cgm_oqg_uc_drop_counter_oqg_uc_drop_cnt {
      type oc-yang:counter64;
      description
        "Counts number of dropped by UC OQG test";
    }
    leaf counter_slice7_tx_cgm_oqg_uc_drop_counter_oqg_uc_drop_cnt {
      type oc-yang:counter64;
      description
        "Counts number of dropped by UC OQG test";
    }
    leaf counter_slice8_tx_cgm_oqg_uc_drop_counter_oqg_uc_drop_cnt {
      type oc-yang:counter64;
      description
        "Counts number of dropped by UC OQG test";
    }
    leaf counter_slice9_tx_cgm_oqg_uc_drop_counter_oqg_uc_drop_cnt {
      type oc-yang:counter64;
      description
        "Counts number of dropped by UC OQG test";
    }
    leaf counter_slice10_tx_cgm_oqg_uc_drop_counter_oqg_uc_drop_cnt {
      type oc-yang:counter64;
      description
        "Counts number of dropped by UC OQG test";
    }
    leaf counter_slice11_tx_cgm_oqg_uc_drop_counter_oqg_uc_drop_cnt {
      type oc-yang:counter64;
      description
        "Counts number of dropped by UC OQG test";
    }
    leaf counter_slice12_tx_cgm_oqg_uc_drop_counter_oqg_uc_drop_cnt {
      type oc-yang:counter64;
      description
        "Counts number of dropped by UC OQG test";
    }
    leaf counter_slice13_tx_cgm_oqg_uc_drop_counter_oqg_uc_drop_cnt {
      type oc-yang:counter64;
      description
        "Counts number of dropped by UC OQG test";
    }
    leaf counter_slice14_tx_cgm_oqg_uc_drop_counter_oqg_uc_drop_cnt {
      type oc-yang:counter64;
      description
        "Counts number of dropped by UC OQG test";
    }
    leaf counter_slice15_tx_cgm_oqg_uc_drop_counter_oqg_uc_drop_cnt {
      type oc-yang:counter64;
      description
        "Counts number of dropped by UC OQG test";
    }
    leaf counter_slice0_tx_cgm_sch_uc_buffers_drop_counter_sch_uc_buffers_drop_cnt {
      type oc-yang:counter64;
      description
        "Counts number of dropped packets by counter C+D";
    }
    leaf counter_slice1_tx_cgm_sch_uc_buffers_drop_counter_sch_uc_buffers_drop_cnt {
      type oc-yang:counter64;
      description
        "Counts number of dropped packets by counter C+D";
    }
    leaf counter_slice2_tx_cgm_sch_uc_buffers_drop_counter_sch_uc_buffers_drop_cnt {
      type oc-yang:counter64;
      description
        "Counts number of dropped packets by counter C+D";
    }
    leaf counter_slice3_tx_cgm_sch_uc_buffers_drop_counter_sch_uc_buffers_drop_cnt {
      type oc-yang:counter64;
      description
        "Counts number of dropped packets by counter C+D";
    }
    leaf counter_slice4_tx_cgm_sch_uc_buffers_drop_counter_sch_uc_buffers_drop_cnt {
      type oc-yang:counter64;
      description
        "Counts number of dropped packets by counter C+D";
    }
    leaf counter_slice5_tx_cgm_sch_uc_buffers_drop_counter_sch_uc_buffers_drop_cnt {
      type oc-yang:counter64;
      description
        "Counts number of dropped packets by counter C+D";
    }
    leaf counter_slice6_tx_cgm_sch_uc_buffers_drop_counter_sch_uc_buffers_drop_cnt {
      type oc-yang:counter64;
      description
        "Counts number of dropped packets by counter C+D";
    }
    leaf counter_slice7_tx_cgm_sch_uc_buffers_drop_counter_sch_uc_buffers_drop_cnt {
      type oc-yang:counter64;
      description
        "Counts number of dropped packets by counter C+D";
    }
    leaf counter_slice8_tx_cgm_sch_uc_buffers_drop_counter_sch_uc_buffers_drop_cnt {
      type oc-yang:counter64;
      description
        "Counts number of dropped packets by counter C+D";
    }
    leaf counter_slice9_tx_cgm_sch_uc_buffers_drop_counter_sch_uc_buffers_drop_cnt {
      type oc-yang:counter64;
      description
        "Counts number of dropped packets by counter C+D";
    }
    leaf counter_slice10_tx_cgm_sch_uc_buffers_drop_counter_sch_uc_buffers_drop_cnt {
      type oc-yang:counter64;
      description
        "Counts number of dropped packets by counter C+D";
    }
    leaf counter_slice11_tx_cgm_sch_uc_buffers_drop_counter_sch_uc_buffers_drop_cnt {
      type oc-yang:counter64;
      description
        "Counts number of dropped packets by counter C+D";
    }
    leaf counter_slice12_tx_cgm_sch_uc_buffers_drop_counter_sch_uc_buffers_drop_cnt {
      type oc-yang:counter64;
      description
        "Counts number of dropped packets by counter C+D";
    }
    leaf counter_slice13_tx_cgm_sch_uc_buffers_drop_counter_sch_uc_buffers_drop_cnt {
      type oc-yang:counter64;
      description
        "Counts number of dropped packets by counter C+D";
    }
    leaf counter_slice14_tx_cgm_sch_uc_buffers_drop_counter_sch_uc_buffers_drop_cnt {
      type oc-yang:counter64;
      description
        "Counts number of dropped packets by counter C+D";
    }
    leaf counter_slice15_tx_cgm_sch_uc_buffers_drop_counter_sch_uc_buffers_drop_cnt {
      type oc-yang:counter64;
      description
        "Counts number of dropped packets by counter C+D";
    }
    leaf counter_slice0_tx_cgm_sch_uc_drop_pds_counter_sch_uc_drop_pds_cnt {
      type oc-yang:counter64;
      description
        "Counts number of dropped packets by counter Z";
    }
    leaf counter_slice1_tx_cgm_sch_uc_drop_pds_counter_sch_uc_drop_pds_cnt {
      type oc-yang:counter64;
      description
        "Counts number of dropped packets by counter Z";
    }
    leaf counter_slice2_tx_cgm_sch_uc_drop_pds_counter_sch_uc_drop_pds_cnt {
      type oc-yang:counter64;
      description
        "Counts number of dropped packets by counter Z";
    }
    leaf counter_slice3_tx_cgm_sch_uc_drop_pds_counter_sch_uc_drop_pds_cnt {
      type oc-yang:counter64;
      description
        "Counts number of dropped packets by counter Z";
    }
    leaf counter_slice4_tx_cgm_sch_uc_drop_pds_counter_sch_uc_drop_pds_cnt {
      type oc-yang:counter64;
      description
        "Counts number of dropped packets by counter Z";
    }
    leaf counter_slice5_tx_cgm_sch_uc_drop_pds_counter_sch_uc_drop_pds_cnt {
      type oc-yang:counter64;
      description
        "Counts number of dropped packets by counter Z";
    }
    leaf counter_slice6_tx_cgm_sch_uc_drop_pds_counter_sch_uc_drop_pds_cnt {
      type oc-yang:counter64;
      description
        "Counts number of dropped packets by counter Z";
    }
    leaf counter_slice7_tx_cgm_sch_uc_drop_pds_counter_sch_uc_drop_pds_cnt {
      type oc-yang:counter64;
      description
        "Counts number of dropped packets by counter Z";
    }
    leaf counter_slice8_tx_cgm_sch_uc_drop_pds_counter_sch_uc_drop_pds_cnt {
      type oc-yang:counter64;
      description
        "Counts number of dropped packets by counter Z";
    }
    leaf counter_slice9_tx_cgm_sch_uc_drop_pds_counter_sch_uc_drop_pds_cnt {
      type oc-yang:counter64;
      description
        "Counts number of dropped packets by counter Z";
    }
    leaf counter_slice10_tx_cgm_sch_uc_drop_pds_counter_sch_uc_drop_pds_cnt {
      type oc-yang:counter64;
      description
        "Counts number of dropped packets by counter Z";
    }
    leaf counter_slice11_tx_cgm_sch_uc_drop_pds_counter_sch_uc_drop_pds_cnt {
      type oc-yang:counter64;
      description
        "Counts number of dropped packets by counter Z";
    }
    leaf counter_slice12_tx_cgm_sch_uc_drop_pds_counter_sch_uc_drop_pds_cnt {
      type oc-yang:counter64;
      description
        "Counts number of dropped packets by counter Z";
    }
    leaf counter_slice13_tx_cgm_sch_uc_drop_pds_counter_sch_uc_drop_pds_cnt {
      type oc-yang:counter64;
      description
        "Counts number of dropped packets by counter Z";
    }
    leaf counter_slice14_tx_cgm_sch_uc_drop_pds_counter_sch_uc_drop_pds_cnt {
      type oc-yang:counter64;
      description
        "Counts number of dropped packets by counter Z";
    }
    leaf counter_slice15_tx_cgm_sch_uc_drop_pds_counter_sch_uc_drop_pds_cnt {
      type oc-yang:counter64;
      description
        "Counts number of dropped packets by counter Z";
    }
    leaf counter_slice0_tx_cgm_total_drop_counter_total_drop_cnt {
      type oc-yang:counter64;
      description
        "Counts number of dropped in TxCGM only packets";
    }
    leaf counter_slice1_tx_cgm_total_drop_counter_total_drop_cnt {
      type oc-yang:counter64;
      description
        "Counts number of dropped in TxCGM only packets";
    }
    leaf counter_slice2_tx_cgm_total_drop_counter_total_drop_cnt {
      type oc-yang:counter64;
      description
        "Counts number of dropped in TxCGM only packets";
    }
    leaf counter_slice3_tx_cgm_total_drop_counter_total_drop_cnt {
      type oc-yang:counter64;
      description
        "Counts number of dropped in TxCGM only packets";
    }
    leaf counter_slice4_tx_cgm_total_drop_counter_total_drop_cnt {
      type oc-yang:counter64;
      description
        "Counts number of dropped in TxCGM only packets";
    }
    leaf counter_slice5_tx_cgm_total_drop_counter_total_drop_cnt {
      type oc-yang:counter64;
      description
        "Counts number of dropped in TxCGM only packets";
    }
    leaf counter_slice6_tx_cgm_total_drop_counter_total_drop_cnt {
      type oc-yang:counter64;
      description
        "Counts number of dropped in TxCGM only packets";
    }
    leaf counter_slice7_tx_cgm_total_drop_counter_total_drop_cnt {
      type oc-yang:counter64;
      description
        "Counts number of dropped in TxCGM only packets";
    }
    leaf counter_slice8_tx_cgm_total_drop_counter_total_drop_cnt {
      type oc-yang:counter64;
      description
        "Counts number of dropped in TxCGM only packets";
    }
    leaf counter_slice9_tx_cgm_total_drop_counter_total_drop_cnt {
      type oc-yang:counter64;
      description
        "Counts number of dropped in TxCGM only packets";
    }
    leaf counter_slice10_tx_cgm_total_drop_counter_total_drop_cnt {
      type oc-yang:counter64;
      description
        "Counts number of dropped in TxCGM only packets";
    }
    leaf counter_slice11_tx_cgm_total_drop_counter_total_drop_cnt {
      type oc-yang:counter64;
      description
        "Counts number of dropped in TxCGM only packets";
    }
    leaf counter_slice12_tx_cgm_total_drop_counter_total_drop_cnt {
      type oc-yang:counter64;
      description
        "Counts number of dropped in TxCGM only packets";
    }
    leaf counter_slice13_tx_cgm_total_drop_counter_total_drop_cnt {
      type oc-yang:counter64;
      description
        "Counts number of dropped in TxCGM only packets";
    }
    leaf counter_slice14_tx_cgm_total_drop_counter_total_drop_cnt {
      type oc-yang:counter64;
      description
        "Counts number of dropped in TxCGM only packets";
    }
    leaf counter_slice15_tx_cgm_total_drop_counter_total_drop_cnt {
      type oc-yang:counter64;
      description
        "Counts number of dropped in TxCGM only packets";
    }
    leaf counter_slice0_tx_cgm_uc_color_drop_counter0_uc_color_drop_cnt {
      type oc-yang:counter64;
      description
        "nan";
    }
    leaf counter_slice0_tx_cgm_uc_color_drop_counter1_uc_color_drop_cnt {
      type oc-yang:counter64;
      description
        "nan";
    }
    leaf counter_slice0_tx_cgm_uc_color_drop_counter2_uc_color_drop_cnt {
      type oc-yang:counter64;
      description
        "nan";
    }
    leaf counter_slice0_tx_cgm_uc_color_drop_counter3_uc_color_drop_cnt {
      type oc-yang:counter64;
      description
        "nan";
    }
    leaf counter_slice1_tx_cgm_uc_color_drop_counter0_uc_color_drop_cnt {
      type oc-yang:counter64;
      description
        "nan";
    }
    leaf counter_slice1_tx_cgm_uc_color_drop_counter1_uc_color_drop_cnt {
      type oc-yang:counter64;
      description
        "nan";
    }
    leaf counter_slice1_tx_cgm_uc_color_drop_counter2_uc_color_drop_cnt {
      type oc-yang:counter64;
      description
        "nan";
    }
    leaf counter_slice1_tx_cgm_uc_color_drop_counter3_uc_color_drop_cnt {
      type oc-yang:counter64;
      description
        "nan";
    }
    leaf counter_slice2_tx_cgm_uc_color_drop_counter0_uc_color_drop_cnt {
      type oc-yang:counter64;
      description
        "nan";
    }
    leaf counter_slice2_tx_cgm_uc_color_drop_counter1_uc_color_drop_cnt {
      type oc-yang:counter64;
      description
        "nan";
    }
    leaf counter_slice2_tx_cgm_uc_color_drop_counter2_uc_color_drop_cnt {
      type oc-yang:counter64;
      description
        "nan";
    }
    leaf counter_slice2_tx_cgm_uc_color_drop_counter3_uc_color_drop_cnt {
      type oc-yang:counter64;
      description
        "nan";
    }
    leaf counter_slice3_tx_cgm_uc_color_drop_counter0_uc_color_drop_cnt {
      type oc-yang:counter64;
      description
        "nan";
    }
    leaf counter_slice3_tx_cgm_uc_color_drop_counter1_uc_color_drop_cnt {
      type oc-yang:counter64;
      description
        "nan";
    }
    leaf counter_slice3_tx_cgm_uc_color_drop_counter2_uc_color_drop_cnt {
      type oc-yang:counter64;
      description
        "nan";
    }
    leaf counter_slice3_tx_cgm_uc_color_drop_counter3_uc_color_drop_cnt {
      type oc-yang:counter64;
      description
        "nan";
    }
    leaf counter_slice4_tx_cgm_uc_color_drop_counter0_uc_color_drop_cnt {
      type oc-yang:counter64;
      description
        "nan";
    }
    leaf counter_slice4_tx_cgm_uc_color_drop_counter1_uc_color_drop_cnt {
      type oc-yang:counter64;
      description
        "nan";
    }
    leaf counter_slice4_tx_cgm_uc_color_drop_counter2_uc_color_drop_cnt {
      type oc-yang:counter64;
      description
        "nan";
    }
    leaf counter_slice4_tx_cgm_uc_color_drop_counter3_uc_color_drop_cnt {
      type oc-yang:counter64;
      description
        "nan";
    }
    leaf counter_slice5_tx_cgm_uc_color_drop_counter0_uc_color_drop_cnt {
      type oc-yang:counter64;
      description
        "nan";
    }
    leaf counter_slice5_tx_cgm_uc_color_drop_counter1_uc_color_drop_cnt {
      type oc-yang:counter64;
      description
        "nan";
    }
    leaf counter_slice5_tx_cgm_uc_color_drop_counter2_uc_color_drop_cnt {
      type oc-yang:counter64;
      description
        "nan";
    }
    leaf counter_slice5_tx_cgm_uc_color_drop_counter3_uc_color_drop_cnt {
      type oc-yang:counter64;
      description
        "nan";
    }
    leaf counter_slice6_tx_cgm_uc_color_drop_counter0_uc_color_drop_cnt {
      type oc-yang:counter64;
      description
        "nan";
    }
    leaf counter_slice6_tx_cgm_uc_color_drop_counter1_uc_color_drop_cnt {
      type oc-yang:counter64;
      description
        "nan";
    }
    leaf counter_slice6_tx_cgm_uc_color_drop_counter2_uc_color_drop_cnt {
      type oc-yang:counter64;
      description
        "nan";
    }
    leaf counter_slice6_tx_cgm_uc_color_drop_counter3_uc_color_drop_cnt {
      type oc-yang:counter64;
      description
        "nan";
    }
    leaf counter_slice7_tx_cgm_uc_color_drop_counter0_uc_color_drop_cnt {
      type oc-yang:counter64;
      description
        "nan";
    }
    leaf counter_slice7_tx_cgm_uc_color_drop_counter1_uc_color_drop_cnt {
      type oc-yang:counter64;
      description
        "nan";
    }
    leaf counter_slice7_tx_cgm_uc_color_drop_counter2_uc_color_drop_cnt {
      type oc-yang:counter64;
      description
        "nan";
    }
    leaf counter_slice7_tx_cgm_uc_color_drop_counter3_uc_color_drop_cnt {
      type oc-yang:counter64;
      description
        "nan";
    }
    leaf counter_slice8_tx_cgm_uc_color_drop_counter0_uc_color_drop_cnt {
      type oc-yang:counter64;
      description
        "nan";
    }
    leaf counter_slice8_tx_cgm_uc_color_drop_counter1_uc_color_drop_cnt {
      type oc-yang:counter64;
      description
        "nan";
    }
    leaf counter_slice8_tx_cgm_uc_color_drop_counter2_uc_color_drop_cnt {
      type oc-yang:counter64;
      description
        "nan";
    }
    leaf counter_slice8_tx_cgm_uc_color_drop_counter3_uc_color_drop_cnt {
      type oc-yang:counter64;
      description
        "nan";
    }
    leaf counter_slice9_tx_cgm_uc_color_drop_counter0_uc_color_drop_cnt {
      type oc-yang:counter64;
      description
        "nan";
    }
    leaf counter_slice9_tx_cgm_uc_color_drop_counter1_uc_color_drop_cnt {
      type oc-yang:counter64;
      description
        "nan";
    }
    leaf counter_slice9_tx_cgm_uc_color_drop_counter2_uc_color_drop_cnt {
      type oc-yang:counter64;
      description
        "nan";
    }
    leaf counter_slice9_tx_cgm_uc_color_drop_counter3_uc_color_drop_cnt {
      type oc-yang:counter64;
      description
        "nan";
    }
    leaf counter_slice10_tx_cgm_uc_color_drop_counter0_uc_color_drop_cnt {
      type oc-yang:counter64;
      description
        "nan";
    }
    leaf counter_slice10_tx_cgm_uc_color_drop_counter1_uc_color_drop_cnt {
      type oc-yang:counter64;
      description
        "nan";
    }
    leaf counter_slice10_tx_cgm_uc_color_drop_counter2_uc_color_drop_cnt {
      type oc-yang:counter64;
      description
        "nan";
    }
    leaf counter_slice10_tx_cgm_uc_color_drop_counter3_uc_color_drop_cnt {
      type oc-yang:counter64;
      description
        "nan";
    }
    leaf counter_slice11_tx_cgm_uc_color_drop_counter0_uc_color_drop_cnt {
      type oc-yang:counter64;
      description
        "nan";
    }
    leaf counter_slice11_tx_cgm_uc_color_drop_counter1_uc_color_drop_cnt {
      type oc-yang:counter64;
      description
        "nan";
    }
    leaf counter_slice11_tx_cgm_uc_color_drop_counter2_uc_color_drop_cnt {
      type oc-yang:counter64;
      description
        "nan";
    }
    leaf counter_slice11_tx_cgm_uc_color_drop_counter3_uc_color_drop_cnt {
      type oc-yang:counter64;
      description
        "nan";
    }
    leaf counter_slice12_tx_cgm_uc_color_drop_counter0_uc_color_drop_cnt {
      type oc-yang:counter64;
      description
        "nan";
    }
    leaf counter_slice12_tx_cgm_uc_color_drop_counter1_uc_color_drop_cnt {
      type oc-yang:counter64;
      description
        "nan";
    }
    leaf counter_slice12_tx_cgm_uc_color_drop_counter2_uc_color_drop_cnt {
      type oc-yang:counter64;
      description
        "nan";
    }
    leaf counter_slice12_tx_cgm_uc_color_drop_counter3_uc_color_drop_cnt {
      type oc-yang:counter64;
      description
        "nan";
    }
    leaf counter_slice13_tx_cgm_uc_color_drop_counter0_uc_color_drop_cnt {
      type oc-yang:counter64;
      description
        "nan";
    }
    leaf counter_slice13_tx_cgm_uc_color_drop_counter1_uc_color_drop_cnt {
      type oc-yang:counter64;
      description
        "nan";
    }
    leaf counter_slice13_tx_cgm_uc_color_drop_counter2_uc_color_drop_cnt {
      type oc-yang:counter64;
      description
        "nan";
    }
    leaf counter_slice13_tx_cgm_uc_color_drop_counter3_uc_color_drop_cnt {
      type oc-yang:counter64;
      description
        "nan";
    }
    leaf counter_slice14_tx_cgm_uc_color_drop_counter0_uc_color_drop_cnt {
      type oc-yang:counter64;
      description
        "nan";
    }
    leaf counter_slice14_tx_cgm_uc_color_drop_counter1_uc_color_drop_cnt {
      type oc-yang:counter64;
      description
        "nan";
    }
    leaf counter_slice14_tx_cgm_uc_color_drop_counter2_uc_color_drop_cnt {
      type oc-yang:counter64;
      description
        "nan";
    }
    leaf counter_slice14_tx_cgm_uc_color_drop_counter3_uc_color_drop_cnt {
      type oc-yang:counter64;
      description
        "nan";
    }
    leaf counter_slice15_tx_cgm_uc_color_drop_counter0_uc_color_drop_cnt {
      type oc-yang:counter64;
      description
        "nan";
    }
    leaf counter_slice15_tx_cgm_uc_color_drop_counter1_uc_color_drop_cnt {
      type oc-yang:counter64;
      description
        "nan";
    }
    leaf counter_slice15_tx_cgm_uc_color_drop_counter2_uc_color_drop_cnt {
      type oc-yang:counter64;
      description
        "nan";
    }
    leaf counter_slice15_tx_cgm_uc_color_drop_counter3_uc_color_drop_cnt {
      type oc-yang:counter64;
      description
        "nan";
    }
    leaf counter_slice0_tx_cgm_unsch_drop_counter_unsch_drop_cnt {
      type oc-yang:counter64;
      description
        "Counts number of dropped packets by counter W";
    }
    leaf counter_slice1_tx_cgm_unsch_drop_counter_unsch_drop_cnt {
      type oc-yang:counter64;
      description
        "Counts number of dropped packets by counter W";
    }
    leaf counter_slice2_tx_cgm_unsch_drop_counter_unsch_drop_cnt {
      type oc-yang:counter64;
      description
        "Counts number of dropped packets by counter W";
    }
    leaf counter_slice3_tx_cgm_unsch_drop_counter_unsch_drop_cnt {
      type oc-yang:counter64;
      description
        "Counts number of dropped packets by counter W";
    }
    leaf counter_slice4_tx_cgm_unsch_drop_counter_unsch_drop_cnt {
      type oc-yang:counter64;
      description
        "Counts number of dropped packets by counter W";
    }
    leaf counter_slice5_tx_cgm_unsch_drop_counter_unsch_drop_cnt {
      type oc-yang:counter64;
      description
        "Counts number of dropped packets by counter W";
    }
    leaf counter_slice6_tx_cgm_unsch_drop_counter_unsch_drop_cnt {
      type oc-yang:counter64;
      description
        "Counts number of dropped packets by counter W";
    }
    leaf counter_slice7_tx_cgm_unsch_drop_counter_unsch_drop_cnt {
      type oc-yang:counter64;
      description
        "Counts number of dropped packets by counter W";
    }
    leaf counter_slice8_tx_cgm_unsch_drop_counter_unsch_drop_cnt {
      type oc-yang:counter64;
      description
        "Counts number of dropped packets by counter W";
    }
    leaf counter_slice9_tx_cgm_unsch_drop_counter_unsch_drop_cnt {
      type oc-yang:counter64;
      description
        "Counts number of dropped packets by counter W";
    }
    leaf counter_slice10_tx_cgm_unsch_drop_counter_unsch_drop_cnt {
      type oc-yang:counter64;
      description
        "Counts number of dropped packets by counter W";
    }
    leaf counter_slice11_tx_cgm_unsch_drop_counter_unsch_drop_cnt {
      type oc-yang:counter64;
      description
        "Counts number of dropped packets by counter W";
    }
    leaf counter_slice12_tx_cgm_unsch_drop_counter_unsch_drop_cnt {
      type oc-yang:counter64;
      description
        "Counts number of dropped packets by counter W";
    }
    leaf counter_slice13_tx_cgm_unsch_drop_counter_unsch_drop_cnt {
      type oc-yang:counter64;
      description
        "Counts number of dropped packets by counter W";
    }
    leaf counter_slice14_tx_cgm_unsch_drop_counter_unsch_drop_cnt {
      type oc-yang:counter64;
      description
        "Counts number of dropped packets by counter W";
    }
    leaf counter_slice15_tx_cgm_unsch_drop_counter_unsch_drop_cnt {
      type oc-yang:counter64;
      description
        "Counts number of dropped packets by counter W";
    }
    leaf counter_slice0_tx_pdr_txrq_full_drop_counter0_txrq_full_drop_cnt {
      type oc-yang:counter64;
      description
        "Number of dropped packets";
    }
    leaf counter_slice0_tx_pdr_txrq_full_drop_counter1_txrq_full_drop_cnt {
      type oc-yang:counter64;
      description
        "Number of dropped packets";
    }
    leaf counter_slice0_tx_pdr_txrq_full_drop_counter2_txrq_full_drop_cnt {
      type oc-yang:counter64;
      description
        "Number of dropped packets";
    }
    leaf counter_slice0_tx_pdr_txrq_full_drop_counter3_txrq_full_drop_cnt {
      type oc-yang:counter64;
      description
        "Number of dropped packets";
    }
    leaf counter_slice1_tx_pdr_txrq_full_drop_counter0_txrq_full_drop_cnt {
      type oc-yang:counter64;
      description
        "Number of dropped packets";
    }
    leaf counter_slice1_tx_pdr_txrq_full_drop_counter1_txrq_full_drop_cnt {
      type oc-yang:counter64;
      description
        "Number of dropped packets";
    }
    leaf counter_slice1_tx_pdr_txrq_full_drop_counter2_txrq_full_drop_cnt {
      type oc-yang:counter64;
      description
        "Number of dropped packets";
    }
    leaf counter_slice1_tx_pdr_txrq_full_drop_counter3_txrq_full_drop_cnt {
      type oc-yang:counter64;
      description
        "Number of dropped packets";
    }
    leaf counter_slice2_tx_pdr_txrq_full_drop_counter0_txrq_full_drop_cnt {
      type oc-yang:counter64;
      description
        "Number of dropped packets";
    }
    leaf counter_slice2_tx_pdr_txrq_full_drop_counter1_txrq_full_drop_cnt {
      type oc-yang:counter64;
      description
        "Number of dropped packets";
    }
    leaf counter_slice2_tx_pdr_txrq_full_drop_counter2_txrq_full_drop_cnt {
      type oc-yang:counter64;
      description
        "Number of dropped packets";
    }
    leaf counter_slice2_tx_pdr_txrq_full_drop_counter3_txrq_full_drop_cnt {
      type oc-yang:counter64;
      description
        "Number of dropped packets";
    }
    leaf counter_slice3_tx_pdr_txrq_full_drop_counter0_txrq_full_drop_cnt {
      type oc-yang:counter64;
      description
        "Number of dropped packets";
    }
    leaf counter_slice3_tx_pdr_txrq_full_drop_counter1_txrq_full_drop_cnt {
      type oc-yang:counter64;
      description
        "Number of dropped packets";
    }
    leaf counter_slice3_tx_pdr_txrq_full_drop_counter2_txrq_full_drop_cnt {
      type oc-yang:counter64;
      description
        "Number of dropped packets";
    }
    leaf counter_slice3_tx_pdr_txrq_full_drop_counter3_txrq_full_drop_cnt {
      type oc-yang:counter64;
      description
        "Number of dropped packets";
    }
    leaf counter_slice4_tx_pdr_txrq_full_drop_counter0_txrq_full_drop_cnt {
      type oc-yang:counter64;
      description
        "Number of dropped packets";
    }
    leaf counter_slice4_tx_pdr_txrq_full_drop_counter1_txrq_full_drop_cnt {
      type oc-yang:counter64;
      description
        "Number of dropped packets";
    }
    leaf counter_slice4_tx_pdr_txrq_full_drop_counter2_txrq_full_drop_cnt {
      type oc-yang:counter64;
      description
        "Number of dropped packets";
    }
    leaf counter_slice4_tx_pdr_txrq_full_drop_counter3_txrq_full_drop_cnt {
      type oc-yang:counter64;
      description
        "Number of dropped packets";
    }
    leaf counter_slice5_tx_pdr_txrq_full_drop_counter0_txrq_full_drop_cnt {
      type oc-yang:counter64;
      description
        "Number of dropped packets";
    }
    leaf counter_slice5_tx_pdr_txrq_full_drop_counter1_txrq_full_drop_cnt {
      type oc-yang:counter64;
      description
        "Number of dropped packets";
    }
    leaf counter_slice5_tx_pdr_txrq_full_drop_counter2_txrq_full_drop_cnt {
      type oc-yang:counter64;
      description
        "Number of dropped packets";
    }
    leaf counter_slice5_tx_pdr_txrq_full_drop_counter3_txrq_full_drop_cnt {
      type oc-yang:counter64;
      description
        "Number of dropped packets";
    }
    leaf counter_slice6_tx_pdr_txrq_full_drop_counter0_txrq_full_drop_cnt {
      type oc-yang:counter64;
      description
        "Number of dropped packets";
    }
    leaf counter_slice6_tx_pdr_txrq_full_drop_counter1_txrq_full_drop_cnt {
      type oc-yang:counter64;
      description
        "Number of dropped packets";
    }
    leaf counter_slice6_tx_pdr_txrq_full_drop_counter2_txrq_full_drop_cnt {
      type oc-yang:counter64;
      description
        "Number of dropped packets";
    }
    leaf counter_slice6_tx_pdr_txrq_full_drop_counter3_txrq_full_drop_cnt {
      type oc-yang:counter64;
      description
        "Number of dropped packets";
    }
    leaf counter_slice7_tx_pdr_txrq_full_drop_counter0_txrq_full_drop_cnt {
      type oc-yang:counter64;
      description
        "Number of dropped packets";
    }
    leaf counter_slice7_tx_pdr_txrq_full_drop_counter1_txrq_full_drop_cnt {
      type oc-yang:counter64;
      description
        "Number of dropped packets";
    }
    leaf counter_slice7_tx_pdr_txrq_full_drop_counter2_txrq_full_drop_cnt {
      type oc-yang:counter64;
      description
        "Number of dropped packets";
    }
    leaf counter_slice7_tx_pdr_txrq_full_drop_counter3_txrq_full_drop_cnt {
      type oc-yang:counter64;
      description
        "Number of dropped packets";
    }
    leaf counter_slice8_tx_pdr_txrq_full_drop_counter0_txrq_full_drop_cnt {
      type oc-yang:counter64;
      description
        "Number of dropped packets";
    }
    leaf counter_slice8_tx_pdr_txrq_full_drop_counter1_txrq_full_drop_cnt {
      type oc-yang:counter64;
      description
        "Number of dropped packets";
    }
    leaf counter_slice8_tx_pdr_txrq_full_drop_counter2_txrq_full_drop_cnt {
      type oc-yang:counter64;
      description
        "Number of dropped packets";
    }
    leaf counter_slice8_tx_pdr_txrq_full_drop_counter3_txrq_full_drop_cnt {
      type oc-yang:counter64;
      description
        "Number of dropped packets";
    }
    leaf counter_slice9_tx_pdr_txrq_full_drop_counter0_txrq_full_drop_cnt {
      type oc-yang:counter64;
      description
        "Number of dropped packets";
    }
    leaf counter_slice9_tx_pdr_txrq_full_drop_counter1_txrq_full_drop_cnt {
      type oc-yang:counter64;
      description
        "Number of dropped packets";
    }
    leaf counter_slice9_tx_pdr_txrq_full_drop_counter2_txrq_full_drop_cnt {
      type oc-yang:counter64;
      description
        "Number of dropped packets";
    }
    leaf counter_slice9_tx_pdr_txrq_full_drop_counter3_txrq_full_drop_cnt {
      type oc-yang:counter64;
      description
        "Number of dropped packets";
    }
    leaf counter_slice10_tx_pdr_txrq_full_drop_counter0_txrq_full_drop_cnt {
      type oc-yang:counter64;
      description
        "Number of dropped packets";
    }
    leaf counter_slice10_tx_pdr_txrq_full_drop_counter1_txrq_full_drop_cnt {
      type oc-yang:counter64;
      description
        "Number of dropped packets";
    }
    leaf counter_slice10_tx_pdr_txrq_full_drop_counter2_txrq_full_drop_cnt {
      type oc-yang:counter64;
      description
        "Number of dropped packets";
    }
    leaf counter_slice10_tx_pdr_txrq_full_drop_counter3_txrq_full_drop_cnt {
      type oc-yang:counter64;
      description
        "Number of dropped packets";
    }
    leaf counter_slice11_tx_pdr_txrq_full_drop_counter0_txrq_full_drop_cnt {
      type oc-yang:counter64;
      description
        "Number of dropped packets";
    }
    leaf counter_slice11_tx_pdr_txrq_full_drop_counter1_txrq_full_drop_cnt {
      type oc-yang:counter64;
      description
        "Number of dropped packets";
    }
    leaf counter_slice11_tx_pdr_txrq_full_drop_counter2_txrq_full_drop_cnt {
      type oc-yang:counter64;
      description
        "Number of dropped packets";
    }
    leaf counter_slice11_tx_pdr_txrq_full_drop_counter3_txrq_full_drop_cnt {
      type oc-yang:counter64;
      description
        "Number of dropped packets";
    }
    leaf counter_slice12_tx_pdr_txrq_full_drop_counter0_txrq_full_drop_cnt {
      type oc-yang:counter64;
      description
        "Number of dropped packets";
    }
    leaf counter_slice12_tx_pdr_txrq_full_drop_counter1_txrq_full_drop_cnt {
      type oc-yang:counter64;
      description
        "Number of dropped packets";
    }
    leaf counter_slice12_tx_pdr_txrq_full_drop_counter2_txrq_full_drop_cnt {
      type oc-yang:counter64;
      description
        "Number of dropped packets";
    }
    leaf counter_slice12_tx_pdr_txrq_full_drop_counter3_txrq_full_drop_cnt {
      type oc-yang:counter64;
      description
        "Number of dropped packets";
    }
    leaf counter_slice13_tx_pdr_txrq_full_drop_counter0_txrq_full_drop_cnt {
      type oc-yang:counter64;
      description
        "Number of dropped packets";
    }
    leaf counter_slice13_tx_pdr_txrq_full_drop_counter1_txrq_full_drop_cnt {
      type oc-yang:counter64;
      description
        "Number of dropped packets";
    }
    leaf counter_slice13_tx_pdr_txrq_full_drop_counter2_txrq_full_drop_cnt {
      type oc-yang:counter64;
      description
        "Number of dropped packets";
    }
    leaf counter_slice13_tx_pdr_txrq_full_drop_counter3_txrq_full_drop_cnt {
      type oc-yang:counter64;
      description
        "Number of dropped packets";
    }
    leaf counter_slice14_tx_pdr_txrq_full_drop_counter0_txrq_full_drop_cnt {
      type oc-yang:counter64;
      description
        "Number of dropped packets";
    }
    leaf counter_slice14_tx_pdr_txrq_full_drop_counter1_txrq_full_drop_cnt {
      type oc-yang:counter64;
      description
        "Number of dropped packets";
    }
    leaf counter_slice14_tx_pdr_txrq_full_drop_counter2_txrq_full_drop_cnt {
      type oc-yang:counter64;
      description
        "Number of dropped packets";
    }
    leaf counter_slice14_tx_pdr_txrq_full_drop_counter3_txrq_full_drop_cnt {
      type oc-yang:counter64;
      description
        "Number of dropped packets";
    }
    leaf counter_slice15_tx_pdr_txrq_full_drop_counter0_txrq_full_drop_cnt {
      type oc-yang:counter64;
      description
        "Number of dropped packets";
    }
    leaf counter_slice15_tx_pdr_txrq_full_drop_counter1_txrq_full_drop_cnt {
      type oc-yang:counter64;
      description
        "Number of dropped packets";
    }
    leaf counter_slice15_tx_pdr_txrq_full_drop_counter2_txrq_full_drop_cnt {
      type oc-yang:counter64;
      description
        "Number of dropped packets";
    }
    leaf counter_slice15_tx_pdr_txrq_full_drop_counter3_txrq_full_drop_cnt {
      type oc-yang:counter64;
      description
        "Number of dropped packets";
    }
    leaf counter_slice0_tx_pdr_txrq_full_total_drop_counter_txrq_full_total_drop_cnt {
      type oc-yang:counter64;
      description
        "Number of dropped packets";
    }
    leaf counter_slice1_tx_pdr_txrq_full_total_drop_counter_txrq_full_total_drop_cnt {
      type oc-yang:counter64;
      description
        "Number of dropped packets";
    }
    leaf counter_slice2_tx_pdr_txrq_full_total_drop_counter_txrq_full_total_drop_cnt {
      type oc-yang:counter64;
      description
        "Number of dropped packets";
    }
    leaf counter_slice3_tx_pdr_txrq_full_total_drop_counter_txrq_full_total_drop_cnt {
      type oc-yang:counter64;
      description
        "Number of dropped packets";
    }
    leaf counter_slice4_tx_pdr_txrq_full_total_drop_counter_txrq_full_total_drop_cnt {
      type oc-yang:counter64;
      description
        "Number of dropped packets";
    }
    leaf counter_slice5_tx_pdr_txrq_full_total_drop_counter_txrq_full_total_drop_cnt {
      type oc-yang:counter64;
      description
        "Number of dropped packets";
    }
    leaf counter_slice6_tx_pdr_txrq_full_total_drop_counter_txrq_full_total_drop_cnt {
      type oc-yang:counter64;
      description
        "Number of dropped packets";
    }
    leaf counter_slice7_tx_pdr_txrq_full_total_drop_counter_txrq_full_total_drop_cnt {
      type oc-yang:counter64;
      description
        "Number of dropped packets";
    }
    leaf counter_slice8_tx_pdr_txrq_full_total_drop_counter_txrq_full_total_drop_cnt {
      type oc-yang:counter64;
      description
        "Number of dropped packets";
    }
    leaf counter_slice9_tx_pdr_txrq_full_total_drop_counter_txrq_full_total_drop_cnt {
      type oc-yang:counter64;
      description
        "Number of dropped packets";
    }
    leaf counter_slice10_tx_pdr_txrq_full_total_drop_counter_txrq_full_total_drop_cnt {
      type oc-yang:counter64;
      description
        "Number of dropped packets";
    }
    leaf counter_slice11_tx_pdr_txrq_full_total_drop_counter_txrq_full_total_drop_cnt {
      type oc-yang:counter64;
      description
        "Number of dropped packets";
    }
    leaf counter_slice12_tx_pdr_txrq_full_total_drop_counter_txrq_full_total_drop_cnt {
      type oc-yang:counter64;
      description
        "Number of dropped packets";
    }
    leaf counter_slice13_tx_pdr_txrq_full_total_drop_counter_txrq_full_total_drop_cnt {
      type oc-yang:counter64;
      description
        "Number of dropped packets";
    }
    leaf counter_slice14_tx_pdr_txrq_full_total_drop_counter_txrq_full_total_drop_cnt {
      type oc-yang:counter64;
      description
        "Number of dropped packets";
    }
    leaf counter_slice15_tx_pdr_txrq_full_total_drop_counter_txrq_full_total_drop_cnt {
      type oc-yang:counter64;
      description
        "Number of dropped packets";
    }
    leaf counter_slice0_tx_pdr_txrq_th0_drop_counter0_txrq_th0_deq_drop_cnt {
      type oc-yang:counter64;
      description
        "Number of dropped packets in TXRQ deq";
    }
    leaf counter_slice0_tx_pdr_txrq_th0_drop_counter1_txrq_th0_deq_drop_cnt {
      type oc-yang:counter64;
      description
        "Number of dropped packets in TXRQ deq";
    }
    leaf counter_slice0_tx_pdr_txrq_th0_drop_counter2_txrq_th0_deq_drop_cnt {
      type oc-yang:counter64;
      description
        "Number of dropped packets in TXRQ deq";
    }
    leaf counter_slice0_tx_pdr_txrq_th0_drop_counter3_txrq_th0_deq_drop_cnt {
      type oc-yang:counter64;
      description
        "Number of dropped packets in TXRQ deq";
    }
    leaf counter_slice1_tx_pdr_txrq_th0_drop_counter0_txrq_th0_deq_drop_cnt {
      type oc-yang:counter64;
      description
        "Number of dropped packets in TXRQ deq";
    }
    leaf counter_slice1_tx_pdr_txrq_th0_drop_counter1_txrq_th0_deq_drop_cnt {
      type oc-yang:counter64;
      description
        "Number of dropped packets in TXRQ deq";
    }
    leaf counter_slice1_tx_pdr_txrq_th0_drop_counter2_txrq_th0_deq_drop_cnt {
      type oc-yang:counter64;
      description
        "Number of dropped packets in TXRQ deq";
    }
    leaf counter_slice1_tx_pdr_txrq_th0_drop_counter3_txrq_th0_deq_drop_cnt {
      type oc-yang:counter64;
      description
        "Number of dropped packets in TXRQ deq";
    }
    leaf counter_slice2_tx_pdr_txrq_th0_drop_counter0_txrq_th0_deq_drop_cnt {
      type oc-yang:counter64;
      description
        "Number of dropped packets in TXRQ deq";
    }
    leaf counter_slice2_tx_pdr_txrq_th0_drop_counter1_txrq_th0_deq_drop_cnt {
      type oc-yang:counter64;
      description
        "Number of dropped packets in TXRQ deq";
    }
    leaf counter_slice2_tx_pdr_txrq_th0_drop_counter2_txrq_th0_deq_drop_cnt {
      type oc-yang:counter64;
      description
        "Number of dropped packets in TXRQ deq";
    }
    leaf counter_slice2_tx_pdr_txrq_th0_drop_counter3_txrq_th0_deq_drop_cnt {
      type oc-yang:counter64;
      description
        "Number of dropped packets in TXRQ deq";
    }
    leaf counter_slice3_tx_pdr_txrq_th0_drop_counter0_txrq_th0_deq_drop_cnt {
      type oc-yang:counter64;
      description
        "Number of dropped packets in TXRQ deq";
    }
    leaf counter_slice3_tx_pdr_txrq_th0_drop_counter1_txrq_th0_deq_drop_cnt {
      type oc-yang:counter64;
      description
        "Number of dropped packets in TXRQ deq";
    }
    leaf counter_slice3_tx_pdr_txrq_th0_drop_counter2_txrq_th0_deq_drop_cnt {
      type oc-yang:counter64;
      description
        "Number of dropped packets in TXRQ deq";
    }
    leaf counter_slice3_tx_pdr_txrq_th0_drop_counter3_txrq_th0_deq_drop_cnt {
      type oc-yang:counter64;
      description
        "Number of dropped packets in TXRQ deq";
    }
    leaf counter_slice4_tx_pdr_txrq_th0_drop_counter0_txrq_th0_deq_drop_cnt {
      type oc-yang:counter64;
      description
        "Number of dropped packets in TXRQ deq";
    }
    leaf counter_slice4_tx_pdr_txrq_th0_drop_counter1_txrq_th0_deq_drop_cnt {
      type oc-yang:counter64;
      description
        "Number of dropped packets in TXRQ deq";
    }
    leaf counter_slice4_tx_pdr_txrq_th0_drop_counter2_txrq_th0_deq_drop_cnt {
      type oc-yang:counter64;
      description
        "Number of dropped packets in TXRQ deq";
    }
    leaf counter_slice4_tx_pdr_txrq_th0_drop_counter3_txrq_th0_deq_drop_cnt {
      type oc-yang:counter64;
      description
        "Number of dropped packets in TXRQ deq";
    }
    leaf counter_slice5_tx_pdr_txrq_th0_drop_counter0_txrq_th0_deq_drop_cnt {
      type oc-yang:counter64;
      description
        "Number of dropped packets in TXRQ deq";
    }
    leaf counter_slice5_tx_pdr_txrq_th0_drop_counter1_txrq_th0_deq_drop_cnt {
      type oc-yang:counter64;
      description
        "Number of dropped packets in TXRQ deq";
    }
    leaf counter_slice5_tx_pdr_txrq_th0_drop_counter2_txrq_th0_deq_drop_cnt {
      type oc-yang:counter64;
      description
        "Number of dropped packets in TXRQ deq";
    }
    leaf counter_slice5_tx_pdr_txrq_th0_drop_counter3_txrq_th0_deq_drop_cnt {
      type oc-yang:counter64;
      description
        "Number of dropped packets in TXRQ deq";
    }
    leaf counter_slice6_tx_pdr_txrq_th0_drop_counter0_txrq_th0_deq_drop_cnt {
      type oc-yang:counter64;
      description
        "Number of dropped packets in TXRQ deq";
    }
    leaf counter_slice6_tx_pdr_txrq_th0_drop_counter1_txrq_th0_deq_drop_cnt {
      type oc-yang:counter64;
      description
        "Number of dropped packets in TXRQ deq";
    }
    leaf counter_slice6_tx_pdr_txrq_th0_drop_counter2_txrq_th0_deq_drop_cnt {
      type oc-yang:counter64;
      description
        "Number of dropped packets in TXRQ deq";
    }
    leaf counter_slice6_tx_pdr_txrq_th0_drop_counter3_txrq_th0_deq_drop_cnt {
      type oc-yang:counter64;
      description
        "Number of dropped packets in TXRQ deq";
    }
    leaf counter_slice7_tx_pdr_txrq_th0_drop_counter0_txrq_th0_deq_drop_cnt {
      type oc-yang:counter64;
      description
        "Number of dropped packets in TXRQ deq";
    }
    leaf counter_slice7_tx_pdr_txrq_th0_drop_counter1_txrq_th0_deq_drop_cnt {
      type oc-yang:counter64;
      description
        "Number of dropped packets in TXRQ deq";
    }
    leaf counter_slice7_tx_pdr_txrq_th0_drop_counter2_txrq_th0_deq_drop_cnt {
      type oc-yang:counter64;
      description
        "Number of dropped packets in TXRQ deq";
    }
    leaf counter_slice7_tx_pdr_txrq_th0_drop_counter3_txrq_th0_deq_drop_cnt {
      type oc-yang:counter64;
      description
        "Number of dropped packets in TXRQ deq";
    }
    leaf counter_slice8_tx_pdr_txrq_th0_drop_counter0_txrq_th0_deq_drop_cnt {
      type oc-yang:counter64;
      description
        "Number of dropped packets in TXRQ deq";
    }
    leaf counter_slice8_tx_pdr_txrq_th0_drop_counter1_txrq_th0_deq_drop_cnt {
      type oc-yang:counter64;
      description
        "Number of dropped packets in TXRQ deq";
    }
    leaf counter_slice8_tx_pdr_txrq_th0_drop_counter2_txrq_th0_deq_drop_cnt {
      type oc-yang:counter64;
      description
        "Number of dropped packets in TXRQ deq";
    }
    leaf counter_slice8_tx_pdr_txrq_th0_drop_counter3_txrq_th0_deq_drop_cnt {
      type oc-yang:counter64;
      description
        "Number of dropped packets in TXRQ deq";
    }
    leaf counter_slice9_tx_pdr_txrq_th0_drop_counter0_txrq_th0_deq_drop_cnt {
      type oc-yang:counter64;
      description
        "Number of dropped packets in TXRQ deq";
    }
    leaf counter_slice9_tx_pdr_txrq_th0_drop_counter1_txrq_th0_deq_drop_cnt {
      type oc-yang:counter64;
      description
        "Number of dropped packets in TXRQ deq";
    }
    leaf counter_slice9_tx_pdr_txrq_th0_drop_counter2_txrq_th0_deq_drop_cnt {
      type oc-yang:counter64;
      description
        "Number of dropped packets in TXRQ deq";
    }
    leaf counter_slice9_tx_pdr_txrq_th0_drop_counter3_txrq_th0_deq_drop_cnt {
      type oc-yang:counter64;
      description
        "Number of dropped packets in TXRQ deq";
    }
    leaf counter_slice10_tx_pdr_txrq_th0_drop_counter0_txrq_th0_deq_drop_cnt {
      type oc-yang:counter64;
      description
        "Number of dropped packets in TXRQ deq";
    }
    leaf counter_slice10_tx_pdr_txrq_th0_drop_counter1_txrq_th0_deq_drop_cnt {
      type oc-yang:counter64;
      description
        "Number of dropped packets in TXRQ deq";
    }
    leaf counter_slice10_tx_pdr_txrq_th0_drop_counter2_txrq_th0_deq_drop_cnt {
      type oc-yang:counter64;
      description
        "Number of dropped packets in TXRQ deq";
    }
    leaf counter_slice10_tx_pdr_txrq_th0_drop_counter3_txrq_th0_deq_drop_cnt {
      type oc-yang:counter64;
      description
        "Number of dropped packets in TXRQ deq";
    }
    leaf counter_slice11_tx_pdr_txrq_th0_drop_counter0_txrq_th0_deq_drop_cnt {
      type oc-yang:counter64;
      description
        "Number of dropped packets in TXRQ deq";
    }
    leaf counter_slice11_tx_pdr_txrq_th0_drop_counter1_txrq_th0_deq_drop_cnt {
      type oc-yang:counter64;
      description
        "Number of dropped packets in TXRQ deq";
    }
    leaf counter_slice11_tx_pdr_txrq_th0_drop_counter2_txrq_th0_deq_drop_cnt {
      type oc-yang:counter64;
      description
        "Number of dropped packets in TXRQ deq";
    }
    leaf counter_slice11_tx_pdr_txrq_th0_drop_counter3_txrq_th0_deq_drop_cnt {
      type oc-yang:counter64;
      description
        "Number of dropped packets in TXRQ deq";
    }
    leaf counter_slice12_tx_pdr_txrq_th0_drop_counter0_txrq_th0_deq_drop_cnt {
      type oc-yang:counter64;
      description
        "Number of dropped packets in TXRQ deq";
    }
    leaf counter_slice12_tx_pdr_txrq_th0_drop_counter1_txrq_th0_deq_drop_cnt {
      type oc-yang:counter64;
      description
        "Number of dropped packets in TXRQ deq";
    }
    leaf counter_slice12_tx_pdr_txrq_th0_drop_counter2_txrq_th0_deq_drop_cnt {
      type oc-yang:counter64;
      description
        "Number of dropped packets in TXRQ deq";
    }
    leaf counter_slice12_tx_pdr_txrq_th0_drop_counter3_txrq_th0_deq_drop_cnt {
      type oc-yang:counter64;
      description
        "Number of dropped packets in TXRQ deq";
    }
    leaf counter_slice13_tx_pdr_txrq_th0_drop_counter0_txrq_th0_deq_drop_cnt {
      type oc-yang:counter64;
      description
        "Number of dropped packets in TXRQ deq";
    }
    leaf counter_slice13_tx_pdr_txrq_th0_drop_counter1_txrq_th0_deq_drop_cnt {
      type oc-yang:counter64;
      description
        "Number of dropped packets in TXRQ deq";
    }
    leaf counter_slice13_tx_pdr_txrq_th0_drop_counter2_txrq_th0_deq_drop_cnt {
      type oc-yang:counter64;
      description
        "Number of dropped packets in TXRQ deq";
    }
    leaf counter_slice13_tx_pdr_txrq_th0_drop_counter3_txrq_th0_deq_drop_cnt {
      type oc-yang:counter64;
      description
        "Number of dropped packets in TXRQ deq";
    }
    leaf counter_slice14_tx_pdr_txrq_th0_drop_counter0_txrq_th0_deq_drop_cnt {
      type oc-yang:counter64;
      description
        "Number of dropped packets in TXRQ deq";
    }
    leaf counter_slice14_tx_pdr_txrq_th0_drop_counter1_txrq_th0_deq_drop_cnt {
      type oc-yang:counter64;
      description
        "Number of dropped packets in TXRQ deq";
    }
    leaf counter_slice14_tx_pdr_txrq_th0_drop_counter2_txrq_th0_deq_drop_cnt {
      type oc-yang:counter64;
      description
        "Number of dropped packets in TXRQ deq";
    }
    leaf counter_slice14_tx_pdr_txrq_th0_drop_counter3_txrq_th0_deq_drop_cnt {
      type oc-yang:counter64;
      description
        "Number of dropped packets in TXRQ deq";
    }
    leaf counter_slice15_tx_pdr_txrq_th0_drop_counter0_txrq_th0_deq_drop_cnt {
      type oc-yang:counter64;
      description
        "Number of dropped packets in TXRQ deq";
    }
    leaf counter_slice15_tx_pdr_txrq_th0_drop_counter1_txrq_th0_deq_drop_cnt {
      type oc-yang:counter64;
      description
        "Number of dropped packets in TXRQ deq";
    }
    leaf counter_slice15_tx_pdr_txrq_th0_drop_counter2_txrq_th0_deq_drop_cnt {
      type oc-yang:counter64;
      description
        "Number of dropped packets in TXRQ deq";
    }
    leaf counter_slice15_tx_pdr_txrq_th0_drop_counter3_txrq_th0_deq_drop_cnt {
      type oc-yang:counter64;
      description
        "Number of dropped packets in TXRQ deq";
    }
    leaf counter_slice0_tx_pdr_txrq_th0_drop_counter0_txrq_th0_drop_cnt {
      type oc-yang:counter64;
      description
        "Number of dropped packets in TXRQ enq";
    }
    leaf counter_slice0_tx_pdr_txrq_th0_drop_counter1_txrq_th0_drop_cnt {
      type oc-yang:counter64;
      description
        "Number of dropped packets in TXRQ enq";
    }
    leaf counter_slice0_tx_pdr_txrq_th0_drop_counter2_txrq_th0_drop_cnt {
      type oc-yang:counter64;
      description
        "Number of dropped packets in TXRQ enq";
    }
    leaf counter_slice0_tx_pdr_txrq_th0_drop_counter3_txrq_th0_drop_cnt {
      type oc-yang:counter64;
      description
        "Number of dropped packets in TXRQ enq";
    }
    leaf counter_slice1_tx_pdr_txrq_th0_drop_counter0_txrq_th0_drop_cnt {
      type oc-yang:counter64;
      description
        "Number of dropped packets in TXRQ enq";
    }
    leaf counter_slice1_tx_pdr_txrq_th0_drop_counter1_txrq_th0_drop_cnt {
      type oc-yang:counter64;
      description
        "Number of dropped packets in TXRQ enq";
    }
    leaf counter_slice1_tx_pdr_txrq_th0_drop_counter2_txrq_th0_drop_cnt {
      type oc-yang:counter64;
      description
        "Number of dropped packets in TXRQ enq";
    }
    leaf counter_slice1_tx_pdr_txrq_th0_drop_counter3_txrq_th0_drop_cnt {
      type oc-yang:counter64;
      description
        "Number of dropped packets in TXRQ enq";
    }
    leaf counter_slice2_tx_pdr_txrq_th0_drop_counter0_txrq_th0_drop_cnt {
      type oc-yang:counter64;
      description
        "Number of dropped packets in TXRQ enq";
    }
    leaf counter_slice2_tx_pdr_txrq_th0_drop_counter1_txrq_th0_drop_cnt {
      type oc-yang:counter64;
      description
        "Number of dropped packets in TXRQ enq";
    }
    leaf counter_slice2_tx_pdr_txrq_th0_drop_counter2_txrq_th0_drop_cnt {
      type oc-yang:counter64;
      description
        "Number of dropped packets in TXRQ enq";
    }
    leaf counter_slice2_tx_pdr_txrq_th0_drop_counter3_txrq_th0_drop_cnt {
      type oc-yang:counter64;
      description
        "Number of dropped packets in TXRQ enq";
    }
    leaf counter_slice3_tx_pdr_txrq_th0_drop_counter0_txrq_th0_drop_cnt {
      type oc-yang:counter64;
      description
        "Number of dropped packets in TXRQ enq";
    }
    leaf counter_slice3_tx_pdr_txrq_th0_drop_counter1_txrq_th0_drop_cnt {
      type oc-yang:counter64;
      description
        "Number of dropped packets in TXRQ enq";
    }
    leaf counter_slice3_tx_pdr_txrq_th0_drop_counter2_txrq_th0_drop_cnt {
      type oc-yang:counter64;
      description
        "Number of dropped packets in TXRQ enq";
    }
    leaf counter_slice3_tx_pdr_txrq_th0_drop_counter3_txrq_th0_drop_cnt {
      type oc-yang:counter64;
      description
        "Number of dropped packets in TXRQ enq";
    }
    leaf counter_slice4_tx_pdr_txrq_th0_drop_counter0_txrq_th0_drop_cnt {
      type oc-yang:counter64;
      description
        "Number of dropped packets in TXRQ enq";
    }
    leaf counter_slice4_tx_pdr_txrq_th0_drop_counter1_txrq_th0_drop_cnt {
      type oc-yang:counter64;
      description
        "Number of dropped packets in TXRQ enq";
    }
    leaf counter_slice4_tx_pdr_txrq_th0_drop_counter2_txrq_th0_drop_cnt {
      type oc-yang:counter64;
      description
        "Number of dropped packets in TXRQ enq";
    }
    leaf counter_slice4_tx_pdr_txrq_th0_drop_counter3_txrq_th0_drop_cnt {
      type oc-yang:counter64;
      description
        "Number of dropped packets in TXRQ enq";
    }
    leaf counter_slice5_tx_pdr_txrq_th0_drop_counter0_txrq_th0_drop_cnt {
      type oc-yang:counter64;
      description
        "Number of dropped packets in TXRQ enq";
    }
    leaf counter_slice5_tx_pdr_txrq_th0_drop_counter1_txrq_th0_drop_cnt {
      type oc-yang:counter64;
      description
        "Number of dropped packets in TXRQ enq";
    }
    leaf counter_slice5_tx_pdr_txrq_th0_drop_counter2_txrq_th0_drop_cnt {
      type oc-yang:counter64;
      description
        "Number of dropped packets in TXRQ enq";
    }
    leaf counter_slice5_tx_pdr_txrq_th0_drop_counter3_txrq_th0_drop_cnt {
      type oc-yang:counter64;
      description
        "Number of dropped packets in TXRQ enq";
    }
    leaf counter_slice6_tx_pdr_txrq_th0_drop_counter0_txrq_th0_drop_cnt {
      type oc-yang:counter64;
      description
        "Number of dropped packets in TXRQ enq";
    }
    leaf counter_slice6_tx_pdr_txrq_th0_drop_counter1_txrq_th0_drop_cnt {
      type oc-yang:counter64;
      description
        "Number of dropped packets in TXRQ enq";
    }
    leaf counter_slice6_tx_pdr_txrq_th0_drop_counter2_txrq_th0_drop_cnt {
      type oc-yang:counter64;
      description
        "Number of dropped packets in TXRQ enq";
    }
    leaf counter_slice6_tx_pdr_txrq_th0_drop_counter3_txrq_th0_drop_cnt {
      type oc-yang:counter64;
      description
        "Number of dropped packets in TXRQ enq";
    }
    leaf counter_slice7_tx_pdr_txrq_th0_drop_counter0_txrq_th0_drop_cnt {
      type oc-yang:counter64;
      description
        "Number of dropped packets in TXRQ enq";
    }
    leaf counter_slice7_tx_pdr_txrq_th0_drop_counter1_txrq_th0_drop_cnt {
      type oc-yang:counter64;
      description
        "Number of dropped packets in TXRQ enq";
    }
    leaf counter_slice7_tx_pdr_txrq_th0_drop_counter2_txrq_th0_drop_cnt {
      type oc-yang:counter64;
      description
        "Number of dropped packets in TXRQ enq";
    }
    leaf counter_slice7_tx_pdr_txrq_th0_drop_counter3_txrq_th0_drop_cnt {
      type oc-yang:counter64;
      description
        "Number of dropped packets in TXRQ enq";
    }
    leaf counter_slice8_tx_pdr_txrq_th0_drop_counter0_txrq_th0_drop_cnt {
      type oc-yang:counter64;
      description
        "Number of dropped packets in TXRQ enq";
    }
    leaf counter_slice8_tx_pdr_txrq_th0_drop_counter1_txrq_th0_drop_cnt {
      type oc-yang:counter64;
      description
        "Number of dropped packets in TXRQ enq";
    }
    leaf counter_slice8_tx_pdr_txrq_th0_drop_counter2_txrq_th0_drop_cnt {
      type oc-yang:counter64;
      description
        "Number of dropped packets in TXRQ enq";
    }
    leaf counter_slice8_tx_pdr_txrq_th0_drop_counter3_txrq_th0_drop_cnt {
      type oc-yang:counter64;
      description
        "Number of dropped packets in TXRQ enq";
    }
    leaf counter_slice9_tx_pdr_txrq_th0_drop_counter0_txrq_th0_drop_cnt {
      type oc-yang:counter64;
      description
        "Number of dropped packets in TXRQ enq";
    }
    leaf counter_slice9_tx_pdr_txrq_th0_drop_counter1_txrq_th0_drop_cnt {
      type oc-yang:counter64;
      description
        "Number of dropped packets in TXRQ enq";
    }
    leaf counter_slice9_tx_pdr_txrq_th0_drop_counter2_txrq_th0_drop_cnt {
      type oc-yang:counter64;
      description
        "Number of dropped packets in TXRQ enq";
    }
    leaf counter_slice9_tx_pdr_txrq_th0_drop_counter3_txrq_th0_drop_cnt {
      type oc-yang:counter64;
      description
        "Number of dropped packets in TXRQ enq";
    }
    leaf counter_slice10_tx_pdr_txrq_th0_drop_counter0_txrq_th0_drop_cnt {
      type oc-yang:counter64;
      description
        "Number of dropped packets in TXRQ enq";
    }
    leaf counter_slice10_tx_pdr_txrq_th0_drop_counter1_txrq_th0_drop_cnt {
      type oc-yang:counter64;
      description
        "Number of dropped packets in TXRQ enq";
    }
    leaf counter_slice10_tx_pdr_txrq_th0_drop_counter2_txrq_th0_drop_cnt {
      type oc-yang:counter64;
      description
        "Number of dropped packets in TXRQ enq";
    }
    leaf counter_slice10_tx_pdr_txrq_th0_drop_counter3_txrq_th0_drop_cnt {
      type oc-yang:counter64;
      description
        "Number of dropped packets in TXRQ enq";
    }
    leaf counter_slice11_tx_pdr_txrq_th0_drop_counter0_txrq_th0_drop_cnt {
      type oc-yang:counter64;
      description
        "Number of dropped packets in TXRQ enq";
    }
    leaf counter_slice11_tx_pdr_txrq_th0_drop_counter1_txrq_th0_drop_cnt {
      type oc-yang:counter64;
      description
        "Number of dropped packets in TXRQ enq";
    }
    leaf counter_slice11_tx_pdr_txrq_th0_drop_counter2_txrq_th0_drop_cnt {
      type oc-yang:counter64;
      description
        "Number of dropped packets in TXRQ enq";
    }
    leaf counter_slice11_tx_pdr_txrq_th0_drop_counter3_txrq_th0_drop_cnt {
      type oc-yang:counter64;
      description
        "Number of dropped packets in TXRQ enq";
    }
    leaf counter_slice12_tx_pdr_txrq_th0_drop_counter0_txrq_th0_drop_cnt {
      type oc-yang:counter64;
      description
        "Number of dropped packets in TXRQ enq";
    }
    leaf counter_slice12_tx_pdr_txrq_th0_drop_counter1_txrq_th0_drop_cnt {
      type oc-yang:counter64;
      description
        "Number of dropped packets in TXRQ enq";
    }
    leaf counter_slice12_tx_pdr_txrq_th0_drop_counter2_txrq_th0_drop_cnt {
      type oc-yang:counter64;
      description
        "Number of dropped packets in TXRQ enq";
    }
    leaf counter_slice12_tx_pdr_txrq_th0_drop_counter3_txrq_th0_drop_cnt {
      type oc-yang:counter64;
      description
        "Number of dropped packets in TXRQ enq";
    }
    leaf counter_slice13_tx_pdr_txrq_th0_drop_counter0_txrq_th0_drop_cnt {
      type oc-yang:counter64;
      description
        "Number of dropped packets in TXRQ enq";
    }
    leaf counter_slice13_tx_pdr_txrq_th0_drop_counter1_txrq_th0_drop_cnt {
      type oc-yang:counter64;
      description
        "Number of dropped packets in TXRQ enq";
    }
    leaf counter_slice13_tx_pdr_txrq_th0_drop_counter2_txrq_th0_drop_cnt {
      type oc-yang:counter64;
      description
        "Number of dropped packets in TXRQ enq";
    }
    leaf counter_slice13_tx_pdr_txrq_th0_drop_counter3_txrq_th0_drop_cnt {
      type oc-yang:counter64;
      description
        "Number of dropped packets in TXRQ enq";
    }
    leaf counter_slice14_tx_pdr_txrq_th0_drop_counter0_txrq_th0_drop_cnt {
      type oc-yang:counter64;
      description
        "Number of dropped packets in TXRQ enq";
    }
    leaf counter_slice14_tx_pdr_txrq_th0_drop_counter1_txrq_th0_drop_cnt {
      type oc-yang:counter64;
      description
        "Number of dropped packets in TXRQ enq";
    }
    leaf counter_slice14_tx_pdr_txrq_th0_drop_counter2_txrq_th0_drop_cnt {
      type oc-yang:counter64;
      description
        "Number of dropped packets in TXRQ enq";
    }
    leaf counter_slice14_tx_pdr_txrq_th0_drop_counter3_txrq_th0_drop_cnt {
      type oc-yang:counter64;
      description
        "Number of dropped packets in TXRQ enq";
    }
    leaf counter_slice15_tx_pdr_txrq_th0_drop_counter0_txrq_th0_drop_cnt {
      type oc-yang:counter64;
      description
        "Number of dropped packets in TXRQ enq";
    }
    leaf counter_slice15_tx_pdr_txrq_th0_drop_counter1_txrq_th0_drop_cnt {
      type oc-yang:counter64;
      description
        "Number of dropped packets in TXRQ enq";
    }
    leaf counter_slice15_tx_pdr_txrq_th0_drop_counter2_txrq_th0_drop_cnt {
      type oc-yang:counter64;
      description
        "Number of dropped packets in TXRQ enq";
    }
    leaf counter_slice15_tx_pdr_txrq_th0_drop_counter3_txrq_th0_drop_cnt {
      type oc-yang:counter64;
      description
        "Number of dropped packets in TXRQ enq";
    }
    leaf counter_slice0_tx_pdr_txrq_th1_drop_counter0_txrq_th1_deq_drop_cnt {
      type oc-yang:counter64;
      description
        "Number of dropped packets in TXRQ deq";
    }
    leaf counter_slice0_tx_pdr_txrq_th1_drop_counter1_txrq_th1_deq_drop_cnt {
      type oc-yang:counter64;
      description
        "Number of dropped packets in TXRQ deq";
    }
    leaf counter_slice0_tx_pdr_txrq_th1_drop_counter2_txrq_th1_deq_drop_cnt {
      type oc-yang:counter64;
      description
        "Number of dropped packets in TXRQ deq";
    }
    leaf counter_slice0_tx_pdr_txrq_th1_drop_counter3_txrq_th1_deq_drop_cnt {
      type oc-yang:counter64;
      description
        "Number of dropped packets in TXRQ deq";
    }
    leaf counter_slice1_tx_pdr_txrq_th1_drop_counter0_txrq_th1_deq_drop_cnt {
      type oc-yang:counter64;
      description
        "Number of dropped packets in TXRQ deq";
    }
    leaf counter_slice1_tx_pdr_txrq_th1_drop_counter1_txrq_th1_deq_drop_cnt {
      type oc-yang:counter64;
      description
        "Number of dropped packets in TXRQ deq";
    }
    leaf counter_slice1_tx_pdr_txrq_th1_drop_counter2_txrq_th1_deq_drop_cnt {
      type oc-yang:counter64;
      description
        "Number of dropped packets in TXRQ deq";
    }
    leaf counter_slice1_tx_pdr_txrq_th1_drop_counter3_txrq_th1_deq_drop_cnt {
      type oc-yang:counter64;
      description
        "Number of dropped packets in TXRQ deq";
    }
    leaf counter_slice2_tx_pdr_txrq_th1_drop_counter0_txrq_th1_deq_drop_cnt {
      type oc-yang:counter64;
      description
        "Number of dropped packets in TXRQ deq";
    }
    leaf counter_slice2_tx_pdr_txrq_th1_drop_counter1_txrq_th1_deq_drop_cnt {
      type oc-yang:counter64;
      description
        "Number of dropped packets in TXRQ deq";
    }
    leaf counter_slice2_tx_pdr_txrq_th1_drop_counter2_txrq_th1_deq_drop_cnt {
      type oc-yang:counter64;
      description
        "Number of dropped packets in TXRQ deq";
    }
    leaf counter_slice2_tx_pdr_txrq_th1_drop_counter3_txrq_th1_deq_drop_cnt {
      type oc-yang:counter64;
      description
        "Number of dropped packets in TXRQ deq";
    }
    leaf counter_slice3_tx_pdr_txrq_th1_drop_counter0_txrq_th1_deq_drop_cnt {
      type oc-yang:counter64;
      description
        "Number of dropped packets in TXRQ deq";
    }
    leaf counter_slice3_tx_pdr_txrq_th1_drop_counter1_txrq_th1_deq_drop_cnt {
      type oc-yang:counter64;
      description
        "Number of dropped packets in TXRQ deq";
    }
    leaf counter_slice3_tx_pdr_txrq_th1_drop_counter2_txrq_th1_deq_drop_cnt {
      type oc-yang:counter64;
      description
        "Number of dropped packets in TXRQ deq";
    }
    leaf counter_slice3_tx_pdr_txrq_th1_drop_counter3_txrq_th1_deq_drop_cnt {
      type oc-yang:counter64;
      description
        "Number of dropped packets in TXRQ deq";
    }
    leaf counter_slice4_tx_pdr_txrq_th1_drop_counter0_txrq_th1_deq_drop_cnt {
      type oc-yang:counter64;
      description
        "Number of dropped packets in TXRQ deq";
    }
    leaf counter_slice4_tx_pdr_txrq_th1_drop_counter1_txrq_th1_deq_drop_cnt {
      type oc-yang:counter64;
      description
        "Number of dropped packets in TXRQ deq";
    }
    leaf counter_slice4_tx_pdr_txrq_th1_drop_counter2_txrq_th1_deq_drop_cnt {
      type oc-yang:counter64;
      description
        "Number of dropped packets in TXRQ deq";
    }
    leaf counter_slice4_tx_pdr_txrq_th1_drop_counter3_txrq_th1_deq_drop_cnt {
      type oc-yang:counter64;
      description
        "Number of dropped packets in TXRQ deq";
    }
    leaf counter_slice5_tx_pdr_txrq_th1_drop_counter0_txrq_th1_deq_drop_cnt {
      type oc-yang:counter64;
      description
        "Number of dropped packets in TXRQ deq";
    }
    leaf counter_slice5_tx_pdr_txrq_th1_drop_counter1_txrq_th1_deq_drop_cnt {
      type oc-yang:counter64;
      description
        "Number of dropped packets in TXRQ deq";
    }
    leaf counter_slice5_tx_pdr_txrq_th1_drop_counter2_txrq_th1_deq_drop_cnt {
      type oc-yang:counter64;
      description
        "Number of dropped packets in TXRQ deq";
    }
    leaf counter_slice5_tx_pdr_txrq_th1_drop_counter3_txrq_th1_deq_drop_cnt {
      type oc-yang:counter64;
      description
        "Number of dropped packets in TXRQ deq";
    }
    leaf counter_slice6_tx_pdr_txrq_th1_drop_counter0_txrq_th1_deq_drop_cnt {
      type oc-yang:counter64;
      description
        "Number of dropped packets in TXRQ deq";
    }
    leaf counter_slice6_tx_pdr_txrq_th1_drop_counter1_txrq_th1_deq_drop_cnt {
      type oc-yang:counter64;
      description
        "Number of dropped packets in TXRQ deq";
    }
    leaf counter_slice6_tx_pdr_txrq_th1_drop_counter2_txrq_th1_deq_drop_cnt {
      type oc-yang:counter64;
      description
        "Number of dropped packets in TXRQ deq";
    }
    leaf counter_slice6_tx_pdr_txrq_th1_drop_counter3_txrq_th1_deq_drop_cnt {
      type oc-yang:counter64;
      description
        "Number of dropped packets in TXRQ deq";
    }
    leaf counter_slice7_tx_pdr_txrq_th1_drop_counter0_txrq_th1_deq_drop_cnt {
      type oc-yang:counter64;
      description
        "Number of dropped packets in TXRQ deq";
    }
    leaf counter_slice7_tx_pdr_txrq_th1_drop_counter1_txrq_th1_deq_drop_cnt {
      type oc-yang:counter64;
      description
        "Number of dropped packets in TXRQ deq";
    }
    leaf counter_slice7_tx_pdr_txrq_th1_drop_counter2_txrq_th1_deq_drop_cnt {
      type oc-yang:counter64;
      description
        "Number of dropped packets in TXRQ deq";
    }
    leaf counter_slice7_tx_pdr_txrq_th1_drop_counter3_txrq_th1_deq_drop_cnt {
      type oc-yang:counter64;
      description
        "Number of dropped packets in TXRQ deq";
    }
    leaf counter_slice8_tx_pdr_txrq_th1_drop_counter0_txrq_th1_deq_drop_cnt {
      type oc-yang:counter64;
      description
        "Number of dropped packets in TXRQ deq";
    }
    leaf counter_slice8_tx_pdr_txrq_th1_drop_counter1_txrq_th1_deq_drop_cnt {
      type oc-yang:counter64;
      description
        "Number of dropped packets in TXRQ deq";
    }
    leaf counter_slice8_tx_pdr_txrq_th1_drop_counter2_txrq_th1_deq_drop_cnt {
      type oc-yang:counter64;
      description
        "Number of dropped packets in TXRQ deq";
    }
    leaf counter_slice8_tx_pdr_txrq_th1_drop_counter3_txrq_th1_deq_drop_cnt {
      type oc-yang:counter64;
      description
        "Number of dropped packets in TXRQ deq";
    }
    leaf counter_slice9_tx_pdr_txrq_th1_drop_counter0_txrq_th1_deq_drop_cnt {
      type oc-yang:counter64;
      description
        "Number of dropped packets in TXRQ deq";
    }
    leaf counter_slice9_tx_pdr_txrq_th1_drop_counter1_txrq_th1_deq_drop_cnt {
      type oc-yang:counter64;
      description
        "Number of dropped packets in TXRQ deq";
    }
    leaf counter_slice9_tx_pdr_txrq_th1_drop_counter2_txrq_th1_deq_drop_cnt {
      type oc-yang:counter64;
      description
        "Number of dropped packets in TXRQ deq";
    }
    leaf counter_slice9_tx_pdr_txrq_th1_drop_counter3_txrq_th1_deq_drop_cnt {
      type oc-yang:counter64;
      description
        "Number of dropped packets in TXRQ deq";
    }
    leaf counter_slice10_tx_pdr_txrq_th1_drop_counter0_txrq_th1_deq_drop_cnt {
      type oc-yang:counter64;
      description
        "Number of dropped packets in TXRQ deq";
    }
    leaf counter_slice10_tx_pdr_txrq_th1_drop_counter1_txrq_th1_deq_drop_cnt {
      type oc-yang:counter64;
      description
        "Number of dropped packets in TXRQ deq";
    }
    leaf counter_slice10_tx_pdr_txrq_th1_drop_counter2_txrq_th1_deq_drop_cnt {
      type oc-yang:counter64;
      description
        "Number of dropped packets in TXRQ deq";
    }
    leaf counter_slice10_tx_pdr_txrq_th1_drop_counter3_txrq_th1_deq_drop_cnt {
      type oc-yang:counter64;
      description
        "Number of dropped packets in TXRQ deq";
    }
    leaf counter_slice11_tx_pdr_txrq_th1_drop_counter0_txrq_th1_deq_drop_cnt {
      type oc-yang:counter64;
      description
        "Number of dropped packets in TXRQ deq";
    }
    leaf counter_slice11_tx_pdr_txrq_th1_drop_counter1_txrq_th1_deq_drop_cnt {
      type oc-yang:counter64;
      description
        "Number of dropped packets in TXRQ deq";
    }
    leaf counter_slice11_tx_pdr_txrq_th1_drop_counter2_txrq_th1_deq_drop_cnt {
      type oc-yang:counter64;
      description
        "Number of dropped packets in TXRQ deq";
    }
    leaf counter_slice11_tx_pdr_txrq_th1_drop_counter3_txrq_th1_deq_drop_cnt {
      type oc-yang:counter64;
      description
        "Number of dropped packets in TXRQ deq";
    }
    leaf counter_slice12_tx_pdr_txrq_th1_drop_counter0_txrq_th1_deq_drop_cnt {
      type oc-yang:counter64;
      description
        "Number of dropped packets in TXRQ deq";
    }
    leaf counter_slice12_tx_pdr_txrq_th1_drop_counter1_txrq_th1_deq_drop_cnt {
      type oc-yang:counter64;
      description
        "Number of dropped packets in TXRQ deq";
    }
    leaf counter_slice12_tx_pdr_txrq_th1_drop_counter2_txrq_th1_deq_drop_cnt {
      type oc-yang:counter64;
      description
        "Number of dropped packets in TXRQ deq";
    }
    leaf counter_slice12_tx_pdr_txrq_th1_drop_counter3_txrq_th1_deq_drop_cnt {
      type oc-yang:counter64;
      description
        "Number of dropped packets in TXRQ deq";
    }
    leaf counter_slice13_tx_pdr_txrq_th1_drop_counter0_txrq_th1_deq_drop_cnt {
      type oc-yang:counter64;
      description
        "Number of dropped packets in TXRQ deq";
    }
    leaf counter_slice13_tx_pdr_txrq_th1_drop_counter1_txrq_th1_deq_drop_cnt {
      type oc-yang:counter64;
      description
        "Number of dropped packets in TXRQ deq";
    }
    leaf counter_slice13_tx_pdr_txrq_th1_drop_counter2_txrq_th1_deq_drop_cnt {
      type oc-yang:counter64;
      description
        "Number of dropped packets in TXRQ deq";
    }
    leaf counter_slice13_tx_pdr_txrq_th1_drop_counter3_txrq_th1_deq_drop_cnt {
      type oc-yang:counter64;
      description
        "Number of dropped packets in TXRQ deq";
    }
    leaf counter_slice14_tx_pdr_txrq_th1_drop_counter0_txrq_th1_deq_drop_cnt {
      type oc-yang:counter64;
      description
        "Number of dropped packets in TXRQ deq";
    }
    leaf counter_slice14_tx_pdr_txrq_th1_drop_counter1_txrq_th1_deq_drop_cnt {
      type oc-yang:counter64;
      description
        "Number of dropped packets in TXRQ deq";
    }
    leaf counter_slice14_tx_pdr_txrq_th1_drop_counter2_txrq_th1_deq_drop_cnt {
      type oc-yang:counter64;
      description
        "Number of dropped packets in TXRQ deq";
    }
    leaf counter_slice14_tx_pdr_txrq_th1_drop_counter3_txrq_th1_deq_drop_cnt {
      type oc-yang:counter64;
      description
        "Number of dropped packets in TXRQ deq";
    }
    leaf counter_slice15_tx_pdr_txrq_th1_drop_counter0_txrq_th1_deq_drop_cnt {
      type oc-yang:counter64;
      description
        "Number of dropped packets in TXRQ deq";
    }
    leaf counter_slice15_tx_pdr_txrq_th1_drop_counter1_txrq_th1_deq_drop_cnt {
      type oc-yang:counter64;
      description
        "Number of dropped packets in TXRQ deq";
    }
    leaf counter_slice15_tx_pdr_txrq_th1_drop_counter2_txrq_th1_deq_drop_cnt {
      type oc-yang:counter64;
      description
        "Number of dropped packets in TXRQ deq";
    }
    leaf counter_slice15_tx_pdr_txrq_th1_drop_counter3_txrq_th1_deq_drop_cnt {
      type oc-yang:counter64;
      description
        "Number of dropped packets in TXRQ deq";
    }
    leaf counter_slice0_tx_pdr_txrq_th1_drop_counter0_txrq_th1_drop_cnt {
      type oc-yang:counter64;
      description
        "Number of dropped packets in TXRQ enq";
    }
    leaf counter_slice0_tx_pdr_txrq_th1_drop_counter1_txrq_th1_drop_cnt {
      type oc-yang:counter64;
      description
        "Number of dropped packets in TXRQ enq";
    }
    leaf counter_slice0_tx_pdr_txrq_th1_drop_counter2_txrq_th1_drop_cnt {
      type oc-yang:counter64;
      description
        "Number of dropped packets in TXRQ enq";
    }
    leaf counter_slice0_tx_pdr_txrq_th1_drop_counter3_txrq_th1_drop_cnt {
      type oc-yang:counter64;
      description
        "Number of dropped packets in TXRQ enq";
    }
    leaf counter_slice1_tx_pdr_txrq_th1_drop_counter0_txrq_th1_drop_cnt {
      type oc-yang:counter64;
      description
        "Number of dropped packets in TXRQ enq";
    }
    leaf counter_slice1_tx_pdr_txrq_th1_drop_counter1_txrq_th1_drop_cnt {
      type oc-yang:counter64;
      description
        "Number of dropped packets in TXRQ enq";
    }
    leaf counter_slice1_tx_pdr_txrq_th1_drop_counter2_txrq_th1_drop_cnt {
      type oc-yang:counter64;
      description
        "Number of dropped packets in TXRQ enq";
    }
    leaf counter_slice1_tx_pdr_txrq_th1_drop_counter3_txrq_th1_drop_cnt {
      type oc-yang:counter64;
      description
        "Number of dropped packets in TXRQ enq";
    }
    leaf counter_slice2_tx_pdr_txrq_th1_drop_counter0_txrq_th1_drop_cnt {
      type oc-yang:counter64;
      description
        "Number of dropped packets in TXRQ enq";
    }
    leaf counter_slice2_tx_pdr_txrq_th1_drop_counter1_txrq_th1_drop_cnt {
      type oc-yang:counter64;
      description
        "Number of dropped packets in TXRQ enq";
    }
    leaf counter_slice2_tx_pdr_txrq_th1_drop_counter2_txrq_th1_drop_cnt {
      type oc-yang:counter64;
      description
        "Number of dropped packets in TXRQ enq";
    }
    leaf counter_slice2_tx_pdr_txrq_th1_drop_counter3_txrq_th1_drop_cnt {
      type oc-yang:counter64;
      description
        "Number of dropped packets in TXRQ enq";
    }
    leaf counter_slice3_tx_pdr_txrq_th1_drop_counter0_txrq_th1_drop_cnt {
      type oc-yang:counter64;
      description
        "Number of dropped packets in TXRQ enq";
    }
    leaf counter_slice3_tx_pdr_txrq_th1_drop_counter1_txrq_th1_drop_cnt {
      type oc-yang:counter64;
      description
        "Number of dropped packets in TXRQ enq";
    }
    leaf counter_slice3_tx_pdr_txrq_th1_drop_counter2_txrq_th1_drop_cnt {
      type oc-yang:counter64;
      description
        "Number of dropped packets in TXRQ enq";
    }
    leaf counter_slice3_tx_pdr_txrq_th1_drop_counter3_txrq_th1_drop_cnt {
      type oc-yang:counter64;
      description
        "Number of dropped packets in TXRQ enq";
    }
    leaf counter_slice4_tx_pdr_txrq_th1_drop_counter0_txrq_th1_drop_cnt {
      type oc-yang:counter64;
      description
        "Number of dropped packets in TXRQ enq";
    }
    leaf counter_slice4_tx_pdr_txrq_th1_drop_counter1_txrq_th1_drop_cnt {
      type oc-yang:counter64;
      description
        "Number of dropped packets in TXRQ enq";
    }
    leaf counter_slice4_tx_pdr_txrq_th1_drop_counter2_txrq_th1_drop_cnt {
      type oc-yang:counter64;
      description
        "Number of dropped packets in TXRQ enq";
    }
    leaf counter_slice4_tx_pdr_txrq_th1_drop_counter3_txrq_th1_drop_cnt {
      type oc-yang:counter64;
      description
        "Number of dropped packets in TXRQ enq";
    }
    leaf counter_slice5_tx_pdr_txrq_th1_drop_counter0_txrq_th1_drop_cnt {
      type oc-yang:counter64;
      description
        "Number of dropped packets in TXRQ enq";
    }
    leaf counter_slice5_tx_pdr_txrq_th1_drop_counter1_txrq_th1_drop_cnt {
      type oc-yang:counter64;
      description
        "Number of dropped packets in TXRQ enq";
    }
    leaf counter_slice5_tx_pdr_txrq_th1_drop_counter2_txrq_th1_drop_cnt {
      type oc-yang:counter64;
      description
        "Number of dropped packets in TXRQ enq";
    }
    leaf counter_slice5_tx_pdr_txrq_th1_drop_counter3_txrq_th1_drop_cnt {
      type oc-yang:counter64;
      description
        "Number of dropped packets in TXRQ enq";
    }
    leaf counter_slice6_tx_pdr_txrq_th1_drop_counter0_txrq_th1_drop_cnt {
      type oc-yang:counter64;
      description
        "Number of dropped packets in TXRQ enq";
    }
    leaf counter_slice6_tx_pdr_txrq_th1_drop_counter1_txrq_th1_drop_cnt {
      type oc-yang:counter64;
      description
        "Number of dropped packets in TXRQ enq";
    }
    leaf counter_slice6_tx_pdr_txrq_th1_drop_counter2_txrq_th1_drop_cnt {
      type oc-yang:counter64;
      description
        "Number of dropped packets in TXRQ enq";
    }
    leaf counter_slice6_tx_pdr_txrq_th1_drop_counter3_txrq_th1_drop_cnt {
      type oc-yang:counter64;
      description
        "Number of dropped packets in TXRQ enq";
    }
    leaf counter_slice7_tx_pdr_txrq_th1_drop_counter0_txrq_th1_drop_cnt {
      type oc-yang:counter64;
      description
        "Number of dropped packets in TXRQ enq";
    }
    leaf counter_slice7_tx_pdr_txrq_th1_drop_counter1_txrq_th1_drop_cnt {
      type oc-yang:counter64;
      description
        "Number of dropped packets in TXRQ enq";
    }
    leaf counter_slice7_tx_pdr_txrq_th1_drop_counter2_txrq_th1_drop_cnt {
      type oc-yang:counter64;
      description
        "Number of dropped packets in TXRQ enq";
    }
    leaf counter_slice7_tx_pdr_txrq_th1_drop_counter3_txrq_th1_drop_cnt {
      type oc-yang:counter64;
      description
        "Number of dropped packets in TXRQ enq";
    }
    leaf counter_slice8_tx_pdr_txrq_th1_drop_counter0_txrq_th1_drop_cnt {
      type oc-yang:counter64;
      description
        "Number of dropped packets in TXRQ enq";
    }
    leaf counter_slice8_tx_pdr_txrq_th1_drop_counter1_txrq_th1_drop_cnt {
      type oc-yang:counter64;
      description
        "Number of dropped packets in TXRQ enq";
    }
    leaf counter_slice8_tx_pdr_txrq_th1_drop_counter2_txrq_th1_drop_cnt {
      type oc-yang:counter64;
      description
        "Number of dropped packets in TXRQ enq";
    }
    leaf counter_slice8_tx_pdr_txrq_th1_drop_counter3_txrq_th1_drop_cnt {
      type oc-yang:counter64;
      description
        "Number of dropped packets in TXRQ enq";
    }
    leaf counter_slice9_tx_pdr_txrq_th1_drop_counter0_txrq_th1_drop_cnt {
      type oc-yang:counter64;
      description
        "Number of dropped packets in TXRQ enq";
    }
    leaf counter_slice9_tx_pdr_txrq_th1_drop_counter1_txrq_th1_drop_cnt {
      type oc-yang:counter64;
      description
        "Number of dropped packets in TXRQ enq";
    }
    leaf counter_slice9_tx_pdr_txrq_th1_drop_counter2_txrq_th1_drop_cnt {
      type oc-yang:counter64;
      description
        "Number of dropped packets in TXRQ enq";
    }
    leaf counter_slice9_tx_pdr_txrq_th1_drop_counter3_txrq_th1_drop_cnt {
      type oc-yang:counter64;
      description
        "Number of dropped packets in TXRQ enq";
    }
    leaf counter_slice10_tx_pdr_txrq_th1_drop_counter0_txrq_th1_drop_cnt {
      type oc-yang:counter64;
      description
        "Number of dropped packets in TXRQ enq";
    }
    leaf counter_slice10_tx_pdr_txrq_th1_drop_counter1_txrq_th1_drop_cnt {
      type oc-yang:counter64;
      description
        "Number of dropped packets in TXRQ enq";
    }
    leaf counter_slice10_tx_pdr_txrq_th1_drop_counter2_txrq_th1_drop_cnt {
      type oc-yang:counter64;
      description
        "Number of dropped packets in TXRQ enq";
    }
    leaf counter_slice10_tx_pdr_txrq_th1_drop_counter3_txrq_th1_drop_cnt {
      type oc-yang:counter64;
      description
        "Number of dropped packets in TXRQ enq";
    }
    leaf counter_slice11_tx_pdr_txrq_th1_drop_counter0_txrq_th1_drop_cnt {
      type oc-yang:counter64;
      description
        "Number of dropped packets in TXRQ enq";
    }
    leaf counter_slice11_tx_pdr_txrq_th1_drop_counter1_txrq_th1_drop_cnt {
      type oc-yang:counter64;
      description
        "Number of dropped packets in TXRQ enq";
    }
    leaf counter_slice11_tx_pdr_txrq_th1_drop_counter2_txrq_th1_drop_cnt {
      type oc-yang:counter64;
      description
        "Number of dropped packets in TXRQ enq";
    }
    leaf counter_slice11_tx_pdr_txrq_th1_drop_counter3_txrq_th1_drop_cnt {
      type oc-yang:counter64;
      description
        "Number of dropped packets in TXRQ enq";
    }
    leaf counter_slice12_tx_pdr_txrq_th1_drop_counter0_txrq_th1_drop_cnt {
      type oc-yang:counter64;
      description
        "Number of dropped packets in TXRQ enq";
    }
    leaf counter_slice12_tx_pdr_txrq_th1_drop_counter1_txrq_th1_drop_cnt {
      type oc-yang:counter64;
      description
        "Number of dropped packets in TXRQ enq";
    }
    leaf counter_slice12_tx_pdr_txrq_th1_drop_counter2_txrq_th1_drop_cnt {
      type oc-yang:counter64;
      description
        "Number of dropped packets in TXRQ enq";
    }
    leaf counter_slice12_tx_pdr_txrq_th1_drop_counter3_txrq_th1_drop_cnt {
      type oc-yang:counter64;
      description
        "Number of dropped packets in TXRQ enq";
    }
    leaf counter_slice13_tx_pdr_txrq_th1_drop_counter0_txrq_th1_drop_cnt {
      type oc-yang:counter64;
      description
        "Number of dropped packets in TXRQ enq";
    }
    leaf counter_slice13_tx_pdr_txrq_th1_drop_counter1_txrq_th1_drop_cnt {
      type oc-yang:counter64;
      description
        "Number of dropped packets in TXRQ enq";
    }
    leaf counter_slice13_tx_pdr_txrq_th1_drop_counter2_txrq_th1_drop_cnt {
      type oc-yang:counter64;
      description
        "Number of dropped packets in TXRQ enq";
    }
    leaf counter_slice13_tx_pdr_txrq_th1_drop_counter3_txrq_th1_drop_cnt {
      type oc-yang:counter64;
      description
        "Number of dropped packets in TXRQ enq";
    }
    leaf counter_slice14_tx_pdr_txrq_th1_drop_counter0_txrq_th1_drop_cnt {
      type oc-yang:counter64;
      description
        "Number of dropped packets in TXRQ enq";
    }
    leaf counter_slice14_tx_pdr_txrq_th1_drop_counter1_txrq_th1_drop_cnt {
      type oc-yang:counter64;
      description
        "Number of dropped packets in TXRQ enq";
    }
    leaf counter_slice14_tx_pdr_txrq_th1_drop_counter2_txrq_th1_drop_cnt {
      type oc-yang:counter64;
      description
        "Number of dropped packets in TXRQ enq";
    }
    leaf counter_slice14_tx_pdr_txrq_th1_drop_counter3_txrq_th1_drop_cnt {
      type oc-yang:counter64;
      description
        "Number of dropped packets in TXRQ enq";
    }
    leaf counter_slice15_tx_pdr_txrq_th1_drop_counter0_txrq_th1_drop_cnt {
      type oc-yang:counter64;
      description
        "Number of dropped packets in TXRQ enq";
    }
    leaf counter_slice15_tx_pdr_txrq_th1_drop_counter1_txrq_th1_drop_cnt {
      type oc-yang:counter64;
      description
        "Number of dropped packets in TXRQ enq";
    }
    leaf counter_slice15_tx_pdr_txrq_th1_drop_counter2_txrq_th1_drop_cnt {
      type oc-yang:counter64;
      description
        "Number of dropped packets in TXRQ enq";
    }
    leaf counter_slice15_tx_pdr_txrq_th1_drop_counter3_txrq_th1_drop_cnt {
      type oc-yang:counter64;
      description
        "Number of dropped packets in TXRQ enq";
    }
    leaf counter_slice0_tx_pdr_txrq_total_drop_counter_txrq_total_drop_cnt {
      type oc-yang:counter64;
      description
        "Number of dropped packets";
    }
    leaf counter_slice1_tx_pdr_txrq_total_drop_counter_txrq_total_drop_cnt {
      type oc-yang:counter64;
      description
        "Number of dropped packets";
    }
    leaf counter_slice2_tx_pdr_txrq_total_drop_counter_txrq_total_drop_cnt {
      type oc-yang:counter64;
      description
        "Number of dropped packets";
    }
    leaf counter_slice3_tx_pdr_txrq_total_drop_counter_txrq_total_drop_cnt {
      type oc-yang:counter64;
      description
        "Number of dropped packets";
    }
    leaf counter_slice4_tx_pdr_txrq_total_drop_counter_txrq_total_drop_cnt {
      type oc-yang:counter64;
      description
        "Number of dropped packets";
    }
    leaf counter_slice5_tx_pdr_txrq_total_drop_counter_txrq_total_drop_cnt {
      type oc-yang:counter64;
      description
        "Number of dropped packets";
    }
    leaf counter_slice6_tx_pdr_txrq_total_drop_counter_txrq_total_drop_cnt {
      type oc-yang:counter64;
      description
        "Number of dropped packets";
    }
    leaf counter_slice7_tx_pdr_txrq_total_drop_counter_txrq_total_drop_cnt {
      type oc-yang:counter64;
      description
        "Number of dropped packets";
    }
    leaf counter_slice8_tx_pdr_txrq_total_drop_counter_txrq_total_drop_cnt {
      type oc-yang:counter64;
      description
        "Number of dropped packets";
    }
    leaf counter_slice9_tx_pdr_txrq_total_drop_counter_txrq_total_drop_cnt {
      type oc-yang:counter64;
      description
        "Number of dropped packets";
    }
    leaf counter_slice10_tx_pdr_txrq_total_drop_counter_txrq_total_drop_cnt {
      type oc-yang:counter64;
      description
        "Number of dropped packets";
    }
    leaf counter_slice11_tx_pdr_txrq_total_drop_counter_txrq_total_drop_cnt {
      type oc-yang:counter64;
      description
        "Number of dropped packets";
    }
    leaf counter_slice12_tx_pdr_txrq_total_drop_counter_txrq_total_drop_cnt {
      type oc-yang:counter64;
      description
        "Number of dropped packets";
    }
    leaf counter_slice13_tx_pdr_txrq_total_drop_counter_txrq_total_drop_cnt {
      type oc-yang:counter64;
      description
        "Number of dropped packets";
    }
    leaf counter_slice14_tx_pdr_txrq_total_drop_counter_txrq_total_drop_cnt {
      type oc-yang:counter64;
      description
        "Number of dropped packets";
    }
    leaf counter_slice15_tx_pdr_txrq_total_drop_counter_txrq_total_drop_cnt {
      type oc-yang:counter64;
      description
        "Number of dropped packets";
    }
    leaf counter_slice0_tx_pdr_txrq_unsch_cgm_th_drop_counter0_txrq_unsch_cgm_th0_drop_cnt {
      type oc-yang:counter64;
      description
        "Number of dropped packets in TXRQ CGM Threshold0";
    }
    leaf counter_slice0_tx_pdr_txrq_unsch_cgm_th_drop_counter1_txrq_unsch_cgm_th0_drop_cnt {
      type oc-yang:counter64;
      description
        "Number of dropped packets in TXRQ CGM Threshold0";
    }
    leaf counter_slice1_tx_pdr_txrq_unsch_cgm_th_drop_counter0_txrq_unsch_cgm_th0_drop_cnt {
      type oc-yang:counter64;
      description
        "Number of dropped packets in TXRQ CGM Threshold0";
    }
    leaf counter_slice1_tx_pdr_txrq_unsch_cgm_th_drop_counter1_txrq_unsch_cgm_th0_drop_cnt {
      type oc-yang:counter64;
      description
        "Number of dropped packets in TXRQ CGM Threshold0";
    }
    leaf counter_slice2_tx_pdr_txrq_unsch_cgm_th_drop_counter0_txrq_unsch_cgm_th0_drop_cnt {
      type oc-yang:counter64;
      description
        "Number of dropped packets in TXRQ CGM Threshold0";
    }
    leaf counter_slice2_tx_pdr_txrq_unsch_cgm_th_drop_counter1_txrq_unsch_cgm_th0_drop_cnt {
      type oc-yang:counter64;
      description
        "Number of dropped packets in TXRQ CGM Threshold0";
    }
    leaf counter_slice3_tx_pdr_txrq_unsch_cgm_th_drop_counter0_txrq_unsch_cgm_th0_drop_cnt {
      type oc-yang:counter64;
      description
        "Number of dropped packets in TXRQ CGM Threshold0";
    }
    leaf counter_slice3_tx_pdr_txrq_unsch_cgm_th_drop_counter1_txrq_unsch_cgm_th0_drop_cnt {
      type oc-yang:counter64;
      description
        "Number of dropped packets in TXRQ CGM Threshold0";
    }
    leaf counter_slice4_tx_pdr_txrq_unsch_cgm_th_drop_counter0_txrq_unsch_cgm_th0_drop_cnt {
      type oc-yang:counter64;
      description
        "Number of dropped packets in TXRQ CGM Threshold0";
    }
    leaf counter_slice4_tx_pdr_txrq_unsch_cgm_th_drop_counter1_txrq_unsch_cgm_th0_drop_cnt {
      type oc-yang:counter64;
      description
        "Number of dropped packets in TXRQ CGM Threshold0";
    }
    leaf counter_slice5_tx_pdr_txrq_unsch_cgm_th_drop_counter0_txrq_unsch_cgm_th0_drop_cnt {
      type oc-yang:counter64;
      description
        "Number of dropped packets in TXRQ CGM Threshold0";
    }
    leaf counter_slice5_tx_pdr_txrq_unsch_cgm_th_drop_counter1_txrq_unsch_cgm_th0_drop_cnt {
      type oc-yang:counter64;
      description
        "Number of dropped packets in TXRQ CGM Threshold0";
    }
    leaf counter_slice6_tx_pdr_txrq_unsch_cgm_th_drop_counter0_txrq_unsch_cgm_th0_drop_cnt {
      type oc-yang:counter64;
      description
        "Number of dropped packets in TXRQ CGM Threshold0";
    }
    leaf counter_slice6_tx_pdr_txrq_unsch_cgm_th_drop_counter1_txrq_unsch_cgm_th0_drop_cnt {
      type oc-yang:counter64;
      description
        "Number of dropped packets in TXRQ CGM Threshold0";
    }
    leaf counter_slice7_tx_pdr_txrq_unsch_cgm_th_drop_counter0_txrq_unsch_cgm_th0_drop_cnt {
      type oc-yang:counter64;
      description
        "Number of dropped packets in TXRQ CGM Threshold0";
    }
    leaf counter_slice7_tx_pdr_txrq_unsch_cgm_th_drop_counter1_txrq_unsch_cgm_th0_drop_cnt {
      type oc-yang:counter64;
      description
        "Number of dropped packets in TXRQ CGM Threshold0";
    }
    leaf counter_slice8_tx_pdr_txrq_unsch_cgm_th_drop_counter0_txrq_unsch_cgm_th0_drop_cnt {
      type oc-yang:counter64;
      description
        "Number of dropped packets in TXRQ CGM Threshold0";
    }
    leaf counter_slice8_tx_pdr_txrq_unsch_cgm_th_drop_counter1_txrq_unsch_cgm_th0_drop_cnt {
      type oc-yang:counter64;
      description
        "Number of dropped packets in TXRQ CGM Threshold0";
    }
    leaf counter_slice9_tx_pdr_txrq_unsch_cgm_th_drop_counter0_txrq_unsch_cgm_th0_drop_cnt {
      type oc-yang:counter64;
      description
        "Number of dropped packets in TXRQ CGM Threshold0";
    }
    leaf counter_slice9_tx_pdr_txrq_unsch_cgm_th_drop_counter1_txrq_unsch_cgm_th0_drop_cnt {
      type oc-yang:counter64;
      description
        "Number of dropped packets in TXRQ CGM Threshold0";
    }
    leaf counter_slice10_tx_pdr_txrq_unsch_cgm_th_drop_counter0_txrq_unsch_cgm_th0_drop_cnt {
      type oc-yang:counter64;
      description
        "Number of dropped packets in TXRQ CGM Threshold0";
    }
    leaf counter_slice10_tx_pdr_txrq_unsch_cgm_th_drop_counter1_txrq_unsch_cgm_th0_drop_cnt {
      type oc-yang:counter64;
      description
        "Number of dropped packets in TXRQ CGM Threshold0";
    }
    leaf counter_slice11_tx_pdr_txrq_unsch_cgm_th_drop_counter0_txrq_unsch_cgm_th0_drop_cnt {
      type oc-yang:counter64;
      description
        "Number of dropped packets in TXRQ CGM Threshold0";
    }
    leaf counter_slice11_tx_pdr_txrq_unsch_cgm_th_drop_counter1_txrq_unsch_cgm_th0_drop_cnt {
      type oc-yang:counter64;
      description
        "Number of dropped packets in TXRQ CGM Threshold0";
    }
    leaf counter_slice12_tx_pdr_txrq_unsch_cgm_th_drop_counter0_txrq_unsch_cgm_th0_drop_cnt {
      type oc-yang:counter64;
      description
        "Number of dropped packets in TXRQ CGM Threshold0";
    }
    leaf counter_slice12_tx_pdr_txrq_unsch_cgm_th_drop_counter1_txrq_unsch_cgm_th0_drop_cnt {
      type oc-yang:counter64;
      description
        "Number of dropped packets in TXRQ CGM Threshold0";
    }
    leaf counter_slice13_tx_pdr_txrq_unsch_cgm_th_drop_counter0_txrq_unsch_cgm_th0_drop_cnt {
      type oc-yang:counter64;
      description
        "Number of dropped packets in TXRQ CGM Threshold0";
    }
    leaf counter_slice13_tx_pdr_txrq_unsch_cgm_th_drop_counter1_txrq_unsch_cgm_th0_drop_cnt {
      type oc-yang:counter64;
      description
        "Number of dropped packets in TXRQ CGM Threshold0";
    }
    leaf counter_slice14_tx_pdr_txrq_unsch_cgm_th_drop_counter0_txrq_unsch_cgm_th0_drop_cnt {
      type oc-yang:counter64;
      description
        "Number of dropped packets in TXRQ CGM Threshold0";
    }
    leaf counter_slice14_tx_pdr_txrq_unsch_cgm_th_drop_counter1_txrq_unsch_cgm_th0_drop_cnt {
      type oc-yang:counter64;
      description
        "Number of dropped packets in TXRQ CGM Threshold0";
    }
    leaf counter_slice15_tx_pdr_txrq_unsch_cgm_th_drop_counter0_txrq_unsch_cgm_th0_drop_cnt {
      type oc-yang:counter64;
      description
        "Number of dropped packets in TXRQ CGM Threshold0";
    }
    leaf counter_slice15_tx_pdr_txrq_unsch_cgm_th_drop_counter1_txrq_unsch_cgm_th0_drop_cnt {
      type oc-yang:counter64;
      description
        "Number of dropped packets in TXRQ CGM Threshold0";
    }
    leaf counter_slice0_tx_pdr_txrq_unsch_cgm_th_drop_counter0_txrq_unsch_cgm_th1_drop_cnt {
      type oc-yang:counter64;
      description
        "Number of dropped packets in TXRQ CGM Threshold1";
    }
    leaf counter_slice0_tx_pdr_txrq_unsch_cgm_th_drop_counter1_txrq_unsch_cgm_th1_drop_cnt {
      type oc-yang:counter64;
      description
        "Number of dropped packets in TXRQ CGM Threshold1";
    }
    leaf counter_slice1_tx_pdr_txrq_unsch_cgm_th_drop_counter0_txrq_unsch_cgm_th1_drop_cnt {
      type oc-yang:counter64;
      description
        "Number of dropped packets in TXRQ CGM Threshold1";
    }
    leaf counter_slice1_tx_pdr_txrq_unsch_cgm_th_drop_counter1_txrq_unsch_cgm_th1_drop_cnt {
      type oc-yang:counter64;
      description
        "Number of dropped packets in TXRQ CGM Threshold1";
    }
    leaf counter_slice2_tx_pdr_txrq_unsch_cgm_th_drop_counter0_txrq_unsch_cgm_th1_drop_cnt {
      type oc-yang:counter64;
      description
        "Number of dropped packets in TXRQ CGM Threshold1";
    }
    leaf counter_slice2_tx_pdr_txrq_unsch_cgm_th_drop_counter1_txrq_unsch_cgm_th1_drop_cnt {
      type oc-yang:counter64;
      description
        "Number of dropped packets in TXRQ CGM Threshold1";
    }
    leaf counter_slice3_tx_pdr_txrq_unsch_cgm_th_drop_counter0_txrq_unsch_cgm_th1_drop_cnt {
      type oc-yang:counter64;
      description
        "Number of dropped packets in TXRQ CGM Threshold1";
    }
    leaf counter_slice3_tx_pdr_txrq_unsch_cgm_th_drop_counter1_txrq_unsch_cgm_th1_drop_cnt {
      type oc-yang:counter64;
      description
        "Number of dropped packets in TXRQ CGM Threshold1";
    }
    leaf counter_slice4_tx_pdr_txrq_unsch_cgm_th_drop_counter0_txrq_unsch_cgm_th1_drop_cnt {
      type oc-yang:counter64;
      description
        "Number of dropped packets in TXRQ CGM Threshold1";
    }
    leaf counter_slice4_tx_pdr_txrq_unsch_cgm_th_drop_counter1_txrq_unsch_cgm_th1_drop_cnt {
      type oc-yang:counter64;
      description
        "Number of dropped packets in TXRQ CGM Threshold1";
    }
    leaf counter_slice5_tx_pdr_txrq_unsch_cgm_th_drop_counter0_txrq_unsch_cgm_th1_drop_cnt {
      type oc-yang:counter64;
      description
        "Number of dropped packets in TXRQ CGM Threshold1";
    }
    leaf counter_slice5_tx_pdr_txrq_unsch_cgm_th_drop_counter1_txrq_unsch_cgm_th1_drop_cnt {
      type oc-yang:counter64;
      description
        "Number of dropped packets in TXRQ CGM Threshold1";
    }
    leaf counter_slice6_tx_pdr_txrq_unsch_cgm_th_drop_counter0_txrq_unsch_cgm_th1_drop_cnt {
      type oc-yang:counter64;
      description
        "Number of dropped packets in TXRQ CGM Threshold1";
    }
    leaf counter_slice6_tx_pdr_txrq_unsch_cgm_th_drop_counter1_txrq_unsch_cgm_th1_drop_cnt {
      type oc-yang:counter64;
      description
        "Number of dropped packets in TXRQ CGM Threshold1";
    }
    leaf counter_slice7_tx_pdr_txrq_unsch_cgm_th_drop_counter0_txrq_unsch_cgm_th1_drop_cnt {
      type oc-yang:counter64;
      description
        "Number of dropped packets in TXRQ CGM Threshold1";
    }
    leaf counter_slice7_tx_pdr_txrq_unsch_cgm_th_drop_counter1_txrq_unsch_cgm_th1_drop_cnt {
      type oc-yang:counter64;
      description
        "Number of dropped packets in TXRQ CGM Threshold1";
    }
    leaf counter_slice8_tx_pdr_txrq_unsch_cgm_th_drop_counter0_txrq_unsch_cgm_th1_drop_cnt {
      type oc-yang:counter64;
      description
        "Number of dropped packets in TXRQ CGM Threshold1";
    }
    leaf counter_slice8_tx_pdr_txrq_unsch_cgm_th_drop_counter1_txrq_unsch_cgm_th1_drop_cnt {
      type oc-yang:counter64;
      description
        "Number of dropped packets in TXRQ CGM Threshold1";
    }
    leaf counter_slice9_tx_pdr_txrq_unsch_cgm_th_drop_counter0_txrq_unsch_cgm_th1_drop_cnt {
      type oc-yang:counter64;
      description
        "Number of dropped packets in TXRQ CGM Threshold1";
    }
    leaf counter_slice9_tx_pdr_txrq_unsch_cgm_th_drop_counter1_txrq_unsch_cgm_th1_drop_cnt {
      type oc-yang:counter64;
      description
        "Number of dropped packets in TXRQ CGM Threshold1";
    }
    leaf counter_slice10_tx_pdr_txrq_unsch_cgm_th_drop_counter0_txrq_unsch_cgm_th1_drop_cnt {
      type oc-yang:counter64;
      description
        "Number of dropped packets in TXRQ CGM Threshold1";
    }
    leaf counter_slice10_tx_pdr_txrq_unsch_cgm_th_drop_counter1_txrq_unsch_cgm_th1_drop_cnt {
      type oc-yang:counter64;
      description
        "Number of dropped packets in TXRQ CGM Threshold1";
    }
    leaf counter_slice11_tx_pdr_txrq_unsch_cgm_th_drop_counter0_txrq_unsch_cgm_th1_drop_cnt {
      type oc-yang:counter64;
      description
        "Number of dropped packets in TXRQ CGM Threshold1";
    }
    leaf counter_slice11_tx_pdr_txrq_unsch_cgm_th_drop_counter1_txrq_unsch_cgm_th1_drop_cnt {
      type oc-yang:counter64;
      description
        "Number of dropped packets in TXRQ CGM Threshold1";
    }
    leaf counter_slice12_tx_pdr_txrq_unsch_cgm_th_drop_counter0_txrq_unsch_cgm_th1_drop_cnt {
      type oc-yang:counter64;
      description
        "Number of dropped packets in TXRQ CGM Threshold1";
    }
    leaf counter_slice12_tx_pdr_txrq_unsch_cgm_th_drop_counter1_txrq_unsch_cgm_th1_drop_cnt {
      type oc-yang:counter64;
      description
        "Number of dropped packets in TXRQ CGM Threshold1";
    }
    leaf counter_slice13_tx_pdr_txrq_unsch_cgm_th_drop_counter0_txrq_unsch_cgm_th1_drop_cnt {
      type oc-yang:counter64;
      description
        "Number of dropped packets in TXRQ CGM Threshold1";
    }
    leaf counter_slice13_tx_pdr_txrq_unsch_cgm_th_drop_counter1_txrq_unsch_cgm_th1_drop_cnt {
      type oc-yang:counter64;
      description
        "Number of dropped packets in TXRQ CGM Threshold1";
    }
    leaf counter_slice14_tx_pdr_txrq_unsch_cgm_th_drop_counter0_txrq_unsch_cgm_th1_drop_cnt {
      type oc-yang:counter64;
      description
        "Number of dropped packets in TXRQ CGM Threshold1";
    }
    leaf counter_slice14_tx_pdr_txrq_unsch_cgm_th_drop_counter1_txrq_unsch_cgm_th1_drop_cnt {
      type oc-yang:counter64;
      description
        "Number of dropped packets in TXRQ CGM Threshold1";
    }
    leaf counter_slice15_tx_pdr_txrq_unsch_cgm_th_drop_counter0_txrq_unsch_cgm_th1_drop_cnt {
      type oc-yang:counter64;
      description
        "Number of dropped packets in TXRQ CGM Threshold1";
    }
    leaf counter_slice15_tx_pdr_txrq_unsch_cgm_th_drop_counter1_txrq_unsch_cgm_th1_drop_cnt {
      type oc-yang:counter64;
      description
        "Number of dropped packets in TXRQ CGM Threshold1";
    }
  }

  grouping cisco-p200-packet-processing-drop-counters {
    description
      "Packet processing Drop leafs grouping for the p200 asic";
    leaf l3_drop_adj_non_inject {
      type oc-yang:counter64;
      description
        "L3 route information is not available for prefix in the VRF";
    }
    leaf l3_ip_unicast_rpf {
      type oc-yang:counter64;
      description
        " Ip unicast RPF check failed Loose or strict mode";
    }
    leaf ipv4_uc_forwarding_disabled {
      type oc-yang:counter64;
      description
        "Incoming packet or inner IP after tunnel termination is IPv4 unicast however IPv4 UC forwarding is disabled on the ingress L3 Logical Port";
    }
    leaf ipv6_uc_forwarding_disabled {
      type oc-yang:counter64;
      description
        "Incoming packet or inner IP after tunnel termination is IPv6 unicast however IPv4 UC forwarding is disabled on the ingress L3 Logical Por";
    }
    leaf ethernet_acceptable_format {
      type oc-yang:counter64;
      description
        "The packet header VLAN format is illegal to the incoming Logical Port";
    }
    leaf ethernet_acl_drop {
      type oc-yang:counter64;
      description
        "The packet matched an ingress security ACL rule with a drop action";
    }
    leaf ethernet_acl_force_punt {
      type oc-yang:counter64;
      description
        "The packet matched an ingress security ACL rule with a punt to host action";
    }
    leaf ethernet_disabled {
      type oc-yang:counter64;
      description
        "Filter packet if L2 or VxLAN port is disabled to allow 1 plus1 protection";
    }
    leaf ethernet_distr_down_mep {
      type oc-yang:counter64;
      description
        "Trap Ingress OAM CFM MEP Packets";
    }
    leaf ethernet_distr_up_mep {
      type oc-yang:counter64;
      description
        " Trap Egress OAM CFM MEP Packets";
    }
    leaf ethernet_dot1_x_learn {
      type oc-yang:counter64;
      description
        "Punt incoming packet for Dot1x learning";
    }
    leaf ethernet_dot1_x_drop {
      type oc-yang:counter64;
      description
        "User or Dot1x device authenticated Drop subsequent packets";
    }
    leaf ethernet_dspa_mc_trim {
      type oc-yang:counter64;
      description
        "ulticast pruning of flood copies to LAG port";
    }
    leaf ethernet_dsp_disabled {
      type oc-yang:counter64;
      description
        "L3 DLP is disabled.Trap to drop transmitted packets on L3 DLP";
    }
    leaf ethernet_egress_stp_block {
      type oc-yang:counter64;
      description
        "Packet transmitted to l2 logical port with STP in blocked state";
    }
    leaf ethernet_incompatible_eve_cmd {
      type oc-yang:counter64;
      description
        "EVE command is incompatible with packet VLAN structure";
    }
    leaf ethernet_ingress_stp_block {
      type oc-yang:counter64;
      description
        "Trap incoming packet if packet is received on Ingress Logical port";
    }
    leaf ethernet_l2_dlp_not_found {
      type oc-yang:counter64;
      description
        "Failed to get attributes for destination L2 logical port in transmit database";
    }
    leaf ethernet_macsec_processing_err {
      type oc-yang:counter64;
      description
        "Macsec internal error occured while decrypting MACSec packets";
    }
    leaf ethernet_mc_snoop_lookup_miss {
      type oc-yang:counter64;
      description
        "IGMP snooping database lookup miss";
    }
    leaf ethernet_no_pwe_l3_dest {
      type oc-yang:counter64;
      description
        "Failed to find PWE to L3 Destination mapping for PWE imposition path";
    }
    leaf ethernet_no_sip_mapping {
      type oc-yang:counter64;
      description
        "Could not terminate tunnel Source IP. trigger snoop to host to add SIP to Source Logical Port mapping in termination database";
    }
    leaf ethernet_no_vni_mapping {
      type oc-yang:counter64;
      description
        "Could not resolve VXLAN VNI to L2  or could not map MAC relay to VNI for L2-VXLAN encapsulation";
    }
    leaf ethernet_padding_residue_in_second_line {
      type oc-yang:counter64;
      description
        "Failed to handle padding in special cases";
    }
    leaf ethernet_sa_error {
      type oc-yang:counter64;
      description
        "Incoming packet MAC SA equals zero";
    }
    leaf ethernet_sa_multicast {
      type oc-yang:counter64;
      description
        "Incoming packet MAC SA is a multicast address";
    }
    leaf ethernet_same_interface {
      type oc-yang:counter64;
      description
        "The packet is being transmitted back to the same port that it was received from";
    }
    leaf ethernet_smac_miss {
      type oc-yang:counter64;
      description
        "Bridged packet MAC SA not found in MAC forwarding table";
    }
    leaf ethernet_split_horizon {
      type oc-yang:counter64;
      description
        "Trap if source and destination Logical Port are not allowed to communicate";
    }
    leaf ethernet_svi_egress_dhcp {
      type oc-yang:counter64;
      description
        "Trap egress L2 packet routed through Switched Virtual Interface that are DHCP over IP";
    }
    leaf ethernet_system_mymac {
      type oc-yang:counter64;
      description
        "Global My-MAC termination of ethernet header";
    }
    leaf ethernet_unknown_bc {
      type oc-yang:counter64;
      description
        "Destination for broadcast packet is unknown.  Logical port attribute is set to drop it";
    }
    leaf ethernet_unknown_mc {
      type oc-yang:counter64;
      description
        "Destination for multicast packet is unknown.  Logical port attribute is set to drop it";
    }
    leaf ethernet_unknown_uc {
      type oc-yang:counter64;
      description
        "Destination for unicast packet is unknown.  Logical port attribute is set to drop it";
    }
    leaf ethernet_unprotected_data_pkt_on_macsec_en_port {
      type oc-yang:counter64;
      description
        "Unencrypted packet received on MACSec enable port expecting encrypted secure packets";
    }
    leaf ethernet_spa_port_member_rx_disabled {
      type oc-yang:counter64;
      description
        "Aggregate Member cannot receive traffic";
    }
    leaf ethernet_unknown_l3 {
      type oc-yang:counter64;
      description
        "Unknown overlay packet protocol following MAC termination of ethernet header";
    }
    leaf ethernet_no_termination_on_l3_port {
      type oc-yang:counter64;
      description
        "Failed to terminate L3-AC ports ";
    }
    leaf l3_glean_adj {
      type oc-yang:counter64;
      description
        "L3 forwarding FIB lookup could not resolve next hop";
    }
    leaf l3_local_subnet {
      type oc-yang:counter64;
      description
        "L3 forwarding FIB lookup is unresolved path It has hit local subnet route. ";
    }
    leaf l3_drop_adj {
      type oc-yang:counter64;
      description
        "L3 forwarding FIB lookup to adjacent node";
    }
    leaf ethernet_no_service_mapping {
      type oc-yang:counter64;
      description
        "Failed to map L2-Logical Port and VLAN-ID to source LP or MAC relay attributes";
    }
    leaf l3_ttl_or_hop_limit_is_one {
      type oc-yang:counter64;
      description
        " OFA_LA_EVENT_L3_TTL_IS_ONE_RX";
    }
    leaf l3_ttl_is_one_rx {
      type oc-yang:counter64;
      description
        "Incoming packet TTL is 1.Set a RX trap";
    }
    leaf ipv6_hop_limit_is_one_rx {
      type oc-yang:counter64;
      description
        " Ipv6 packet hop Limit is 1";
    }
    leaf mpls_ilm_miss {
      type oc-yang:counter64;
      description
        "MPLS packet forwarding lookup failed in MPLS forwarding database";
    }
    leaf l3_bfd_micro_ip_disabled {
      type oc-yang:counter64;
      description
        "Set a trap if IP protocol is disabled and incoming packet is IP UDP BFD micro hop packet required to bring up member link";
    }
    leaf ipv4_unknown_protocol {
      type oc-yang:counter64;
      description
        "Incoming packet IPv4 header protocol field is unknown";
    }
    leaf ipv6_illegal_dip {
      type oc-yang:counter64;
      description
        "Incoming IPv6 packet identified with illegal Destination IP";
    }
    leaf ipv6_zero_payload {
      type oc-yang:counter64;
      description
        "Incoming IPv6 packet identified with illegal payload-length is 0 and not hop-by-hop packet";
    }
    leaf l3_acl_drop {
      type oc-yang:counter64;
      description
        "L3 egress security ACL or User-Defined-Fields ACLs policy action deny packet";
    }
    leaf l3_acl_force_punt {
      type oc-yang:counter64;
      description
        "L3 egress security ACL or User-Defined-Fields ACLs policy action to punt packet to host";
    }
    leaf l3_no_l3_dlp_mapping {
      type oc-yang:counter64;
      description
        " The L3 DLP mapping is not available for the packet";
    }
    leaf l3_l3_dlp_disabled {
      type oc-yang:counter64;
      description
        "set a trap if egress L3 Destination Logical Port is disabled for 1 plus 1 linear protection";
    }
    leaf l3_asbr_table_miss {
      type oc-yang:counter64;
      description
        "No match found in per DPE and ASBR table during BGPLU label lookup ";
    }
    leaf l3_egress_monitor {
      type oc-yang:counter64;
      description
        "L3 egress interface is enabled for Netflow ";
    }
    leaf l3_encap_table_miss {
      type oc-yang:counter64;
      description
        "Trap if enacapsulation header or data for MPLS ASBR label or SRv6 SID cannot be determined";
    }
    leaf l3_glean_aci_proxy {
      type oc-yang:counter64;
      description
        "Forwarding destination resolved to glean adjacency Cisco ACI";
    }
    leaf l3_null_adj {
      type oc-yang:counter64;
      description
        "L3 forwarding FIB lookup indicates packets destined to a NULL interface";
    }
    leaf l3_no_hbm_access_dip {
      type oc-yang:counter64;
      description
        "IP packet destination IP LPM lookup failed";
    }
    leaf l3_no_hbm_access_sip {
      type oc-yang:counter64;
      description
        "IP packet source IP LPM lookup failed";
    }
    leaf l3_invalid_spi {
      type oc-yang:counter64;
      description
        "Incoming packet is processed only if packet intended for Security Engine.Trap if security profile cannot be determined or unencrypted clear packet destined to receive SEC";
    }
    leaf l3_int_hop_limit {
      type oc-yang:counter64;
      description
        "L3 egress packets header hop limit is less than or equal to 1";
    }
    leaf l3_ip_mc_drop {
      type oc-yang:counter64;
      description
        "IP MC packet simple MC RPF check failed";
    }
    leaf l3_ip_mc_punt_dc_pass {
      type oc-yang:counter64;
      description
        "Directly connected route IP multicast and IP MC RPF check passed";
    }
    leaf l3_ip_multicast_not_found {
      type oc-yang:counter64;
      description
        " IP multicast packet forwarding lookup failed in Multicast Group database";
    }
    leaf l3_l3_same_tunnel_intf {
      type oc-yang:counter64;
      description
        " Trap if source tunnel port is equal to destination tunnel port";
    }
    leaf l3_lpm_drop {
      type oc-yang:counter64;
      description
        "IP unicast packet LPM destination resolved to a drop destination or VRF redirect exceeded iterations";
    }
    leaf l3_lpm_error {
      type oc-yang:counter64;
      description
        "trap if IP prefix database lookup failed";
    }
    leaf l3_mc_same_interface {
      type oc-yang:counter64;
      description
        "Filter IP multicast packets copies destined to the same L3 interface packet received from excluding collapsed multicast bridge copies";
    }
    leaf l3_no_hbm_access_og {
      type oc-yang:counter64;
      description
        "Database lookup to retrieve IP object group compression failed";
    }
    leaf l3_packet_from_tunnel {
      type oc-yang:counter64;
      description
        "Trap if packet was decapsulated on an IP tunnel and destined to another IP tunnel";
    }
    leaf l3_split_horizon {
      type oc-yang:counter64;
      description
        "Checks if egress L3-DLP is allowed to receive packets from ingress L3-DLP";
    }
    leaf l3_tx_drop {
      type oc-yang:counter64;
      description
        "L3 Packet dropped in the transmit side";
    }
    leaf l3_user_trap1 {
      type oc-yang:counter64;
      description
        "General purpose trap";
    }
    leaf l3_user_trap2 {
      type oc-yang:counter64;
      description
        " Generalpurpose trap";
    }
    leaf l3_rx_mru_failure {
      type oc-yang:counter64;
      description
        "L3 RX MRU exceeded";
    }
    leaf l3_no_lp_over_lag_mapping {
      type oc-yang:counter64;
      description
        "trap if failed to resolve Virtual Output Queue over LAG";
    }
    leaf l3_no_vni_mapping {
      type oc-yang:counter64;
      description
        " trap if could not resolve VNI from packet VRF in encapsulation";
    }
    leaf l3_no_vpn_label_found {
      type oc-yang:counter64;
      description
        "trap if expecting L3 IPv4 or IPv6 VPN label or L2 MPLS VPN label";
    }
    leaf l3_tunnel_sip_invalid {
      type oc-yang:counter64;
      description
        "Tunnel SIP ACL qualification failed";
    }
    leaf l3_tx_frr_drop {
      type oc-yang:counter64;
      description
        "Packet failed egress MLDP Transmit FRR checks";
    }
    leaf l3_tx_mtu_failure {
      type oc-yang:counter64;
      description
        "Transmit Packet exceeds egress port MTU";
    }
    leaf mpls_te_midpoint_ldp_labels_miss {
      type oc-yang:counter64;
      description
        "On egress failed to resolve the Midpoint Traffic-Engineering or LDP labels in encap database";
    }
    leaf mpls_unknown_protocol_after_bos {
      type oc-yang:counter64;
      description
        "MPLS packet reached BOS. Next layer protocol is unknown";
    }
    leaf mpls_ttl_is_zero {
      type oc-yang:counter64;
      description
        "Incoming MPLS packets header TTL value equal to 1";
    }
    leaf mpls_forwarding_disabled {
      type oc-yang:counter64;
      description
        "Received MPLS packet however MPLS forwarding is disabled";
    }
    leaf mpls_invalid_ttl {
      type oc-yang:counter64;
      description
        "Outgoing MPLS packet to be transmitted has MPLS header TTL field equal set 1";
    }
    leaf mpls_ilm_vrf_label_miss {
      type oc-yang:counter64;
      description
        "Label lookup in VRF fails on a CsC lookup miss in VRF MPLS forwarding database";
    }
    leaf mpls_ipv4_over_ipv6_explicit_null {
      type oc-yang:counter64;
      description
        "Error identified in packet format";
    }
    leaf mpls_extension_label {
      type oc-yang:counter64;
      description
        "Incoming MPLS packets label is reserved extension label";
    }
    leaf mpls_term_forwarding_disabled {
      type oc-yang:counter64;
      description
        " MPLS Termination Forwarding is Disabled";
    }
    leaf mpls_mpls_tp_over_lsp {
      type oc-yang:counter64;
      description
        "Incoming MPLS packets label is reserved GAL label";
    }
    leaf mpls_vpn_ttl_one {
      type oc-yang:counter64;
      description
        "VPN terminated";
    }
    leaf mpls_pwhe_fwd_unconfigured_slice {
      type oc-yang:counter64;
      description
        "MPLS PWE packet is forwarded on the slice where the configuration is not present";
    }
    leaf mpls_unexpected_reserved_label {
      type oc-yang:counter64;
      description
        "Incoming MPLS packets label is unknow reserved label";
    }
    leaf ipv4_iic_check_fail {
      type oc-yang:counter64;
      description
        "Ingress L3 Logical port is not in FTAG Tree";
    }
    leaf ipv4_non_comp_mc {
      type oc-yang:counter64;
      description
        "Incompatible IPV4 MC Addresses";
    }
    leaf ipv6_non_comp_mc {
      type oc-yang:counter64;
      description
        "Incompatible IPv6 MC Addresses";
    }
    leaf oamp_pfc_lookup_failed {
      type oc-yang:counter64;
      description
        "PFC SSP Lookup Failed";
    }
    leaf oamp_eth_mep_mapping_failed {
      type oc-yang:counter64;
      description
        "No Match in MEP Mapping lookup";
    }
    leaf oamp_eth_bad_md_name_format {
      type oc-yang:counter64;
      description
        "MD Name format is not equal to 01 Y1731";
    }
    leaf oamp_eth_multicast_da_no_match {
      type oc-yang:counter64;
      description
        "wRONG mULTICAST DA in OAM packet";
    }
    leaf oamp_eth_wrong_meg_id_format {
      type oc-yang:counter64;
      description
        " MEG Id format or length does not match MEP DB entry";
    }
    leaf oamp_eth_ccm_tlv_no_match {
      type oc-yang:counter64;
      description
        " TLV Offset packet is not equal to 70";
    }
    leaf oamp_transport_not_supported {
      type oc-yang:counter64;
      description
        " BFD or SR-PM processing session with incorrect transport";
    }
    leaf oamp_session_lookup_failed {
      type oc-yang:counter64;
      description
        " BFD or SR-PM session lookup failed";
    }
    leaf oamp_incorrect_ttl {
      type oc-yang:counter64;
      description
        "BFD failing TTL check";
    }
    leaf oamp_invalid_protocol {
      type oc-yang:counter64;
      description
        "BFD or SR-PM processing failing protocol check";
    }
    leaf oamp_bfd_incorrect_version {
      type oc-yang:counter64;
      description
        " BFD incorrect version";
    }
    leaf oamp_incorrect_address {
      type oc-yang:counter64;
      description
        "BFD or SR-PM processing incorrect address";
    }
    leaf oamp_session_received {
      type oc-yang:counter64;
      description
        "BFD or SR-PM session received";
    }
    leaf oamp_eth_unicast_da_no_match {
      type oc-yang:counter64;
      description
        "Unicast DA in OAM Packet doesnt match the MEP Mac address ";
    }
    leaf oamp_pfc_drop_invalid_rx {
      type oc-yang:counter64;
      description
        " PFC invalid Receive packet";
    }
    leaf oamp_icmp_incorrect_session_type_or_ssp {
      type oc-yang:counter64;
      description
        " Received incorrect ession type or on a wrong ssp";
    }
    leaf ipv4_options_exist_rx {
      type oc-yang:counter64;
      description
        " Received packet has IPV4 OPTIONS";
    }
    leaf ipv4_options_exist_tx {
      type oc-yang:counter64;
      description
        " Packet that needs to be transmitted needs IPV4 OPTIONS addition";
    }
    leaf ipv4_checksum {
      type oc-yang:counter64;
      description
        " Error in IPV4 CHECKSUM";
    }
    leaf ipv4_header_error {
      type oc-yang:counter64;
      description
        " Error in IPv4 header fields";
    }
    leaf ipv6_hop_by_hop {
      type oc-yang:counter64;
      description
        "Hop by hop header is set as the next header for the IPV6 packet";
    }
    leaf ipv6_header_error {
      type oc-yang:counter64;
      description
        " Error in IPV6 HEADER fields";
    }
    leaf ipv4_mc_forwarding_disabled {
      type oc-yang:counter64;
      description
        "IPV4 Multicast forwarding is disabled on the received port";
    }
    leaf ipv6_mc_forwarding_disabled {
      type oc-yang:counter64;
      description
        " IPV6 Multicast forwarding is disabled on the received port";
    }
    leaf counter_slice0_ifg_ifgbe_core_rx_oobe_crc_err_counter0_rx_oobe_port_crc_err_cnt {
      type oc-yang:counter64;
      description
        "OOB Extract CRC error counter per port";
    }
    leaf counter_slice0_ifg_ifgbe_core_rx_oobe_crc_err_counter1_rx_oobe_port_crc_err_cnt {
      type oc-yang:counter64;
      description
        "OOB Extract CRC error counter per port";
    }
    leaf counter_slice0_ifg_ifgbe_core_rx_oobe_crc_err_counter2_rx_oobe_port_crc_err_cnt {
      type oc-yang:counter64;
      description
        "OOB Extract CRC error counter per port";
    }
    leaf counter_slice0_ifg_ifgbe_core_rx_oobe_crc_err_counter3_rx_oobe_port_crc_err_cnt {
      type oc-yang:counter64;
      description
        "OOB Extract CRC error counter per port";
    }
    leaf counter_slice0_ifg_ifgbe_core_rx_oobe_crc_err_counter4_rx_oobe_port_crc_err_cnt {
      type oc-yang:counter64;
      description
        "OOB Extract CRC error counter per port";
    }
    leaf counter_slice0_ifg_ifgbe_core_rx_oobe_crc_err_counter5_rx_oobe_port_crc_err_cnt {
      type oc-yang:counter64;
      description
        "OOB Extract CRC error counter per port";
    }
    leaf counter_slice0_ifg_ifgbe_core_rx_oobe_crc_err_counter6_rx_oobe_port_crc_err_cnt {
      type oc-yang:counter64;
      description
        "OOB Extract CRC error counter per port";
    }
    leaf counter_slice0_ifg_ifgbe_core_rx_oobe_crc_err_counter7_rx_oobe_port_crc_err_cnt {
      type oc-yang:counter64;
      description
        "OOB Extract CRC error counter per port";
    }
    leaf counter_slice0_ifg_ifgbe_core_rx_oobe_crc_err_counter8_rx_oobe_port_crc_err_cnt {
      type oc-yang:counter64;
      description
        "OOB Extract CRC error counter per port";
    }
    leaf counter_slice0_ifg_ifgbe_core_rx_oobe_crc_err_counter9_rx_oobe_port_crc_err_cnt {
      type oc-yang:counter64;
      description
        "OOB Extract CRC error counter per port";
    }
    leaf counter_slice0_ifg_ifgbe_core_rx_oobe_crc_err_counter10_rx_oobe_port_crc_err_cnt {
      type oc-yang:counter64;
      description
        "OOB Extract CRC error counter per port";
    }
    leaf counter_slice0_ifg_ifgbe_core_rx_oobe_crc_err_counter11_rx_oobe_port_crc_err_cnt {
      type oc-yang:counter64;
      description
        "OOB Extract CRC error counter per port";
    }
    leaf counter_slice0_ifg_ifgbe_core_rx_oobe_crc_err_counter12_rx_oobe_port_crc_err_cnt {
      type oc-yang:counter64;
      description
        "OOB Extract CRC error counter per port";
    }
    leaf counter_slice0_ifg_ifgbe_core_rx_oobe_crc_err_counter13_rx_oobe_port_crc_err_cnt {
      type oc-yang:counter64;
      description
        "OOB Extract CRC error counter per port";
    }
    leaf counter_slice0_ifg_ifgbe_core_rx_oobe_crc_err_counter14_rx_oobe_port_crc_err_cnt {
      type oc-yang:counter64;
      description
        "OOB Extract CRC error counter per port";
    }
    leaf counter_slice0_ifg_ifgbe_core_rx_oobe_crc_err_counter15_rx_oobe_port_crc_err_cnt {
      type oc-yang:counter64;
      description
        "OOB Extract CRC error counter per port";
    }
    leaf counter_slice0_ifg_ifgbe_core_rx_oobe_crc_err_counter16_rx_oobe_port_crc_err_cnt {
      type oc-yang:counter64;
      description
        "OOB Extract CRC error counter per port";
    }
    leaf counter_slice0_ifg_ifgbe_core_rx_oobe_crc_err_counter17_rx_oobe_port_crc_err_cnt {
      type oc-yang:counter64;
      description
        "OOB Extract CRC error counter per port";
    }
    leaf counter_slice0_ifg_ifgbe_core_rx_oobe_crc_err_counter18_rx_oobe_port_crc_err_cnt {
      type oc-yang:counter64;
      description
        "OOB Extract CRC error counter per port";
    }
    leaf counter_slice0_ifg_ifgbe_core_rx_oobe_crc_err_counter19_rx_oobe_port_crc_err_cnt {
      type oc-yang:counter64;
      description
        "OOB Extract CRC error counter per port";
    }
    leaf counter_slice0_ifg_ifgbe_core_rx_oobe_crc_err_counter20_rx_oobe_port_crc_err_cnt {
      type oc-yang:counter64;
      description
        "OOB Extract CRC error counter per port";
    }
    leaf counter_slice0_ifg_ifgbe_core_rx_oobe_crc_err_counter21_rx_oobe_port_crc_err_cnt {
      type oc-yang:counter64;
      description
        "OOB Extract CRC error counter per port";
    }
    leaf counter_slice0_ifg_ifgbe_core_rx_oobe_crc_err_counter22_rx_oobe_port_crc_err_cnt {
      type oc-yang:counter64;
      description
        "OOB Extract CRC error counter per port";
    }
    leaf counter_slice0_ifg_ifgbe_core_rx_oobe_crc_err_counter23_rx_oobe_port_crc_err_cnt {
      type oc-yang:counter64;
      description
        "OOB Extract CRC error counter per port";
    }
    leaf counter_slice0_ifg_ifgbe_core_rx_oobe_crc_err_counter24_rx_oobe_port_crc_err_cnt {
      type oc-yang:counter64;
      description
        "OOB Extract CRC error counter per port";
    }
    leaf counter_slice0_ifg_ifgbe_core_rx_oobe_crc_err_counter25_rx_oobe_port_crc_err_cnt {
      type oc-yang:counter64;
      description
        "OOB Extract CRC error counter per port";
    }
    leaf counter_slice0_ifg_ifgbe_core_rx_oobe_crc_err_counter26_rx_oobe_port_crc_err_cnt {
      type oc-yang:counter64;
      description
        "OOB Extract CRC error counter per port";
    }
    leaf counter_slice0_ifg_ifgbe_core_rx_oobe_crc_err_counter27_rx_oobe_port_crc_err_cnt {
      type oc-yang:counter64;
      description
        "OOB Extract CRC error counter per port";
    }
    leaf counter_slice0_ifg_ifgbe_core_rx_oobe_crc_err_counter28_rx_oobe_port_crc_err_cnt {
      type oc-yang:counter64;
      description
        "OOB Extract CRC error counter per port";
    }
    leaf counter_slice0_ifg_ifgbe_core_rx_oobe_crc_err_counter29_rx_oobe_port_crc_err_cnt {
      type oc-yang:counter64;
      description
        "OOB Extract CRC error counter per port";
    }
    leaf counter_slice0_ifg_ifgbe_core_rx_oobe_crc_err_counter30_rx_oobe_port_crc_err_cnt {
      type oc-yang:counter64;
      description
        "OOB Extract CRC error counter per port";
    }
    leaf counter_slice0_ifg_ifgbe_core_rx_oobe_crc_err_counter31_rx_oobe_port_crc_err_cnt {
      type oc-yang:counter64;
      description
        "OOB Extract CRC error counter per port";
    }
    leaf counter_slice1_ifg_ifgbe_core_rx_oobe_crc_err_counter0_rx_oobe_port_crc_err_cnt {
      type oc-yang:counter64;
      description
        "OOB Extract CRC error counter per port";
    }
    leaf counter_slice1_ifg_ifgbe_core_rx_oobe_crc_err_counter1_rx_oobe_port_crc_err_cnt {
      type oc-yang:counter64;
      description
        "OOB Extract CRC error counter per port";
    }
    leaf counter_slice1_ifg_ifgbe_core_rx_oobe_crc_err_counter2_rx_oobe_port_crc_err_cnt {
      type oc-yang:counter64;
      description
        "OOB Extract CRC error counter per port";
    }
    leaf counter_slice1_ifg_ifgbe_core_rx_oobe_crc_err_counter3_rx_oobe_port_crc_err_cnt {
      type oc-yang:counter64;
      description
        "OOB Extract CRC error counter per port";
    }
    leaf counter_slice1_ifg_ifgbe_core_rx_oobe_crc_err_counter4_rx_oobe_port_crc_err_cnt {
      type oc-yang:counter64;
      description
        "OOB Extract CRC error counter per port";
    }
    leaf counter_slice1_ifg_ifgbe_core_rx_oobe_crc_err_counter5_rx_oobe_port_crc_err_cnt {
      type oc-yang:counter64;
      description
        "OOB Extract CRC error counter per port";
    }
    leaf counter_slice1_ifg_ifgbe_core_rx_oobe_crc_err_counter6_rx_oobe_port_crc_err_cnt {
      type oc-yang:counter64;
      description
        "OOB Extract CRC error counter per port";
    }
    leaf counter_slice1_ifg_ifgbe_core_rx_oobe_crc_err_counter7_rx_oobe_port_crc_err_cnt {
      type oc-yang:counter64;
      description
        "OOB Extract CRC error counter per port";
    }
    leaf counter_slice1_ifg_ifgbe_core_rx_oobe_crc_err_counter8_rx_oobe_port_crc_err_cnt {
      type oc-yang:counter64;
      description
        "OOB Extract CRC error counter per port";
    }
    leaf counter_slice1_ifg_ifgbe_core_rx_oobe_crc_err_counter9_rx_oobe_port_crc_err_cnt {
      type oc-yang:counter64;
      description
        "OOB Extract CRC error counter per port";
    }
    leaf counter_slice1_ifg_ifgbe_core_rx_oobe_crc_err_counter10_rx_oobe_port_crc_err_cnt {
      type oc-yang:counter64;
      description
        "OOB Extract CRC error counter per port";
    }
    leaf counter_slice1_ifg_ifgbe_core_rx_oobe_crc_err_counter11_rx_oobe_port_crc_err_cnt {
      type oc-yang:counter64;
      description
        "OOB Extract CRC error counter per port";
    }
    leaf counter_slice1_ifg_ifgbe_core_rx_oobe_crc_err_counter12_rx_oobe_port_crc_err_cnt {
      type oc-yang:counter64;
      description
        "OOB Extract CRC error counter per port";
    }
    leaf counter_slice1_ifg_ifgbe_core_rx_oobe_crc_err_counter13_rx_oobe_port_crc_err_cnt {
      type oc-yang:counter64;
      description
        "OOB Extract CRC error counter per port";
    }
    leaf counter_slice1_ifg_ifgbe_core_rx_oobe_crc_err_counter14_rx_oobe_port_crc_err_cnt {
      type oc-yang:counter64;
      description
        "OOB Extract CRC error counter per port";
    }
    leaf counter_slice1_ifg_ifgbe_core_rx_oobe_crc_err_counter15_rx_oobe_port_crc_err_cnt {
      type oc-yang:counter64;
      description
        "OOB Extract CRC error counter per port";
    }
    leaf counter_slice1_ifg_ifgbe_core_rx_oobe_crc_err_counter16_rx_oobe_port_crc_err_cnt {
      type oc-yang:counter64;
      description
        "OOB Extract CRC error counter per port";
    }
    leaf counter_slice1_ifg_ifgbe_core_rx_oobe_crc_err_counter17_rx_oobe_port_crc_err_cnt {
      type oc-yang:counter64;
      description
        "OOB Extract CRC error counter per port";
    }
    leaf counter_slice1_ifg_ifgbe_core_rx_oobe_crc_err_counter18_rx_oobe_port_crc_err_cnt {
      type oc-yang:counter64;
      description
        "OOB Extract CRC error counter per port";
    }
    leaf counter_slice1_ifg_ifgbe_core_rx_oobe_crc_err_counter19_rx_oobe_port_crc_err_cnt {
      type oc-yang:counter64;
      description
        "OOB Extract CRC error counter per port";
    }
    leaf counter_slice1_ifg_ifgbe_core_rx_oobe_crc_err_counter20_rx_oobe_port_crc_err_cnt {
      type oc-yang:counter64;
      description
        "OOB Extract CRC error counter per port";
    }
    leaf counter_slice1_ifg_ifgbe_core_rx_oobe_crc_err_counter21_rx_oobe_port_crc_err_cnt {
      type oc-yang:counter64;
      description
        "OOB Extract CRC error counter per port";
    }
    leaf counter_slice1_ifg_ifgbe_core_rx_oobe_crc_err_counter22_rx_oobe_port_crc_err_cnt {
      type oc-yang:counter64;
      description
        "OOB Extract CRC error counter per port";
    }
    leaf counter_slice1_ifg_ifgbe_core_rx_oobe_crc_err_counter23_rx_oobe_port_crc_err_cnt {
      type oc-yang:counter64;
      description
        "OOB Extract CRC error counter per port";
    }
    leaf counter_slice1_ifg_ifgbe_core_rx_oobe_crc_err_counter24_rx_oobe_port_crc_err_cnt {
      type oc-yang:counter64;
      description
        "OOB Extract CRC error counter per port";
    }
    leaf counter_slice1_ifg_ifgbe_core_rx_oobe_crc_err_counter25_rx_oobe_port_crc_err_cnt {
      type oc-yang:counter64;
      description
        "OOB Extract CRC error counter per port";
    }
    leaf counter_slice1_ifg_ifgbe_core_rx_oobe_crc_err_counter26_rx_oobe_port_crc_err_cnt {
      type oc-yang:counter64;
      description
        "OOB Extract CRC error counter per port";
    }
    leaf counter_slice1_ifg_ifgbe_core_rx_oobe_crc_err_counter27_rx_oobe_port_crc_err_cnt {
      type oc-yang:counter64;
      description
        "OOB Extract CRC error counter per port";
    }
    leaf counter_slice1_ifg_ifgbe_core_rx_oobe_crc_err_counter28_rx_oobe_port_crc_err_cnt {
      type oc-yang:counter64;
      description
        "OOB Extract CRC error counter per port";
    }
    leaf counter_slice1_ifg_ifgbe_core_rx_oobe_crc_err_counter29_rx_oobe_port_crc_err_cnt {
      type oc-yang:counter64;
      description
        "OOB Extract CRC error counter per port";
    }
    leaf counter_slice1_ifg_ifgbe_core_rx_oobe_crc_err_counter30_rx_oobe_port_crc_err_cnt {
      type oc-yang:counter64;
      description
        "OOB Extract CRC error counter per port";
    }
    leaf counter_slice1_ifg_ifgbe_core_rx_oobe_crc_err_counter31_rx_oobe_port_crc_err_cnt {
      type oc-yang:counter64;
      description
        "OOB Extract CRC error counter per port";
    }
    leaf counter_slice2_ifg_ifgbe_core_rx_oobe_crc_err_counter0_rx_oobe_port_crc_err_cnt {
      type oc-yang:counter64;
      description
        "OOB Extract CRC error counter per port";
    }
    leaf counter_slice2_ifg_ifgbe_core_rx_oobe_crc_err_counter1_rx_oobe_port_crc_err_cnt {
      type oc-yang:counter64;
      description
        "OOB Extract CRC error counter per port";
    }
    leaf counter_slice2_ifg_ifgbe_core_rx_oobe_crc_err_counter2_rx_oobe_port_crc_err_cnt {
      type oc-yang:counter64;
      description
        "OOB Extract CRC error counter per port";
    }
    leaf counter_slice2_ifg_ifgbe_core_rx_oobe_crc_err_counter3_rx_oobe_port_crc_err_cnt {
      type oc-yang:counter64;
      description
        "OOB Extract CRC error counter per port";
    }
    leaf counter_slice2_ifg_ifgbe_core_rx_oobe_crc_err_counter4_rx_oobe_port_crc_err_cnt {
      type oc-yang:counter64;
      description
        "OOB Extract CRC error counter per port";
    }
    leaf counter_slice2_ifg_ifgbe_core_rx_oobe_crc_err_counter5_rx_oobe_port_crc_err_cnt {
      type oc-yang:counter64;
      description
        "OOB Extract CRC error counter per port";
    }
    leaf counter_slice2_ifg_ifgbe_core_rx_oobe_crc_err_counter6_rx_oobe_port_crc_err_cnt {
      type oc-yang:counter64;
      description
        "OOB Extract CRC error counter per port";
    }
    leaf counter_slice2_ifg_ifgbe_core_rx_oobe_crc_err_counter7_rx_oobe_port_crc_err_cnt {
      type oc-yang:counter64;
      description
        "OOB Extract CRC error counter per port";
    }
    leaf counter_slice2_ifg_ifgbe_core_rx_oobe_crc_err_counter8_rx_oobe_port_crc_err_cnt {
      type oc-yang:counter64;
      description
        "OOB Extract CRC error counter per port";
    }
    leaf counter_slice2_ifg_ifgbe_core_rx_oobe_crc_err_counter9_rx_oobe_port_crc_err_cnt {
      type oc-yang:counter64;
      description
        "OOB Extract CRC error counter per port";
    }
    leaf counter_slice2_ifg_ifgbe_core_rx_oobe_crc_err_counter10_rx_oobe_port_crc_err_cnt {
      type oc-yang:counter64;
      description
        "OOB Extract CRC error counter per port";
    }
    leaf counter_slice2_ifg_ifgbe_core_rx_oobe_crc_err_counter11_rx_oobe_port_crc_err_cnt {
      type oc-yang:counter64;
      description
        "OOB Extract CRC error counter per port";
    }
    leaf counter_slice2_ifg_ifgbe_core_rx_oobe_crc_err_counter12_rx_oobe_port_crc_err_cnt {
      type oc-yang:counter64;
      description
        "OOB Extract CRC error counter per port";
    }
    leaf counter_slice2_ifg_ifgbe_core_rx_oobe_crc_err_counter13_rx_oobe_port_crc_err_cnt {
      type oc-yang:counter64;
      description
        "OOB Extract CRC error counter per port";
    }
    leaf counter_slice2_ifg_ifgbe_core_rx_oobe_crc_err_counter14_rx_oobe_port_crc_err_cnt {
      type oc-yang:counter64;
      description
        "OOB Extract CRC error counter per port";
    }
    leaf counter_slice2_ifg_ifgbe_core_rx_oobe_crc_err_counter15_rx_oobe_port_crc_err_cnt {
      type oc-yang:counter64;
      description
        "OOB Extract CRC error counter per port";
    }
    leaf counter_slice2_ifg_ifgbe_core_rx_oobe_crc_err_counter16_rx_oobe_port_crc_err_cnt {
      type oc-yang:counter64;
      description
        "OOB Extract CRC error counter per port";
    }
    leaf counter_slice2_ifg_ifgbe_core_rx_oobe_crc_err_counter17_rx_oobe_port_crc_err_cnt {
      type oc-yang:counter64;
      description
        "OOB Extract CRC error counter per port";
    }
    leaf counter_slice2_ifg_ifgbe_core_rx_oobe_crc_err_counter18_rx_oobe_port_crc_err_cnt {
      type oc-yang:counter64;
      description
        "OOB Extract CRC error counter per port";
    }
    leaf counter_slice2_ifg_ifgbe_core_rx_oobe_crc_err_counter19_rx_oobe_port_crc_err_cnt {
      type oc-yang:counter64;
      description
        "OOB Extract CRC error counter per port";
    }
    leaf counter_slice2_ifg_ifgbe_core_rx_oobe_crc_err_counter20_rx_oobe_port_crc_err_cnt {
      type oc-yang:counter64;
      description
        "OOB Extract CRC error counter per port";
    }
    leaf counter_slice2_ifg_ifgbe_core_rx_oobe_crc_err_counter21_rx_oobe_port_crc_err_cnt {
      type oc-yang:counter64;
      description
        "OOB Extract CRC error counter per port";
    }
    leaf counter_slice2_ifg_ifgbe_core_rx_oobe_crc_err_counter22_rx_oobe_port_crc_err_cnt {
      type oc-yang:counter64;
      description
        "OOB Extract CRC error counter per port";
    }
    leaf counter_slice2_ifg_ifgbe_core_rx_oobe_crc_err_counter23_rx_oobe_port_crc_err_cnt {
      type oc-yang:counter64;
      description
        "OOB Extract CRC error counter per port";
    }
    leaf counter_slice2_ifg_ifgbe_core_rx_oobe_crc_err_counter24_rx_oobe_port_crc_err_cnt {
      type oc-yang:counter64;
      description
        "OOB Extract CRC error counter per port";
    }
    leaf counter_slice2_ifg_ifgbe_core_rx_oobe_crc_err_counter25_rx_oobe_port_crc_err_cnt {
      type oc-yang:counter64;
      description
        "OOB Extract CRC error counter per port";
    }
    leaf counter_slice2_ifg_ifgbe_core_rx_oobe_crc_err_counter26_rx_oobe_port_crc_err_cnt {
      type oc-yang:counter64;
      description
        "OOB Extract CRC error counter per port";
    }
    leaf counter_slice2_ifg_ifgbe_core_rx_oobe_crc_err_counter27_rx_oobe_port_crc_err_cnt {
      type oc-yang:counter64;
      description
        "OOB Extract CRC error counter per port";
    }
    leaf counter_slice2_ifg_ifgbe_core_rx_oobe_crc_err_counter28_rx_oobe_port_crc_err_cnt {
      type oc-yang:counter64;
      description
        "OOB Extract CRC error counter per port";
    }
    leaf counter_slice2_ifg_ifgbe_core_rx_oobe_crc_err_counter29_rx_oobe_port_crc_err_cnt {
      type oc-yang:counter64;
      description
        "OOB Extract CRC error counter per port";
    }
    leaf counter_slice2_ifg_ifgbe_core_rx_oobe_crc_err_counter30_rx_oobe_port_crc_err_cnt {
      type oc-yang:counter64;
      description
        "OOB Extract CRC error counter per port";
    }
    leaf counter_slice2_ifg_ifgbe_core_rx_oobe_crc_err_counter31_rx_oobe_port_crc_err_cnt {
      type oc-yang:counter64;
      description
        "OOB Extract CRC error counter per port";
    }
    leaf counter_slice3_ifg_ifgbe_core_rx_oobe_crc_err_counter0_rx_oobe_port_crc_err_cnt {
      type oc-yang:counter64;
      description
        "OOB Extract CRC error counter per port";
    }
    leaf counter_slice3_ifg_ifgbe_core_rx_oobe_crc_err_counter1_rx_oobe_port_crc_err_cnt {
      type oc-yang:counter64;
      description
        "OOB Extract CRC error counter per port";
    }
    leaf counter_slice3_ifg_ifgbe_core_rx_oobe_crc_err_counter2_rx_oobe_port_crc_err_cnt {
      type oc-yang:counter64;
      description
        "OOB Extract CRC error counter per port";
    }
    leaf counter_slice3_ifg_ifgbe_core_rx_oobe_crc_err_counter3_rx_oobe_port_crc_err_cnt {
      type oc-yang:counter64;
      description
        "OOB Extract CRC error counter per port";
    }
    leaf counter_slice3_ifg_ifgbe_core_rx_oobe_crc_err_counter4_rx_oobe_port_crc_err_cnt {
      type oc-yang:counter64;
      description
        "OOB Extract CRC error counter per port";
    }
    leaf counter_slice3_ifg_ifgbe_core_rx_oobe_crc_err_counter5_rx_oobe_port_crc_err_cnt {
      type oc-yang:counter64;
      description
        "OOB Extract CRC error counter per port";
    }
    leaf counter_slice3_ifg_ifgbe_core_rx_oobe_crc_err_counter6_rx_oobe_port_crc_err_cnt {
      type oc-yang:counter64;
      description
        "OOB Extract CRC error counter per port";
    }
    leaf counter_slice3_ifg_ifgbe_core_rx_oobe_crc_err_counter7_rx_oobe_port_crc_err_cnt {
      type oc-yang:counter64;
      description
        "OOB Extract CRC error counter per port";
    }
    leaf counter_slice3_ifg_ifgbe_core_rx_oobe_crc_err_counter8_rx_oobe_port_crc_err_cnt {
      type oc-yang:counter64;
      description
        "OOB Extract CRC error counter per port";
    }
    leaf counter_slice3_ifg_ifgbe_core_rx_oobe_crc_err_counter9_rx_oobe_port_crc_err_cnt {
      type oc-yang:counter64;
      description
        "OOB Extract CRC error counter per port";
    }
    leaf counter_slice3_ifg_ifgbe_core_rx_oobe_crc_err_counter10_rx_oobe_port_crc_err_cnt {
      type oc-yang:counter64;
      description
        "OOB Extract CRC error counter per port";
    }
    leaf counter_slice3_ifg_ifgbe_core_rx_oobe_crc_err_counter11_rx_oobe_port_crc_err_cnt {
      type oc-yang:counter64;
      description
        "OOB Extract CRC error counter per port";
    }
    leaf counter_slice3_ifg_ifgbe_core_rx_oobe_crc_err_counter12_rx_oobe_port_crc_err_cnt {
      type oc-yang:counter64;
      description
        "OOB Extract CRC error counter per port";
    }
    leaf counter_slice3_ifg_ifgbe_core_rx_oobe_crc_err_counter13_rx_oobe_port_crc_err_cnt {
      type oc-yang:counter64;
      description
        "OOB Extract CRC error counter per port";
    }
    leaf counter_slice3_ifg_ifgbe_core_rx_oobe_crc_err_counter14_rx_oobe_port_crc_err_cnt {
      type oc-yang:counter64;
      description
        "OOB Extract CRC error counter per port";
    }
    leaf counter_slice3_ifg_ifgbe_core_rx_oobe_crc_err_counter15_rx_oobe_port_crc_err_cnt {
      type oc-yang:counter64;
      description
        "OOB Extract CRC error counter per port";
    }
    leaf counter_slice3_ifg_ifgbe_core_rx_oobe_crc_err_counter16_rx_oobe_port_crc_err_cnt {
      type oc-yang:counter64;
      description
        "OOB Extract CRC error counter per port";
    }
    leaf counter_slice3_ifg_ifgbe_core_rx_oobe_crc_err_counter17_rx_oobe_port_crc_err_cnt {
      type oc-yang:counter64;
      description
        "OOB Extract CRC error counter per port";
    }
    leaf counter_slice3_ifg_ifgbe_core_rx_oobe_crc_err_counter18_rx_oobe_port_crc_err_cnt {
      type oc-yang:counter64;
      description
        "OOB Extract CRC error counter per port";
    }
    leaf counter_slice3_ifg_ifgbe_core_rx_oobe_crc_err_counter19_rx_oobe_port_crc_err_cnt {
      type oc-yang:counter64;
      description
        "OOB Extract CRC error counter per port";
    }
    leaf counter_slice3_ifg_ifgbe_core_rx_oobe_crc_err_counter20_rx_oobe_port_crc_err_cnt {
      type oc-yang:counter64;
      description
        "OOB Extract CRC error counter per port";
    }
    leaf counter_slice3_ifg_ifgbe_core_rx_oobe_crc_err_counter21_rx_oobe_port_crc_err_cnt {
      type oc-yang:counter64;
      description
        "OOB Extract CRC error counter per port";
    }
    leaf counter_slice3_ifg_ifgbe_core_rx_oobe_crc_err_counter22_rx_oobe_port_crc_err_cnt {
      type oc-yang:counter64;
      description
        "OOB Extract CRC error counter per port";
    }
    leaf counter_slice3_ifg_ifgbe_core_rx_oobe_crc_err_counter23_rx_oobe_port_crc_err_cnt {
      type oc-yang:counter64;
      description
        "OOB Extract CRC error counter per port";
    }
    leaf counter_slice3_ifg_ifgbe_core_rx_oobe_crc_err_counter24_rx_oobe_port_crc_err_cnt {
      type oc-yang:counter64;
      description
        "OOB Extract CRC error counter per port";
    }
    leaf counter_slice3_ifg_ifgbe_core_rx_oobe_crc_err_counter25_rx_oobe_port_crc_err_cnt {
      type oc-yang:counter64;
      description
        "OOB Extract CRC error counter per port";
    }
    leaf counter_slice3_ifg_ifgbe_core_rx_oobe_crc_err_counter26_rx_oobe_port_crc_err_cnt {
      type oc-yang:counter64;
      description
        "OOB Extract CRC error counter per port";
    }
    leaf counter_slice3_ifg_ifgbe_core_rx_oobe_crc_err_counter27_rx_oobe_port_crc_err_cnt {
      type oc-yang:counter64;
      description
        "OOB Extract CRC error counter per port";
    }
    leaf counter_slice3_ifg_ifgbe_core_rx_oobe_crc_err_counter28_rx_oobe_port_crc_err_cnt {
      type oc-yang:counter64;
      description
        "OOB Extract CRC error counter per port";
    }
    leaf counter_slice3_ifg_ifgbe_core_rx_oobe_crc_err_counter29_rx_oobe_port_crc_err_cnt {
      type oc-yang:counter64;
      description
        "OOB Extract CRC error counter per port";
    }
    leaf counter_slice3_ifg_ifgbe_core_rx_oobe_crc_err_counter30_rx_oobe_port_crc_err_cnt {
      type oc-yang:counter64;
      description
        "OOB Extract CRC error counter per port";
    }
    leaf counter_slice3_ifg_ifgbe_core_rx_oobe_crc_err_counter31_rx_oobe_port_crc_err_cnt {
      type oc-yang:counter64;
      description
        "OOB Extract CRC error counter per port";
    }
    leaf counter_slice4_ifg_ifgbe_core_rx_oobe_crc_err_counter0_rx_oobe_port_crc_err_cnt {
      type oc-yang:counter64;
      description
        "OOB Extract CRC error counter per port";
    }
    leaf counter_slice4_ifg_ifgbe_core_rx_oobe_crc_err_counter1_rx_oobe_port_crc_err_cnt {
      type oc-yang:counter64;
      description
        "OOB Extract CRC error counter per port";
    }
    leaf counter_slice4_ifg_ifgbe_core_rx_oobe_crc_err_counter2_rx_oobe_port_crc_err_cnt {
      type oc-yang:counter64;
      description
        "OOB Extract CRC error counter per port";
    }
    leaf counter_slice4_ifg_ifgbe_core_rx_oobe_crc_err_counter3_rx_oobe_port_crc_err_cnt {
      type oc-yang:counter64;
      description
        "OOB Extract CRC error counter per port";
    }
    leaf counter_slice4_ifg_ifgbe_core_rx_oobe_crc_err_counter4_rx_oobe_port_crc_err_cnt {
      type oc-yang:counter64;
      description
        "OOB Extract CRC error counter per port";
    }
    leaf counter_slice4_ifg_ifgbe_core_rx_oobe_crc_err_counter5_rx_oobe_port_crc_err_cnt {
      type oc-yang:counter64;
      description
        "OOB Extract CRC error counter per port";
    }
    leaf counter_slice4_ifg_ifgbe_core_rx_oobe_crc_err_counter6_rx_oobe_port_crc_err_cnt {
      type oc-yang:counter64;
      description
        "OOB Extract CRC error counter per port";
    }
    leaf counter_slice4_ifg_ifgbe_core_rx_oobe_crc_err_counter7_rx_oobe_port_crc_err_cnt {
      type oc-yang:counter64;
      description
        "OOB Extract CRC error counter per port";
    }
    leaf counter_slice4_ifg_ifgbe_core_rx_oobe_crc_err_counter8_rx_oobe_port_crc_err_cnt {
      type oc-yang:counter64;
      description
        "OOB Extract CRC error counter per port";
    }
    leaf counter_slice4_ifg_ifgbe_core_rx_oobe_crc_err_counter9_rx_oobe_port_crc_err_cnt {
      type oc-yang:counter64;
      description
        "OOB Extract CRC error counter per port";
    }
    leaf counter_slice4_ifg_ifgbe_core_rx_oobe_crc_err_counter10_rx_oobe_port_crc_err_cnt {
      type oc-yang:counter64;
      description
        "OOB Extract CRC error counter per port";
    }
    leaf counter_slice4_ifg_ifgbe_core_rx_oobe_crc_err_counter11_rx_oobe_port_crc_err_cnt {
      type oc-yang:counter64;
      description
        "OOB Extract CRC error counter per port";
    }
    leaf counter_slice4_ifg_ifgbe_core_rx_oobe_crc_err_counter12_rx_oobe_port_crc_err_cnt {
      type oc-yang:counter64;
      description
        "OOB Extract CRC error counter per port";
    }
    leaf counter_slice4_ifg_ifgbe_core_rx_oobe_crc_err_counter13_rx_oobe_port_crc_err_cnt {
      type oc-yang:counter64;
      description
        "OOB Extract CRC error counter per port";
    }
    leaf counter_slice4_ifg_ifgbe_core_rx_oobe_crc_err_counter14_rx_oobe_port_crc_err_cnt {
      type oc-yang:counter64;
      description
        "OOB Extract CRC error counter per port";
    }
    leaf counter_slice4_ifg_ifgbe_core_rx_oobe_crc_err_counter15_rx_oobe_port_crc_err_cnt {
      type oc-yang:counter64;
      description
        "OOB Extract CRC error counter per port";
    }
    leaf counter_slice4_ifg_ifgbe_core_rx_oobe_crc_err_counter16_rx_oobe_port_crc_err_cnt {
      type oc-yang:counter64;
      description
        "OOB Extract CRC error counter per port";
    }
    leaf counter_slice4_ifg_ifgbe_core_rx_oobe_crc_err_counter17_rx_oobe_port_crc_err_cnt {
      type oc-yang:counter64;
      description
        "OOB Extract CRC error counter per port";
    }
    leaf counter_slice4_ifg_ifgbe_core_rx_oobe_crc_err_counter18_rx_oobe_port_crc_err_cnt {
      type oc-yang:counter64;
      description
        "OOB Extract CRC error counter per port";
    }
    leaf counter_slice4_ifg_ifgbe_core_rx_oobe_crc_err_counter19_rx_oobe_port_crc_err_cnt {
      type oc-yang:counter64;
      description
        "OOB Extract CRC error counter per port";
    }
    leaf counter_slice4_ifg_ifgbe_core_rx_oobe_crc_err_counter20_rx_oobe_port_crc_err_cnt {
      type oc-yang:counter64;
      description
        "OOB Extract CRC error counter per port";
    }
    leaf counter_slice4_ifg_ifgbe_core_rx_oobe_crc_err_counter21_rx_oobe_port_crc_err_cnt {
      type oc-yang:counter64;
      description
        "OOB Extract CRC error counter per port";
    }
    leaf counter_slice4_ifg_ifgbe_core_rx_oobe_crc_err_counter22_rx_oobe_port_crc_err_cnt {
      type oc-yang:counter64;
      description
        "OOB Extract CRC error counter per port";
    }
    leaf counter_slice4_ifg_ifgbe_core_rx_oobe_crc_err_counter23_rx_oobe_port_crc_err_cnt {
      type oc-yang:counter64;
      description
        "OOB Extract CRC error counter per port";
    }
    leaf counter_slice4_ifg_ifgbe_core_rx_oobe_crc_err_counter24_rx_oobe_port_crc_err_cnt {
      type oc-yang:counter64;
      description
        "OOB Extract CRC error counter per port";
    }
    leaf counter_slice4_ifg_ifgbe_core_rx_oobe_crc_err_counter25_rx_oobe_port_crc_err_cnt {
      type oc-yang:counter64;
      description
        "OOB Extract CRC error counter per port";
    }
    leaf counter_slice4_ifg_ifgbe_core_rx_oobe_crc_err_counter26_rx_oobe_port_crc_err_cnt {
      type oc-yang:counter64;
      description
        "OOB Extract CRC error counter per port";
    }
    leaf counter_slice4_ifg_ifgbe_core_rx_oobe_crc_err_counter27_rx_oobe_port_crc_err_cnt {
      type oc-yang:counter64;
      description
        "OOB Extract CRC error counter per port";
    }
    leaf counter_slice4_ifg_ifgbe_core_rx_oobe_crc_err_counter28_rx_oobe_port_crc_err_cnt {
      type oc-yang:counter64;
      description
        "OOB Extract CRC error counter per port";
    }
    leaf counter_slice4_ifg_ifgbe_core_rx_oobe_crc_err_counter29_rx_oobe_port_crc_err_cnt {
      type oc-yang:counter64;
      description
        "OOB Extract CRC error counter per port";
    }
    leaf counter_slice4_ifg_ifgbe_core_rx_oobe_crc_err_counter30_rx_oobe_port_crc_err_cnt {
      type oc-yang:counter64;
      description
        "OOB Extract CRC error counter per port";
    }
    leaf counter_slice4_ifg_ifgbe_core_rx_oobe_crc_err_counter31_rx_oobe_port_crc_err_cnt {
      type oc-yang:counter64;
      description
        "OOB Extract CRC error counter per port";
    }
    leaf counter_slice5_ifg_ifgbe_core_rx_oobe_crc_err_counter0_rx_oobe_port_crc_err_cnt {
      type oc-yang:counter64;
      description
        "OOB Extract CRC error counter per port";
    }
    leaf counter_slice5_ifg_ifgbe_core_rx_oobe_crc_err_counter1_rx_oobe_port_crc_err_cnt {
      type oc-yang:counter64;
      description
        "OOB Extract CRC error counter per port";
    }
    leaf counter_slice5_ifg_ifgbe_core_rx_oobe_crc_err_counter2_rx_oobe_port_crc_err_cnt {
      type oc-yang:counter64;
      description
        "OOB Extract CRC error counter per port";
    }
    leaf counter_slice5_ifg_ifgbe_core_rx_oobe_crc_err_counter3_rx_oobe_port_crc_err_cnt {
      type oc-yang:counter64;
      description
        "OOB Extract CRC error counter per port";
    }
    leaf counter_slice5_ifg_ifgbe_core_rx_oobe_crc_err_counter4_rx_oobe_port_crc_err_cnt {
      type oc-yang:counter64;
      description
        "OOB Extract CRC error counter per port";
    }
    leaf counter_slice5_ifg_ifgbe_core_rx_oobe_crc_err_counter5_rx_oobe_port_crc_err_cnt {
      type oc-yang:counter64;
      description
        "OOB Extract CRC error counter per port";
    }
    leaf counter_slice5_ifg_ifgbe_core_rx_oobe_crc_err_counter6_rx_oobe_port_crc_err_cnt {
      type oc-yang:counter64;
      description
        "OOB Extract CRC error counter per port";
    }
    leaf counter_slice5_ifg_ifgbe_core_rx_oobe_crc_err_counter7_rx_oobe_port_crc_err_cnt {
      type oc-yang:counter64;
      description
        "OOB Extract CRC error counter per port";
    }
    leaf counter_slice5_ifg_ifgbe_core_rx_oobe_crc_err_counter8_rx_oobe_port_crc_err_cnt {
      type oc-yang:counter64;
      description
        "OOB Extract CRC error counter per port";
    }
    leaf counter_slice5_ifg_ifgbe_core_rx_oobe_crc_err_counter9_rx_oobe_port_crc_err_cnt {
      type oc-yang:counter64;
      description
        "OOB Extract CRC error counter per port";
    }
    leaf counter_slice5_ifg_ifgbe_core_rx_oobe_crc_err_counter10_rx_oobe_port_crc_err_cnt {
      type oc-yang:counter64;
      description
        "OOB Extract CRC error counter per port";
    }
    leaf counter_slice5_ifg_ifgbe_core_rx_oobe_crc_err_counter11_rx_oobe_port_crc_err_cnt {
      type oc-yang:counter64;
      description
        "OOB Extract CRC error counter per port";
    }
    leaf counter_slice5_ifg_ifgbe_core_rx_oobe_crc_err_counter12_rx_oobe_port_crc_err_cnt {
      type oc-yang:counter64;
      description
        "OOB Extract CRC error counter per port";
    }
    leaf counter_slice5_ifg_ifgbe_core_rx_oobe_crc_err_counter13_rx_oobe_port_crc_err_cnt {
      type oc-yang:counter64;
      description
        "OOB Extract CRC error counter per port";
    }
    leaf counter_slice5_ifg_ifgbe_core_rx_oobe_crc_err_counter14_rx_oobe_port_crc_err_cnt {
      type oc-yang:counter64;
      description
        "OOB Extract CRC error counter per port";
    }
    leaf counter_slice5_ifg_ifgbe_core_rx_oobe_crc_err_counter15_rx_oobe_port_crc_err_cnt {
      type oc-yang:counter64;
      description
        "OOB Extract CRC error counter per port";
    }
    leaf counter_slice5_ifg_ifgbe_core_rx_oobe_crc_err_counter16_rx_oobe_port_crc_err_cnt {
      type oc-yang:counter64;
      description
        "OOB Extract CRC error counter per port";
    }
    leaf counter_slice5_ifg_ifgbe_core_rx_oobe_crc_err_counter17_rx_oobe_port_crc_err_cnt {
      type oc-yang:counter64;
      description
        "OOB Extract CRC error counter per port";
    }
    leaf counter_slice5_ifg_ifgbe_core_rx_oobe_crc_err_counter18_rx_oobe_port_crc_err_cnt {
      type oc-yang:counter64;
      description
        "OOB Extract CRC error counter per port";
    }
    leaf counter_slice5_ifg_ifgbe_core_rx_oobe_crc_err_counter19_rx_oobe_port_crc_err_cnt {
      type oc-yang:counter64;
      description
        "OOB Extract CRC error counter per port";
    }
    leaf counter_slice5_ifg_ifgbe_core_rx_oobe_crc_err_counter20_rx_oobe_port_crc_err_cnt {
      type oc-yang:counter64;
      description
        "OOB Extract CRC error counter per port";
    }
    leaf counter_slice5_ifg_ifgbe_core_rx_oobe_crc_err_counter21_rx_oobe_port_crc_err_cnt {
      type oc-yang:counter64;
      description
        "OOB Extract CRC error counter per port";
    }
    leaf counter_slice5_ifg_ifgbe_core_rx_oobe_crc_err_counter22_rx_oobe_port_crc_err_cnt {
      type oc-yang:counter64;
      description
        "OOB Extract CRC error counter per port";
    }
    leaf counter_slice5_ifg_ifgbe_core_rx_oobe_crc_err_counter23_rx_oobe_port_crc_err_cnt {
      type oc-yang:counter64;
      description
        "OOB Extract CRC error counter per port";
    }
    leaf counter_slice5_ifg_ifgbe_core_rx_oobe_crc_err_counter24_rx_oobe_port_crc_err_cnt {
      type oc-yang:counter64;
      description
        "OOB Extract CRC error counter per port";
    }
    leaf counter_slice5_ifg_ifgbe_core_rx_oobe_crc_err_counter25_rx_oobe_port_crc_err_cnt {
      type oc-yang:counter64;
      description
        "OOB Extract CRC error counter per port";
    }
    leaf counter_slice5_ifg_ifgbe_core_rx_oobe_crc_err_counter26_rx_oobe_port_crc_err_cnt {
      type oc-yang:counter64;
      description
        "OOB Extract CRC error counter per port";
    }
    leaf counter_slice5_ifg_ifgbe_core_rx_oobe_crc_err_counter27_rx_oobe_port_crc_err_cnt {
      type oc-yang:counter64;
      description
        "OOB Extract CRC error counter per port";
    }
    leaf counter_slice5_ifg_ifgbe_core_rx_oobe_crc_err_counter28_rx_oobe_port_crc_err_cnt {
      type oc-yang:counter64;
      description
        "OOB Extract CRC error counter per port";
    }
    leaf counter_slice5_ifg_ifgbe_core_rx_oobe_crc_err_counter29_rx_oobe_port_crc_err_cnt {
      type oc-yang:counter64;
      description
        "OOB Extract CRC error counter per port";
    }
    leaf counter_slice5_ifg_ifgbe_core_rx_oobe_crc_err_counter30_rx_oobe_port_crc_err_cnt {
      type oc-yang:counter64;
      description
        "OOB Extract CRC error counter per port";
    }
    leaf counter_slice5_ifg_ifgbe_core_rx_oobe_crc_err_counter31_rx_oobe_port_crc_err_cnt {
      type oc-yang:counter64;
      description
        "OOB Extract CRC error counter per port";
    }
    leaf counter_slice6_ifg_ifgbe_core_rx_oobe_crc_err_counter0_rx_oobe_port_crc_err_cnt {
      type oc-yang:counter64;
      description
        "OOB Extract CRC error counter per port";
    }
    leaf counter_slice6_ifg_ifgbe_core_rx_oobe_crc_err_counter1_rx_oobe_port_crc_err_cnt {
      type oc-yang:counter64;
      description
        "OOB Extract CRC error counter per port";
    }
    leaf counter_slice6_ifg_ifgbe_core_rx_oobe_crc_err_counter2_rx_oobe_port_crc_err_cnt {
      type oc-yang:counter64;
      description
        "OOB Extract CRC error counter per port";
    }
    leaf counter_slice6_ifg_ifgbe_core_rx_oobe_crc_err_counter3_rx_oobe_port_crc_err_cnt {
      type oc-yang:counter64;
      description
        "OOB Extract CRC error counter per port";
    }
    leaf counter_slice6_ifg_ifgbe_core_rx_oobe_crc_err_counter4_rx_oobe_port_crc_err_cnt {
      type oc-yang:counter64;
      description
        "OOB Extract CRC error counter per port";
    }
    leaf counter_slice6_ifg_ifgbe_core_rx_oobe_crc_err_counter5_rx_oobe_port_crc_err_cnt {
      type oc-yang:counter64;
      description
        "OOB Extract CRC error counter per port";
    }
    leaf counter_slice6_ifg_ifgbe_core_rx_oobe_crc_err_counter6_rx_oobe_port_crc_err_cnt {
      type oc-yang:counter64;
      description
        "OOB Extract CRC error counter per port";
    }
    leaf counter_slice6_ifg_ifgbe_core_rx_oobe_crc_err_counter7_rx_oobe_port_crc_err_cnt {
      type oc-yang:counter64;
      description
        "OOB Extract CRC error counter per port";
    }
    leaf counter_slice6_ifg_ifgbe_core_rx_oobe_crc_err_counter8_rx_oobe_port_crc_err_cnt {
      type oc-yang:counter64;
      description
        "OOB Extract CRC error counter per port";
    }
    leaf counter_slice6_ifg_ifgbe_core_rx_oobe_crc_err_counter9_rx_oobe_port_crc_err_cnt {
      type oc-yang:counter64;
      description
        "OOB Extract CRC error counter per port";
    }
    leaf counter_slice6_ifg_ifgbe_core_rx_oobe_crc_err_counter10_rx_oobe_port_crc_err_cnt {
      type oc-yang:counter64;
      description
        "OOB Extract CRC error counter per port";
    }
    leaf counter_slice6_ifg_ifgbe_core_rx_oobe_crc_err_counter11_rx_oobe_port_crc_err_cnt {
      type oc-yang:counter64;
      description
        "OOB Extract CRC error counter per port";
    }
    leaf counter_slice6_ifg_ifgbe_core_rx_oobe_crc_err_counter12_rx_oobe_port_crc_err_cnt {
      type oc-yang:counter64;
      description
        "OOB Extract CRC error counter per port";
    }
    leaf counter_slice6_ifg_ifgbe_core_rx_oobe_crc_err_counter13_rx_oobe_port_crc_err_cnt {
      type oc-yang:counter64;
      description
        "OOB Extract CRC error counter per port";
    }
    leaf counter_slice6_ifg_ifgbe_core_rx_oobe_crc_err_counter14_rx_oobe_port_crc_err_cnt {
      type oc-yang:counter64;
      description
        "OOB Extract CRC error counter per port";
    }
    leaf counter_slice6_ifg_ifgbe_core_rx_oobe_crc_err_counter15_rx_oobe_port_crc_err_cnt {
      type oc-yang:counter64;
      description
        "OOB Extract CRC error counter per port";
    }
    leaf counter_slice6_ifg_ifgbe_core_rx_oobe_crc_err_counter16_rx_oobe_port_crc_err_cnt {
      type oc-yang:counter64;
      description
        "OOB Extract CRC error counter per port";
    }
    leaf counter_slice6_ifg_ifgbe_core_rx_oobe_crc_err_counter17_rx_oobe_port_crc_err_cnt {
      type oc-yang:counter64;
      description
        "OOB Extract CRC error counter per port";
    }
    leaf counter_slice6_ifg_ifgbe_core_rx_oobe_crc_err_counter18_rx_oobe_port_crc_err_cnt {
      type oc-yang:counter64;
      description
        "OOB Extract CRC error counter per port";
    }
    leaf counter_slice6_ifg_ifgbe_core_rx_oobe_crc_err_counter19_rx_oobe_port_crc_err_cnt {
      type oc-yang:counter64;
      description
        "OOB Extract CRC error counter per port";
    }
    leaf counter_slice6_ifg_ifgbe_core_rx_oobe_crc_err_counter20_rx_oobe_port_crc_err_cnt {
      type oc-yang:counter64;
      description
        "OOB Extract CRC error counter per port";
    }
    leaf counter_slice6_ifg_ifgbe_core_rx_oobe_crc_err_counter21_rx_oobe_port_crc_err_cnt {
      type oc-yang:counter64;
      description
        "OOB Extract CRC error counter per port";
    }
    leaf counter_slice6_ifg_ifgbe_core_rx_oobe_crc_err_counter22_rx_oobe_port_crc_err_cnt {
      type oc-yang:counter64;
      description
        "OOB Extract CRC error counter per port";
    }
    leaf counter_slice6_ifg_ifgbe_core_rx_oobe_crc_err_counter23_rx_oobe_port_crc_err_cnt {
      type oc-yang:counter64;
      description
        "OOB Extract CRC error counter per port";
    }
    leaf counter_slice6_ifg_ifgbe_core_rx_oobe_crc_err_counter24_rx_oobe_port_crc_err_cnt {
      type oc-yang:counter64;
      description
        "OOB Extract CRC error counter per port";
    }
    leaf counter_slice6_ifg_ifgbe_core_rx_oobe_crc_err_counter25_rx_oobe_port_crc_err_cnt {
      type oc-yang:counter64;
      description
        "OOB Extract CRC error counter per port";
    }
    leaf counter_slice6_ifg_ifgbe_core_rx_oobe_crc_err_counter26_rx_oobe_port_crc_err_cnt {
      type oc-yang:counter64;
      description
        "OOB Extract CRC error counter per port";
    }
    leaf counter_slice6_ifg_ifgbe_core_rx_oobe_crc_err_counter27_rx_oobe_port_crc_err_cnt {
      type oc-yang:counter64;
      description
        "OOB Extract CRC error counter per port";
    }
    leaf counter_slice6_ifg_ifgbe_core_rx_oobe_crc_err_counter28_rx_oobe_port_crc_err_cnt {
      type oc-yang:counter64;
      description
        "OOB Extract CRC error counter per port";
    }
    leaf counter_slice6_ifg_ifgbe_core_rx_oobe_crc_err_counter29_rx_oobe_port_crc_err_cnt {
      type oc-yang:counter64;
      description
        "OOB Extract CRC error counter per port";
    }
    leaf counter_slice6_ifg_ifgbe_core_rx_oobe_crc_err_counter30_rx_oobe_port_crc_err_cnt {
      type oc-yang:counter64;
      description
        "OOB Extract CRC error counter per port";
    }
    leaf counter_slice6_ifg_ifgbe_core_rx_oobe_crc_err_counter31_rx_oobe_port_crc_err_cnt {
      type oc-yang:counter64;
      description
        "OOB Extract CRC error counter per port";
    }
    leaf counter_slice7_ifg_ifgbe_core_rx_oobe_crc_err_counter0_rx_oobe_port_crc_err_cnt {
      type oc-yang:counter64;
      description
        "OOB Extract CRC error counter per port";
    }
    leaf counter_slice7_ifg_ifgbe_core_rx_oobe_crc_err_counter1_rx_oobe_port_crc_err_cnt {
      type oc-yang:counter64;
      description
        "OOB Extract CRC error counter per port";
    }
    leaf counter_slice7_ifg_ifgbe_core_rx_oobe_crc_err_counter2_rx_oobe_port_crc_err_cnt {
      type oc-yang:counter64;
      description
        "OOB Extract CRC error counter per port";
    }
    leaf counter_slice7_ifg_ifgbe_core_rx_oobe_crc_err_counter3_rx_oobe_port_crc_err_cnt {
      type oc-yang:counter64;
      description
        "OOB Extract CRC error counter per port";
    }
    leaf counter_slice7_ifg_ifgbe_core_rx_oobe_crc_err_counter4_rx_oobe_port_crc_err_cnt {
      type oc-yang:counter64;
      description
        "OOB Extract CRC error counter per port";
    }
    leaf counter_slice7_ifg_ifgbe_core_rx_oobe_crc_err_counter5_rx_oobe_port_crc_err_cnt {
      type oc-yang:counter64;
      description
        "OOB Extract CRC error counter per port";
    }
    leaf counter_slice7_ifg_ifgbe_core_rx_oobe_crc_err_counter6_rx_oobe_port_crc_err_cnt {
      type oc-yang:counter64;
      description
        "OOB Extract CRC error counter per port";
    }
    leaf counter_slice7_ifg_ifgbe_core_rx_oobe_crc_err_counter7_rx_oobe_port_crc_err_cnt {
      type oc-yang:counter64;
      description
        "OOB Extract CRC error counter per port";
    }
    leaf counter_slice7_ifg_ifgbe_core_rx_oobe_crc_err_counter8_rx_oobe_port_crc_err_cnt {
      type oc-yang:counter64;
      description
        "OOB Extract CRC error counter per port";
    }
    leaf counter_slice7_ifg_ifgbe_core_rx_oobe_crc_err_counter9_rx_oobe_port_crc_err_cnt {
      type oc-yang:counter64;
      description
        "OOB Extract CRC error counter per port";
    }
    leaf counter_slice7_ifg_ifgbe_core_rx_oobe_crc_err_counter10_rx_oobe_port_crc_err_cnt {
      type oc-yang:counter64;
      description
        "OOB Extract CRC error counter per port";
    }
    leaf counter_slice7_ifg_ifgbe_core_rx_oobe_crc_err_counter11_rx_oobe_port_crc_err_cnt {
      type oc-yang:counter64;
      description
        "OOB Extract CRC error counter per port";
    }
    leaf counter_slice7_ifg_ifgbe_core_rx_oobe_crc_err_counter12_rx_oobe_port_crc_err_cnt {
      type oc-yang:counter64;
      description
        "OOB Extract CRC error counter per port";
    }
    leaf counter_slice7_ifg_ifgbe_core_rx_oobe_crc_err_counter13_rx_oobe_port_crc_err_cnt {
      type oc-yang:counter64;
      description
        "OOB Extract CRC error counter per port";
    }
    leaf counter_slice7_ifg_ifgbe_core_rx_oobe_crc_err_counter14_rx_oobe_port_crc_err_cnt {
      type oc-yang:counter64;
      description
        "OOB Extract CRC error counter per port";
    }
    leaf counter_slice7_ifg_ifgbe_core_rx_oobe_crc_err_counter15_rx_oobe_port_crc_err_cnt {
      type oc-yang:counter64;
      description
        "OOB Extract CRC error counter per port";
    }
    leaf counter_slice7_ifg_ifgbe_core_rx_oobe_crc_err_counter16_rx_oobe_port_crc_err_cnt {
      type oc-yang:counter64;
      description
        "OOB Extract CRC error counter per port";
    }
    leaf counter_slice7_ifg_ifgbe_core_rx_oobe_crc_err_counter17_rx_oobe_port_crc_err_cnt {
      type oc-yang:counter64;
      description
        "OOB Extract CRC error counter per port";
    }
    leaf counter_slice7_ifg_ifgbe_core_rx_oobe_crc_err_counter18_rx_oobe_port_crc_err_cnt {
      type oc-yang:counter64;
      description
        "OOB Extract CRC error counter per port";
    }
    leaf counter_slice7_ifg_ifgbe_core_rx_oobe_crc_err_counter19_rx_oobe_port_crc_err_cnt {
      type oc-yang:counter64;
      description
        "OOB Extract CRC error counter per port";
    }
    leaf counter_slice7_ifg_ifgbe_core_rx_oobe_crc_err_counter20_rx_oobe_port_crc_err_cnt {
      type oc-yang:counter64;
      description
        "OOB Extract CRC error counter per port";
    }
    leaf counter_slice7_ifg_ifgbe_core_rx_oobe_crc_err_counter21_rx_oobe_port_crc_err_cnt {
      type oc-yang:counter64;
      description
        "OOB Extract CRC error counter per port";
    }
    leaf counter_slice7_ifg_ifgbe_core_rx_oobe_crc_err_counter22_rx_oobe_port_crc_err_cnt {
      type oc-yang:counter64;
      description
        "OOB Extract CRC error counter per port";
    }
    leaf counter_slice7_ifg_ifgbe_core_rx_oobe_crc_err_counter23_rx_oobe_port_crc_err_cnt {
      type oc-yang:counter64;
      description
        "OOB Extract CRC error counter per port";
    }
    leaf counter_slice7_ifg_ifgbe_core_rx_oobe_crc_err_counter24_rx_oobe_port_crc_err_cnt {
      type oc-yang:counter64;
      description
        "OOB Extract CRC error counter per port";
    }
    leaf counter_slice7_ifg_ifgbe_core_rx_oobe_crc_err_counter25_rx_oobe_port_crc_err_cnt {
      type oc-yang:counter64;
      description
        "OOB Extract CRC error counter per port";
    }
    leaf counter_slice7_ifg_ifgbe_core_rx_oobe_crc_err_counter26_rx_oobe_port_crc_err_cnt {
      type oc-yang:counter64;
      description
        "OOB Extract CRC error counter per port";
    }
    leaf counter_slice7_ifg_ifgbe_core_rx_oobe_crc_err_counter27_rx_oobe_port_crc_err_cnt {
      type oc-yang:counter64;
      description
        "OOB Extract CRC error counter per port";
    }
    leaf counter_slice7_ifg_ifgbe_core_rx_oobe_crc_err_counter28_rx_oobe_port_crc_err_cnt {
      type oc-yang:counter64;
      description
        "OOB Extract CRC error counter per port";
    }
    leaf counter_slice7_ifg_ifgbe_core_rx_oobe_crc_err_counter29_rx_oobe_port_crc_err_cnt {
      type oc-yang:counter64;
      description
        "OOB Extract CRC error counter per port";
    }
    leaf counter_slice7_ifg_ifgbe_core_rx_oobe_crc_err_counter30_rx_oobe_port_crc_err_cnt {
      type oc-yang:counter64;
      description
        "OOB Extract CRC error counter per port";
    }
    leaf counter_slice7_ifg_ifgbe_core_rx_oobe_crc_err_counter31_rx_oobe_port_crc_err_cnt {
      type oc-yang:counter64;
      description
        "OOB Extract CRC error counter per port";
    }
    leaf counter_slice8_ifg_ifgbe_core_rx_oobe_crc_err_counter0_rx_oobe_port_crc_err_cnt {
      type oc-yang:counter64;
      description
        "OOB Extract CRC error counter per port";
    }
    leaf counter_slice8_ifg_ifgbe_core_rx_oobe_crc_err_counter1_rx_oobe_port_crc_err_cnt {
      type oc-yang:counter64;
      description
        "OOB Extract CRC error counter per port";
    }
    leaf counter_slice8_ifg_ifgbe_core_rx_oobe_crc_err_counter2_rx_oobe_port_crc_err_cnt {
      type oc-yang:counter64;
      description
        "OOB Extract CRC error counter per port";
    }
    leaf counter_slice8_ifg_ifgbe_core_rx_oobe_crc_err_counter3_rx_oobe_port_crc_err_cnt {
      type oc-yang:counter64;
      description
        "OOB Extract CRC error counter per port";
    }
    leaf counter_slice8_ifg_ifgbe_core_rx_oobe_crc_err_counter4_rx_oobe_port_crc_err_cnt {
      type oc-yang:counter64;
      description
        "OOB Extract CRC error counter per port";
    }
    leaf counter_slice8_ifg_ifgbe_core_rx_oobe_crc_err_counter5_rx_oobe_port_crc_err_cnt {
      type oc-yang:counter64;
      description
        "OOB Extract CRC error counter per port";
    }
    leaf counter_slice8_ifg_ifgbe_core_rx_oobe_crc_err_counter6_rx_oobe_port_crc_err_cnt {
      type oc-yang:counter64;
      description
        "OOB Extract CRC error counter per port";
    }
    leaf counter_slice8_ifg_ifgbe_core_rx_oobe_crc_err_counter7_rx_oobe_port_crc_err_cnt {
      type oc-yang:counter64;
      description
        "OOB Extract CRC error counter per port";
    }
    leaf counter_slice8_ifg_ifgbe_core_rx_oobe_crc_err_counter8_rx_oobe_port_crc_err_cnt {
      type oc-yang:counter64;
      description
        "OOB Extract CRC error counter per port";
    }
    leaf counter_slice8_ifg_ifgbe_core_rx_oobe_crc_err_counter9_rx_oobe_port_crc_err_cnt {
      type oc-yang:counter64;
      description
        "OOB Extract CRC error counter per port";
    }
    leaf counter_slice8_ifg_ifgbe_core_rx_oobe_crc_err_counter10_rx_oobe_port_crc_err_cnt {
      type oc-yang:counter64;
      description
        "OOB Extract CRC error counter per port";
    }
    leaf counter_slice8_ifg_ifgbe_core_rx_oobe_crc_err_counter11_rx_oobe_port_crc_err_cnt {
      type oc-yang:counter64;
      description
        "OOB Extract CRC error counter per port";
    }
    leaf counter_slice8_ifg_ifgbe_core_rx_oobe_crc_err_counter12_rx_oobe_port_crc_err_cnt {
      type oc-yang:counter64;
      description
        "OOB Extract CRC error counter per port";
    }
    leaf counter_slice8_ifg_ifgbe_core_rx_oobe_crc_err_counter13_rx_oobe_port_crc_err_cnt {
      type oc-yang:counter64;
      description
        "OOB Extract CRC error counter per port";
    }
    leaf counter_slice8_ifg_ifgbe_core_rx_oobe_crc_err_counter14_rx_oobe_port_crc_err_cnt {
      type oc-yang:counter64;
      description
        "OOB Extract CRC error counter per port";
    }
    leaf counter_slice8_ifg_ifgbe_core_rx_oobe_crc_err_counter15_rx_oobe_port_crc_err_cnt {
      type oc-yang:counter64;
      description
        "OOB Extract CRC error counter per port";
    }
    leaf counter_slice8_ifg_ifgbe_core_rx_oobe_crc_err_counter16_rx_oobe_port_crc_err_cnt {
      type oc-yang:counter64;
      description
        "OOB Extract CRC error counter per port";
    }
    leaf counter_slice8_ifg_ifgbe_core_rx_oobe_crc_err_counter17_rx_oobe_port_crc_err_cnt {
      type oc-yang:counter64;
      description
        "OOB Extract CRC error counter per port";
    }
    leaf counter_slice8_ifg_ifgbe_core_rx_oobe_crc_err_counter18_rx_oobe_port_crc_err_cnt {
      type oc-yang:counter64;
      description
        "OOB Extract CRC error counter per port";
    }
    leaf counter_slice8_ifg_ifgbe_core_rx_oobe_crc_err_counter19_rx_oobe_port_crc_err_cnt {
      type oc-yang:counter64;
      description
        "OOB Extract CRC error counter per port";
    }
    leaf counter_slice8_ifg_ifgbe_core_rx_oobe_crc_err_counter20_rx_oobe_port_crc_err_cnt {
      type oc-yang:counter64;
      description
        "OOB Extract CRC error counter per port";
    }
    leaf counter_slice8_ifg_ifgbe_core_rx_oobe_crc_err_counter21_rx_oobe_port_crc_err_cnt {
      type oc-yang:counter64;
      description
        "OOB Extract CRC error counter per port";
    }
    leaf counter_slice8_ifg_ifgbe_core_rx_oobe_crc_err_counter22_rx_oobe_port_crc_err_cnt {
      type oc-yang:counter64;
      description
        "OOB Extract CRC error counter per port";
    }
    leaf counter_slice8_ifg_ifgbe_core_rx_oobe_crc_err_counter23_rx_oobe_port_crc_err_cnt {
      type oc-yang:counter64;
      description
        "OOB Extract CRC error counter per port";
    }
    leaf counter_slice8_ifg_ifgbe_core_rx_oobe_crc_err_counter24_rx_oobe_port_crc_err_cnt {
      type oc-yang:counter64;
      description
        "OOB Extract CRC error counter per port";
    }
    leaf counter_slice8_ifg_ifgbe_core_rx_oobe_crc_err_counter25_rx_oobe_port_crc_err_cnt {
      type oc-yang:counter64;
      description
        "OOB Extract CRC error counter per port";
    }
    leaf counter_slice8_ifg_ifgbe_core_rx_oobe_crc_err_counter26_rx_oobe_port_crc_err_cnt {
      type oc-yang:counter64;
      description
        "OOB Extract CRC error counter per port";
    }
    leaf counter_slice8_ifg_ifgbe_core_rx_oobe_crc_err_counter27_rx_oobe_port_crc_err_cnt {
      type oc-yang:counter64;
      description
        "OOB Extract CRC error counter per port";
    }
    leaf counter_slice8_ifg_ifgbe_core_rx_oobe_crc_err_counter28_rx_oobe_port_crc_err_cnt {
      type oc-yang:counter64;
      description
        "OOB Extract CRC error counter per port";
    }
    leaf counter_slice8_ifg_ifgbe_core_rx_oobe_crc_err_counter29_rx_oobe_port_crc_err_cnt {
      type oc-yang:counter64;
      description
        "OOB Extract CRC error counter per port";
    }
    leaf counter_slice8_ifg_ifgbe_core_rx_oobe_crc_err_counter30_rx_oobe_port_crc_err_cnt {
      type oc-yang:counter64;
      description
        "OOB Extract CRC error counter per port";
    }
    leaf counter_slice8_ifg_ifgbe_core_rx_oobe_crc_err_counter31_rx_oobe_port_crc_err_cnt {
      type oc-yang:counter64;
      description
        "OOB Extract CRC error counter per port";
    }
    leaf counter_slice9_ifg_ifgbe_core_rx_oobe_crc_err_counter0_rx_oobe_port_crc_err_cnt {
      type oc-yang:counter64;
      description
        "OOB Extract CRC error counter per port";
    }
    leaf counter_slice9_ifg_ifgbe_core_rx_oobe_crc_err_counter1_rx_oobe_port_crc_err_cnt {
      type oc-yang:counter64;
      description
        "OOB Extract CRC error counter per port";
    }
    leaf counter_slice9_ifg_ifgbe_core_rx_oobe_crc_err_counter2_rx_oobe_port_crc_err_cnt {
      type oc-yang:counter64;
      description
        "OOB Extract CRC error counter per port";
    }
    leaf counter_slice9_ifg_ifgbe_core_rx_oobe_crc_err_counter3_rx_oobe_port_crc_err_cnt {
      type oc-yang:counter64;
      description
        "OOB Extract CRC error counter per port";
    }
    leaf counter_slice9_ifg_ifgbe_core_rx_oobe_crc_err_counter4_rx_oobe_port_crc_err_cnt {
      type oc-yang:counter64;
      description
        "OOB Extract CRC error counter per port";
    }
    leaf counter_slice9_ifg_ifgbe_core_rx_oobe_crc_err_counter5_rx_oobe_port_crc_err_cnt {
      type oc-yang:counter64;
      description
        "OOB Extract CRC error counter per port";
    }
    leaf counter_slice9_ifg_ifgbe_core_rx_oobe_crc_err_counter6_rx_oobe_port_crc_err_cnt {
      type oc-yang:counter64;
      description
        "OOB Extract CRC error counter per port";
    }
    leaf counter_slice9_ifg_ifgbe_core_rx_oobe_crc_err_counter7_rx_oobe_port_crc_err_cnt {
      type oc-yang:counter64;
      description
        "OOB Extract CRC error counter per port";
    }
    leaf counter_slice9_ifg_ifgbe_core_rx_oobe_crc_err_counter8_rx_oobe_port_crc_err_cnt {
      type oc-yang:counter64;
      description
        "OOB Extract CRC error counter per port";
    }
    leaf counter_slice9_ifg_ifgbe_core_rx_oobe_crc_err_counter9_rx_oobe_port_crc_err_cnt {
      type oc-yang:counter64;
      description
        "OOB Extract CRC error counter per port";
    }
    leaf counter_slice9_ifg_ifgbe_core_rx_oobe_crc_err_counter10_rx_oobe_port_crc_err_cnt {
      type oc-yang:counter64;
      description
        "OOB Extract CRC error counter per port";
    }
    leaf counter_slice9_ifg_ifgbe_core_rx_oobe_crc_err_counter11_rx_oobe_port_crc_err_cnt {
      type oc-yang:counter64;
      description
        "OOB Extract CRC error counter per port";
    }
    leaf counter_slice9_ifg_ifgbe_core_rx_oobe_crc_err_counter12_rx_oobe_port_crc_err_cnt {
      type oc-yang:counter64;
      description
        "OOB Extract CRC error counter per port";
    }
    leaf counter_slice9_ifg_ifgbe_core_rx_oobe_crc_err_counter13_rx_oobe_port_crc_err_cnt {
      type oc-yang:counter64;
      description
        "OOB Extract CRC error counter per port";
    }
    leaf counter_slice9_ifg_ifgbe_core_rx_oobe_crc_err_counter14_rx_oobe_port_crc_err_cnt {
      type oc-yang:counter64;
      description
        "OOB Extract CRC error counter per port";
    }
    leaf counter_slice9_ifg_ifgbe_core_rx_oobe_crc_err_counter15_rx_oobe_port_crc_err_cnt {
      type oc-yang:counter64;
      description
        "OOB Extract CRC error counter per port";
    }
    leaf counter_slice9_ifg_ifgbe_core_rx_oobe_crc_err_counter16_rx_oobe_port_crc_err_cnt {
      type oc-yang:counter64;
      description
        "OOB Extract CRC error counter per port";
    }
    leaf counter_slice9_ifg_ifgbe_core_rx_oobe_crc_err_counter17_rx_oobe_port_crc_err_cnt {
      type oc-yang:counter64;
      description
        "OOB Extract CRC error counter per port";
    }
    leaf counter_slice9_ifg_ifgbe_core_rx_oobe_crc_err_counter18_rx_oobe_port_crc_err_cnt {
      type oc-yang:counter64;
      description
        "OOB Extract CRC error counter per port";
    }
    leaf counter_slice9_ifg_ifgbe_core_rx_oobe_crc_err_counter19_rx_oobe_port_crc_err_cnt {
      type oc-yang:counter64;
      description
        "OOB Extract CRC error counter per port";
    }
    leaf counter_slice9_ifg_ifgbe_core_rx_oobe_crc_err_counter20_rx_oobe_port_crc_err_cnt {
      type oc-yang:counter64;
      description
        "OOB Extract CRC error counter per port";
    }
    leaf counter_slice9_ifg_ifgbe_core_rx_oobe_crc_err_counter21_rx_oobe_port_crc_err_cnt {
      type oc-yang:counter64;
      description
        "OOB Extract CRC error counter per port";
    }
    leaf counter_slice9_ifg_ifgbe_core_rx_oobe_crc_err_counter22_rx_oobe_port_crc_err_cnt {
      type oc-yang:counter64;
      description
        "OOB Extract CRC error counter per port";
    }
    leaf counter_slice9_ifg_ifgbe_core_rx_oobe_crc_err_counter23_rx_oobe_port_crc_err_cnt {
      type oc-yang:counter64;
      description
        "OOB Extract CRC error counter per port";
    }
    leaf counter_slice9_ifg_ifgbe_core_rx_oobe_crc_err_counter24_rx_oobe_port_crc_err_cnt {
      type oc-yang:counter64;
      description
        "OOB Extract CRC error counter per port";
    }
    leaf counter_slice9_ifg_ifgbe_core_rx_oobe_crc_err_counter25_rx_oobe_port_crc_err_cnt {
      type oc-yang:counter64;
      description
        "OOB Extract CRC error counter per port";
    }
    leaf counter_slice9_ifg_ifgbe_core_rx_oobe_crc_err_counter26_rx_oobe_port_crc_err_cnt {
      type oc-yang:counter64;
      description
        "OOB Extract CRC error counter per port";
    }
    leaf counter_slice9_ifg_ifgbe_core_rx_oobe_crc_err_counter27_rx_oobe_port_crc_err_cnt {
      type oc-yang:counter64;
      description
        "OOB Extract CRC error counter per port";
    }
    leaf counter_slice9_ifg_ifgbe_core_rx_oobe_crc_err_counter28_rx_oobe_port_crc_err_cnt {
      type oc-yang:counter64;
      description
        "OOB Extract CRC error counter per port";
    }
    leaf counter_slice9_ifg_ifgbe_core_rx_oobe_crc_err_counter29_rx_oobe_port_crc_err_cnt {
      type oc-yang:counter64;
      description
        "OOB Extract CRC error counter per port";
    }
    leaf counter_slice9_ifg_ifgbe_core_rx_oobe_crc_err_counter30_rx_oobe_port_crc_err_cnt {
      type oc-yang:counter64;
      description
        "OOB Extract CRC error counter per port";
    }
    leaf counter_slice9_ifg_ifgbe_core_rx_oobe_crc_err_counter31_rx_oobe_port_crc_err_cnt {
      type oc-yang:counter64;
      description
        "OOB Extract CRC error counter per port";
    }
    leaf counter_slice10_ifg_ifgbe_core_rx_oobe_crc_err_counter0_rx_oobe_port_crc_err_cnt {
      type oc-yang:counter64;
      description
        "OOB Extract CRC error counter per port";
    }
    leaf counter_slice10_ifg_ifgbe_core_rx_oobe_crc_err_counter1_rx_oobe_port_crc_err_cnt {
      type oc-yang:counter64;
      description
        "OOB Extract CRC error counter per port";
    }
    leaf counter_slice10_ifg_ifgbe_core_rx_oobe_crc_err_counter2_rx_oobe_port_crc_err_cnt {
      type oc-yang:counter64;
      description
        "OOB Extract CRC error counter per port";
    }
    leaf counter_slice10_ifg_ifgbe_core_rx_oobe_crc_err_counter3_rx_oobe_port_crc_err_cnt {
      type oc-yang:counter64;
      description
        "OOB Extract CRC error counter per port";
    }
    leaf counter_slice10_ifg_ifgbe_core_rx_oobe_crc_err_counter4_rx_oobe_port_crc_err_cnt {
      type oc-yang:counter64;
      description
        "OOB Extract CRC error counter per port";
    }
    leaf counter_slice10_ifg_ifgbe_core_rx_oobe_crc_err_counter5_rx_oobe_port_crc_err_cnt {
      type oc-yang:counter64;
      description
        "OOB Extract CRC error counter per port";
    }
    leaf counter_slice10_ifg_ifgbe_core_rx_oobe_crc_err_counter6_rx_oobe_port_crc_err_cnt {
      type oc-yang:counter64;
      description
        "OOB Extract CRC error counter per port";
    }
    leaf counter_slice10_ifg_ifgbe_core_rx_oobe_crc_err_counter7_rx_oobe_port_crc_err_cnt {
      type oc-yang:counter64;
      description
        "OOB Extract CRC error counter per port";
    }
    leaf counter_slice10_ifg_ifgbe_core_rx_oobe_crc_err_counter8_rx_oobe_port_crc_err_cnt {
      type oc-yang:counter64;
      description
        "OOB Extract CRC error counter per port";
    }
    leaf counter_slice10_ifg_ifgbe_core_rx_oobe_crc_err_counter9_rx_oobe_port_crc_err_cnt {
      type oc-yang:counter64;
      description
        "OOB Extract CRC error counter per port";
    }
    leaf counter_slice10_ifg_ifgbe_core_rx_oobe_crc_err_counter10_rx_oobe_port_crc_err_cnt {
      type oc-yang:counter64;
      description
        "OOB Extract CRC error counter per port";
    }
    leaf counter_slice10_ifg_ifgbe_core_rx_oobe_crc_err_counter11_rx_oobe_port_crc_err_cnt {
      type oc-yang:counter64;
      description
        "OOB Extract CRC error counter per port";
    }
    leaf counter_slice10_ifg_ifgbe_core_rx_oobe_crc_err_counter12_rx_oobe_port_crc_err_cnt {
      type oc-yang:counter64;
      description
        "OOB Extract CRC error counter per port";
    }
    leaf counter_slice10_ifg_ifgbe_core_rx_oobe_crc_err_counter13_rx_oobe_port_crc_err_cnt {
      type oc-yang:counter64;
      description
        "OOB Extract CRC error counter per port";
    }
    leaf counter_slice10_ifg_ifgbe_core_rx_oobe_crc_err_counter14_rx_oobe_port_crc_err_cnt {
      type oc-yang:counter64;
      description
        "OOB Extract CRC error counter per port";
    }
    leaf counter_slice10_ifg_ifgbe_core_rx_oobe_crc_err_counter15_rx_oobe_port_crc_err_cnt {
      type oc-yang:counter64;
      description
        "OOB Extract CRC error counter per port";
    }
    leaf counter_slice10_ifg_ifgbe_core_rx_oobe_crc_err_counter16_rx_oobe_port_crc_err_cnt {
      type oc-yang:counter64;
      description
        "OOB Extract CRC error counter per port";
    }
    leaf counter_slice10_ifg_ifgbe_core_rx_oobe_crc_err_counter17_rx_oobe_port_crc_err_cnt {
      type oc-yang:counter64;
      description
        "OOB Extract CRC error counter per port";
    }
    leaf counter_slice10_ifg_ifgbe_core_rx_oobe_crc_err_counter18_rx_oobe_port_crc_err_cnt {
      type oc-yang:counter64;
      description
        "OOB Extract CRC error counter per port";
    }
    leaf counter_slice10_ifg_ifgbe_core_rx_oobe_crc_err_counter19_rx_oobe_port_crc_err_cnt {
      type oc-yang:counter64;
      description
        "OOB Extract CRC error counter per port";
    }
    leaf counter_slice10_ifg_ifgbe_core_rx_oobe_crc_err_counter20_rx_oobe_port_crc_err_cnt {
      type oc-yang:counter64;
      description
        "OOB Extract CRC error counter per port";
    }
    leaf counter_slice10_ifg_ifgbe_core_rx_oobe_crc_err_counter21_rx_oobe_port_crc_err_cnt {
      type oc-yang:counter64;
      description
        "OOB Extract CRC error counter per port";
    }
    leaf counter_slice10_ifg_ifgbe_core_rx_oobe_crc_err_counter22_rx_oobe_port_crc_err_cnt {
      type oc-yang:counter64;
      description
        "OOB Extract CRC error counter per port";
    }
    leaf counter_slice10_ifg_ifgbe_core_rx_oobe_crc_err_counter23_rx_oobe_port_crc_err_cnt {
      type oc-yang:counter64;
      description
        "OOB Extract CRC error counter per port";
    }
    leaf counter_slice10_ifg_ifgbe_core_rx_oobe_crc_err_counter24_rx_oobe_port_crc_err_cnt {
      type oc-yang:counter64;
      description
        "OOB Extract CRC error counter per port";
    }
    leaf counter_slice10_ifg_ifgbe_core_rx_oobe_crc_err_counter25_rx_oobe_port_crc_err_cnt {
      type oc-yang:counter64;
      description
        "OOB Extract CRC error counter per port";
    }
    leaf counter_slice10_ifg_ifgbe_core_rx_oobe_crc_err_counter26_rx_oobe_port_crc_err_cnt {
      type oc-yang:counter64;
      description
        "OOB Extract CRC error counter per port";
    }
    leaf counter_slice10_ifg_ifgbe_core_rx_oobe_crc_err_counter27_rx_oobe_port_crc_err_cnt {
      type oc-yang:counter64;
      description
        "OOB Extract CRC error counter per port";
    }
    leaf counter_slice10_ifg_ifgbe_core_rx_oobe_crc_err_counter28_rx_oobe_port_crc_err_cnt {
      type oc-yang:counter64;
      description
        "OOB Extract CRC error counter per port";
    }
    leaf counter_slice10_ifg_ifgbe_core_rx_oobe_crc_err_counter29_rx_oobe_port_crc_err_cnt {
      type oc-yang:counter64;
      description
        "OOB Extract CRC error counter per port";
    }
    leaf counter_slice10_ifg_ifgbe_core_rx_oobe_crc_err_counter30_rx_oobe_port_crc_err_cnt {
      type oc-yang:counter64;
      description
        "OOB Extract CRC error counter per port";
    }
    leaf counter_slice10_ifg_ifgbe_core_rx_oobe_crc_err_counter31_rx_oobe_port_crc_err_cnt {
      type oc-yang:counter64;
      description
        "OOB Extract CRC error counter per port";
    }
    leaf counter_slice11_ifg_ifgbe_core_rx_oobe_crc_err_counter0_rx_oobe_port_crc_err_cnt {
      type oc-yang:counter64;
      description
        "OOB Extract CRC error counter per port";
    }
    leaf counter_slice11_ifg_ifgbe_core_rx_oobe_crc_err_counter1_rx_oobe_port_crc_err_cnt {
      type oc-yang:counter64;
      description
        "OOB Extract CRC error counter per port";
    }
    leaf counter_slice11_ifg_ifgbe_core_rx_oobe_crc_err_counter2_rx_oobe_port_crc_err_cnt {
      type oc-yang:counter64;
      description
        "OOB Extract CRC error counter per port";
    }
    leaf counter_slice11_ifg_ifgbe_core_rx_oobe_crc_err_counter3_rx_oobe_port_crc_err_cnt {
      type oc-yang:counter64;
      description
        "OOB Extract CRC error counter per port";
    }
    leaf counter_slice11_ifg_ifgbe_core_rx_oobe_crc_err_counter4_rx_oobe_port_crc_err_cnt {
      type oc-yang:counter64;
      description
        "OOB Extract CRC error counter per port";
    }
    leaf counter_slice11_ifg_ifgbe_core_rx_oobe_crc_err_counter5_rx_oobe_port_crc_err_cnt {
      type oc-yang:counter64;
      description
        "OOB Extract CRC error counter per port";
    }
    leaf counter_slice11_ifg_ifgbe_core_rx_oobe_crc_err_counter6_rx_oobe_port_crc_err_cnt {
      type oc-yang:counter64;
      description
        "OOB Extract CRC error counter per port";
    }
    leaf counter_slice11_ifg_ifgbe_core_rx_oobe_crc_err_counter7_rx_oobe_port_crc_err_cnt {
      type oc-yang:counter64;
      description
        "OOB Extract CRC error counter per port";
    }
    leaf counter_slice11_ifg_ifgbe_core_rx_oobe_crc_err_counter8_rx_oobe_port_crc_err_cnt {
      type oc-yang:counter64;
      description
        "OOB Extract CRC error counter per port";
    }
    leaf counter_slice11_ifg_ifgbe_core_rx_oobe_crc_err_counter9_rx_oobe_port_crc_err_cnt {
      type oc-yang:counter64;
      description
        "OOB Extract CRC error counter per port";
    }
    leaf counter_slice11_ifg_ifgbe_core_rx_oobe_crc_err_counter10_rx_oobe_port_crc_err_cnt {
      type oc-yang:counter64;
      description
        "OOB Extract CRC error counter per port";
    }
    leaf counter_slice11_ifg_ifgbe_core_rx_oobe_crc_err_counter11_rx_oobe_port_crc_err_cnt {
      type oc-yang:counter64;
      description
        "OOB Extract CRC error counter per port";
    }
    leaf counter_slice11_ifg_ifgbe_core_rx_oobe_crc_err_counter12_rx_oobe_port_crc_err_cnt {
      type oc-yang:counter64;
      description
        "OOB Extract CRC error counter per port";
    }
    leaf counter_slice11_ifg_ifgbe_core_rx_oobe_crc_err_counter13_rx_oobe_port_crc_err_cnt {
      type oc-yang:counter64;
      description
        "OOB Extract CRC error counter per port";
    }
    leaf counter_slice11_ifg_ifgbe_core_rx_oobe_crc_err_counter14_rx_oobe_port_crc_err_cnt {
      type oc-yang:counter64;
      description
        "OOB Extract CRC error counter per port";
    }
    leaf counter_slice11_ifg_ifgbe_core_rx_oobe_crc_err_counter15_rx_oobe_port_crc_err_cnt {
      type oc-yang:counter64;
      description
        "OOB Extract CRC error counter per port";
    }
    leaf counter_slice11_ifg_ifgbe_core_rx_oobe_crc_err_counter16_rx_oobe_port_crc_err_cnt {
      type oc-yang:counter64;
      description
        "OOB Extract CRC error counter per port";
    }
    leaf counter_slice11_ifg_ifgbe_core_rx_oobe_crc_err_counter17_rx_oobe_port_crc_err_cnt {
      type oc-yang:counter64;
      description
        "OOB Extract CRC error counter per port";
    }
    leaf counter_slice11_ifg_ifgbe_core_rx_oobe_crc_err_counter18_rx_oobe_port_crc_err_cnt {
      type oc-yang:counter64;
      description
        "OOB Extract CRC error counter per port";
    }
    leaf counter_slice11_ifg_ifgbe_core_rx_oobe_crc_err_counter19_rx_oobe_port_crc_err_cnt {
      type oc-yang:counter64;
      description
        "OOB Extract CRC error counter per port";
    }
    leaf counter_slice11_ifg_ifgbe_core_rx_oobe_crc_err_counter20_rx_oobe_port_crc_err_cnt {
      type oc-yang:counter64;
      description
        "OOB Extract CRC error counter per port";
    }
    leaf counter_slice11_ifg_ifgbe_core_rx_oobe_crc_err_counter21_rx_oobe_port_crc_err_cnt {
      type oc-yang:counter64;
      description
        "OOB Extract CRC error counter per port";
    }
    leaf counter_slice11_ifg_ifgbe_core_rx_oobe_crc_err_counter22_rx_oobe_port_crc_err_cnt {
      type oc-yang:counter64;
      description
        "OOB Extract CRC error counter per port";
    }
    leaf counter_slice11_ifg_ifgbe_core_rx_oobe_crc_err_counter23_rx_oobe_port_crc_err_cnt {
      type oc-yang:counter64;
      description
        "OOB Extract CRC error counter per port";
    }
    leaf counter_slice11_ifg_ifgbe_core_rx_oobe_crc_err_counter24_rx_oobe_port_crc_err_cnt {
      type oc-yang:counter64;
      description
        "OOB Extract CRC error counter per port";
    }
    leaf counter_slice11_ifg_ifgbe_core_rx_oobe_crc_err_counter25_rx_oobe_port_crc_err_cnt {
      type oc-yang:counter64;
      description
        "OOB Extract CRC error counter per port";
    }
    leaf counter_slice11_ifg_ifgbe_core_rx_oobe_crc_err_counter26_rx_oobe_port_crc_err_cnt {
      type oc-yang:counter64;
      description
        "OOB Extract CRC error counter per port";
    }
    leaf counter_slice11_ifg_ifgbe_core_rx_oobe_crc_err_counter27_rx_oobe_port_crc_err_cnt {
      type oc-yang:counter64;
      description
        "OOB Extract CRC error counter per port";
    }
    leaf counter_slice11_ifg_ifgbe_core_rx_oobe_crc_err_counter28_rx_oobe_port_crc_err_cnt {
      type oc-yang:counter64;
      description
        "OOB Extract CRC error counter per port";
    }
    leaf counter_slice11_ifg_ifgbe_core_rx_oobe_crc_err_counter29_rx_oobe_port_crc_err_cnt {
      type oc-yang:counter64;
      description
        "OOB Extract CRC error counter per port";
    }
    leaf counter_slice11_ifg_ifgbe_core_rx_oobe_crc_err_counter30_rx_oobe_port_crc_err_cnt {
      type oc-yang:counter64;
      description
        "OOB Extract CRC error counter per port";
    }
    leaf counter_slice11_ifg_ifgbe_core_rx_oobe_crc_err_counter31_rx_oobe_port_crc_err_cnt {
      type oc-yang:counter64;
      description
        "OOB Extract CRC error counter per port";
    }
    leaf counter_slice12_ifg_ifgbe_core_rx_oobe_crc_err_counter0_rx_oobe_port_crc_err_cnt {
      type oc-yang:counter64;
      description
        "OOB Extract CRC error counter per port";
    }
    leaf counter_slice12_ifg_ifgbe_core_rx_oobe_crc_err_counter1_rx_oobe_port_crc_err_cnt {
      type oc-yang:counter64;
      description
        "OOB Extract CRC error counter per port";
    }
    leaf counter_slice12_ifg_ifgbe_core_rx_oobe_crc_err_counter2_rx_oobe_port_crc_err_cnt {
      type oc-yang:counter64;
      description
        "OOB Extract CRC error counter per port";
    }
    leaf counter_slice12_ifg_ifgbe_core_rx_oobe_crc_err_counter3_rx_oobe_port_crc_err_cnt {
      type oc-yang:counter64;
      description
        "OOB Extract CRC error counter per port";
    }
    leaf counter_slice12_ifg_ifgbe_core_rx_oobe_crc_err_counter4_rx_oobe_port_crc_err_cnt {
      type oc-yang:counter64;
      description
        "OOB Extract CRC error counter per port";
    }
    leaf counter_slice12_ifg_ifgbe_core_rx_oobe_crc_err_counter5_rx_oobe_port_crc_err_cnt {
      type oc-yang:counter64;
      description
        "OOB Extract CRC error counter per port";
    }
    leaf counter_slice12_ifg_ifgbe_core_rx_oobe_crc_err_counter6_rx_oobe_port_crc_err_cnt {
      type oc-yang:counter64;
      description
        "OOB Extract CRC error counter per port";
    }
    leaf counter_slice12_ifg_ifgbe_core_rx_oobe_crc_err_counter7_rx_oobe_port_crc_err_cnt {
      type oc-yang:counter64;
      description
        "OOB Extract CRC error counter per port";
    }
    leaf counter_slice12_ifg_ifgbe_core_rx_oobe_crc_err_counter8_rx_oobe_port_crc_err_cnt {
      type oc-yang:counter64;
      description
        "OOB Extract CRC error counter per port";
    }
    leaf counter_slice12_ifg_ifgbe_core_rx_oobe_crc_err_counter9_rx_oobe_port_crc_err_cnt {
      type oc-yang:counter64;
      description
        "OOB Extract CRC error counter per port";
    }
    leaf counter_slice12_ifg_ifgbe_core_rx_oobe_crc_err_counter10_rx_oobe_port_crc_err_cnt {
      type oc-yang:counter64;
      description
        "OOB Extract CRC error counter per port";
    }
    leaf counter_slice12_ifg_ifgbe_core_rx_oobe_crc_err_counter11_rx_oobe_port_crc_err_cnt {
      type oc-yang:counter64;
      description
        "OOB Extract CRC error counter per port";
    }
    leaf counter_slice12_ifg_ifgbe_core_rx_oobe_crc_err_counter12_rx_oobe_port_crc_err_cnt {
      type oc-yang:counter64;
      description
        "OOB Extract CRC error counter per port";
    }
    leaf counter_slice12_ifg_ifgbe_core_rx_oobe_crc_err_counter13_rx_oobe_port_crc_err_cnt {
      type oc-yang:counter64;
      description
        "OOB Extract CRC error counter per port";
    }
    leaf counter_slice12_ifg_ifgbe_core_rx_oobe_crc_err_counter14_rx_oobe_port_crc_err_cnt {
      type oc-yang:counter64;
      description
        "OOB Extract CRC error counter per port";
    }
    leaf counter_slice12_ifg_ifgbe_core_rx_oobe_crc_err_counter15_rx_oobe_port_crc_err_cnt {
      type oc-yang:counter64;
      description
        "OOB Extract CRC error counter per port";
    }
    leaf counter_slice12_ifg_ifgbe_core_rx_oobe_crc_err_counter16_rx_oobe_port_crc_err_cnt {
      type oc-yang:counter64;
      description
        "OOB Extract CRC error counter per port";
    }
    leaf counter_slice12_ifg_ifgbe_core_rx_oobe_crc_err_counter17_rx_oobe_port_crc_err_cnt {
      type oc-yang:counter64;
      description
        "OOB Extract CRC error counter per port";
    }
    leaf counter_slice12_ifg_ifgbe_core_rx_oobe_crc_err_counter18_rx_oobe_port_crc_err_cnt {
      type oc-yang:counter64;
      description
        "OOB Extract CRC error counter per port";
    }
    leaf counter_slice12_ifg_ifgbe_core_rx_oobe_crc_err_counter19_rx_oobe_port_crc_err_cnt {
      type oc-yang:counter64;
      description
        "OOB Extract CRC error counter per port";
    }
    leaf counter_slice12_ifg_ifgbe_core_rx_oobe_crc_err_counter20_rx_oobe_port_crc_err_cnt {
      type oc-yang:counter64;
      description
        "OOB Extract CRC error counter per port";
    }
    leaf counter_slice12_ifg_ifgbe_core_rx_oobe_crc_err_counter21_rx_oobe_port_crc_err_cnt {
      type oc-yang:counter64;
      description
        "OOB Extract CRC error counter per port";
    }
    leaf counter_slice12_ifg_ifgbe_core_rx_oobe_crc_err_counter22_rx_oobe_port_crc_err_cnt {
      type oc-yang:counter64;
      description
        "OOB Extract CRC error counter per port";
    }
    leaf counter_slice12_ifg_ifgbe_core_rx_oobe_crc_err_counter23_rx_oobe_port_crc_err_cnt {
      type oc-yang:counter64;
      description
        "OOB Extract CRC error counter per port";
    }
    leaf counter_slice12_ifg_ifgbe_core_rx_oobe_crc_err_counter24_rx_oobe_port_crc_err_cnt {
      type oc-yang:counter64;
      description
        "OOB Extract CRC error counter per port";
    }
    leaf counter_slice12_ifg_ifgbe_core_rx_oobe_crc_err_counter25_rx_oobe_port_crc_err_cnt {
      type oc-yang:counter64;
      description
        "OOB Extract CRC error counter per port";
    }
    leaf counter_slice12_ifg_ifgbe_core_rx_oobe_crc_err_counter26_rx_oobe_port_crc_err_cnt {
      type oc-yang:counter64;
      description
        "OOB Extract CRC error counter per port";
    }
    leaf counter_slice12_ifg_ifgbe_core_rx_oobe_crc_err_counter27_rx_oobe_port_crc_err_cnt {
      type oc-yang:counter64;
      description
        "OOB Extract CRC error counter per port";
    }
    leaf counter_slice12_ifg_ifgbe_core_rx_oobe_crc_err_counter28_rx_oobe_port_crc_err_cnt {
      type oc-yang:counter64;
      description
        "OOB Extract CRC error counter per port";
    }
    leaf counter_slice12_ifg_ifgbe_core_rx_oobe_crc_err_counter29_rx_oobe_port_crc_err_cnt {
      type oc-yang:counter64;
      description
        "OOB Extract CRC error counter per port";
    }
    leaf counter_slice12_ifg_ifgbe_core_rx_oobe_crc_err_counter30_rx_oobe_port_crc_err_cnt {
      type oc-yang:counter64;
      description
        "OOB Extract CRC error counter per port";
    }
    leaf counter_slice12_ifg_ifgbe_core_rx_oobe_crc_err_counter31_rx_oobe_port_crc_err_cnt {
      type oc-yang:counter64;
      description
        "OOB Extract CRC error counter per port";
    }
    leaf counter_slice13_ifg_ifgbe_core_rx_oobe_crc_err_counter0_rx_oobe_port_crc_err_cnt {
      type oc-yang:counter64;
      description
        "OOB Extract CRC error counter per port";
    }
    leaf counter_slice13_ifg_ifgbe_core_rx_oobe_crc_err_counter1_rx_oobe_port_crc_err_cnt {
      type oc-yang:counter64;
      description
        "OOB Extract CRC error counter per port";
    }
    leaf counter_slice13_ifg_ifgbe_core_rx_oobe_crc_err_counter2_rx_oobe_port_crc_err_cnt {
      type oc-yang:counter64;
      description
        "OOB Extract CRC error counter per port";
    }
    leaf counter_slice13_ifg_ifgbe_core_rx_oobe_crc_err_counter3_rx_oobe_port_crc_err_cnt {
      type oc-yang:counter64;
      description
        "OOB Extract CRC error counter per port";
    }
    leaf counter_slice13_ifg_ifgbe_core_rx_oobe_crc_err_counter4_rx_oobe_port_crc_err_cnt {
      type oc-yang:counter64;
      description
        "OOB Extract CRC error counter per port";
    }
    leaf counter_slice13_ifg_ifgbe_core_rx_oobe_crc_err_counter5_rx_oobe_port_crc_err_cnt {
      type oc-yang:counter64;
      description
        "OOB Extract CRC error counter per port";
    }
    leaf counter_slice13_ifg_ifgbe_core_rx_oobe_crc_err_counter6_rx_oobe_port_crc_err_cnt {
      type oc-yang:counter64;
      description
        "OOB Extract CRC error counter per port";
    }
    leaf counter_slice13_ifg_ifgbe_core_rx_oobe_crc_err_counter7_rx_oobe_port_crc_err_cnt {
      type oc-yang:counter64;
      description
        "OOB Extract CRC error counter per port";
    }
    leaf counter_slice13_ifg_ifgbe_core_rx_oobe_crc_err_counter8_rx_oobe_port_crc_err_cnt {
      type oc-yang:counter64;
      description
        "OOB Extract CRC error counter per port";
    }
    leaf counter_slice13_ifg_ifgbe_core_rx_oobe_crc_err_counter9_rx_oobe_port_crc_err_cnt {
      type oc-yang:counter64;
      description
        "OOB Extract CRC error counter per port";
    }
    leaf counter_slice13_ifg_ifgbe_core_rx_oobe_crc_err_counter10_rx_oobe_port_crc_err_cnt {
      type oc-yang:counter64;
      description
        "OOB Extract CRC error counter per port";
    }
    leaf counter_slice13_ifg_ifgbe_core_rx_oobe_crc_err_counter11_rx_oobe_port_crc_err_cnt {
      type oc-yang:counter64;
      description
        "OOB Extract CRC error counter per port";
    }
    leaf counter_slice13_ifg_ifgbe_core_rx_oobe_crc_err_counter12_rx_oobe_port_crc_err_cnt {
      type oc-yang:counter64;
      description
        "OOB Extract CRC error counter per port";
    }
    leaf counter_slice13_ifg_ifgbe_core_rx_oobe_crc_err_counter13_rx_oobe_port_crc_err_cnt {
      type oc-yang:counter64;
      description
        "OOB Extract CRC error counter per port";
    }
    leaf counter_slice13_ifg_ifgbe_core_rx_oobe_crc_err_counter14_rx_oobe_port_crc_err_cnt {
      type oc-yang:counter64;
      description
        "OOB Extract CRC error counter per port";
    }
    leaf counter_slice13_ifg_ifgbe_core_rx_oobe_crc_err_counter15_rx_oobe_port_crc_err_cnt {
      type oc-yang:counter64;
      description
        "OOB Extract CRC error counter per port";
    }
    leaf counter_slice13_ifg_ifgbe_core_rx_oobe_crc_err_counter16_rx_oobe_port_crc_err_cnt {
      type oc-yang:counter64;
      description
        "OOB Extract CRC error counter per port";
    }
    leaf counter_slice13_ifg_ifgbe_core_rx_oobe_crc_err_counter17_rx_oobe_port_crc_err_cnt {
      type oc-yang:counter64;
      description
        "OOB Extract CRC error counter per port";
    }
    leaf counter_slice13_ifg_ifgbe_core_rx_oobe_crc_err_counter18_rx_oobe_port_crc_err_cnt {
      type oc-yang:counter64;
      description
        "OOB Extract CRC error counter per port";
    }
    leaf counter_slice13_ifg_ifgbe_core_rx_oobe_crc_err_counter19_rx_oobe_port_crc_err_cnt {
      type oc-yang:counter64;
      description
        "OOB Extract CRC error counter per port";
    }
    leaf counter_slice13_ifg_ifgbe_core_rx_oobe_crc_err_counter20_rx_oobe_port_crc_err_cnt {
      type oc-yang:counter64;
      description
        "OOB Extract CRC error counter per port";
    }
    leaf counter_slice13_ifg_ifgbe_core_rx_oobe_crc_err_counter21_rx_oobe_port_crc_err_cnt {
      type oc-yang:counter64;
      description
        "OOB Extract CRC error counter per port";
    }
    leaf counter_slice13_ifg_ifgbe_core_rx_oobe_crc_err_counter22_rx_oobe_port_crc_err_cnt {
      type oc-yang:counter64;
      description
        "OOB Extract CRC error counter per port";
    }
    leaf counter_slice13_ifg_ifgbe_core_rx_oobe_crc_err_counter23_rx_oobe_port_crc_err_cnt {
      type oc-yang:counter64;
      description
        "OOB Extract CRC error counter per port";
    }
    leaf counter_slice13_ifg_ifgbe_core_rx_oobe_crc_err_counter24_rx_oobe_port_crc_err_cnt {
      type oc-yang:counter64;
      description
        "OOB Extract CRC error counter per port";
    }
    leaf counter_slice13_ifg_ifgbe_core_rx_oobe_crc_err_counter25_rx_oobe_port_crc_err_cnt {
      type oc-yang:counter64;
      description
        "OOB Extract CRC error counter per port";
    }
    leaf counter_slice13_ifg_ifgbe_core_rx_oobe_crc_err_counter26_rx_oobe_port_crc_err_cnt {
      type oc-yang:counter64;
      description
        "OOB Extract CRC error counter per port";
    }
    leaf counter_slice13_ifg_ifgbe_core_rx_oobe_crc_err_counter27_rx_oobe_port_crc_err_cnt {
      type oc-yang:counter64;
      description
        "OOB Extract CRC error counter per port";
    }
    leaf counter_slice13_ifg_ifgbe_core_rx_oobe_crc_err_counter28_rx_oobe_port_crc_err_cnt {
      type oc-yang:counter64;
      description
        "OOB Extract CRC error counter per port";
    }
    leaf counter_slice13_ifg_ifgbe_core_rx_oobe_crc_err_counter29_rx_oobe_port_crc_err_cnt {
      type oc-yang:counter64;
      description
        "OOB Extract CRC error counter per port";
    }
    leaf counter_slice13_ifg_ifgbe_core_rx_oobe_crc_err_counter30_rx_oobe_port_crc_err_cnt {
      type oc-yang:counter64;
      description
        "OOB Extract CRC error counter per port";
    }
    leaf counter_slice13_ifg_ifgbe_core_rx_oobe_crc_err_counter31_rx_oobe_port_crc_err_cnt {
      type oc-yang:counter64;
      description
        "OOB Extract CRC error counter per port";
    }
    leaf counter_slice14_ifg_ifgbe_core_rx_oobe_crc_err_counter0_rx_oobe_port_crc_err_cnt {
      type oc-yang:counter64;
      description
        "OOB Extract CRC error counter per port";
    }
    leaf counter_slice14_ifg_ifgbe_core_rx_oobe_crc_err_counter1_rx_oobe_port_crc_err_cnt {
      type oc-yang:counter64;
      description
        "OOB Extract CRC error counter per port";
    }
    leaf counter_slice14_ifg_ifgbe_core_rx_oobe_crc_err_counter2_rx_oobe_port_crc_err_cnt {
      type oc-yang:counter64;
      description
        "OOB Extract CRC error counter per port";
    }
    leaf counter_slice14_ifg_ifgbe_core_rx_oobe_crc_err_counter3_rx_oobe_port_crc_err_cnt {
      type oc-yang:counter64;
      description
        "OOB Extract CRC error counter per port";
    }
    leaf counter_slice14_ifg_ifgbe_core_rx_oobe_crc_err_counter4_rx_oobe_port_crc_err_cnt {
      type oc-yang:counter64;
      description
        "OOB Extract CRC error counter per port";
    }
    leaf counter_slice14_ifg_ifgbe_core_rx_oobe_crc_err_counter5_rx_oobe_port_crc_err_cnt {
      type oc-yang:counter64;
      description
        "OOB Extract CRC error counter per port";
    }
    leaf counter_slice14_ifg_ifgbe_core_rx_oobe_crc_err_counter6_rx_oobe_port_crc_err_cnt {
      type oc-yang:counter64;
      description
        "OOB Extract CRC error counter per port";
    }
    leaf counter_slice14_ifg_ifgbe_core_rx_oobe_crc_err_counter7_rx_oobe_port_crc_err_cnt {
      type oc-yang:counter64;
      description
        "OOB Extract CRC error counter per port";
    }
    leaf counter_slice14_ifg_ifgbe_core_rx_oobe_crc_err_counter8_rx_oobe_port_crc_err_cnt {
      type oc-yang:counter64;
      description
        "OOB Extract CRC error counter per port";
    }
    leaf counter_slice14_ifg_ifgbe_core_rx_oobe_crc_err_counter9_rx_oobe_port_crc_err_cnt {
      type oc-yang:counter64;
      description
        "OOB Extract CRC error counter per port";
    }
    leaf counter_slice14_ifg_ifgbe_core_rx_oobe_crc_err_counter10_rx_oobe_port_crc_err_cnt {
      type oc-yang:counter64;
      description
        "OOB Extract CRC error counter per port";
    }
    leaf counter_slice14_ifg_ifgbe_core_rx_oobe_crc_err_counter11_rx_oobe_port_crc_err_cnt {
      type oc-yang:counter64;
      description
        "OOB Extract CRC error counter per port";
    }
    leaf counter_slice14_ifg_ifgbe_core_rx_oobe_crc_err_counter12_rx_oobe_port_crc_err_cnt {
      type oc-yang:counter64;
      description
        "OOB Extract CRC error counter per port";
    }
    leaf counter_slice14_ifg_ifgbe_core_rx_oobe_crc_err_counter13_rx_oobe_port_crc_err_cnt {
      type oc-yang:counter64;
      description
        "OOB Extract CRC error counter per port";
    }
    leaf counter_slice14_ifg_ifgbe_core_rx_oobe_crc_err_counter14_rx_oobe_port_crc_err_cnt {
      type oc-yang:counter64;
      description
        "OOB Extract CRC error counter per port";
    }
    leaf counter_slice14_ifg_ifgbe_core_rx_oobe_crc_err_counter15_rx_oobe_port_crc_err_cnt {
      type oc-yang:counter64;
      description
        "OOB Extract CRC error counter per port";
    }
    leaf counter_slice14_ifg_ifgbe_core_rx_oobe_crc_err_counter16_rx_oobe_port_crc_err_cnt {
      type oc-yang:counter64;
      description
        "OOB Extract CRC error counter per port";
    }
    leaf counter_slice14_ifg_ifgbe_core_rx_oobe_crc_err_counter17_rx_oobe_port_crc_err_cnt {
      type oc-yang:counter64;
      description
        "OOB Extract CRC error counter per port";
    }
    leaf counter_slice14_ifg_ifgbe_core_rx_oobe_crc_err_counter18_rx_oobe_port_crc_err_cnt {
      type oc-yang:counter64;
      description
        "OOB Extract CRC error counter per port";
    }
    leaf counter_slice14_ifg_ifgbe_core_rx_oobe_crc_err_counter19_rx_oobe_port_crc_err_cnt {
      type oc-yang:counter64;
      description
        "OOB Extract CRC error counter per port";
    }
    leaf counter_slice14_ifg_ifgbe_core_rx_oobe_crc_err_counter20_rx_oobe_port_crc_err_cnt {
      type oc-yang:counter64;
      description
        "OOB Extract CRC error counter per port";
    }
    leaf counter_slice14_ifg_ifgbe_core_rx_oobe_crc_err_counter21_rx_oobe_port_crc_err_cnt {
      type oc-yang:counter64;
      description
        "OOB Extract CRC error counter per port";
    }
    leaf counter_slice14_ifg_ifgbe_core_rx_oobe_crc_err_counter22_rx_oobe_port_crc_err_cnt {
      type oc-yang:counter64;
      description
        "OOB Extract CRC error counter per port";
    }
    leaf counter_slice14_ifg_ifgbe_core_rx_oobe_crc_err_counter23_rx_oobe_port_crc_err_cnt {
      type oc-yang:counter64;
      description
        "OOB Extract CRC error counter per port";
    }
    leaf counter_slice14_ifg_ifgbe_core_rx_oobe_crc_err_counter24_rx_oobe_port_crc_err_cnt {
      type oc-yang:counter64;
      description
        "OOB Extract CRC error counter per port";
    }
    leaf counter_slice14_ifg_ifgbe_core_rx_oobe_crc_err_counter25_rx_oobe_port_crc_err_cnt {
      type oc-yang:counter64;
      description
        "OOB Extract CRC error counter per port";
    }
    leaf counter_slice14_ifg_ifgbe_core_rx_oobe_crc_err_counter26_rx_oobe_port_crc_err_cnt {
      type oc-yang:counter64;
      description
        "OOB Extract CRC error counter per port";
    }
    leaf counter_slice14_ifg_ifgbe_core_rx_oobe_crc_err_counter27_rx_oobe_port_crc_err_cnt {
      type oc-yang:counter64;
      description
        "OOB Extract CRC error counter per port";
    }
    leaf counter_slice14_ifg_ifgbe_core_rx_oobe_crc_err_counter28_rx_oobe_port_crc_err_cnt {
      type oc-yang:counter64;
      description
        "OOB Extract CRC error counter per port";
    }
    leaf counter_slice14_ifg_ifgbe_core_rx_oobe_crc_err_counter29_rx_oobe_port_crc_err_cnt {
      type oc-yang:counter64;
      description
        "OOB Extract CRC error counter per port";
    }
    leaf counter_slice14_ifg_ifgbe_core_rx_oobe_crc_err_counter30_rx_oobe_port_crc_err_cnt {
      type oc-yang:counter64;
      description
        "OOB Extract CRC error counter per port";
    }
    leaf counter_slice14_ifg_ifgbe_core_rx_oobe_crc_err_counter31_rx_oobe_port_crc_err_cnt {
      type oc-yang:counter64;
      description
        "OOB Extract CRC error counter per port";
    }
    leaf counter_slice15_ifg_ifgbe_core_rx_oobe_crc_err_counter0_rx_oobe_port_crc_err_cnt {
      type oc-yang:counter64;
      description
        "OOB Extract CRC error counter per port";
    }
    leaf counter_slice15_ifg_ifgbe_core_rx_oobe_crc_err_counter1_rx_oobe_port_crc_err_cnt {
      type oc-yang:counter64;
      description
        "OOB Extract CRC error counter per port";
    }
    leaf counter_slice15_ifg_ifgbe_core_rx_oobe_crc_err_counter2_rx_oobe_port_crc_err_cnt {
      type oc-yang:counter64;
      description
        "OOB Extract CRC error counter per port";
    }
    leaf counter_slice15_ifg_ifgbe_core_rx_oobe_crc_err_counter3_rx_oobe_port_crc_err_cnt {
      type oc-yang:counter64;
      description
        "OOB Extract CRC error counter per port";
    }
    leaf counter_slice15_ifg_ifgbe_core_rx_oobe_crc_err_counter4_rx_oobe_port_crc_err_cnt {
      type oc-yang:counter64;
      description
        "OOB Extract CRC error counter per port";
    }
    leaf counter_slice15_ifg_ifgbe_core_rx_oobe_crc_err_counter5_rx_oobe_port_crc_err_cnt {
      type oc-yang:counter64;
      description
        "OOB Extract CRC error counter per port";
    }
    leaf counter_slice15_ifg_ifgbe_core_rx_oobe_crc_err_counter6_rx_oobe_port_crc_err_cnt {
      type oc-yang:counter64;
      description
        "OOB Extract CRC error counter per port";
    }
    leaf counter_slice15_ifg_ifgbe_core_rx_oobe_crc_err_counter7_rx_oobe_port_crc_err_cnt {
      type oc-yang:counter64;
      description
        "OOB Extract CRC error counter per port";
    }
    leaf counter_slice15_ifg_ifgbe_core_rx_oobe_crc_err_counter8_rx_oobe_port_crc_err_cnt {
      type oc-yang:counter64;
      description
        "OOB Extract CRC error counter per port";
    }
    leaf counter_slice15_ifg_ifgbe_core_rx_oobe_crc_err_counter9_rx_oobe_port_crc_err_cnt {
      type oc-yang:counter64;
      description
        "OOB Extract CRC error counter per port";
    }
    leaf counter_slice15_ifg_ifgbe_core_rx_oobe_crc_err_counter10_rx_oobe_port_crc_err_cnt {
      type oc-yang:counter64;
      description
        "OOB Extract CRC error counter per port";
    }
    leaf counter_slice15_ifg_ifgbe_core_rx_oobe_crc_err_counter11_rx_oobe_port_crc_err_cnt {
      type oc-yang:counter64;
      description
        "OOB Extract CRC error counter per port";
    }
    leaf counter_slice15_ifg_ifgbe_core_rx_oobe_crc_err_counter12_rx_oobe_port_crc_err_cnt {
      type oc-yang:counter64;
      description
        "OOB Extract CRC error counter per port";
    }
    leaf counter_slice15_ifg_ifgbe_core_rx_oobe_crc_err_counter13_rx_oobe_port_crc_err_cnt {
      type oc-yang:counter64;
      description
        "OOB Extract CRC error counter per port";
    }
    leaf counter_slice15_ifg_ifgbe_core_rx_oobe_crc_err_counter14_rx_oobe_port_crc_err_cnt {
      type oc-yang:counter64;
      description
        "OOB Extract CRC error counter per port";
    }
    leaf counter_slice15_ifg_ifgbe_core_rx_oobe_crc_err_counter15_rx_oobe_port_crc_err_cnt {
      type oc-yang:counter64;
      description
        "OOB Extract CRC error counter per port";
    }
    leaf counter_slice15_ifg_ifgbe_core_rx_oobe_crc_err_counter16_rx_oobe_port_crc_err_cnt {
      type oc-yang:counter64;
      description
        "OOB Extract CRC error counter per port";
    }
    leaf counter_slice15_ifg_ifgbe_core_rx_oobe_crc_err_counter17_rx_oobe_port_crc_err_cnt {
      type oc-yang:counter64;
      description
        "OOB Extract CRC error counter per port";
    }
    leaf counter_slice15_ifg_ifgbe_core_rx_oobe_crc_err_counter18_rx_oobe_port_crc_err_cnt {
      type oc-yang:counter64;
      description
        "OOB Extract CRC error counter per port";
    }
    leaf counter_slice15_ifg_ifgbe_core_rx_oobe_crc_err_counter19_rx_oobe_port_crc_err_cnt {
      type oc-yang:counter64;
      description
        "OOB Extract CRC error counter per port";
    }
    leaf counter_slice15_ifg_ifgbe_core_rx_oobe_crc_err_counter20_rx_oobe_port_crc_err_cnt {
      type oc-yang:counter64;
      description
        "OOB Extract CRC error counter per port";
    }
    leaf counter_slice15_ifg_ifgbe_core_rx_oobe_crc_err_counter21_rx_oobe_port_crc_err_cnt {
      type oc-yang:counter64;
      description
        "OOB Extract CRC error counter per port";
    }
    leaf counter_slice15_ifg_ifgbe_core_rx_oobe_crc_err_counter22_rx_oobe_port_crc_err_cnt {
      type oc-yang:counter64;
      description
        "OOB Extract CRC error counter per port";
    }
    leaf counter_slice15_ifg_ifgbe_core_rx_oobe_crc_err_counter23_rx_oobe_port_crc_err_cnt {
      type oc-yang:counter64;
      description
        "OOB Extract CRC error counter per port";
    }
    leaf counter_slice15_ifg_ifgbe_core_rx_oobe_crc_err_counter24_rx_oobe_port_crc_err_cnt {
      type oc-yang:counter64;
      description
        "OOB Extract CRC error counter per port";
    }
    leaf counter_slice15_ifg_ifgbe_core_rx_oobe_crc_err_counter25_rx_oobe_port_crc_err_cnt {
      type oc-yang:counter64;
      description
        "OOB Extract CRC error counter per port";
    }
    leaf counter_slice15_ifg_ifgbe_core_rx_oobe_crc_err_counter26_rx_oobe_port_crc_err_cnt {
      type oc-yang:counter64;
      description
        "OOB Extract CRC error counter per port";
    }
    leaf counter_slice15_ifg_ifgbe_core_rx_oobe_crc_err_counter27_rx_oobe_port_crc_err_cnt {
      type oc-yang:counter64;
      description
        "OOB Extract CRC error counter per port";
    }
    leaf counter_slice15_ifg_ifgbe_core_rx_oobe_crc_err_counter28_rx_oobe_port_crc_err_cnt {
      type oc-yang:counter64;
      description
        "OOB Extract CRC error counter per port";
    }
    leaf counter_slice15_ifg_ifgbe_core_rx_oobe_crc_err_counter29_rx_oobe_port_crc_err_cnt {
      type oc-yang:counter64;
      description
        "OOB Extract CRC error counter per port";
    }
    leaf counter_slice15_ifg_ifgbe_core_rx_oobe_crc_err_counter30_rx_oobe_port_crc_err_cnt {
      type oc-yang:counter64;
      description
        "OOB Extract CRC error counter per port";
    }
    leaf counter_slice15_ifg_ifgbe_core_rx_oobe_crc_err_counter31_rx_oobe_port_crc_err_cnt {
      type oc-yang:counter64;
      description
        "OOB Extract CRC error counter per port";
    }
    leaf counter_slice0_ifg_ifgbe_ra_rx_csms_cgm_drop_counter0_rx_csms_drop_cnt {
      type oc-yang:counter64;
      description
        "RX CSMS packets drop counter.";
    }
    leaf counter_slice0_ifg_ifgbe_ra_rx_csms_cgm_drop_counter1_rx_csms_drop_cnt {
      type oc-yang:counter64;
      description
        "RX CSMS packets drop counter.";
    }
    leaf counter_slice0_ifg_ifgbe_ra_rx_csms_cgm_drop_counter2_rx_csms_drop_cnt {
      type oc-yang:counter64;
      description
        "RX CSMS packets drop counter.";
    }
    leaf counter_slice0_ifg_ifgbe_ra_rx_csms_cgm_drop_counter3_rx_csms_drop_cnt {
      type oc-yang:counter64;
      description
        "RX CSMS packets drop counter.";
    }
    leaf counter_slice0_ifg_ifgbe_ra_rx_csms_cgm_drop_counter4_rx_csms_drop_cnt {
      type oc-yang:counter64;
      description
        "RX CSMS packets drop counter.";
    }
    leaf counter_slice0_ifg_ifgbe_ra_rx_csms_cgm_drop_counter5_rx_csms_drop_cnt {
      type oc-yang:counter64;
      description
        "RX CSMS packets drop counter.";
    }
    leaf counter_slice0_ifg_ifgbe_ra_rx_csms_cgm_drop_counter6_rx_csms_drop_cnt {
      type oc-yang:counter64;
      description
        "RX CSMS packets drop counter.";
    }
    leaf counter_slice0_ifg_ifgbe_ra_rx_csms_cgm_drop_counter7_rx_csms_drop_cnt {
      type oc-yang:counter64;
      description
        "RX CSMS packets drop counter.";
    }
    leaf counter_slice1_ifg_ifgbe_ra_rx_csms_cgm_drop_counter0_rx_csms_drop_cnt {
      type oc-yang:counter64;
      description
        "RX CSMS packets drop counter.";
    }
    leaf counter_slice1_ifg_ifgbe_ra_rx_csms_cgm_drop_counter1_rx_csms_drop_cnt {
      type oc-yang:counter64;
      description
        "RX CSMS packets drop counter.";
    }
    leaf counter_slice1_ifg_ifgbe_ra_rx_csms_cgm_drop_counter2_rx_csms_drop_cnt {
      type oc-yang:counter64;
      description
        "RX CSMS packets drop counter.";
    }
    leaf counter_slice1_ifg_ifgbe_ra_rx_csms_cgm_drop_counter3_rx_csms_drop_cnt {
      type oc-yang:counter64;
      description
        "RX CSMS packets drop counter.";
    }
    leaf counter_slice1_ifg_ifgbe_ra_rx_csms_cgm_drop_counter4_rx_csms_drop_cnt {
      type oc-yang:counter64;
      description
        "RX CSMS packets drop counter.";
    }
    leaf counter_slice1_ifg_ifgbe_ra_rx_csms_cgm_drop_counter5_rx_csms_drop_cnt {
      type oc-yang:counter64;
      description
        "RX CSMS packets drop counter.";
    }
    leaf counter_slice1_ifg_ifgbe_ra_rx_csms_cgm_drop_counter6_rx_csms_drop_cnt {
      type oc-yang:counter64;
      description
        "RX CSMS packets drop counter.";
    }
    leaf counter_slice1_ifg_ifgbe_ra_rx_csms_cgm_drop_counter7_rx_csms_drop_cnt {
      type oc-yang:counter64;
      description
        "RX CSMS packets drop counter.";
    }
    leaf counter_slice2_ifg_ifgbe_ra_rx_csms_cgm_drop_counter0_rx_csms_drop_cnt {
      type oc-yang:counter64;
      description
        "RX CSMS packets drop counter.";
    }
    leaf counter_slice2_ifg_ifgbe_ra_rx_csms_cgm_drop_counter1_rx_csms_drop_cnt {
      type oc-yang:counter64;
      description
        "RX CSMS packets drop counter.";
    }
    leaf counter_slice2_ifg_ifgbe_ra_rx_csms_cgm_drop_counter2_rx_csms_drop_cnt {
      type oc-yang:counter64;
      description
        "RX CSMS packets drop counter.";
    }
    leaf counter_slice2_ifg_ifgbe_ra_rx_csms_cgm_drop_counter3_rx_csms_drop_cnt {
      type oc-yang:counter64;
      description
        "RX CSMS packets drop counter.";
    }
    leaf counter_slice2_ifg_ifgbe_ra_rx_csms_cgm_drop_counter4_rx_csms_drop_cnt {
      type oc-yang:counter64;
      description
        "RX CSMS packets drop counter.";
    }
    leaf counter_slice2_ifg_ifgbe_ra_rx_csms_cgm_drop_counter5_rx_csms_drop_cnt {
      type oc-yang:counter64;
      description
        "RX CSMS packets drop counter.";
    }
    leaf counter_slice2_ifg_ifgbe_ra_rx_csms_cgm_drop_counter6_rx_csms_drop_cnt {
      type oc-yang:counter64;
      description
        "RX CSMS packets drop counter.";
    }
    leaf counter_slice2_ifg_ifgbe_ra_rx_csms_cgm_drop_counter7_rx_csms_drop_cnt {
      type oc-yang:counter64;
      description
        "RX CSMS packets drop counter.";
    }
    leaf counter_slice3_ifg_ifgbe_ra_rx_csms_cgm_drop_counter0_rx_csms_drop_cnt {
      type oc-yang:counter64;
      description
        "RX CSMS packets drop counter.";
    }
    leaf counter_slice3_ifg_ifgbe_ra_rx_csms_cgm_drop_counter1_rx_csms_drop_cnt {
      type oc-yang:counter64;
      description
        "RX CSMS packets drop counter.";
    }
    leaf counter_slice3_ifg_ifgbe_ra_rx_csms_cgm_drop_counter2_rx_csms_drop_cnt {
      type oc-yang:counter64;
      description
        "RX CSMS packets drop counter.";
    }
    leaf counter_slice3_ifg_ifgbe_ra_rx_csms_cgm_drop_counter3_rx_csms_drop_cnt {
      type oc-yang:counter64;
      description
        "RX CSMS packets drop counter.";
    }
    leaf counter_slice3_ifg_ifgbe_ra_rx_csms_cgm_drop_counter4_rx_csms_drop_cnt {
      type oc-yang:counter64;
      description
        "RX CSMS packets drop counter.";
    }
    leaf counter_slice3_ifg_ifgbe_ra_rx_csms_cgm_drop_counter5_rx_csms_drop_cnt {
      type oc-yang:counter64;
      description
        "RX CSMS packets drop counter.";
    }
    leaf counter_slice3_ifg_ifgbe_ra_rx_csms_cgm_drop_counter6_rx_csms_drop_cnt {
      type oc-yang:counter64;
      description
        "RX CSMS packets drop counter.";
    }
    leaf counter_slice3_ifg_ifgbe_ra_rx_csms_cgm_drop_counter7_rx_csms_drop_cnt {
      type oc-yang:counter64;
      description
        "RX CSMS packets drop counter.";
    }
    leaf counter_slice4_ifg_ifgbe_ra_rx_csms_cgm_drop_counter0_rx_csms_drop_cnt {
      type oc-yang:counter64;
      description
        "RX CSMS packets drop counter.";
    }
    leaf counter_slice4_ifg_ifgbe_ra_rx_csms_cgm_drop_counter1_rx_csms_drop_cnt {
      type oc-yang:counter64;
      description
        "RX CSMS packets drop counter.";
    }
    leaf counter_slice4_ifg_ifgbe_ra_rx_csms_cgm_drop_counter2_rx_csms_drop_cnt {
      type oc-yang:counter64;
      description
        "RX CSMS packets drop counter.";
    }
    leaf counter_slice4_ifg_ifgbe_ra_rx_csms_cgm_drop_counter3_rx_csms_drop_cnt {
      type oc-yang:counter64;
      description
        "RX CSMS packets drop counter.";
    }
    leaf counter_slice4_ifg_ifgbe_ra_rx_csms_cgm_drop_counter4_rx_csms_drop_cnt {
      type oc-yang:counter64;
      description
        "RX CSMS packets drop counter.";
    }
    leaf counter_slice4_ifg_ifgbe_ra_rx_csms_cgm_drop_counter5_rx_csms_drop_cnt {
      type oc-yang:counter64;
      description
        "RX CSMS packets drop counter.";
    }
    leaf counter_slice4_ifg_ifgbe_ra_rx_csms_cgm_drop_counter6_rx_csms_drop_cnt {
      type oc-yang:counter64;
      description
        "RX CSMS packets drop counter.";
    }
    leaf counter_slice4_ifg_ifgbe_ra_rx_csms_cgm_drop_counter7_rx_csms_drop_cnt {
      type oc-yang:counter64;
      description
        "RX CSMS packets drop counter.";
    }
    leaf counter_slice5_ifg_ifgbe_ra_rx_csms_cgm_drop_counter0_rx_csms_drop_cnt {
      type oc-yang:counter64;
      description
        "RX CSMS packets drop counter.";
    }
    leaf counter_slice5_ifg_ifgbe_ra_rx_csms_cgm_drop_counter1_rx_csms_drop_cnt {
      type oc-yang:counter64;
      description
        "RX CSMS packets drop counter.";
    }
    leaf counter_slice5_ifg_ifgbe_ra_rx_csms_cgm_drop_counter2_rx_csms_drop_cnt {
      type oc-yang:counter64;
      description
        "RX CSMS packets drop counter.";
    }
    leaf counter_slice5_ifg_ifgbe_ra_rx_csms_cgm_drop_counter3_rx_csms_drop_cnt {
      type oc-yang:counter64;
      description
        "RX CSMS packets drop counter.";
    }
    leaf counter_slice5_ifg_ifgbe_ra_rx_csms_cgm_drop_counter4_rx_csms_drop_cnt {
      type oc-yang:counter64;
      description
        "RX CSMS packets drop counter.";
    }
    leaf counter_slice5_ifg_ifgbe_ra_rx_csms_cgm_drop_counter5_rx_csms_drop_cnt {
      type oc-yang:counter64;
      description
        "RX CSMS packets drop counter.";
    }
    leaf counter_slice5_ifg_ifgbe_ra_rx_csms_cgm_drop_counter6_rx_csms_drop_cnt {
      type oc-yang:counter64;
      description
        "RX CSMS packets drop counter.";
    }
    leaf counter_slice5_ifg_ifgbe_ra_rx_csms_cgm_drop_counter7_rx_csms_drop_cnt {
      type oc-yang:counter64;
      description
        "RX CSMS packets drop counter.";
    }
    leaf counter_slice6_ifg_ifgbe_ra_rx_csms_cgm_drop_counter0_rx_csms_drop_cnt {
      type oc-yang:counter64;
      description
        "RX CSMS packets drop counter.";
    }
    leaf counter_slice6_ifg_ifgbe_ra_rx_csms_cgm_drop_counter1_rx_csms_drop_cnt {
      type oc-yang:counter64;
      description
        "RX CSMS packets drop counter.";
    }
    leaf counter_slice6_ifg_ifgbe_ra_rx_csms_cgm_drop_counter2_rx_csms_drop_cnt {
      type oc-yang:counter64;
      description
        "RX CSMS packets drop counter.";
    }
    leaf counter_slice6_ifg_ifgbe_ra_rx_csms_cgm_drop_counter3_rx_csms_drop_cnt {
      type oc-yang:counter64;
      description
        "RX CSMS packets drop counter.";
    }
    leaf counter_slice6_ifg_ifgbe_ra_rx_csms_cgm_drop_counter4_rx_csms_drop_cnt {
      type oc-yang:counter64;
      description
        "RX CSMS packets drop counter.";
    }
    leaf counter_slice6_ifg_ifgbe_ra_rx_csms_cgm_drop_counter5_rx_csms_drop_cnt {
      type oc-yang:counter64;
      description
        "RX CSMS packets drop counter.";
    }
    leaf counter_slice6_ifg_ifgbe_ra_rx_csms_cgm_drop_counter6_rx_csms_drop_cnt {
      type oc-yang:counter64;
      description
        "RX CSMS packets drop counter.";
    }
    leaf counter_slice6_ifg_ifgbe_ra_rx_csms_cgm_drop_counter7_rx_csms_drop_cnt {
      type oc-yang:counter64;
      description
        "RX CSMS packets drop counter.";
    }
    leaf counter_slice7_ifg_ifgbe_ra_rx_csms_cgm_drop_counter0_rx_csms_drop_cnt {
      type oc-yang:counter64;
      description
        "RX CSMS packets drop counter.";
    }
    leaf counter_slice7_ifg_ifgbe_ra_rx_csms_cgm_drop_counter1_rx_csms_drop_cnt {
      type oc-yang:counter64;
      description
        "RX CSMS packets drop counter.";
    }
    leaf counter_slice7_ifg_ifgbe_ra_rx_csms_cgm_drop_counter2_rx_csms_drop_cnt {
      type oc-yang:counter64;
      description
        "RX CSMS packets drop counter.";
    }
    leaf counter_slice7_ifg_ifgbe_ra_rx_csms_cgm_drop_counter3_rx_csms_drop_cnt {
      type oc-yang:counter64;
      description
        "RX CSMS packets drop counter.";
    }
    leaf counter_slice7_ifg_ifgbe_ra_rx_csms_cgm_drop_counter4_rx_csms_drop_cnt {
      type oc-yang:counter64;
      description
        "RX CSMS packets drop counter.";
    }
    leaf counter_slice7_ifg_ifgbe_ra_rx_csms_cgm_drop_counter5_rx_csms_drop_cnt {
      type oc-yang:counter64;
      description
        "RX CSMS packets drop counter.";
    }
    leaf counter_slice7_ifg_ifgbe_ra_rx_csms_cgm_drop_counter6_rx_csms_drop_cnt {
      type oc-yang:counter64;
      description
        "RX CSMS packets drop counter.";
    }
    leaf counter_slice7_ifg_ifgbe_ra_rx_csms_cgm_drop_counter7_rx_csms_drop_cnt {
      type oc-yang:counter64;
      description
        "RX CSMS packets drop counter.";
    }
    leaf counter_slice8_ifg_ifgbe_ra_rx_csms_cgm_drop_counter0_rx_csms_drop_cnt {
      type oc-yang:counter64;
      description
        "RX CSMS packets drop counter.";
    }
    leaf counter_slice8_ifg_ifgbe_ra_rx_csms_cgm_drop_counter1_rx_csms_drop_cnt {
      type oc-yang:counter64;
      description
        "RX CSMS packets drop counter.";
    }
    leaf counter_slice8_ifg_ifgbe_ra_rx_csms_cgm_drop_counter2_rx_csms_drop_cnt {
      type oc-yang:counter64;
      description
        "RX CSMS packets drop counter.";
    }
    leaf counter_slice8_ifg_ifgbe_ra_rx_csms_cgm_drop_counter3_rx_csms_drop_cnt {
      type oc-yang:counter64;
      description
        "RX CSMS packets drop counter.";
    }
    leaf counter_slice8_ifg_ifgbe_ra_rx_csms_cgm_drop_counter4_rx_csms_drop_cnt {
      type oc-yang:counter64;
      description
        "RX CSMS packets drop counter.";
    }
    leaf counter_slice8_ifg_ifgbe_ra_rx_csms_cgm_drop_counter5_rx_csms_drop_cnt {
      type oc-yang:counter64;
      description
        "RX CSMS packets drop counter.";
    }
    leaf counter_slice8_ifg_ifgbe_ra_rx_csms_cgm_drop_counter6_rx_csms_drop_cnt {
      type oc-yang:counter64;
      description
        "RX CSMS packets drop counter.";
    }
    leaf counter_slice8_ifg_ifgbe_ra_rx_csms_cgm_drop_counter7_rx_csms_drop_cnt {
      type oc-yang:counter64;
      description
        "RX CSMS packets drop counter.";
    }
    leaf counter_slice9_ifg_ifgbe_ra_rx_csms_cgm_drop_counter0_rx_csms_drop_cnt {
      type oc-yang:counter64;
      description
        "RX CSMS packets drop counter.";
    }
    leaf counter_slice9_ifg_ifgbe_ra_rx_csms_cgm_drop_counter1_rx_csms_drop_cnt {
      type oc-yang:counter64;
      description
        "RX CSMS packets drop counter.";
    }
    leaf counter_slice9_ifg_ifgbe_ra_rx_csms_cgm_drop_counter2_rx_csms_drop_cnt {
      type oc-yang:counter64;
      description
        "RX CSMS packets drop counter.";
    }
    leaf counter_slice9_ifg_ifgbe_ra_rx_csms_cgm_drop_counter3_rx_csms_drop_cnt {
      type oc-yang:counter64;
      description
        "RX CSMS packets drop counter.";
    }
    leaf counter_slice9_ifg_ifgbe_ra_rx_csms_cgm_drop_counter4_rx_csms_drop_cnt {
      type oc-yang:counter64;
      description
        "RX CSMS packets drop counter.";
    }
    leaf counter_slice9_ifg_ifgbe_ra_rx_csms_cgm_drop_counter5_rx_csms_drop_cnt {
      type oc-yang:counter64;
      description
        "RX CSMS packets drop counter.";
    }
    leaf counter_slice9_ifg_ifgbe_ra_rx_csms_cgm_drop_counter6_rx_csms_drop_cnt {
      type oc-yang:counter64;
      description
        "RX CSMS packets drop counter.";
    }
    leaf counter_slice9_ifg_ifgbe_ra_rx_csms_cgm_drop_counter7_rx_csms_drop_cnt {
      type oc-yang:counter64;
      description
        "RX CSMS packets drop counter.";
    }
    leaf counter_slice10_ifg_ifgbe_ra_rx_csms_cgm_drop_counter0_rx_csms_drop_cnt {
      type oc-yang:counter64;
      description
        "RX CSMS packets drop counter.";
    }
    leaf counter_slice10_ifg_ifgbe_ra_rx_csms_cgm_drop_counter1_rx_csms_drop_cnt {
      type oc-yang:counter64;
      description
        "RX CSMS packets drop counter.";
    }
    leaf counter_slice10_ifg_ifgbe_ra_rx_csms_cgm_drop_counter2_rx_csms_drop_cnt {
      type oc-yang:counter64;
      description
        "RX CSMS packets drop counter.";
    }
    leaf counter_slice10_ifg_ifgbe_ra_rx_csms_cgm_drop_counter3_rx_csms_drop_cnt {
      type oc-yang:counter64;
      description
        "RX CSMS packets drop counter.";
    }
    leaf counter_slice10_ifg_ifgbe_ra_rx_csms_cgm_drop_counter4_rx_csms_drop_cnt {
      type oc-yang:counter64;
      description
        "RX CSMS packets drop counter.";
    }
    leaf counter_slice10_ifg_ifgbe_ra_rx_csms_cgm_drop_counter5_rx_csms_drop_cnt {
      type oc-yang:counter64;
      description
        "RX CSMS packets drop counter.";
    }
    leaf counter_slice10_ifg_ifgbe_ra_rx_csms_cgm_drop_counter6_rx_csms_drop_cnt {
      type oc-yang:counter64;
      description
        "RX CSMS packets drop counter.";
    }
    leaf counter_slice10_ifg_ifgbe_ra_rx_csms_cgm_drop_counter7_rx_csms_drop_cnt {
      type oc-yang:counter64;
      description
        "RX CSMS packets drop counter.";
    }
    leaf counter_slice11_ifg_ifgbe_ra_rx_csms_cgm_drop_counter0_rx_csms_drop_cnt {
      type oc-yang:counter64;
      description
        "RX CSMS packets drop counter.";
    }
    leaf counter_slice11_ifg_ifgbe_ra_rx_csms_cgm_drop_counter1_rx_csms_drop_cnt {
      type oc-yang:counter64;
      description
        "RX CSMS packets drop counter.";
    }
    leaf counter_slice11_ifg_ifgbe_ra_rx_csms_cgm_drop_counter2_rx_csms_drop_cnt {
      type oc-yang:counter64;
      description
        "RX CSMS packets drop counter.";
    }
    leaf counter_slice11_ifg_ifgbe_ra_rx_csms_cgm_drop_counter3_rx_csms_drop_cnt {
      type oc-yang:counter64;
      description
        "RX CSMS packets drop counter.";
    }
    leaf counter_slice11_ifg_ifgbe_ra_rx_csms_cgm_drop_counter4_rx_csms_drop_cnt {
      type oc-yang:counter64;
      description
        "RX CSMS packets drop counter.";
    }
    leaf counter_slice11_ifg_ifgbe_ra_rx_csms_cgm_drop_counter5_rx_csms_drop_cnt {
      type oc-yang:counter64;
      description
        "RX CSMS packets drop counter.";
    }
    leaf counter_slice11_ifg_ifgbe_ra_rx_csms_cgm_drop_counter6_rx_csms_drop_cnt {
      type oc-yang:counter64;
      description
        "RX CSMS packets drop counter.";
    }
    leaf counter_slice11_ifg_ifgbe_ra_rx_csms_cgm_drop_counter7_rx_csms_drop_cnt {
      type oc-yang:counter64;
      description
        "RX CSMS packets drop counter.";
    }
    leaf counter_slice12_ifg_ifgbe_ra_rx_csms_cgm_drop_counter0_rx_csms_drop_cnt {
      type oc-yang:counter64;
      description
        "RX CSMS packets drop counter.";
    }
    leaf counter_slice12_ifg_ifgbe_ra_rx_csms_cgm_drop_counter1_rx_csms_drop_cnt {
      type oc-yang:counter64;
      description
        "RX CSMS packets drop counter.";
    }
    leaf counter_slice12_ifg_ifgbe_ra_rx_csms_cgm_drop_counter2_rx_csms_drop_cnt {
      type oc-yang:counter64;
      description
        "RX CSMS packets drop counter.";
    }
    leaf counter_slice12_ifg_ifgbe_ra_rx_csms_cgm_drop_counter3_rx_csms_drop_cnt {
      type oc-yang:counter64;
      description
        "RX CSMS packets drop counter.";
    }
    leaf counter_slice12_ifg_ifgbe_ra_rx_csms_cgm_drop_counter4_rx_csms_drop_cnt {
      type oc-yang:counter64;
      description
        "RX CSMS packets drop counter.";
    }
    leaf counter_slice12_ifg_ifgbe_ra_rx_csms_cgm_drop_counter5_rx_csms_drop_cnt {
      type oc-yang:counter64;
      description
        "RX CSMS packets drop counter.";
    }
    leaf counter_slice12_ifg_ifgbe_ra_rx_csms_cgm_drop_counter6_rx_csms_drop_cnt {
      type oc-yang:counter64;
      description
        "RX CSMS packets drop counter.";
    }
    leaf counter_slice12_ifg_ifgbe_ra_rx_csms_cgm_drop_counter7_rx_csms_drop_cnt {
      type oc-yang:counter64;
      description
        "RX CSMS packets drop counter.";
    }
    leaf counter_slice13_ifg_ifgbe_ra_rx_csms_cgm_drop_counter0_rx_csms_drop_cnt {
      type oc-yang:counter64;
      description
        "RX CSMS packets drop counter.";
    }
    leaf counter_slice13_ifg_ifgbe_ra_rx_csms_cgm_drop_counter1_rx_csms_drop_cnt {
      type oc-yang:counter64;
      description
        "RX CSMS packets drop counter.";
    }
    leaf counter_slice13_ifg_ifgbe_ra_rx_csms_cgm_drop_counter2_rx_csms_drop_cnt {
      type oc-yang:counter64;
      description
        "RX CSMS packets drop counter.";
    }
    leaf counter_slice13_ifg_ifgbe_ra_rx_csms_cgm_drop_counter3_rx_csms_drop_cnt {
      type oc-yang:counter64;
      description
        "RX CSMS packets drop counter.";
    }
    leaf counter_slice13_ifg_ifgbe_ra_rx_csms_cgm_drop_counter4_rx_csms_drop_cnt {
      type oc-yang:counter64;
      description
        "RX CSMS packets drop counter.";
    }
    leaf counter_slice13_ifg_ifgbe_ra_rx_csms_cgm_drop_counter5_rx_csms_drop_cnt {
      type oc-yang:counter64;
      description
        "RX CSMS packets drop counter.";
    }
    leaf counter_slice13_ifg_ifgbe_ra_rx_csms_cgm_drop_counter6_rx_csms_drop_cnt {
      type oc-yang:counter64;
      description
        "RX CSMS packets drop counter.";
    }
    leaf counter_slice13_ifg_ifgbe_ra_rx_csms_cgm_drop_counter7_rx_csms_drop_cnt {
      type oc-yang:counter64;
      description
        "RX CSMS packets drop counter.";
    }
    leaf counter_slice14_ifg_ifgbe_ra_rx_csms_cgm_drop_counter0_rx_csms_drop_cnt {
      type oc-yang:counter64;
      description
        "RX CSMS packets drop counter.";
    }
    leaf counter_slice14_ifg_ifgbe_ra_rx_csms_cgm_drop_counter1_rx_csms_drop_cnt {
      type oc-yang:counter64;
      description
        "RX CSMS packets drop counter.";
    }
    leaf counter_slice14_ifg_ifgbe_ra_rx_csms_cgm_drop_counter2_rx_csms_drop_cnt {
      type oc-yang:counter64;
      description
        "RX CSMS packets drop counter.";
    }
    leaf counter_slice14_ifg_ifgbe_ra_rx_csms_cgm_drop_counter3_rx_csms_drop_cnt {
      type oc-yang:counter64;
      description
        "RX CSMS packets drop counter.";
    }
    leaf counter_slice14_ifg_ifgbe_ra_rx_csms_cgm_drop_counter4_rx_csms_drop_cnt {
      type oc-yang:counter64;
      description
        "RX CSMS packets drop counter.";
    }
    leaf counter_slice14_ifg_ifgbe_ra_rx_csms_cgm_drop_counter5_rx_csms_drop_cnt {
      type oc-yang:counter64;
      description
        "RX CSMS packets drop counter.";
    }
    leaf counter_slice14_ifg_ifgbe_ra_rx_csms_cgm_drop_counter6_rx_csms_drop_cnt {
      type oc-yang:counter64;
      description
        "RX CSMS packets drop counter.";
    }
    leaf counter_slice14_ifg_ifgbe_ra_rx_csms_cgm_drop_counter7_rx_csms_drop_cnt {
      type oc-yang:counter64;
      description
        "RX CSMS packets drop counter.";
    }
    leaf counter_slice15_ifg_ifgbe_ra_rx_csms_cgm_drop_counter0_rx_csms_drop_cnt {
      type oc-yang:counter64;
      description
        "RX CSMS packets drop counter.";
    }
    leaf counter_slice15_ifg_ifgbe_ra_rx_csms_cgm_drop_counter1_rx_csms_drop_cnt {
      type oc-yang:counter64;
      description
        "RX CSMS packets drop counter.";
    }
    leaf counter_slice15_ifg_ifgbe_ra_rx_csms_cgm_drop_counter2_rx_csms_drop_cnt {
      type oc-yang:counter64;
      description
        "RX CSMS packets drop counter.";
    }
    leaf counter_slice15_ifg_ifgbe_ra_rx_csms_cgm_drop_counter3_rx_csms_drop_cnt {
      type oc-yang:counter64;
      description
        "RX CSMS packets drop counter.";
    }
    leaf counter_slice15_ifg_ifgbe_ra_rx_csms_cgm_drop_counter4_rx_csms_drop_cnt {
      type oc-yang:counter64;
      description
        "RX CSMS packets drop counter.";
    }
    leaf counter_slice15_ifg_ifgbe_ra_rx_csms_cgm_drop_counter5_rx_csms_drop_cnt {
      type oc-yang:counter64;
      description
        "RX CSMS packets drop counter.";
    }
    leaf counter_slice15_ifg_ifgbe_ra_rx_csms_cgm_drop_counter6_rx_csms_drop_cnt {
      type oc-yang:counter64;
      description
        "RX CSMS packets drop counter.";
    }
    leaf counter_slice15_ifg_ifgbe_ra_rx_csms_cgm_drop_counter7_rx_csms_drop_cnt {
      type oc-yang:counter64;
      description
        "RX CSMS packets drop counter.";
    }
    leaf counter_slice0_ifg_ifgbe_ra_rx_frm_cgm_drop_counter0_rx_frm_drop_cnt {
      type oc-yang:counter64;
      description
        "RX FRM packets drop counter.";
    }
    leaf counter_slice0_ifg_ifgbe_ra_rx_frm_cgm_drop_counter1_rx_frm_drop_cnt {
      type oc-yang:counter64;
      description
        "RX FRM packets drop counter.";
    }
    leaf counter_slice0_ifg_ifgbe_ra_rx_frm_cgm_drop_counter2_rx_frm_drop_cnt {
      type oc-yang:counter64;
      description
        "RX FRM packets drop counter.";
    }
    leaf counter_slice0_ifg_ifgbe_ra_rx_frm_cgm_drop_counter3_rx_frm_drop_cnt {
      type oc-yang:counter64;
      description
        "RX FRM packets drop counter.";
    }
    leaf counter_slice0_ifg_ifgbe_ra_rx_frm_cgm_drop_counter4_rx_frm_drop_cnt {
      type oc-yang:counter64;
      description
        "RX FRM packets drop counter.";
    }
    leaf counter_slice0_ifg_ifgbe_ra_rx_frm_cgm_drop_counter5_rx_frm_drop_cnt {
      type oc-yang:counter64;
      description
        "RX FRM packets drop counter.";
    }
    leaf counter_slice0_ifg_ifgbe_ra_rx_frm_cgm_drop_counter6_rx_frm_drop_cnt {
      type oc-yang:counter64;
      description
        "RX FRM packets drop counter.";
    }
    leaf counter_slice0_ifg_ifgbe_ra_rx_frm_cgm_drop_counter7_rx_frm_drop_cnt {
      type oc-yang:counter64;
      description
        "RX FRM packets drop counter.";
    }
    leaf counter_slice1_ifg_ifgbe_ra_rx_frm_cgm_drop_counter0_rx_frm_drop_cnt {
      type oc-yang:counter64;
      description
        "RX FRM packets drop counter.";
    }
    leaf counter_slice1_ifg_ifgbe_ra_rx_frm_cgm_drop_counter1_rx_frm_drop_cnt {
      type oc-yang:counter64;
      description
        "RX FRM packets drop counter.";
    }
    leaf counter_slice1_ifg_ifgbe_ra_rx_frm_cgm_drop_counter2_rx_frm_drop_cnt {
      type oc-yang:counter64;
      description
        "RX FRM packets drop counter.";
    }
    leaf counter_slice1_ifg_ifgbe_ra_rx_frm_cgm_drop_counter3_rx_frm_drop_cnt {
      type oc-yang:counter64;
      description
        "RX FRM packets drop counter.";
    }
    leaf counter_slice1_ifg_ifgbe_ra_rx_frm_cgm_drop_counter4_rx_frm_drop_cnt {
      type oc-yang:counter64;
      description
        "RX FRM packets drop counter.";
    }
    leaf counter_slice1_ifg_ifgbe_ra_rx_frm_cgm_drop_counter5_rx_frm_drop_cnt {
      type oc-yang:counter64;
      description
        "RX FRM packets drop counter.";
    }
    leaf counter_slice1_ifg_ifgbe_ra_rx_frm_cgm_drop_counter6_rx_frm_drop_cnt {
      type oc-yang:counter64;
      description
        "RX FRM packets drop counter.";
    }
    leaf counter_slice1_ifg_ifgbe_ra_rx_frm_cgm_drop_counter7_rx_frm_drop_cnt {
      type oc-yang:counter64;
      description
        "RX FRM packets drop counter.";
    }
    leaf counter_slice2_ifg_ifgbe_ra_rx_frm_cgm_drop_counter0_rx_frm_drop_cnt {
      type oc-yang:counter64;
      description
        "RX FRM packets drop counter.";
    }
    leaf counter_slice2_ifg_ifgbe_ra_rx_frm_cgm_drop_counter1_rx_frm_drop_cnt {
      type oc-yang:counter64;
      description
        "RX FRM packets drop counter.";
    }
    leaf counter_slice2_ifg_ifgbe_ra_rx_frm_cgm_drop_counter2_rx_frm_drop_cnt {
      type oc-yang:counter64;
      description
        "RX FRM packets drop counter.";
    }
    leaf counter_slice2_ifg_ifgbe_ra_rx_frm_cgm_drop_counter3_rx_frm_drop_cnt {
      type oc-yang:counter64;
      description
        "RX FRM packets drop counter.";
    }
    leaf counter_slice2_ifg_ifgbe_ra_rx_frm_cgm_drop_counter4_rx_frm_drop_cnt {
      type oc-yang:counter64;
      description
        "RX FRM packets drop counter.";
    }
    leaf counter_slice2_ifg_ifgbe_ra_rx_frm_cgm_drop_counter5_rx_frm_drop_cnt {
      type oc-yang:counter64;
      description
        "RX FRM packets drop counter.";
    }
    leaf counter_slice2_ifg_ifgbe_ra_rx_frm_cgm_drop_counter6_rx_frm_drop_cnt {
      type oc-yang:counter64;
      description
        "RX FRM packets drop counter.";
    }
    leaf counter_slice2_ifg_ifgbe_ra_rx_frm_cgm_drop_counter7_rx_frm_drop_cnt {
      type oc-yang:counter64;
      description
        "RX FRM packets drop counter.";
    }
    leaf counter_slice3_ifg_ifgbe_ra_rx_frm_cgm_drop_counter0_rx_frm_drop_cnt {
      type oc-yang:counter64;
      description
        "RX FRM packets drop counter.";
    }
    leaf counter_slice3_ifg_ifgbe_ra_rx_frm_cgm_drop_counter1_rx_frm_drop_cnt {
      type oc-yang:counter64;
      description
        "RX FRM packets drop counter.";
    }
    leaf counter_slice3_ifg_ifgbe_ra_rx_frm_cgm_drop_counter2_rx_frm_drop_cnt {
      type oc-yang:counter64;
      description
        "RX FRM packets drop counter.";
    }
    leaf counter_slice3_ifg_ifgbe_ra_rx_frm_cgm_drop_counter3_rx_frm_drop_cnt {
      type oc-yang:counter64;
      description
        "RX FRM packets drop counter.";
    }
    leaf counter_slice3_ifg_ifgbe_ra_rx_frm_cgm_drop_counter4_rx_frm_drop_cnt {
      type oc-yang:counter64;
      description
        "RX FRM packets drop counter.";
    }
    leaf counter_slice3_ifg_ifgbe_ra_rx_frm_cgm_drop_counter5_rx_frm_drop_cnt {
      type oc-yang:counter64;
      description
        "RX FRM packets drop counter.";
    }
    leaf counter_slice3_ifg_ifgbe_ra_rx_frm_cgm_drop_counter6_rx_frm_drop_cnt {
      type oc-yang:counter64;
      description
        "RX FRM packets drop counter.";
    }
    leaf counter_slice3_ifg_ifgbe_ra_rx_frm_cgm_drop_counter7_rx_frm_drop_cnt {
      type oc-yang:counter64;
      description
        "RX FRM packets drop counter.";
    }
    leaf counter_slice4_ifg_ifgbe_ra_rx_frm_cgm_drop_counter0_rx_frm_drop_cnt {
      type oc-yang:counter64;
      description
        "RX FRM packets drop counter.";
    }
    leaf counter_slice4_ifg_ifgbe_ra_rx_frm_cgm_drop_counter1_rx_frm_drop_cnt {
      type oc-yang:counter64;
      description
        "RX FRM packets drop counter.";
    }
    leaf counter_slice4_ifg_ifgbe_ra_rx_frm_cgm_drop_counter2_rx_frm_drop_cnt {
      type oc-yang:counter64;
      description
        "RX FRM packets drop counter.";
    }
    leaf counter_slice4_ifg_ifgbe_ra_rx_frm_cgm_drop_counter3_rx_frm_drop_cnt {
      type oc-yang:counter64;
      description
        "RX FRM packets drop counter.";
    }
    leaf counter_slice4_ifg_ifgbe_ra_rx_frm_cgm_drop_counter4_rx_frm_drop_cnt {
      type oc-yang:counter64;
      description
        "RX FRM packets drop counter.";
    }
    leaf counter_slice4_ifg_ifgbe_ra_rx_frm_cgm_drop_counter5_rx_frm_drop_cnt {
      type oc-yang:counter64;
      description
        "RX FRM packets drop counter.";
    }
    leaf counter_slice4_ifg_ifgbe_ra_rx_frm_cgm_drop_counter6_rx_frm_drop_cnt {
      type oc-yang:counter64;
      description
        "RX FRM packets drop counter.";
    }
    leaf counter_slice4_ifg_ifgbe_ra_rx_frm_cgm_drop_counter7_rx_frm_drop_cnt {
      type oc-yang:counter64;
      description
        "RX FRM packets drop counter.";
    }
    leaf counter_slice5_ifg_ifgbe_ra_rx_frm_cgm_drop_counter0_rx_frm_drop_cnt {
      type oc-yang:counter64;
      description
        "RX FRM packets drop counter.";
    }
    leaf counter_slice5_ifg_ifgbe_ra_rx_frm_cgm_drop_counter1_rx_frm_drop_cnt {
      type oc-yang:counter64;
      description
        "RX FRM packets drop counter.";
    }
    leaf counter_slice5_ifg_ifgbe_ra_rx_frm_cgm_drop_counter2_rx_frm_drop_cnt {
      type oc-yang:counter64;
      description
        "RX FRM packets drop counter.";
    }
    leaf counter_slice5_ifg_ifgbe_ra_rx_frm_cgm_drop_counter3_rx_frm_drop_cnt {
      type oc-yang:counter64;
      description
        "RX FRM packets drop counter.";
    }
    leaf counter_slice5_ifg_ifgbe_ra_rx_frm_cgm_drop_counter4_rx_frm_drop_cnt {
      type oc-yang:counter64;
      description
        "RX FRM packets drop counter.";
    }
    leaf counter_slice5_ifg_ifgbe_ra_rx_frm_cgm_drop_counter5_rx_frm_drop_cnt {
      type oc-yang:counter64;
      description
        "RX FRM packets drop counter.";
    }
    leaf counter_slice5_ifg_ifgbe_ra_rx_frm_cgm_drop_counter6_rx_frm_drop_cnt {
      type oc-yang:counter64;
      description
        "RX FRM packets drop counter.";
    }
    leaf counter_slice5_ifg_ifgbe_ra_rx_frm_cgm_drop_counter7_rx_frm_drop_cnt {
      type oc-yang:counter64;
      description
        "RX FRM packets drop counter.";
    }
    leaf counter_slice6_ifg_ifgbe_ra_rx_frm_cgm_drop_counter0_rx_frm_drop_cnt {
      type oc-yang:counter64;
      description
        "RX FRM packets drop counter.";
    }
    leaf counter_slice6_ifg_ifgbe_ra_rx_frm_cgm_drop_counter1_rx_frm_drop_cnt {
      type oc-yang:counter64;
      description
        "RX FRM packets drop counter.";
    }
    leaf counter_slice6_ifg_ifgbe_ra_rx_frm_cgm_drop_counter2_rx_frm_drop_cnt {
      type oc-yang:counter64;
      description
        "RX FRM packets drop counter.";
    }
    leaf counter_slice6_ifg_ifgbe_ra_rx_frm_cgm_drop_counter3_rx_frm_drop_cnt {
      type oc-yang:counter64;
      description
        "RX FRM packets drop counter.";
    }
    leaf counter_slice6_ifg_ifgbe_ra_rx_frm_cgm_drop_counter4_rx_frm_drop_cnt {
      type oc-yang:counter64;
      description
        "RX FRM packets drop counter.";
    }
    leaf counter_slice6_ifg_ifgbe_ra_rx_frm_cgm_drop_counter5_rx_frm_drop_cnt {
      type oc-yang:counter64;
      description
        "RX FRM packets drop counter.";
    }
    leaf counter_slice6_ifg_ifgbe_ra_rx_frm_cgm_drop_counter6_rx_frm_drop_cnt {
      type oc-yang:counter64;
      description
        "RX FRM packets drop counter.";
    }
    leaf counter_slice6_ifg_ifgbe_ra_rx_frm_cgm_drop_counter7_rx_frm_drop_cnt {
      type oc-yang:counter64;
      description
        "RX FRM packets drop counter.";
    }
    leaf counter_slice7_ifg_ifgbe_ra_rx_frm_cgm_drop_counter0_rx_frm_drop_cnt {
      type oc-yang:counter64;
      description
        "RX FRM packets drop counter.";
    }
    leaf counter_slice7_ifg_ifgbe_ra_rx_frm_cgm_drop_counter1_rx_frm_drop_cnt {
      type oc-yang:counter64;
      description
        "RX FRM packets drop counter.";
    }
    leaf counter_slice7_ifg_ifgbe_ra_rx_frm_cgm_drop_counter2_rx_frm_drop_cnt {
      type oc-yang:counter64;
      description
        "RX FRM packets drop counter.";
    }
    leaf counter_slice7_ifg_ifgbe_ra_rx_frm_cgm_drop_counter3_rx_frm_drop_cnt {
      type oc-yang:counter64;
      description
        "RX FRM packets drop counter.";
    }
    leaf counter_slice7_ifg_ifgbe_ra_rx_frm_cgm_drop_counter4_rx_frm_drop_cnt {
      type oc-yang:counter64;
      description
        "RX FRM packets drop counter.";
    }
    leaf counter_slice7_ifg_ifgbe_ra_rx_frm_cgm_drop_counter5_rx_frm_drop_cnt {
      type oc-yang:counter64;
      description
        "RX FRM packets drop counter.";
    }
    leaf counter_slice7_ifg_ifgbe_ra_rx_frm_cgm_drop_counter6_rx_frm_drop_cnt {
      type oc-yang:counter64;
      description
        "RX FRM packets drop counter.";
    }
    leaf counter_slice7_ifg_ifgbe_ra_rx_frm_cgm_drop_counter7_rx_frm_drop_cnt {
      type oc-yang:counter64;
      description
        "RX FRM packets drop counter.";
    }
    leaf counter_slice8_ifg_ifgbe_ra_rx_frm_cgm_drop_counter0_rx_frm_drop_cnt {
      type oc-yang:counter64;
      description
        "RX FRM packets drop counter.";
    }
    leaf counter_slice8_ifg_ifgbe_ra_rx_frm_cgm_drop_counter1_rx_frm_drop_cnt {
      type oc-yang:counter64;
      description
        "RX FRM packets drop counter.";
    }
    leaf counter_slice8_ifg_ifgbe_ra_rx_frm_cgm_drop_counter2_rx_frm_drop_cnt {
      type oc-yang:counter64;
      description
        "RX FRM packets drop counter.";
    }
    leaf counter_slice8_ifg_ifgbe_ra_rx_frm_cgm_drop_counter3_rx_frm_drop_cnt {
      type oc-yang:counter64;
      description
        "RX FRM packets drop counter.";
    }
    leaf counter_slice8_ifg_ifgbe_ra_rx_frm_cgm_drop_counter4_rx_frm_drop_cnt {
      type oc-yang:counter64;
      description
        "RX FRM packets drop counter.";
    }
    leaf counter_slice8_ifg_ifgbe_ra_rx_frm_cgm_drop_counter5_rx_frm_drop_cnt {
      type oc-yang:counter64;
      description
        "RX FRM packets drop counter.";
    }
    leaf counter_slice8_ifg_ifgbe_ra_rx_frm_cgm_drop_counter6_rx_frm_drop_cnt {
      type oc-yang:counter64;
      description
        "RX FRM packets drop counter.";
    }
    leaf counter_slice8_ifg_ifgbe_ra_rx_frm_cgm_drop_counter7_rx_frm_drop_cnt {
      type oc-yang:counter64;
      description
        "RX FRM packets drop counter.";
    }
    leaf counter_slice9_ifg_ifgbe_ra_rx_frm_cgm_drop_counter0_rx_frm_drop_cnt {
      type oc-yang:counter64;
      description
        "RX FRM packets drop counter.";
    }
    leaf counter_slice9_ifg_ifgbe_ra_rx_frm_cgm_drop_counter1_rx_frm_drop_cnt {
      type oc-yang:counter64;
      description
        "RX FRM packets drop counter.";
    }
    leaf counter_slice9_ifg_ifgbe_ra_rx_frm_cgm_drop_counter2_rx_frm_drop_cnt {
      type oc-yang:counter64;
      description
        "RX FRM packets drop counter.";
    }
    leaf counter_slice9_ifg_ifgbe_ra_rx_frm_cgm_drop_counter3_rx_frm_drop_cnt {
      type oc-yang:counter64;
      description
        "RX FRM packets drop counter.";
    }
    leaf counter_slice9_ifg_ifgbe_ra_rx_frm_cgm_drop_counter4_rx_frm_drop_cnt {
      type oc-yang:counter64;
      description
        "RX FRM packets drop counter.";
    }
    leaf counter_slice9_ifg_ifgbe_ra_rx_frm_cgm_drop_counter5_rx_frm_drop_cnt {
      type oc-yang:counter64;
      description
        "RX FRM packets drop counter.";
    }
    leaf counter_slice9_ifg_ifgbe_ra_rx_frm_cgm_drop_counter6_rx_frm_drop_cnt {
      type oc-yang:counter64;
      description
        "RX FRM packets drop counter.";
    }
    leaf counter_slice9_ifg_ifgbe_ra_rx_frm_cgm_drop_counter7_rx_frm_drop_cnt {
      type oc-yang:counter64;
      description
        "RX FRM packets drop counter.";
    }
    leaf counter_slice10_ifg_ifgbe_ra_rx_frm_cgm_drop_counter0_rx_frm_drop_cnt {
      type oc-yang:counter64;
      description
        "RX FRM packets drop counter.";
    }
    leaf counter_slice10_ifg_ifgbe_ra_rx_frm_cgm_drop_counter1_rx_frm_drop_cnt {
      type oc-yang:counter64;
      description
        "RX FRM packets drop counter.";
    }
    leaf counter_slice10_ifg_ifgbe_ra_rx_frm_cgm_drop_counter2_rx_frm_drop_cnt {
      type oc-yang:counter64;
      description
        "RX FRM packets drop counter.";
    }
    leaf counter_slice10_ifg_ifgbe_ra_rx_frm_cgm_drop_counter3_rx_frm_drop_cnt {
      type oc-yang:counter64;
      description
        "RX FRM packets drop counter.";
    }
    leaf counter_slice10_ifg_ifgbe_ra_rx_frm_cgm_drop_counter4_rx_frm_drop_cnt {
      type oc-yang:counter64;
      description
        "RX FRM packets drop counter.";
    }
    leaf counter_slice10_ifg_ifgbe_ra_rx_frm_cgm_drop_counter5_rx_frm_drop_cnt {
      type oc-yang:counter64;
      description
        "RX FRM packets drop counter.";
    }
    leaf counter_slice10_ifg_ifgbe_ra_rx_frm_cgm_drop_counter6_rx_frm_drop_cnt {
      type oc-yang:counter64;
      description
        "RX FRM packets drop counter.";
    }
    leaf counter_slice10_ifg_ifgbe_ra_rx_frm_cgm_drop_counter7_rx_frm_drop_cnt {
      type oc-yang:counter64;
      description
        "RX FRM packets drop counter.";
    }
    leaf counter_slice11_ifg_ifgbe_ra_rx_frm_cgm_drop_counter0_rx_frm_drop_cnt {
      type oc-yang:counter64;
      description
        "RX FRM packets drop counter.";
    }
    leaf counter_slice11_ifg_ifgbe_ra_rx_frm_cgm_drop_counter1_rx_frm_drop_cnt {
      type oc-yang:counter64;
      description
        "RX FRM packets drop counter.";
    }
    leaf counter_slice11_ifg_ifgbe_ra_rx_frm_cgm_drop_counter2_rx_frm_drop_cnt {
      type oc-yang:counter64;
      description
        "RX FRM packets drop counter.";
    }
    leaf counter_slice11_ifg_ifgbe_ra_rx_frm_cgm_drop_counter3_rx_frm_drop_cnt {
      type oc-yang:counter64;
      description
        "RX FRM packets drop counter.";
    }
    leaf counter_slice11_ifg_ifgbe_ra_rx_frm_cgm_drop_counter4_rx_frm_drop_cnt {
      type oc-yang:counter64;
      description
        "RX FRM packets drop counter.";
    }
    leaf counter_slice11_ifg_ifgbe_ra_rx_frm_cgm_drop_counter5_rx_frm_drop_cnt {
      type oc-yang:counter64;
      description
        "RX FRM packets drop counter.";
    }
    leaf counter_slice11_ifg_ifgbe_ra_rx_frm_cgm_drop_counter6_rx_frm_drop_cnt {
      type oc-yang:counter64;
      description
        "RX FRM packets drop counter.";
    }
    leaf counter_slice11_ifg_ifgbe_ra_rx_frm_cgm_drop_counter7_rx_frm_drop_cnt {
      type oc-yang:counter64;
      description
        "RX FRM packets drop counter.";
    }
    leaf counter_slice12_ifg_ifgbe_ra_rx_frm_cgm_drop_counter0_rx_frm_drop_cnt {
      type oc-yang:counter64;
      description
        "RX FRM packets drop counter.";
    }
    leaf counter_slice12_ifg_ifgbe_ra_rx_frm_cgm_drop_counter1_rx_frm_drop_cnt {
      type oc-yang:counter64;
      description
        "RX FRM packets drop counter.";
    }
    leaf counter_slice12_ifg_ifgbe_ra_rx_frm_cgm_drop_counter2_rx_frm_drop_cnt {
      type oc-yang:counter64;
      description
        "RX FRM packets drop counter.";
    }
    leaf counter_slice12_ifg_ifgbe_ra_rx_frm_cgm_drop_counter3_rx_frm_drop_cnt {
      type oc-yang:counter64;
      description
        "RX FRM packets drop counter.";
    }
    leaf counter_slice12_ifg_ifgbe_ra_rx_frm_cgm_drop_counter4_rx_frm_drop_cnt {
      type oc-yang:counter64;
      description
        "RX FRM packets drop counter.";
    }
    leaf counter_slice12_ifg_ifgbe_ra_rx_frm_cgm_drop_counter5_rx_frm_drop_cnt {
      type oc-yang:counter64;
      description
        "RX FRM packets drop counter.";
    }
    leaf counter_slice12_ifg_ifgbe_ra_rx_frm_cgm_drop_counter6_rx_frm_drop_cnt {
      type oc-yang:counter64;
      description
        "RX FRM packets drop counter.";
    }
    leaf counter_slice12_ifg_ifgbe_ra_rx_frm_cgm_drop_counter7_rx_frm_drop_cnt {
      type oc-yang:counter64;
      description
        "RX FRM packets drop counter.";
    }
    leaf counter_slice13_ifg_ifgbe_ra_rx_frm_cgm_drop_counter0_rx_frm_drop_cnt {
      type oc-yang:counter64;
      description
        "RX FRM packets drop counter.";
    }
    leaf counter_slice13_ifg_ifgbe_ra_rx_frm_cgm_drop_counter1_rx_frm_drop_cnt {
      type oc-yang:counter64;
      description
        "RX FRM packets drop counter.";
    }
    leaf counter_slice13_ifg_ifgbe_ra_rx_frm_cgm_drop_counter2_rx_frm_drop_cnt {
      type oc-yang:counter64;
      description
        "RX FRM packets drop counter.";
    }
    leaf counter_slice13_ifg_ifgbe_ra_rx_frm_cgm_drop_counter3_rx_frm_drop_cnt {
      type oc-yang:counter64;
      description
        "RX FRM packets drop counter.";
    }
    leaf counter_slice13_ifg_ifgbe_ra_rx_frm_cgm_drop_counter4_rx_frm_drop_cnt {
      type oc-yang:counter64;
      description
        "RX FRM packets drop counter.";
    }
    leaf counter_slice13_ifg_ifgbe_ra_rx_frm_cgm_drop_counter5_rx_frm_drop_cnt {
      type oc-yang:counter64;
      description
        "RX FRM packets drop counter.";
    }
    leaf counter_slice13_ifg_ifgbe_ra_rx_frm_cgm_drop_counter6_rx_frm_drop_cnt {
      type oc-yang:counter64;
      description
        "RX FRM packets drop counter.";
    }
    leaf counter_slice13_ifg_ifgbe_ra_rx_frm_cgm_drop_counter7_rx_frm_drop_cnt {
      type oc-yang:counter64;
      description
        "RX FRM packets drop counter.";
    }
    leaf counter_slice14_ifg_ifgbe_ra_rx_frm_cgm_drop_counter0_rx_frm_drop_cnt {
      type oc-yang:counter64;
      description
        "RX FRM packets drop counter.";
    }
    leaf counter_slice14_ifg_ifgbe_ra_rx_frm_cgm_drop_counter1_rx_frm_drop_cnt {
      type oc-yang:counter64;
      description
        "RX FRM packets drop counter.";
    }
    leaf counter_slice14_ifg_ifgbe_ra_rx_frm_cgm_drop_counter2_rx_frm_drop_cnt {
      type oc-yang:counter64;
      description
        "RX FRM packets drop counter.";
    }
    leaf counter_slice14_ifg_ifgbe_ra_rx_frm_cgm_drop_counter3_rx_frm_drop_cnt {
      type oc-yang:counter64;
      description
        "RX FRM packets drop counter.";
    }
    leaf counter_slice14_ifg_ifgbe_ra_rx_frm_cgm_drop_counter4_rx_frm_drop_cnt {
      type oc-yang:counter64;
      description
        "RX FRM packets drop counter.";
    }
    leaf counter_slice14_ifg_ifgbe_ra_rx_frm_cgm_drop_counter5_rx_frm_drop_cnt {
      type oc-yang:counter64;
      description
        "RX FRM packets drop counter.";
    }
    leaf counter_slice14_ifg_ifgbe_ra_rx_frm_cgm_drop_counter6_rx_frm_drop_cnt {
      type oc-yang:counter64;
      description
        "RX FRM packets drop counter.";
    }
    leaf counter_slice14_ifg_ifgbe_ra_rx_frm_cgm_drop_counter7_rx_frm_drop_cnt {
      type oc-yang:counter64;
      description
        "RX FRM packets drop counter.";
    }
    leaf counter_slice15_ifg_ifgbe_ra_rx_frm_cgm_drop_counter0_rx_frm_drop_cnt {
      type oc-yang:counter64;
      description
        "RX FRM packets drop counter.";
    }
    leaf counter_slice15_ifg_ifgbe_ra_rx_frm_cgm_drop_counter1_rx_frm_drop_cnt {
      type oc-yang:counter64;
      description
        "RX FRM packets drop counter.";
    }
    leaf counter_slice15_ifg_ifgbe_ra_rx_frm_cgm_drop_counter2_rx_frm_drop_cnt {
      type oc-yang:counter64;
      description
        "RX FRM packets drop counter.";
    }
    leaf counter_slice15_ifg_ifgbe_ra_rx_frm_cgm_drop_counter3_rx_frm_drop_cnt {
      type oc-yang:counter64;
      description
        "RX FRM packets drop counter.";
    }
    leaf counter_slice15_ifg_ifgbe_ra_rx_frm_cgm_drop_counter4_rx_frm_drop_cnt {
      type oc-yang:counter64;
      description
        "RX FRM packets drop counter.";
    }
    leaf counter_slice15_ifg_ifgbe_ra_rx_frm_cgm_drop_counter5_rx_frm_drop_cnt {
      type oc-yang:counter64;
      description
        "RX FRM packets drop counter.";
    }
    leaf counter_slice15_ifg_ifgbe_ra_rx_frm_cgm_drop_counter6_rx_frm_drop_cnt {
      type oc-yang:counter64;
      description
        "RX FRM packets drop counter.";
    }
    leaf counter_slice15_ifg_ifgbe_ra_rx_frm_cgm_drop_counter7_rx_frm_drop_cnt {
      type oc-yang:counter64;
      description
        "RX FRM packets drop counter.";
    }
    leaf counter_slice0_ifg_ifgbe_ra_rx_fte_cgm_drop_counter0_rx_fte_drop_cnt {
      type oc-yang:counter64;
      description
        "RX FTE packets drop counter.";
    }
    leaf counter_slice0_ifg_ifgbe_ra_rx_fte_cgm_drop_counter1_rx_fte_drop_cnt {
      type oc-yang:counter64;
      description
        "RX FTE packets drop counter.";
    }
    leaf counter_slice0_ifg_ifgbe_ra_rx_fte_cgm_drop_counter2_rx_fte_drop_cnt {
      type oc-yang:counter64;
      description
        "RX FTE packets drop counter.";
    }
    leaf counter_slice0_ifg_ifgbe_ra_rx_fte_cgm_drop_counter3_rx_fte_drop_cnt {
      type oc-yang:counter64;
      description
        "RX FTE packets drop counter.";
    }
    leaf counter_slice0_ifg_ifgbe_ra_rx_fte_cgm_drop_counter4_rx_fte_drop_cnt {
      type oc-yang:counter64;
      description
        "RX FTE packets drop counter.";
    }
    leaf counter_slice0_ifg_ifgbe_ra_rx_fte_cgm_drop_counter5_rx_fte_drop_cnt {
      type oc-yang:counter64;
      description
        "RX FTE packets drop counter.";
    }
    leaf counter_slice0_ifg_ifgbe_ra_rx_fte_cgm_drop_counter6_rx_fte_drop_cnt {
      type oc-yang:counter64;
      description
        "RX FTE packets drop counter.";
    }
    leaf counter_slice0_ifg_ifgbe_ra_rx_fte_cgm_drop_counter7_rx_fte_drop_cnt {
      type oc-yang:counter64;
      description
        "RX FTE packets drop counter.";
    }
    leaf counter_slice1_ifg_ifgbe_ra_rx_fte_cgm_drop_counter0_rx_fte_drop_cnt {
      type oc-yang:counter64;
      description
        "RX FTE packets drop counter.";
    }
    leaf counter_slice1_ifg_ifgbe_ra_rx_fte_cgm_drop_counter1_rx_fte_drop_cnt {
      type oc-yang:counter64;
      description
        "RX FTE packets drop counter.";
    }
    leaf counter_slice1_ifg_ifgbe_ra_rx_fte_cgm_drop_counter2_rx_fte_drop_cnt {
      type oc-yang:counter64;
      description
        "RX FTE packets drop counter.";
    }
    leaf counter_slice1_ifg_ifgbe_ra_rx_fte_cgm_drop_counter3_rx_fte_drop_cnt {
      type oc-yang:counter64;
      description
        "RX FTE packets drop counter.";
    }
    leaf counter_slice1_ifg_ifgbe_ra_rx_fte_cgm_drop_counter4_rx_fte_drop_cnt {
      type oc-yang:counter64;
      description
        "RX FTE packets drop counter.";
    }
    leaf counter_slice1_ifg_ifgbe_ra_rx_fte_cgm_drop_counter5_rx_fte_drop_cnt {
      type oc-yang:counter64;
      description
        "RX FTE packets drop counter.";
    }
    leaf counter_slice1_ifg_ifgbe_ra_rx_fte_cgm_drop_counter6_rx_fte_drop_cnt {
      type oc-yang:counter64;
      description
        "RX FTE packets drop counter.";
    }
    leaf counter_slice1_ifg_ifgbe_ra_rx_fte_cgm_drop_counter7_rx_fte_drop_cnt {
      type oc-yang:counter64;
      description
        "RX FTE packets drop counter.";
    }
    leaf counter_slice2_ifg_ifgbe_ra_rx_fte_cgm_drop_counter0_rx_fte_drop_cnt {
      type oc-yang:counter64;
      description
        "RX FTE packets drop counter.";
    }
    leaf counter_slice2_ifg_ifgbe_ra_rx_fte_cgm_drop_counter1_rx_fte_drop_cnt {
      type oc-yang:counter64;
      description
        "RX FTE packets drop counter.";
    }
    leaf counter_slice2_ifg_ifgbe_ra_rx_fte_cgm_drop_counter2_rx_fte_drop_cnt {
      type oc-yang:counter64;
      description
        "RX FTE packets drop counter.";
    }
    leaf counter_slice2_ifg_ifgbe_ra_rx_fte_cgm_drop_counter3_rx_fte_drop_cnt {
      type oc-yang:counter64;
      description
        "RX FTE packets drop counter.";
    }
    leaf counter_slice2_ifg_ifgbe_ra_rx_fte_cgm_drop_counter4_rx_fte_drop_cnt {
      type oc-yang:counter64;
      description
        "RX FTE packets drop counter.";
    }
    leaf counter_slice2_ifg_ifgbe_ra_rx_fte_cgm_drop_counter5_rx_fte_drop_cnt {
      type oc-yang:counter64;
      description
        "RX FTE packets drop counter.";
    }
    leaf counter_slice2_ifg_ifgbe_ra_rx_fte_cgm_drop_counter6_rx_fte_drop_cnt {
      type oc-yang:counter64;
      description
        "RX FTE packets drop counter.";
    }
    leaf counter_slice2_ifg_ifgbe_ra_rx_fte_cgm_drop_counter7_rx_fte_drop_cnt {
      type oc-yang:counter64;
      description
        "RX FTE packets drop counter.";
    }
    leaf counter_slice3_ifg_ifgbe_ra_rx_fte_cgm_drop_counter0_rx_fte_drop_cnt {
      type oc-yang:counter64;
      description
        "RX FTE packets drop counter.";
    }
    leaf counter_slice3_ifg_ifgbe_ra_rx_fte_cgm_drop_counter1_rx_fte_drop_cnt {
      type oc-yang:counter64;
      description
        "RX FTE packets drop counter.";
    }
    leaf counter_slice3_ifg_ifgbe_ra_rx_fte_cgm_drop_counter2_rx_fte_drop_cnt {
      type oc-yang:counter64;
      description
        "RX FTE packets drop counter.";
    }
    leaf counter_slice3_ifg_ifgbe_ra_rx_fte_cgm_drop_counter3_rx_fte_drop_cnt {
      type oc-yang:counter64;
      description
        "RX FTE packets drop counter.";
    }
    leaf counter_slice3_ifg_ifgbe_ra_rx_fte_cgm_drop_counter4_rx_fte_drop_cnt {
      type oc-yang:counter64;
      description
        "RX FTE packets drop counter.";
    }
    leaf counter_slice3_ifg_ifgbe_ra_rx_fte_cgm_drop_counter5_rx_fte_drop_cnt {
      type oc-yang:counter64;
      description
        "RX FTE packets drop counter.";
    }
    leaf counter_slice3_ifg_ifgbe_ra_rx_fte_cgm_drop_counter6_rx_fte_drop_cnt {
      type oc-yang:counter64;
      description
        "RX FTE packets drop counter.";
    }
    leaf counter_slice3_ifg_ifgbe_ra_rx_fte_cgm_drop_counter7_rx_fte_drop_cnt {
      type oc-yang:counter64;
      description
        "RX FTE packets drop counter.";
    }
    leaf counter_slice4_ifg_ifgbe_ra_rx_fte_cgm_drop_counter0_rx_fte_drop_cnt {
      type oc-yang:counter64;
      description
        "RX FTE packets drop counter.";
    }
    leaf counter_slice4_ifg_ifgbe_ra_rx_fte_cgm_drop_counter1_rx_fte_drop_cnt {
      type oc-yang:counter64;
      description
        "RX FTE packets drop counter.";
    }
    leaf counter_slice4_ifg_ifgbe_ra_rx_fte_cgm_drop_counter2_rx_fte_drop_cnt {
      type oc-yang:counter64;
      description
        "RX FTE packets drop counter.";
    }
    leaf counter_slice4_ifg_ifgbe_ra_rx_fte_cgm_drop_counter3_rx_fte_drop_cnt {
      type oc-yang:counter64;
      description
        "RX FTE packets drop counter.";
    }
    leaf counter_slice4_ifg_ifgbe_ra_rx_fte_cgm_drop_counter4_rx_fte_drop_cnt {
      type oc-yang:counter64;
      description
        "RX FTE packets drop counter.";
    }
    leaf counter_slice4_ifg_ifgbe_ra_rx_fte_cgm_drop_counter5_rx_fte_drop_cnt {
      type oc-yang:counter64;
      description
        "RX FTE packets drop counter.";
    }
    leaf counter_slice4_ifg_ifgbe_ra_rx_fte_cgm_drop_counter6_rx_fte_drop_cnt {
      type oc-yang:counter64;
      description
        "RX FTE packets drop counter.";
    }
    leaf counter_slice4_ifg_ifgbe_ra_rx_fte_cgm_drop_counter7_rx_fte_drop_cnt {
      type oc-yang:counter64;
      description
        "RX FTE packets drop counter.";
    }
    leaf counter_slice5_ifg_ifgbe_ra_rx_fte_cgm_drop_counter0_rx_fte_drop_cnt {
      type oc-yang:counter64;
      description
        "RX FTE packets drop counter.";
    }
    leaf counter_slice5_ifg_ifgbe_ra_rx_fte_cgm_drop_counter1_rx_fte_drop_cnt {
      type oc-yang:counter64;
      description
        "RX FTE packets drop counter.";
    }
    leaf counter_slice5_ifg_ifgbe_ra_rx_fte_cgm_drop_counter2_rx_fte_drop_cnt {
      type oc-yang:counter64;
      description
        "RX FTE packets drop counter.";
    }
    leaf counter_slice5_ifg_ifgbe_ra_rx_fte_cgm_drop_counter3_rx_fte_drop_cnt {
      type oc-yang:counter64;
      description
        "RX FTE packets drop counter.";
    }
    leaf counter_slice5_ifg_ifgbe_ra_rx_fte_cgm_drop_counter4_rx_fte_drop_cnt {
      type oc-yang:counter64;
      description
        "RX FTE packets drop counter.";
    }
    leaf counter_slice5_ifg_ifgbe_ra_rx_fte_cgm_drop_counter5_rx_fte_drop_cnt {
      type oc-yang:counter64;
      description
        "RX FTE packets drop counter.";
    }
    leaf counter_slice5_ifg_ifgbe_ra_rx_fte_cgm_drop_counter6_rx_fte_drop_cnt {
      type oc-yang:counter64;
      description
        "RX FTE packets drop counter.";
    }
    leaf counter_slice5_ifg_ifgbe_ra_rx_fte_cgm_drop_counter7_rx_fte_drop_cnt {
      type oc-yang:counter64;
      description
        "RX FTE packets drop counter.";
    }
    leaf counter_slice6_ifg_ifgbe_ra_rx_fte_cgm_drop_counter0_rx_fte_drop_cnt {
      type oc-yang:counter64;
      description
        "RX FTE packets drop counter.";
    }
    leaf counter_slice6_ifg_ifgbe_ra_rx_fte_cgm_drop_counter1_rx_fte_drop_cnt {
      type oc-yang:counter64;
      description
        "RX FTE packets drop counter.";
    }
    leaf counter_slice6_ifg_ifgbe_ra_rx_fte_cgm_drop_counter2_rx_fte_drop_cnt {
      type oc-yang:counter64;
      description
        "RX FTE packets drop counter.";
    }
    leaf counter_slice6_ifg_ifgbe_ra_rx_fte_cgm_drop_counter3_rx_fte_drop_cnt {
      type oc-yang:counter64;
      description
        "RX FTE packets drop counter.";
    }
    leaf counter_slice6_ifg_ifgbe_ra_rx_fte_cgm_drop_counter4_rx_fte_drop_cnt {
      type oc-yang:counter64;
      description
        "RX FTE packets drop counter.";
    }
    leaf counter_slice6_ifg_ifgbe_ra_rx_fte_cgm_drop_counter5_rx_fte_drop_cnt {
      type oc-yang:counter64;
      description
        "RX FTE packets drop counter.";
    }
    leaf counter_slice6_ifg_ifgbe_ra_rx_fte_cgm_drop_counter6_rx_fte_drop_cnt {
      type oc-yang:counter64;
      description
        "RX FTE packets drop counter.";
    }
    leaf counter_slice6_ifg_ifgbe_ra_rx_fte_cgm_drop_counter7_rx_fte_drop_cnt {
      type oc-yang:counter64;
      description
        "RX FTE packets drop counter.";
    }
    leaf counter_slice7_ifg_ifgbe_ra_rx_fte_cgm_drop_counter0_rx_fte_drop_cnt {
      type oc-yang:counter64;
      description
        "RX FTE packets drop counter.";
    }
    leaf counter_slice7_ifg_ifgbe_ra_rx_fte_cgm_drop_counter1_rx_fte_drop_cnt {
      type oc-yang:counter64;
      description
        "RX FTE packets drop counter.";
    }
    leaf counter_slice7_ifg_ifgbe_ra_rx_fte_cgm_drop_counter2_rx_fte_drop_cnt {
      type oc-yang:counter64;
      description
        "RX FTE packets drop counter.";
    }
    leaf counter_slice7_ifg_ifgbe_ra_rx_fte_cgm_drop_counter3_rx_fte_drop_cnt {
      type oc-yang:counter64;
      description
        "RX FTE packets drop counter.";
    }
    leaf counter_slice7_ifg_ifgbe_ra_rx_fte_cgm_drop_counter4_rx_fte_drop_cnt {
      type oc-yang:counter64;
      description
        "RX FTE packets drop counter.";
    }
    leaf counter_slice7_ifg_ifgbe_ra_rx_fte_cgm_drop_counter5_rx_fte_drop_cnt {
      type oc-yang:counter64;
      description
        "RX FTE packets drop counter.";
    }
    leaf counter_slice7_ifg_ifgbe_ra_rx_fte_cgm_drop_counter6_rx_fte_drop_cnt {
      type oc-yang:counter64;
      description
        "RX FTE packets drop counter.";
    }
    leaf counter_slice7_ifg_ifgbe_ra_rx_fte_cgm_drop_counter7_rx_fte_drop_cnt {
      type oc-yang:counter64;
      description
        "RX FTE packets drop counter.";
    }
    leaf counter_slice8_ifg_ifgbe_ra_rx_fte_cgm_drop_counter0_rx_fte_drop_cnt {
      type oc-yang:counter64;
      description
        "RX FTE packets drop counter.";
    }
    leaf counter_slice8_ifg_ifgbe_ra_rx_fte_cgm_drop_counter1_rx_fte_drop_cnt {
      type oc-yang:counter64;
      description
        "RX FTE packets drop counter.";
    }
    leaf counter_slice8_ifg_ifgbe_ra_rx_fte_cgm_drop_counter2_rx_fte_drop_cnt {
      type oc-yang:counter64;
      description
        "RX FTE packets drop counter.";
    }
    leaf counter_slice8_ifg_ifgbe_ra_rx_fte_cgm_drop_counter3_rx_fte_drop_cnt {
      type oc-yang:counter64;
      description
        "RX FTE packets drop counter.";
    }
    leaf counter_slice8_ifg_ifgbe_ra_rx_fte_cgm_drop_counter4_rx_fte_drop_cnt {
      type oc-yang:counter64;
      description
        "RX FTE packets drop counter.";
    }
    leaf counter_slice8_ifg_ifgbe_ra_rx_fte_cgm_drop_counter5_rx_fte_drop_cnt {
      type oc-yang:counter64;
      description
        "RX FTE packets drop counter.";
    }
    leaf counter_slice8_ifg_ifgbe_ra_rx_fte_cgm_drop_counter6_rx_fte_drop_cnt {
      type oc-yang:counter64;
      description
        "RX FTE packets drop counter.";
    }
    leaf counter_slice8_ifg_ifgbe_ra_rx_fte_cgm_drop_counter7_rx_fte_drop_cnt {
      type oc-yang:counter64;
      description
        "RX FTE packets drop counter.";
    }
    leaf counter_slice9_ifg_ifgbe_ra_rx_fte_cgm_drop_counter0_rx_fte_drop_cnt {
      type oc-yang:counter64;
      description
        "RX FTE packets drop counter.";
    }
    leaf counter_slice9_ifg_ifgbe_ra_rx_fte_cgm_drop_counter1_rx_fte_drop_cnt {
      type oc-yang:counter64;
      description
        "RX FTE packets drop counter.";
    }
    leaf counter_slice9_ifg_ifgbe_ra_rx_fte_cgm_drop_counter2_rx_fte_drop_cnt {
      type oc-yang:counter64;
      description
        "RX FTE packets drop counter.";
    }
    leaf counter_slice9_ifg_ifgbe_ra_rx_fte_cgm_drop_counter3_rx_fte_drop_cnt {
      type oc-yang:counter64;
      description
        "RX FTE packets drop counter.";
    }
    leaf counter_slice9_ifg_ifgbe_ra_rx_fte_cgm_drop_counter4_rx_fte_drop_cnt {
      type oc-yang:counter64;
      description
        "RX FTE packets drop counter.";
    }
    leaf counter_slice9_ifg_ifgbe_ra_rx_fte_cgm_drop_counter5_rx_fte_drop_cnt {
      type oc-yang:counter64;
      description
        "RX FTE packets drop counter.";
    }
    leaf counter_slice9_ifg_ifgbe_ra_rx_fte_cgm_drop_counter6_rx_fte_drop_cnt {
      type oc-yang:counter64;
      description
        "RX FTE packets drop counter.";
    }
    leaf counter_slice9_ifg_ifgbe_ra_rx_fte_cgm_drop_counter7_rx_fte_drop_cnt {
      type oc-yang:counter64;
      description
        "RX FTE packets drop counter.";
    }
    leaf counter_slice10_ifg_ifgbe_ra_rx_fte_cgm_drop_counter0_rx_fte_drop_cnt {
      type oc-yang:counter64;
      description
        "RX FTE packets drop counter.";
    }
    leaf counter_slice10_ifg_ifgbe_ra_rx_fte_cgm_drop_counter1_rx_fte_drop_cnt {
      type oc-yang:counter64;
      description
        "RX FTE packets drop counter.";
    }
    leaf counter_slice10_ifg_ifgbe_ra_rx_fte_cgm_drop_counter2_rx_fte_drop_cnt {
      type oc-yang:counter64;
      description
        "RX FTE packets drop counter.";
    }
    leaf counter_slice10_ifg_ifgbe_ra_rx_fte_cgm_drop_counter3_rx_fte_drop_cnt {
      type oc-yang:counter64;
      description
        "RX FTE packets drop counter.";
    }
    leaf counter_slice10_ifg_ifgbe_ra_rx_fte_cgm_drop_counter4_rx_fte_drop_cnt {
      type oc-yang:counter64;
      description
        "RX FTE packets drop counter.";
    }
    leaf counter_slice10_ifg_ifgbe_ra_rx_fte_cgm_drop_counter5_rx_fte_drop_cnt {
      type oc-yang:counter64;
      description
        "RX FTE packets drop counter.";
    }
    leaf counter_slice10_ifg_ifgbe_ra_rx_fte_cgm_drop_counter6_rx_fte_drop_cnt {
      type oc-yang:counter64;
      description
        "RX FTE packets drop counter.";
    }
    leaf counter_slice10_ifg_ifgbe_ra_rx_fte_cgm_drop_counter7_rx_fte_drop_cnt {
      type oc-yang:counter64;
      description
        "RX FTE packets drop counter.";
    }
    leaf counter_slice11_ifg_ifgbe_ra_rx_fte_cgm_drop_counter0_rx_fte_drop_cnt {
      type oc-yang:counter64;
      description
        "RX FTE packets drop counter.";
    }
    leaf counter_slice11_ifg_ifgbe_ra_rx_fte_cgm_drop_counter1_rx_fte_drop_cnt {
      type oc-yang:counter64;
      description
        "RX FTE packets drop counter.";
    }
    leaf counter_slice11_ifg_ifgbe_ra_rx_fte_cgm_drop_counter2_rx_fte_drop_cnt {
      type oc-yang:counter64;
      description
        "RX FTE packets drop counter.";
    }
    leaf counter_slice11_ifg_ifgbe_ra_rx_fte_cgm_drop_counter3_rx_fte_drop_cnt {
      type oc-yang:counter64;
      description
        "RX FTE packets drop counter.";
    }
    leaf counter_slice11_ifg_ifgbe_ra_rx_fte_cgm_drop_counter4_rx_fte_drop_cnt {
      type oc-yang:counter64;
      description
        "RX FTE packets drop counter.";
    }
    leaf counter_slice11_ifg_ifgbe_ra_rx_fte_cgm_drop_counter5_rx_fte_drop_cnt {
      type oc-yang:counter64;
      description
        "RX FTE packets drop counter.";
    }
    leaf counter_slice11_ifg_ifgbe_ra_rx_fte_cgm_drop_counter6_rx_fte_drop_cnt {
      type oc-yang:counter64;
      description
        "RX FTE packets drop counter.";
    }
    leaf counter_slice11_ifg_ifgbe_ra_rx_fte_cgm_drop_counter7_rx_fte_drop_cnt {
      type oc-yang:counter64;
      description
        "RX FTE packets drop counter.";
    }
    leaf counter_slice12_ifg_ifgbe_ra_rx_fte_cgm_drop_counter0_rx_fte_drop_cnt {
      type oc-yang:counter64;
      description
        "RX FTE packets drop counter.";
    }
    leaf counter_slice12_ifg_ifgbe_ra_rx_fte_cgm_drop_counter1_rx_fte_drop_cnt {
      type oc-yang:counter64;
      description
        "RX FTE packets drop counter.";
    }
    leaf counter_slice12_ifg_ifgbe_ra_rx_fte_cgm_drop_counter2_rx_fte_drop_cnt {
      type oc-yang:counter64;
      description
        "RX FTE packets drop counter.";
    }
    leaf counter_slice12_ifg_ifgbe_ra_rx_fte_cgm_drop_counter3_rx_fte_drop_cnt {
      type oc-yang:counter64;
      description
        "RX FTE packets drop counter.";
    }
    leaf counter_slice12_ifg_ifgbe_ra_rx_fte_cgm_drop_counter4_rx_fte_drop_cnt {
      type oc-yang:counter64;
      description
        "RX FTE packets drop counter.";
    }
    leaf counter_slice12_ifg_ifgbe_ra_rx_fte_cgm_drop_counter5_rx_fte_drop_cnt {
      type oc-yang:counter64;
      description
        "RX FTE packets drop counter.";
    }
    leaf counter_slice12_ifg_ifgbe_ra_rx_fte_cgm_drop_counter6_rx_fte_drop_cnt {
      type oc-yang:counter64;
      description
        "RX FTE packets drop counter.";
    }
    leaf counter_slice12_ifg_ifgbe_ra_rx_fte_cgm_drop_counter7_rx_fte_drop_cnt {
      type oc-yang:counter64;
      description
        "RX FTE packets drop counter.";
    }
    leaf counter_slice13_ifg_ifgbe_ra_rx_fte_cgm_drop_counter0_rx_fte_drop_cnt {
      type oc-yang:counter64;
      description
        "RX FTE packets drop counter.";
    }
    leaf counter_slice13_ifg_ifgbe_ra_rx_fte_cgm_drop_counter1_rx_fte_drop_cnt {
      type oc-yang:counter64;
      description
        "RX FTE packets drop counter.";
    }
    leaf counter_slice13_ifg_ifgbe_ra_rx_fte_cgm_drop_counter2_rx_fte_drop_cnt {
      type oc-yang:counter64;
      description
        "RX FTE packets drop counter.";
    }
    leaf counter_slice13_ifg_ifgbe_ra_rx_fte_cgm_drop_counter3_rx_fte_drop_cnt {
      type oc-yang:counter64;
      description
        "RX FTE packets drop counter.";
    }
    leaf counter_slice13_ifg_ifgbe_ra_rx_fte_cgm_drop_counter4_rx_fte_drop_cnt {
      type oc-yang:counter64;
      description
        "RX FTE packets drop counter.";
    }
    leaf counter_slice13_ifg_ifgbe_ra_rx_fte_cgm_drop_counter5_rx_fte_drop_cnt {
      type oc-yang:counter64;
      description
        "RX FTE packets drop counter.";
    }
    leaf counter_slice13_ifg_ifgbe_ra_rx_fte_cgm_drop_counter6_rx_fte_drop_cnt {
      type oc-yang:counter64;
      description
        "RX FTE packets drop counter.";
    }
    leaf counter_slice13_ifg_ifgbe_ra_rx_fte_cgm_drop_counter7_rx_fte_drop_cnt {
      type oc-yang:counter64;
      description
        "RX FTE packets drop counter.";
    }
    leaf counter_slice14_ifg_ifgbe_ra_rx_fte_cgm_drop_counter0_rx_fte_drop_cnt {
      type oc-yang:counter64;
      description
        "RX FTE packets drop counter.";
    }
    leaf counter_slice14_ifg_ifgbe_ra_rx_fte_cgm_drop_counter1_rx_fte_drop_cnt {
      type oc-yang:counter64;
      description
        "RX FTE packets drop counter.";
    }
    leaf counter_slice14_ifg_ifgbe_ra_rx_fte_cgm_drop_counter2_rx_fte_drop_cnt {
      type oc-yang:counter64;
      description
        "RX FTE packets drop counter.";
    }
    leaf counter_slice14_ifg_ifgbe_ra_rx_fte_cgm_drop_counter3_rx_fte_drop_cnt {
      type oc-yang:counter64;
      description
        "RX FTE packets drop counter.";
    }
    leaf counter_slice14_ifg_ifgbe_ra_rx_fte_cgm_drop_counter4_rx_fte_drop_cnt {
      type oc-yang:counter64;
      description
        "RX FTE packets drop counter.";
    }
    leaf counter_slice14_ifg_ifgbe_ra_rx_fte_cgm_drop_counter5_rx_fte_drop_cnt {
      type oc-yang:counter64;
      description
        "RX FTE packets drop counter.";
    }
    leaf counter_slice14_ifg_ifgbe_ra_rx_fte_cgm_drop_counter6_rx_fte_drop_cnt {
      type oc-yang:counter64;
      description
        "RX FTE packets drop counter.";
    }
    leaf counter_slice14_ifg_ifgbe_ra_rx_fte_cgm_drop_counter7_rx_fte_drop_cnt {
      type oc-yang:counter64;
      description
        "RX FTE packets drop counter.";
    }
    leaf counter_slice15_ifg_ifgbe_ra_rx_fte_cgm_drop_counter0_rx_fte_drop_cnt {
      type oc-yang:counter64;
      description
        "RX FTE packets drop counter.";
    }
    leaf counter_slice15_ifg_ifgbe_ra_rx_fte_cgm_drop_counter1_rx_fte_drop_cnt {
      type oc-yang:counter64;
      description
        "RX FTE packets drop counter.";
    }
    leaf counter_slice15_ifg_ifgbe_ra_rx_fte_cgm_drop_counter2_rx_fte_drop_cnt {
      type oc-yang:counter64;
      description
        "RX FTE packets drop counter.";
    }
    leaf counter_slice15_ifg_ifgbe_ra_rx_fte_cgm_drop_counter3_rx_fte_drop_cnt {
      type oc-yang:counter64;
      description
        "RX FTE packets drop counter.";
    }
    leaf counter_slice15_ifg_ifgbe_ra_rx_fte_cgm_drop_counter4_rx_fte_drop_cnt {
      type oc-yang:counter64;
      description
        "RX FTE packets drop counter.";
    }
    leaf counter_slice15_ifg_ifgbe_ra_rx_fte_cgm_drop_counter5_rx_fte_drop_cnt {
      type oc-yang:counter64;
      description
        "RX FTE packets drop counter.";
    }
    leaf counter_slice15_ifg_ifgbe_ra_rx_fte_cgm_drop_counter6_rx_fte_drop_cnt {
      type oc-yang:counter64;
      description
        "RX FTE packets drop counter.";
    }
    leaf counter_slice15_ifg_ifgbe_ra_rx_fte_cgm_drop_counter7_rx_fte_drop_cnt {
      type oc-yang:counter64;
      description
        "RX FTE packets drop counter.";
    }
    leaf counter_slice0_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice1_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice2_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice3_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice4_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice5_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice6_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice7_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice8_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice9_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice10_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice11_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice12_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice13_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice14_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice15_ifg_ifgbe_ra_rx_undersize_pkt_drop_counter0_rx_port0_undersize_pkt_drop_cnt {
      type oc-yang:counter64;
      description
        "RX undersize packet drop - counter for packets that were dropped because they were smaller than 64B can be with error indication from MAC.";
    }
    leaf counter_slice0_ifg_ifgbe_ra_rx_undersize_pkt_drop_counter1_rx_port1_undersize_pkt_drop_cnt {
      type oc-yang:counter64;
      description
        "nan";
    }
    leaf counter_slice1_ifg_ifgbe_ra_rx_undersize_pkt_drop_counter1_rx_port1_undersize_pkt_drop_cnt {
      type oc-yang:counter64;
      description
        "nan";
    }
    leaf counter_slice2_ifg_ifgbe_ra_rx_undersize_pkt_drop_counter1_rx_port1_undersize_pkt_drop_cnt {
      type oc-yang:counter64;
      description
        "nan";
    }
    leaf counter_slice3_ifg_ifgbe_ra_rx_undersize_pkt_drop_counter1_rx_port1_undersize_pkt_drop_cnt {
      type oc-yang:counter64;
      description
        "nan";
    }
    leaf counter_slice4_ifg_ifgbe_ra_rx_undersize_pkt_drop_counter1_rx_port1_undersize_pkt_drop_cnt {
      type oc-yang:counter64;
      description
        "nan";
    }
    leaf counter_slice5_ifg_ifgbe_ra_rx_undersize_pkt_drop_counter1_rx_port1_undersize_pkt_drop_cnt {
      type oc-yang:counter64;
      description
        "nan";
    }
    leaf counter_slice6_ifg_ifgbe_ra_rx_undersize_pkt_drop_counter1_rx_port1_undersize_pkt_drop_cnt {
      type oc-yang:counter64;
      description
        "nan";
    }
    leaf counter_slice7_ifg_ifgbe_ra_rx_undersize_pkt_drop_counter1_rx_port1_undersize_pkt_drop_cnt {
      type oc-yang:counter64;
      description
        "nan";
    }
    leaf counter_slice8_ifg_ifgbe_ra_rx_undersize_pkt_drop_counter1_rx_port1_undersize_pkt_drop_cnt {
      type oc-yang:counter64;
      description
        "nan";
    }
    leaf counter_slice9_ifg_ifgbe_ra_rx_undersize_pkt_drop_counter1_rx_port1_undersize_pkt_drop_cnt {
      type oc-yang:counter64;
      description
        "nan";
    }
    leaf counter_slice10_ifg_ifgbe_ra_rx_undersize_pkt_drop_counter1_rx_port1_undersize_pkt_drop_cnt {
      type oc-yang:counter64;
      description
        "nan";
    }
    leaf counter_slice11_ifg_ifgbe_ra_rx_undersize_pkt_drop_counter1_rx_port1_undersize_pkt_drop_cnt {
      type oc-yang:counter64;
      description
        "nan";
    }
    leaf counter_slice12_ifg_ifgbe_ra_rx_undersize_pkt_drop_counter1_rx_port1_undersize_pkt_drop_cnt {
      type oc-yang:counter64;
      description
        "nan";
    }
    leaf counter_slice13_ifg_ifgbe_ra_rx_undersize_pkt_drop_counter1_rx_port1_undersize_pkt_drop_cnt {
      type oc-yang:counter64;
      description
        "nan";
    }
    leaf counter_slice14_ifg_ifgbe_ra_rx_undersize_pkt_drop_counter1_rx_port1_undersize_pkt_drop_cnt {
      type oc-yang:counter64;
      description
        "nan";
    }
    leaf counter_slice15_ifg_ifgbe_ra_rx_undersize_pkt_drop_counter1_rx_port1_undersize_pkt_drop_cnt {
      type oc-yang:counter64;
      description
        "nan";
    }
    leaf counter_slice0_ifg_ifgbe_ra_rx_undersize_pkt_drop_counter10_rx_port10_undersize_pkt_drop_cnt {
      type oc-yang:counter64;
      description
        "nan";
    }
    leaf counter_slice1_ifg_ifgbe_ra_rx_undersize_pkt_drop_counter10_rx_port10_undersize_pkt_drop_cnt {
      type oc-yang:counter64;
      description
        "nan";
    }
    leaf counter_slice2_ifg_ifgbe_ra_rx_undersize_pkt_drop_counter10_rx_port10_undersize_pkt_drop_cnt {
      type oc-yang:counter64;
      description
        "nan";
    }
    leaf counter_slice3_ifg_ifgbe_ra_rx_undersize_pkt_drop_counter10_rx_port10_undersize_pkt_drop_cnt {
      type oc-yang:counter64;
      description
        "nan";
    }
    leaf counter_slice4_ifg_ifgbe_ra_rx_undersize_pkt_drop_counter10_rx_port10_undersize_pkt_drop_cnt {
      type oc-yang:counter64;
      description
        "nan";
    }
    leaf counter_slice5_ifg_ifgbe_ra_rx_undersize_pkt_drop_counter10_rx_port10_undersize_pkt_drop_cnt {
      type oc-yang:counter64;
      description
        "nan";
    }
    leaf counter_slice6_ifg_ifgbe_ra_rx_undersize_pkt_drop_counter10_rx_port10_undersize_pkt_drop_cnt {
      type oc-yang:counter64;
      description
        "nan";
    }
    leaf counter_slice7_ifg_ifgbe_ra_rx_undersize_pkt_drop_counter10_rx_port10_undersize_pkt_drop_cnt {
      type oc-yang:counter64;
      description
        "nan";
    }
    leaf counter_slice8_ifg_ifgbe_ra_rx_undersize_pkt_drop_counter10_rx_port10_undersize_pkt_drop_cnt {
      type oc-yang:counter64;
      description
        "nan";
    }
    leaf counter_slice9_ifg_ifgbe_ra_rx_undersize_pkt_drop_counter10_rx_port10_undersize_pkt_drop_cnt {
      type oc-yang:counter64;
      description
        "nan";
    }
    leaf counter_slice10_ifg_ifgbe_ra_rx_undersize_pkt_drop_counter10_rx_port10_undersize_pkt_drop_cnt {
      type oc-yang:counter64;
      description
        "nan";
    }
    leaf counter_slice11_ifg_ifgbe_ra_rx_undersize_pkt_drop_counter10_rx_port10_undersize_pkt_drop_cnt {
      type oc-yang:counter64;
      description
        "nan";
    }
    leaf counter_slice12_ifg_ifgbe_ra_rx_undersize_pkt_drop_counter10_rx_port10_undersize_pkt_drop_cnt {
      type oc-yang:counter64;
      description
        "nan";
    }
    leaf counter_slice13_ifg_ifgbe_ra_rx_undersize_pkt_drop_counter10_rx_port10_undersize_pkt_drop_cnt {
      type oc-yang:counter64;
      description
        "nan";
    }
    leaf counter_slice14_ifg_ifgbe_ra_rx_undersize_pkt_drop_counter10_rx_port10_undersize_pkt_drop_cnt {
      type oc-yang:counter64;
      description
        "nan";
    }
    leaf counter_slice15_ifg_ifgbe_ra_rx_undersize_pkt_drop_counter10_rx_port10_undersize_pkt_drop_cnt {
      type oc-yang:counter64;
      description
        "nan";
    }
    leaf counter_slice0_ifg_ifgbe_ra_rx_undersize_pkt_drop_counter11_rx_port11_undersize_pkt_drop_cnt {
      type oc-yang:counter64;
      description
        "nan";
    }
    leaf counter_slice1_ifg_ifgbe_ra_rx_undersize_pkt_drop_counter11_rx_port11_undersize_pkt_drop_cnt {
      type oc-yang:counter64;
      description
        "nan";
    }
    leaf counter_slice2_ifg_ifgbe_ra_rx_undersize_pkt_drop_counter11_rx_port11_undersize_pkt_drop_cnt {
      type oc-yang:counter64;
      description
        "nan";
    }
    leaf counter_slice3_ifg_ifgbe_ra_rx_undersize_pkt_drop_counter11_rx_port11_undersize_pkt_drop_cnt {
      type oc-yang:counter64;
      description
        "nan";
    }
    leaf counter_slice4_ifg_ifgbe_ra_rx_undersize_pkt_drop_counter11_rx_port11_undersize_pkt_drop_cnt {
      type oc-yang:counter64;
      description
        "nan";
    }
    leaf counter_slice5_ifg_ifgbe_ra_rx_undersize_pkt_drop_counter11_rx_port11_undersize_pkt_drop_cnt {
      type oc-yang:counter64;
      description
        "nan";
    }
    leaf counter_slice6_ifg_ifgbe_ra_rx_undersize_pkt_drop_counter11_rx_port11_undersize_pkt_drop_cnt {
      type oc-yang:counter64;
      description
        "nan";
    }
    leaf counter_slice7_ifg_ifgbe_ra_rx_undersize_pkt_drop_counter11_rx_port11_undersize_pkt_drop_cnt {
      type oc-yang:counter64;
      description
        "nan";
    }
    leaf counter_slice8_ifg_ifgbe_ra_rx_undersize_pkt_drop_counter11_rx_port11_undersize_pkt_drop_cnt {
      type oc-yang:counter64;
      description
        "nan";
    }
    leaf counter_slice9_ifg_ifgbe_ra_rx_undersize_pkt_drop_counter11_rx_port11_undersize_pkt_drop_cnt {
      type oc-yang:counter64;
      description
        "nan";
    }
    leaf counter_slice10_ifg_ifgbe_ra_rx_undersize_pkt_drop_counter11_rx_port11_undersize_pkt_drop_cnt {
      type oc-yang:counter64;
      description
        "nan";
    }
    leaf counter_slice11_ifg_ifgbe_ra_rx_undersize_pkt_drop_counter11_rx_port11_undersize_pkt_drop_cnt {
      type oc-yang:counter64;
      description
        "nan";
    }
    leaf counter_slice12_ifg_ifgbe_ra_rx_undersize_pkt_drop_counter11_rx_port11_undersize_pkt_drop_cnt {
      type oc-yang:counter64;
      description
        "nan";
    }
    leaf counter_slice13_ifg_ifgbe_ra_rx_undersize_pkt_drop_counter11_rx_port11_undersize_pkt_drop_cnt {
      type oc-yang:counter64;
      description
        "nan";
    }
    leaf counter_slice14_ifg_ifgbe_ra_rx_undersize_pkt_drop_counter11_rx_port11_undersize_pkt_drop_cnt {
      type oc-yang:counter64;
      description
        "nan";
    }
    leaf counter_slice15_ifg_ifgbe_ra_rx_undersize_pkt_drop_counter11_rx_port11_undersize_pkt_drop_cnt {
      type oc-yang:counter64;
      description
        "nan";
    }
    leaf counter_slice0_ifg_ifgbe_ra_rx_undersize_pkt_drop_counter12_rx_port12_undersize_pkt_drop_cnt {
      type oc-yang:counter64;
      description
        "nan";
    }
    leaf counter_slice1_ifg_ifgbe_ra_rx_undersize_pkt_drop_counter12_rx_port12_undersize_pkt_drop_cnt {
      type oc-yang:counter64;
      description
        "nan";
    }
    leaf counter_slice2_ifg_ifgbe_ra_rx_undersize_pkt_drop_counter12_rx_port12_undersize_pkt_drop_cnt {
      type oc-yang:counter64;
      description
        "nan";
    }
    leaf counter_slice3_ifg_ifgbe_ra_rx_undersize_pkt_drop_counter12_rx_port12_undersize_pkt_drop_cnt {
      type oc-yang:counter64;
      description
        "nan";
    }
    leaf counter_slice4_ifg_ifgbe_ra_rx_undersize_pkt_drop_counter12_rx_port12_undersize_pkt_drop_cnt {
      type oc-yang:counter64;
      description
        "nan";
    }
    leaf counter_slice5_ifg_ifgbe_ra_rx_undersize_pkt_drop_counter12_rx_port12_undersize_pkt_drop_cnt {
      type oc-yang:counter64;
      description
        "nan";
    }
    leaf counter_slice6_ifg_ifgbe_ra_rx_undersize_pkt_drop_counter12_rx_port12_undersize_pkt_drop_cnt {
      type oc-yang:counter64;
      description
        "nan";
    }
    leaf counter_slice7_ifg_ifgbe_ra_rx_undersize_pkt_drop_counter12_rx_port12_undersize_pkt_drop_cnt {
      type oc-yang:counter64;
      description
        "nan";
    }
    leaf counter_slice8_ifg_ifgbe_ra_rx_undersize_pkt_drop_counter12_rx_port12_undersize_pkt_drop_cnt {
      type oc-yang:counter64;
      description
        "nan";
    }
    leaf counter_slice9_ifg_ifgbe_ra_rx_undersize_pkt_drop_counter12_rx_port12_undersize_pkt_drop_cnt {
      type oc-yang:counter64;
      description
        "nan";
    }
    leaf counter_slice10_ifg_ifgbe_ra_rx_undersize_pkt_drop_counter12_rx_port12_undersize_pkt_drop_cnt {
      type oc-yang:counter64;
      description
        "nan";
    }
    leaf counter_slice11_ifg_ifgbe_ra_rx_undersize_pkt_drop_counter12_rx_port12_undersize_pkt_drop_cnt {
      type oc-yang:counter64;
      description
        "nan";
    }
    leaf counter_slice12_ifg_ifgbe_ra_rx_undersize_pkt_drop_counter12_rx_port12_undersize_pkt_drop_cnt {
      type oc-yang:counter64;
      description
        "nan";
    }
    leaf counter_slice13_ifg_ifgbe_ra_rx_undersize_pkt_drop_counter12_rx_port12_undersize_pkt_drop_cnt {
      type oc-yang:counter64;
      description
        "nan";
    }
    leaf counter_slice14_ifg_ifgbe_ra_rx_undersize_pkt_drop_counter12_rx_port12_undersize_pkt_drop_cnt {
      type oc-yang:counter64;
      description
        "nan";
    }
    leaf counter_slice15_ifg_ifgbe_ra_rx_undersize_pkt_drop_counter12_rx_port12_undersize_pkt_drop_cnt {
      type oc-yang:counter64;
      description
        "nan";
    }
    leaf counter_slice0_ifg_ifgbe_ra_rx_undersize_pkt_drop_counter13_rx_port13_undersize_pkt_drop_cnt {
      type oc-yang:counter64;
      description
        "nan";
    }
    leaf counter_slice1_ifg_ifgbe_ra_rx_undersize_pkt_drop_counter13_rx_port13_undersize_pkt_drop_cnt {
      type oc-yang:counter64;
      description
        "nan";
    }
    leaf counter_slice2_ifg_ifgbe_ra_rx_undersize_pkt_drop_counter13_rx_port13_undersize_pkt_drop_cnt {
      type oc-yang:counter64;
      description
        "nan";
    }
    leaf counter_slice3_ifg_ifgbe_ra_rx_undersize_pkt_drop_counter13_rx_port13_undersize_pkt_drop_cnt {
      type oc-yang:counter64;
      description
        "nan";
    }
    leaf counter_slice4_ifg_ifgbe_ra_rx_undersize_pkt_drop_counter13_rx_port13_undersize_pkt_drop_cnt {
      type oc-yang:counter64;
      description
        "nan";
    }
    leaf counter_slice5_ifg_ifgbe_ra_rx_undersize_pkt_drop_counter13_rx_port13_undersize_pkt_drop_cnt {
      type oc-yang:counter64;
      description
        "nan";
    }
    leaf counter_slice6_ifg_ifgbe_ra_rx_undersize_pkt_drop_counter13_rx_port13_undersize_pkt_drop_cnt {
      type oc-yang:counter64;
      description
        "nan";
    }
    leaf counter_slice7_ifg_ifgbe_ra_rx_undersize_pkt_drop_counter13_rx_port13_undersize_pkt_drop_cnt {
      type oc-yang:counter64;
      description
        "nan";
    }
    leaf counter_slice8_ifg_ifgbe_ra_rx_undersize_pkt_drop_counter13_rx_port13_undersize_pkt_drop_cnt {
      type oc-yang:counter64;
      description
        "nan";
    }
    leaf counter_slice9_ifg_ifgbe_ra_rx_undersize_pkt_drop_counter13_rx_port13_undersize_pkt_drop_cnt {
      type oc-yang:counter64;
      description
        "nan";
    }
    leaf counter_slice10_ifg_ifgbe_ra_rx_undersize_pkt_drop_counter13_rx_port13_undersize_pkt_drop_cnt {
      type oc-yang:counter64;
      description
        "nan";
    }
    leaf counter_slice11_ifg_ifgbe_ra_rx_undersize_pkt_drop_counter13_rx_port13_undersize_pkt_drop_cnt {
      type oc-yang:counter64;
      description
        "nan";
    }
    leaf counter_slice12_ifg_ifgbe_ra_rx_undersize_pkt_drop_counter13_rx_port13_undersize_pkt_drop_cnt {
      type oc-yang:counter64;
      description
        "nan";
    }
    leaf counter_slice13_ifg_ifgbe_ra_rx_undersize_pkt_drop_counter13_rx_port13_undersize_pkt_drop_cnt {
      type oc-yang:counter64;
      description
        "nan";
    }
    leaf counter_slice14_ifg_ifgbe_ra_rx_undersize_pkt_drop_counter13_rx_port13_undersize_pkt_drop_cnt {
      type oc-yang:counter64;
      description
        "nan";
    }
    leaf counter_slice15_ifg_ifgbe_ra_rx_undersize_pkt_drop_counter13_rx_port13_undersize_pkt_drop_cnt {
      type oc-yang:counter64;
      description
        "nan";
    }
    leaf counter_slice0_ifg_ifgbe_ra_rx_undersize_pkt_drop_counter14_rx_port14_undersize_pkt_drop_cnt {
      type oc-yang:counter64;
      description
        "nan";
    }
    leaf counter_slice1_ifg_ifgbe_ra_rx_undersize_pkt_drop_counter14_rx_port14_undersize_pkt_drop_cnt {
      type oc-yang:counter64;
      description
        "nan";
    }
    leaf counter_slice2_ifg_ifgbe_ra_rx_undersize_pkt_drop_counter14_rx_port14_undersize_pkt_drop_cnt {
      type oc-yang:counter64;
      description
        "nan";
    }
    leaf counter_slice3_ifg_ifgbe_ra_rx_undersize_pkt_drop_counter14_rx_port14_undersize_pkt_drop_cnt {
      type oc-yang:counter64;
      description
        "nan";
    }
    leaf counter_slice4_ifg_ifgbe_ra_rx_undersize_pkt_drop_counter14_rx_port14_undersize_pkt_drop_cnt {
      type oc-yang:counter64;
      description
        "nan";
    }
    leaf counter_slice5_ifg_ifgbe_ra_rx_undersize_pkt_drop_counter14_rx_port14_undersize_pkt_drop_cnt {
      type oc-yang:counter64;
      description
        "nan";
    }
    leaf counter_slice6_ifg_ifgbe_ra_rx_undersize_pkt_drop_counter14_rx_port14_undersize_pkt_drop_cnt {
      type oc-yang:counter64;
      description
        "nan";
    }
    leaf counter_slice7_ifg_ifgbe_ra_rx_undersize_pkt_drop_counter14_rx_port14_undersize_pkt_drop_cnt {
      type oc-yang:counter64;
      description
        "nan";
    }
    leaf counter_slice8_ifg_ifgbe_ra_rx_undersize_pkt_drop_counter14_rx_port14_undersize_pkt_drop_cnt {
      type oc-yang:counter64;
      description
        "nan";
    }
    leaf counter_slice9_ifg_ifgbe_ra_rx_undersize_pkt_drop_counter14_rx_port14_undersize_pkt_drop_cnt {
      type oc-yang:counter64;
      description
        "nan";
    }
    leaf counter_slice10_ifg_ifgbe_ra_rx_undersize_pkt_drop_counter14_rx_port14_undersize_pkt_drop_cnt {
      type oc-yang:counter64;
      description
        "nan";
    }
    leaf counter_slice11_ifg_ifgbe_ra_rx_undersize_pkt_drop_counter14_rx_port14_undersize_pkt_drop_cnt {
      type oc-yang:counter64;
      description
        "nan";
    }
    leaf counter_slice12_ifg_ifgbe_ra_rx_undersize_pkt_drop_counter14_rx_port14_undersize_pkt_drop_cnt {
      type oc-yang:counter64;
      description
        "nan";
    }
    leaf counter_slice13_ifg_ifgbe_ra_rx_undersize_pkt_drop_counter14_rx_port14_undersize_pkt_drop_cnt {
      type oc-yang:counter64;
      description
        "nan";
    }
    leaf counter_slice14_ifg_ifgbe_ra_rx_undersize_pkt_drop_counter14_rx_port14_undersize_pkt_drop_cnt {
      type oc-yang:counter64;
      description
        "nan";
    }
    leaf counter_slice15_ifg_ifgbe_ra_rx_undersize_pkt_drop_counter14_rx_port14_undersize_pkt_drop_cnt {
      type oc-yang:counter64;
      description
        "nan";
    }
    leaf counter_slice0_ifg_ifgbe_ra_rx_undersize_pkt_drop_counter15_rx_port15_undersize_pkt_drop_cnt {
      type oc-yang:counter64;
      description
        "nan";
    }
    leaf counter_slice1_ifg_ifgbe_ra_rx_undersize_pkt_drop_counter15_rx_port15_undersize_pkt_drop_cnt {
      type oc-yang:counter64;
      description
        "nan";
    }
    leaf counter_slice2_ifg_ifgbe_ra_rx_undersize_pkt_drop_counter15_rx_port15_undersize_pkt_drop_cnt {
      type oc-yang:counter64;
      description
        "nan";
    }
    leaf counter_slice3_ifg_ifgbe_ra_rx_undersize_pkt_drop_counter15_rx_port15_undersize_pkt_drop_cnt {
      type oc-yang:counter64;
      description
        "nan";
    }
    leaf counter_slice4_ifg_ifgbe_ra_rx_undersize_pkt_drop_counter15_rx_port15_undersize_pkt_drop_cnt {
      type oc-yang:counter64;
      description
        "nan";
    }
    leaf counter_slice5_ifg_ifgbe_ra_rx_undersize_pkt_drop_counter15_rx_port15_undersize_pkt_drop_cnt {
      type oc-yang:counter64;
      description
        "nan";
    }
    leaf counter_slice6_ifg_ifgbe_ra_rx_undersize_pkt_drop_counter15_rx_port15_undersize_pkt_drop_cnt {
      type oc-yang:counter64;
      description
        "nan";
    }
    leaf counter_slice7_ifg_ifgbe_ra_rx_undersize_pkt_drop_counter15_rx_port15_undersize_pkt_drop_cnt {
      type oc-yang:counter64;
      description
        "nan";
    }
    leaf counter_slice8_ifg_ifgbe_ra_rx_undersize_pkt_drop_counter15_rx_port15_undersize_pkt_drop_cnt {
      type oc-yang:counter64;
      description
        "nan";
    }
    leaf counter_slice9_ifg_ifgbe_ra_rx_undersize_pkt_drop_counter15_rx_port15_undersize_pkt_drop_cnt {
      type oc-yang:counter64;
      description
        "nan";
    }
    leaf counter_slice10_ifg_ifgbe_ra_rx_undersize_pkt_drop_counter15_rx_port15_undersize_pkt_drop_cnt {
      type oc-yang:counter64;
      description
        "nan";
    }
    leaf counter_slice11_ifg_ifgbe_ra_rx_undersize_pkt_drop_counter15_rx_port15_undersize_pkt_drop_cnt {
      type oc-yang:counter64;
      description
        "nan";
    }
    leaf counter_slice12_ifg_ifgbe_ra_rx_undersize_pkt_drop_counter15_rx_port15_undersize_pkt_drop_cnt {
      type oc-yang:counter64;
      description
        "nan";
    }
    leaf counter_slice13_ifg_ifgbe_ra_rx_undersize_pkt_drop_counter15_rx_port15_undersize_pkt_drop_cnt {
      type oc-yang:counter64;
      description
        "nan";
    }
    leaf counter_slice14_ifg_ifgbe_ra_rx_undersize_pkt_drop_counter15_rx_port15_undersize_pkt_drop_cnt {
      type oc-yang:counter64;
      description
        "nan";
    }
    leaf counter_slice15_ifg_ifgbe_ra_rx_undersize_pkt_drop_counter15_rx_port15_undersize_pkt_drop_cnt {
      type oc-yang:counter64;
      description
        "nan";
    }
    leaf counter_slice0_ifg_ifgbe_ra_rx_undersize_pkt_drop_counter16_rx_port16_undersize_pkt_drop_cnt {
      type oc-yang:counter64;
      description
        "nan";
    }
    leaf counter_slice1_ifg_ifgbe_ra_rx_undersize_pkt_drop_counter16_rx_port16_undersize_pkt_drop_cnt {
      type oc-yang:counter64;
      description
        "nan";
    }
    leaf counter_slice2_ifg_ifgbe_ra_rx_undersize_pkt_drop_counter16_rx_port16_undersize_pkt_drop_cnt {
      type oc-yang:counter64;
      description
        "nan";
    }
    leaf counter_slice3_ifg_ifgbe_ra_rx_undersize_pkt_drop_counter16_rx_port16_undersize_pkt_drop_cnt {
      type oc-yang:counter64;
      description
        "nan";
    }
    leaf counter_slice4_ifg_ifgbe_ra_rx_undersize_pkt_drop_counter16_rx_port16_undersize_pkt_drop_cnt {
      type oc-yang:counter64;
      description
        "nan";
    }
    leaf counter_slice5_ifg_ifgbe_ra_rx_undersize_pkt_drop_counter16_rx_port16_undersize_pkt_drop_cnt {
      type oc-yang:counter64;
      description
        "nan";
    }
    leaf counter_slice6_ifg_ifgbe_ra_rx_undersize_pkt_drop_counter16_rx_port16_undersize_pkt_drop_cnt {
      type oc-yang:counter64;
      description
        "nan";
    }
    leaf counter_slice7_ifg_ifgbe_ra_rx_undersize_pkt_drop_counter16_rx_port16_undersize_pkt_drop_cnt {
      type oc-yang:counter64;
      description
        "nan";
    }
    leaf counter_slice8_ifg_ifgbe_ra_rx_undersize_pkt_drop_counter16_rx_port16_undersize_pkt_drop_cnt {
      type oc-yang:counter64;
      description
        "nan";
    }
    leaf counter_slice9_ifg_ifgbe_ra_rx_undersize_pkt_drop_counter16_rx_port16_undersize_pkt_drop_cnt {
      type oc-yang:counter64;
      description
        "nan";
    }
    leaf counter_slice10_ifg_ifgbe_ra_rx_undersize_pkt_drop_counter16_rx_port16_undersize_pkt_drop_cnt {
      type oc-yang:counter64;
      description
        "nan";
    }
    leaf counter_slice11_ifg_ifgbe_ra_rx_undersize_pkt_drop_counter16_rx_port16_undersize_pkt_drop_cnt {
      type oc-yang:counter64;
      description
        "nan";
    }
    leaf counter_slice12_ifg_ifgbe_ra_rx_undersize_pkt_drop_counter16_rx_port16_undersize_pkt_drop_cnt {
      type oc-yang:counter64;
      description
        "nan";
    }
    leaf counter_slice13_ifg_ifgbe_ra_rx_undersize_pkt_drop_counter16_rx_port16_undersize_pkt_drop_cnt {
      type oc-yang:counter64;
      description
        "nan";
    }
    leaf counter_slice14_ifg_ifgbe_ra_rx_undersize_pkt_drop_counter16_rx_port16_undersize_pkt_drop_cnt {
      type oc-yang:counter64;
      description
        "nan";
    }
    leaf counter_slice15_ifg_ifgbe_ra_rx_undersize_pkt_drop_counter16_rx_port16_undersize_pkt_drop_cnt {
      type oc-yang:counter64;
      description
        "nan";
    }
    leaf counter_slice0_ifg_ifgbe_ra_rx_undersize_pkt_drop_counter17_rx_port17_undersize_pkt_drop_cnt {
      type oc-yang:counter64;
      description
        "nan";
    }
    leaf counter_slice1_ifg_ifgbe_ra_rx_undersize_pkt_drop_counter17_rx_port17_undersize_pkt_drop_cnt {
      type oc-yang:counter64;
      description
        "nan";
    }
    leaf counter_slice2_ifg_ifgbe_ra_rx_undersize_pkt_drop_counter17_rx_port17_undersize_pkt_drop_cnt {
      type oc-yang:counter64;
      description
        "nan";
    }
    leaf counter_slice3_ifg_ifgbe_ra_rx_undersize_pkt_drop_counter17_rx_port17_undersize_pkt_drop_cnt {
      type oc-yang:counter64;
      description
        "nan";
    }
    leaf counter_slice4_ifg_ifgbe_ra_rx_undersize_pkt_drop_counter17_rx_port17_undersize_pkt_drop_cnt {
      type oc-yang:counter64;
      description
        "nan";
    }
    leaf counter_slice5_ifg_ifgbe_ra_rx_undersize_pkt_drop_counter17_rx_port17_undersize_pkt_drop_cnt {
      type oc-yang:counter64;
      description
        "nan";
    }
    leaf counter_slice6_ifg_ifgbe_ra_rx_undersize_pkt_drop_counter17_rx_port17_undersize_pkt_drop_cnt {
      type oc-yang:counter64;
      description
        "nan";
    }
    leaf counter_slice7_ifg_ifgbe_ra_rx_undersize_pkt_drop_counter17_rx_port17_undersize_pkt_drop_cnt {
      type oc-yang:counter64;
      description
        "nan";
    }
    leaf counter_slice8_ifg_ifgbe_ra_rx_undersize_pkt_drop_counter17_rx_port17_undersize_pkt_drop_cnt {
      type oc-yang:counter64;
      description
        "nan";
    }
    leaf counter_slice9_ifg_ifgbe_ra_rx_undersize_pkt_drop_counter17_rx_port17_undersize_pkt_drop_cnt {
      type oc-yang:counter64;
      description
        "nan";
    }
    leaf counter_slice10_ifg_ifgbe_ra_rx_undersize_pkt_drop_counter17_rx_port17_undersize_pkt_drop_cnt {
      type oc-yang:counter64;
      description
        "nan";
    }
    leaf counter_slice11_ifg_ifgbe_ra_rx_undersize_pkt_drop_counter17_rx_port17_undersize_pkt_drop_cnt {
      type oc-yang:counter64;
      description
        "nan";
    }
    leaf counter_slice12_ifg_ifgbe_ra_rx_undersize_pkt_drop_counter17_rx_port17_undersize_pkt_drop_cnt {
      type oc-yang:counter64;
      description
        "nan";
    }
    leaf counter_slice13_ifg_ifgbe_ra_rx_undersize_pkt_drop_counter17_rx_port17_undersize_pkt_drop_cnt {
      type oc-yang:counter64;
      description
        "nan";
    }
    leaf counter_slice14_ifg_ifgbe_ra_rx_undersize_pkt_drop_counter17_rx_port17_undersize_pkt_drop_cnt {
      type oc-yang:counter64;
      description
        "nan";
    }
    leaf counter_slice15_ifg_ifgbe_ra_rx_undersize_pkt_drop_counter17_rx_port17_undersize_pkt_drop_cnt {
      type oc-yang:counter64;
      description
        "nan";
    }
    leaf counter_slice0_ifg_ifgbe_ra_rx_undersize_pkt_drop_counter18_rx_port18_undersize_pkt_drop_cnt {
      type oc-yang:counter64;
      description
        "nan";
    }
    leaf counter_slice1_ifg_ifgbe_ra_rx_undersize_pkt_drop_counter18_rx_port18_undersize_pkt_drop_cnt {
      type oc-yang:counter64;
      description
        "nan";
    }
    leaf counter_slice2_ifg_ifgbe_ra_rx_undersize_pkt_drop_counter18_rx_port18_undersize_pkt_drop_cnt {
      type oc-yang:counter64;
      description
        "nan";
    }
    leaf counter_slice3_ifg_ifgbe_ra_rx_undersize_pkt_drop_counter18_rx_port18_undersize_pkt_drop_cnt {
      type oc-yang:counter64;
      description
        "nan";
    }
    leaf counter_slice4_ifg_ifgbe_ra_rx_undersize_pkt_drop_counter18_rx_port18_undersize_pkt_drop_cnt {
      type oc-yang:counter64;
      description
        "nan";
    }
    leaf counter_slice5_ifg_ifgbe_ra_rx_undersize_pkt_drop_counter18_rx_port18_undersize_pkt_drop_cnt {
      type oc-yang:counter64;
      description
        "nan";
    }
    leaf counter_slice6_ifg_ifgbe_ra_rx_undersize_pkt_drop_counter18_rx_port18_undersize_pkt_drop_cnt {
      type oc-yang:counter64;
      description
        "nan";
    }
    leaf counter_slice7_ifg_ifgbe_ra_rx_undersize_pkt_drop_counter18_rx_port18_undersize_pkt_drop_cnt {
      type oc-yang:counter64;
      description
        "nan";
    }
    leaf counter_slice8_ifg_ifgbe_ra_rx_undersize_pkt_drop_counter18_rx_port18_undersize_pkt_drop_cnt {
      type oc-yang:counter64;
      description
        "nan";
    }
    leaf counter_slice9_ifg_ifgbe_ra_rx_undersize_pkt_drop_counter18_rx_port18_undersize_pkt_drop_cnt {
      type oc-yang:counter64;
      description
        "nan";
    }
    leaf counter_slice10_ifg_ifgbe_ra_rx_undersize_pkt_drop_counter18_rx_port18_undersize_pkt_drop_cnt {
      type oc-yang:counter64;
      description
        "nan";
    }
    leaf counter_slice11_ifg_ifgbe_ra_rx_undersize_pkt_drop_counter18_rx_port18_undersize_pkt_drop_cnt {
      type oc-yang:counter64;
      description
        "nan";
    }
    leaf counter_slice12_ifg_ifgbe_ra_rx_undersize_pkt_drop_counter18_rx_port18_undersize_pkt_drop_cnt {
      type oc-yang:counter64;
      description
        "nan";
    }
    leaf counter_slice13_ifg_ifgbe_ra_rx_undersize_pkt_drop_counter18_rx_port18_undersize_pkt_drop_cnt {
      type oc-yang:counter64;
      description
        "nan";
    }
    leaf counter_slice14_ifg_ifgbe_ra_rx_undersize_pkt_drop_counter18_rx_port18_undersize_pkt_drop_cnt {
      type oc-yang:counter64;
      description
        "nan";
    }
    leaf counter_slice15_ifg_ifgbe_ra_rx_undersize_pkt_drop_counter18_rx_port18_undersize_pkt_drop_cnt {
      type oc-yang:counter64;
      description
        "nan";
    }
    leaf counter_slice0_ifg_ifgbe_ra_rx_undersize_pkt_drop_counter19_rx_port19_undersize_pkt_drop_cnt {
      type oc-yang:counter64;
      description
        "nan";
    }
    leaf counter_slice1_ifg_ifgbe_ra_rx_undersize_pkt_drop_counter19_rx_port19_undersize_pkt_drop_cnt {
      type oc-yang:counter64;
      description
        "nan";
    }
    leaf counter_slice2_ifg_ifgbe_ra_rx_undersize_pkt_drop_counter19_rx_port19_undersize_pkt_drop_cnt {
      type oc-yang:counter64;
      description
        "nan";
    }
    leaf counter_slice3_ifg_ifgbe_ra_rx_undersize_pkt_drop_counter19_rx_port19_undersize_pkt_drop_cnt {
      type oc-yang:counter64;
      description
        "nan";
    }
    leaf counter_slice4_ifg_ifgbe_ra_rx_undersize_pkt_drop_counter19_rx_port19_undersize_pkt_drop_cnt {
      type oc-yang:counter64;
      description
        "nan";
    }
    leaf counter_slice5_ifg_ifgbe_ra_rx_undersize_pkt_drop_counter19_rx_port19_undersize_pkt_drop_cnt {
      type oc-yang:counter64;
      description
        "nan";
    }
    leaf counter_slice6_ifg_ifgbe_ra_rx_undersize_pkt_drop_counter19_rx_port19_undersize_pkt_drop_cnt {
      type oc-yang:counter64;
      description
        "nan";
    }
    leaf counter_slice7_ifg_ifgbe_ra_rx_undersize_pkt_drop_counter19_rx_port19_undersize_pkt_drop_cnt {
      type oc-yang:counter64;
      description
        "nan";
    }
    leaf counter_slice8_ifg_ifgbe_ra_rx_undersize_pkt_drop_counter19_rx_port19_undersize_pkt_drop_cnt {
      type oc-yang:counter64;
      description
        "nan";
    }
    leaf counter_slice9_ifg_ifgbe_ra_rx_undersize_pkt_drop_counter19_rx_port19_undersize_pkt_drop_cnt {
      type oc-yang:counter64;
      description
        "nan";
    }
    leaf counter_slice10_ifg_ifgbe_ra_rx_undersize_pkt_drop_counter19_rx_port19_undersize_pkt_drop_cnt {
      type oc-yang:counter64;
      description
        "nan";
    }
    leaf counter_slice11_ifg_ifgbe_ra_rx_undersize_pkt_drop_counter19_rx_port19_undersize_pkt_drop_cnt {
      type oc-yang:counter64;
      description
        "nan";
    }
    leaf counter_slice12_ifg_ifgbe_ra_rx_undersize_pkt_drop_counter19_rx_port19_undersize_pkt_drop_cnt {
      type oc-yang:counter64;
      description
        "nan";
    }
    leaf counter_slice13_ifg_ifgbe_ra_rx_undersize_pkt_drop_counter19_rx_port19_undersize_pkt_drop_cnt {
      type oc-yang:counter64;
      description
        "nan";
    }
    leaf counter_slice14_ifg_ifgbe_ra_rx_undersize_pkt_drop_counter19_rx_port19_undersize_pkt_drop_cnt {
      type oc-yang:counter64;
      description
        "nan";
    }
    leaf counter_slice15_ifg_ifgbe_ra_rx_undersize_pkt_drop_counter19_rx_port19_undersize_pkt_drop_cnt {
      type oc-yang:counter64;
      description
        "nan";
    }
    leaf counter_slice0_ifg_ifgbe_ra_rx_undersize_pkt_drop_counter2_rx_port2_undersize_pkt_drop_cnt {
      type oc-yang:counter64;
      description
        "nan";
    }
    leaf counter_slice1_ifg_ifgbe_ra_rx_undersize_pkt_drop_counter2_rx_port2_undersize_pkt_drop_cnt {
      type oc-yang:counter64;
      description
        "nan";
    }
    leaf counter_slice2_ifg_ifgbe_ra_rx_undersize_pkt_drop_counter2_rx_port2_undersize_pkt_drop_cnt {
      type oc-yang:counter64;
      description
        "nan";
    }
    leaf counter_slice3_ifg_ifgbe_ra_rx_undersize_pkt_drop_counter2_rx_port2_undersize_pkt_drop_cnt {
      type oc-yang:counter64;
      description
        "nan";
    }
    leaf counter_slice4_ifg_ifgbe_ra_rx_undersize_pkt_drop_counter2_rx_port2_undersize_pkt_drop_cnt {
      type oc-yang:counter64;
      description
        "nan";
    }
    leaf counter_slice5_ifg_ifgbe_ra_rx_undersize_pkt_drop_counter2_rx_port2_undersize_pkt_drop_cnt {
      type oc-yang:counter64;
      description
        "nan";
    }
    leaf counter_slice6_ifg_ifgbe_ra_rx_undersize_pkt_drop_counter2_rx_port2_undersize_pkt_drop_cnt {
      type oc-yang:counter64;
      description
        "nan";
    }
    leaf counter_slice7_ifg_ifgbe_ra_rx_undersize_pkt_drop_counter2_rx_port2_undersize_pkt_drop_cnt {
      type oc-yang:counter64;
      description
        "nan";
    }
    leaf counter_slice8_ifg_ifgbe_ra_rx_undersize_pkt_drop_counter2_rx_port2_undersize_pkt_drop_cnt {
      type oc-yang:counter64;
      description
        "nan";
    }
    leaf counter_slice9_ifg_ifgbe_ra_rx_undersize_pkt_drop_counter2_rx_port2_undersize_pkt_drop_cnt {
      type oc-yang:counter64;
      description
        "nan";
    }
    leaf counter_slice10_ifg_ifgbe_ra_rx_undersize_pkt_drop_counter2_rx_port2_undersize_pkt_drop_cnt {
      type oc-yang:counter64;
      description
        "nan";
    }
    leaf counter_slice11_ifg_ifgbe_ra_rx_undersize_pkt_drop_counter2_rx_port2_undersize_pkt_drop_cnt {
      type oc-yang:counter64;
      description
        "nan";
    }
    leaf counter_slice12_ifg_ifgbe_ra_rx_undersize_pkt_drop_counter2_rx_port2_undersize_pkt_drop_cnt {
      type oc-yang:counter64;
      description
        "nan";
    }
    leaf counter_slice13_ifg_ifgbe_ra_rx_undersize_pkt_drop_counter2_rx_port2_undersize_pkt_drop_cnt {
      type oc-yang:counter64;
      description
        "nan";
    }
    leaf counter_slice14_ifg_ifgbe_ra_rx_undersize_pkt_drop_counter2_rx_port2_undersize_pkt_drop_cnt {
      type oc-yang:counter64;
      description
        "nan";
    }
    leaf counter_slice15_ifg_ifgbe_ra_rx_undersize_pkt_drop_counter2_rx_port2_undersize_pkt_drop_cnt {
      type oc-yang:counter64;
      description
        "nan";
    }
    leaf counter_slice0_ifg_ifgbe_ra_rx_undersize_pkt_drop_counter20_rx_port20_undersize_pkt_drop_cnt {
      type oc-yang:counter64;
      description
        "nan";
    }
    leaf counter_slice1_ifg_ifgbe_ra_rx_undersize_pkt_drop_counter20_rx_port20_undersize_pkt_drop_cnt {
      type oc-yang:counter64;
      description
        "nan";
    }
    leaf counter_slice2_ifg_ifgbe_ra_rx_undersize_pkt_drop_counter20_rx_port20_undersize_pkt_drop_cnt {
      type oc-yang:counter64;
      description
        "nan";
    }
    leaf counter_slice3_ifg_ifgbe_ra_rx_undersize_pkt_drop_counter20_rx_port20_undersize_pkt_drop_cnt {
      type oc-yang:counter64;
      description
        "nan";
    }
    leaf counter_slice4_ifg_ifgbe_ra_rx_undersize_pkt_drop_counter20_rx_port20_undersize_pkt_drop_cnt {
      type oc-yang:counter64;
      description
        "nan";
    }
    leaf counter_slice5_ifg_ifgbe_ra_rx_undersize_pkt_drop_counter20_rx_port20_undersize_pkt_drop_cnt {
      type oc-yang:counter64;
      description
        "nan";
    }
    leaf counter_slice6_ifg_ifgbe_ra_rx_undersize_pkt_drop_counter20_rx_port20_undersize_pkt_drop_cnt {
      type oc-yang:counter64;
      description
        "nan";
    }
    leaf counter_slice7_ifg_ifgbe_ra_rx_undersize_pkt_drop_counter20_rx_port20_undersize_pkt_drop_cnt {
      type oc-yang:counter64;
      description
        "nan";
    }
    leaf counter_slice8_ifg_ifgbe_ra_rx_undersize_pkt_drop_counter20_rx_port20_undersize_pkt_drop_cnt {
      type oc-yang:counter64;
      description
        "nan";
    }
    leaf counter_slice9_ifg_ifgbe_ra_rx_undersize_pkt_drop_counter20_rx_port20_undersize_pkt_drop_cnt {
      type oc-yang:counter64;
      description
        "nan";
    }
    leaf counter_slice10_ifg_ifgbe_ra_rx_undersize_pkt_drop_counter20_rx_port20_undersize_pkt_drop_cnt {
      type oc-yang:counter64;
      description
        "nan";
    }
    leaf counter_slice11_ifg_ifgbe_ra_rx_undersize_pkt_drop_counter20_rx_port20_undersize_pkt_drop_cnt {
      type oc-yang:counter64;
      description
        "nan";
    }
    leaf counter_slice12_ifg_ifgbe_ra_rx_undersize_pkt_drop_counter20_rx_port20_undersize_pkt_drop_cnt {
      type oc-yang:counter64;
      description
        "nan";
    }
    leaf counter_slice13_ifg_ifgbe_ra_rx_undersize_pkt_drop_counter20_rx_port20_undersize_pkt_drop_cnt {
      type oc-yang:counter64;
      description
        "nan";
    }
    leaf counter_slice14_ifg_ifgbe_ra_rx_undersize_pkt_drop_counter20_rx_port20_undersize_pkt_drop_cnt {
      type oc-yang:counter64;
      description
        "nan";
    }
    leaf counter_slice15_ifg_ifgbe_ra_rx_undersize_pkt_drop_counter20_rx_port20_undersize_pkt_drop_cnt {
      type oc-yang:counter64;
      description
        "nan";
    }
    leaf counter_slice0_ifg_ifgbe_ra_rx_undersize_pkt_drop_counter21_rx_port21_undersize_pkt_drop_cnt {
      type oc-yang:counter64;
      description
        "nan";
    }
    leaf counter_slice1_ifg_ifgbe_ra_rx_undersize_pkt_drop_counter21_rx_port21_undersize_pkt_drop_cnt {
      type oc-yang:counter64;
      description
        "nan";
    }
    leaf counter_slice2_ifg_ifgbe_ra_rx_undersize_pkt_drop_counter21_rx_port21_undersize_pkt_drop_cnt {
      type oc-yang:counter64;
      description
        "nan";
    }
    leaf counter_slice3_ifg_ifgbe_ra_rx_undersize_pkt_drop_counter21_rx_port21_undersize_pkt_drop_cnt {
      type oc-yang:counter64;
      description
        "nan";
    }
    leaf counter_slice4_ifg_ifgbe_ra_rx_undersize_pkt_drop_counter21_rx_port21_undersize_pkt_drop_cnt {
      type oc-yang:counter64;
      description
        "nan";
    }
    leaf counter_slice5_ifg_ifgbe_ra_rx_undersize_pkt_drop_counter21_rx_port21_undersize_pkt_drop_cnt {
      type oc-yang:counter64;
      description
        "nan";
    }
    leaf counter_slice6_ifg_ifgbe_ra_rx_undersize_pkt_drop_counter21_rx_port21_undersize_pkt_drop_cnt {
      type oc-yang:counter64;
      description
        "nan";
    }
    leaf counter_slice7_ifg_ifgbe_ra_rx_undersize_pkt_drop_counter21_rx_port21_undersize_pkt_drop_cnt {
      type oc-yang:counter64;
      description
        "nan";
    }
    leaf counter_slice8_ifg_ifgbe_ra_rx_undersize_pkt_drop_counter21_rx_port21_undersize_pkt_drop_cnt {
      type oc-yang:counter64;
      description
        "nan";
    }
    leaf counter_slice9_ifg_ifgbe_ra_rx_undersize_pkt_drop_counter21_rx_port21_undersize_pkt_drop_cnt {
      type oc-yang:counter64;
      description
        "nan";
    }
    leaf counter_slice10_ifg_ifgbe_ra_rx_undersize_pkt_drop_counter21_rx_port21_undersize_pkt_drop_cnt {
      type oc-yang:counter64;
      description
        "nan";
    }
    leaf counter_slice11_ifg_ifgbe_ra_rx_undersize_pkt_drop_counter21_rx_port21_undersize_pkt_drop_cnt {
      type oc-yang:counter64;
      description
        "nan";
    }
    leaf counter_slice12_ifg_ifgbe_ra_rx_undersize_pkt_drop_counter21_rx_port21_undersize_pkt_drop_cnt {
      type oc-yang:counter64;
      description
        "nan";
    }
    leaf counter_slice13_ifg_ifgbe_ra_rx_undersize_pkt_drop_counter21_rx_port21_undersize_pkt_drop_cnt {
      type oc-yang:counter64;
      description
        "nan";
    }
    leaf counter_slice14_ifg_ifgbe_ra_rx_undersize_pkt_drop_counter21_rx_port21_undersize_pkt_drop_cnt {
      type oc-yang:counter64;
      description
        "nan";
    }
    leaf counter_slice15_ifg_ifgbe_ra_rx_undersize_pkt_drop_counter21_rx_port21_undersize_pkt_drop_cnt {
      type oc-yang:counter64;
      description
        "nan";
    }
    leaf counter_slice0_ifg_ifgbe_ra_rx_undersize_pkt_drop_counter22_rx_port22_undersize_pkt_drop_cnt {
      type oc-yang:counter64;
      description
        "nan";
    }
    leaf counter_slice1_ifg_ifgbe_ra_rx_undersize_pkt_drop_counter22_rx_port22_undersize_pkt_drop_cnt {
      type oc-yang:counter64;
      description
        "nan";
    }
    leaf counter_slice2_ifg_ifgbe_ra_rx_undersize_pkt_drop_counter22_rx_port22_undersize_pkt_drop_cnt {
      type oc-yang:counter64;
      description
        "nan";
    }
    leaf counter_slice3_ifg_ifgbe_ra_rx_undersize_pkt_drop_counter22_rx_port22_undersize_pkt_drop_cnt {
      type oc-yang:counter64;
      description
        "nan";
    }
    leaf counter_slice4_ifg_ifgbe_ra_rx_undersize_pkt_drop_counter22_rx_port22_undersize_pkt_drop_cnt {
      type oc-yang:counter64;
      description
        "nan";
    }
    leaf counter_slice5_ifg_ifgbe_ra_rx_undersize_pkt_drop_counter22_rx_port22_undersize_pkt_drop_cnt {
      type oc-yang:counter64;
      description
        "nan";
    }
    leaf counter_slice6_ifg_ifgbe_ra_rx_undersize_pkt_drop_counter22_rx_port22_undersize_pkt_drop_cnt {
      type oc-yang:counter64;
      description
        "nan";
    }
    leaf counter_slice7_ifg_ifgbe_ra_rx_undersize_pkt_drop_counter22_rx_port22_undersize_pkt_drop_cnt {
      type oc-yang:counter64;
      description
        "nan";
    }
    leaf counter_slice8_ifg_ifgbe_ra_rx_undersize_pkt_drop_counter22_rx_port22_undersize_pkt_drop_cnt {
      type oc-yang:counter64;
      description
        "nan";
    }
    leaf counter_slice9_ifg_ifgbe_ra_rx_undersize_pkt_drop_counter22_rx_port22_undersize_pkt_drop_cnt {
      type oc-yang:counter64;
      description
        "nan";
    }
    leaf counter_slice10_ifg_ifgbe_ra_rx_undersize_pkt_drop_counter22_rx_port22_undersize_pkt_drop_cnt {
      type oc-yang:counter64;
      description
        "nan";
    }
    leaf counter_slice11_ifg_ifgbe_ra_rx_undersize_pkt_drop_counter22_rx_port22_undersize_pkt_drop_cnt {
      type oc-yang:counter64;
      description
        "nan";
    }
    leaf counter_slice12_ifg_ifgbe_ra_rx_undersize_pkt_drop_counter22_rx_port22_undersize_pkt_drop_cnt {
      type oc-yang:counter64;
      description
        "nan";
    }
    leaf counter_slice13_ifg_ifgbe_ra_rx_undersize_pkt_drop_counter22_rx_port22_undersize_pkt_drop_cnt {
      type oc-yang:counter64;
      description
        "nan";
    }
    leaf counter_slice14_ifg_ifgbe_ra_rx_undersize_pkt_drop_counter22_rx_port22_undersize_pkt_drop_cnt {
      type oc-yang:counter64;
      description
        "nan";
    }
    leaf counter_slice15_ifg_ifgbe_ra_rx_undersize_pkt_drop_counter22_rx_port22_undersize_pkt_drop_cnt {
      type oc-yang:counter64;
      description
        "nan";
    }
    leaf counter_slice0_ifg_ifgbe_ra_rx_undersize_pkt_drop_counter23_rx_port23_undersize_pkt_drop_cnt {
      type oc-yang:counter64;
      description
        "nan";
    }
    leaf counter_slice1_ifg_ifgbe_ra_rx_undersize_pkt_drop_counter23_rx_port23_undersize_pkt_drop_cnt {
      type oc-yang:counter64;
      description
        "nan";
    }
    leaf counter_slice2_ifg_ifgbe_ra_rx_undersize_pkt_drop_counter23_rx_port23_undersize_pkt_drop_cnt {
      type oc-yang:counter64;
      description
        "nan";
    }
    leaf counter_slice3_ifg_ifgbe_ra_rx_undersize_pkt_drop_counter23_rx_port23_undersize_pkt_drop_cnt {
      type oc-yang:counter64;
      description
        "nan";
    }
    leaf counter_slice4_ifg_ifgbe_ra_rx_undersize_pkt_drop_counter23_rx_port23_undersize_pkt_drop_cnt {
      type oc-yang:counter64;
      description
        "nan";
    }
    leaf counter_slice5_ifg_ifgbe_ra_rx_undersize_pkt_drop_counter23_rx_port23_undersize_pkt_drop_cnt {
      type oc-yang:counter64;
      description
        "nan";
    }
    leaf counter_slice6_ifg_ifgbe_ra_rx_undersize_pkt_drop_counter23_rx_port23_undersize_pkt_drop_cnt {
      type oc-yang:counter64;
      description
        "nan";
    }
    leaf counter_slice7_ifg_ifgbe_ra_rx_undersize_pkt_drop_counter23_rx_port23_undersize_pkt_drop_cnt {
      type oc-yang:counter64;
      description
        "nan";
    }
    leaf counter_slice8_ifg_ifgbe_ra_rx_undersize_pkt_drop_counter23_rx_port23_undersize_pkt_drop_cnt {
      type oc-yang:counter64;
      description
        "nan";
    }
    leaf counter_slice9_ifg_ifgbe_ra_rx_undersize_pkt_drop_counter23_rx_port23_undersize_pkt_drop_cnt {
      type oc-yang:counter64;
      description
        "nan";
    }
    leaf counter_slice10_ifg_ifgbe_ra_rx_undersize_pkt_drop_counter23_rx_port23_undersize_pkt_drop_cnt {
      type oc-yang:counter64;
      description
        "nan";
    }
    leaf counter_slice11_ifg_ifgbe_ra_rx_undersize_pkt_drop_counter23_rx_port23_undersize_pkt_drop_cnt {
      type oc-yang:counter64;
      description
        "nan";
    }
    leaf counter_slice12_ifg_ifgbe_ra_rx_undersize_pkt_drop_counter23_rx_port23_undersize_pkt_drop_cnt {
      type oc-yang:counter64;
      description
        "nan";
    }
    leaf counter_slice13_ifg_ifgbe_ra_rx_undersize_pkt_drop_counter23_rx_port23_undersize_pkt_drop_cnt {
      type oc-yang:counter64;
      description
        "nan";
    }
    leaf counter_slice14_ifg_ifgbe_ra_rx_undersize_pkt_drop_counter23_rx_port23_undersize_pkt_drop_cnt {
      type oc-yang:counter64;
      description
        "nan";
    }
    leaf counter_slice15_ifg_ifgbe_ra_rx_undersize_pkt_drop_counter23_rx_port23_undersize_pkt_drop_cnt {
      type oc-yang:counter64;
      description
        "nan";
    }
    leaf counter_slice0_ifg_ifgbe_ra_rx_undersize_pkt_drop_counter24_rx_port24_undersize_pkt_drop_cnt {
      type oc-yang:counter64;
      description
        "nan";
    }
    leaf counter_slice1_ifg_ifgbe_ra_rx_undersize_pkt_drop_counter24_rx_port24_undersize_pkt_drop_cnt {
      type oc-yang:counter64;
      description
        "nan";
    }
    leaf counter_slice2_ifg_ifgbe_ra_rx_undersize_pkt_drop_counter24_rx_port24_undersize_pkt_drop_cnt {
      type oc-yang:counter64;
      description
        "nan";
    }
    leaf counter_slice3_ifg_ifgbe_ra_rx_undersize_pkt_drop_counter24_rx_port24_undersize_pkt_drop_cnt {
      type oc-yang:counter64;
      description
        "nan";
    }
    leaf counter_slice4_ifg_ifgbe_ra_rx_undersize_pkt_drop_counter24_rx_port24_undersize_pkt_drop_cnt {
      type oc-yang:counter64;
      description
        "nan";
    }
    leaf counter_slice5_ifg_ifgbe_ra_rx_undersize_pkt_drop_counter24_rx_port24_undersize_pkt_drop_cnt {
      type oc-yang:counter64;
      description
        "nan";
    }
    leaf counter_slice6_ifg_ifgbe_ra_rx_undersize_pkt_drop_counter24_rx_port24_undersize_pkt_drop_cnt {
      type oc-yang:counter64;
      description
        "nan";
    }
    leaf counter_slice7_ifg_ifgbe_ra_rx_undersize_pkt_drop_counter24_rx_port24_undersize_pkt_drop_cnt {
      type oc-yang:counter64;
      description
        "nan";
    }
    leaf counter_slice8_ifg_ifgbe_ra_rx_undersize_pkt_drop_counter24_rx_port24_undersize_pkt_drop_cnt {
      type oc-yang:counter64;
      description
        "nan";
    }
    leaf counter_slice9_ifg_ifgbe_ra_rx_undersize_pkt_drop_counter24_rx_port24_undersize_pkt_drop_cnt {
      type oc-yang:counter64;
      description
        "nan";
    }
    leaf counter_slice10_ifg_ifgbe_ra_rx_undersize_pkt_drop_counter24_rx_port24_undersize_pkt_drop_cnt {
      type oc-yang:counter64;
      description
        "nan";
    }
    leaf counter_slice11_ifg_ifgbe_ra_rx_undersize_pkt_drop_counter24_rx_port24_undersize_pkt_drop_cnt {
      type oc-yang:counter64;
      description
        "nan";
    }
    leaf counter_slice12_ifg_ifgbe_ra_rx_undersize_pkt_drop_counter24_rx_port24_undersize_pkt_drop_cnt {
      type oc-yang:counter64;
      description
        "nan";
    }
    leaf counter_slice13_ifg_ifgbe_ra_rx_undersize_pkt_drop_counter24_rx_port24_undersize_pkt_drop_cnt {
      type oc-yang:counter64;
      description
        "nan";
    }
    leaf counter_slice14_ifg_ifgbe_ra_rx_undersize_pkt_drop_counter24_rx_port24_undersize_pkt_drop_cnt {
      type oc-yang:counter64;
      description
        "nan";
    }
    leaf counter_slice15_ifg_ifgbe_ra_rx_undersize_pkt_drop_counter24_rx_port24_undersize_pkt_drop_cnt {
      type oc-yang:counter64;
      description
        "nan";
    }
    leaf counter_slice0_ifg_ifgbe_ra_rx_undersize_pkt_drop_counter25_rx_port25_undersize_pkt_drop_cnt {
      type oc-yang:counter64;
      description
        "nan";
    }
    leaf counter_slice1_ifg_ifgbe_ra_rx_undersize_pkt_drop_counter25_rx_port25_undersize_pkt_drop_cnt {
      type oc-yang:counter64;
      description
        "nan";
    }
    leaf counter_slice2_ifg_ifgbe_ra_rx_undersize_pkt_drop_counter25_rx_port25_undersize_pkt_drop_cnt {
      type oc-yang:counter64;
      description
        "nan";
    }
    leaf counter_slice3_ifg_ifgbe_ra_rx_undersize_pkt_drop_counter25_rx_port25_undersize_pkt_drop_cnt {
      type oc-yang:counter64;
      description
        "nan";
    }
    leaf counter_slice4_ifg_ifgbe_ra_rx_undersize_pkt_drop_counter25_rx_port25_undersize_pkt_drop_cnt {
      type oc-yang:counter64;
      description
        "nan";
    }
    leaf counter_slice5_ifg_ifgbe_ra_rx_undersize_pkt_drop_counter25_rx_port25_undersize_pkt_drop_cnt {
      type oc-yang:counter64;
      description
        "nan";
    }
    leaf counter_slice6_ifg_ifgbe_ra_rx_undersize_pkt_drop_counter25_rx_port25_undersize_pkt_drop_cnt {
      type oc-yang:counter64;
      description
        "nan";
    }
    leaf counter_slice7_ifg_ifgbe_ra_rx_undersize_pkt_drop_counter25_rx_port25_undersize_pkt_drop_cnt {
      type oc-yang:counter64;
      description
        "nan";
    }
    leaf counter_slice8_ifg_ifgbe_ra_rx_undersize_pkt_drop_counter25_rx_port25_undersize_pkt_drop_cnt {
      type oc-yang:counter64;
      description
        "nan";
    }
    leaf counter_slice9_ifg_ifgbe_ra_rx_undersize_pkt_drop_counter25_rx_port25_undersize_pkt_drop_cnt {
      type oc-yang:counter64;
      description
        "nan";
    }
    leaf counter_slice10_ifg_ifgbe_ra_rx_undersize_pkt_drop_counter25_rx_port25_undersize_pkt_drop_cnt {
      type oc-yang:counter64;
      description
        "nan";
    }
    leaf counter_slice11_ifg_ifgbe_ra_rx_undersize_pkt_drop_counter25_rx_port25_undersize_pkt_drop_cnt {
      type oc-yang:counter64;
      description
        "nan";
    }
    leaf counter_slice12_ifg_ifgbe_ra_rx_undersize_pkt_drop_counter25_rx_port25_undersize_pkt_drop_cnt {
      type oc-yang:counter64;
      description
        "nan";
    }
    leaf counter_slice13_ifg_ifgbe_ra_rx_undersize_pkt_drop_counter25_rx_port25_undersize_pkt_drop_cnt {
      type oc-yang:counter64;
      description
        "nan";
    }
    leaf counter_slice14_ifg_ifgbe_ra_rx_undersize_pkt_drop_counter25_rx_port25_undersize_pkt_drop_cnt {
      type oc-yang:counter64;
      description
        "nan";
    }
    leaf counter_slice15_ifg_ifgbe_ra_rx_undersize_pkt_drop_counter25_rx_port25_undersize_pkt_drop_cnt {
      type oc-yang:counter64;
      description
        "nan";
    }
    leaf counter_slice0_ifg_ifgbe_ra_rx_undersize_pkt_drop_counter26_rx_port26_undersize_pkt_drop_cnt {
      type oc-yang:counter64;
      description
        "nan";
    }
    leaf counter_slice1_ifg_ifgbe_ra_rx_undersize_pkt_drop_counter26_rx_port26_undersize_pkt_drop_cnt {
      type oc-yang:counter64;
      description
        "nan";
    }
    leaf counter_slice2_ifg_ifgbe_ra_rx_undersize_pkt_drop_counter26_rx_port26_undersize_pkt_drop_cnt {
      type oc-yang:counter64;
      description
        "nan";
    }
    leaf counter_slice3_ifg_ifgbe_ra_rx_undersize_pkt_drop_counter26_rx_port26_undersize_pkt_drop_cnt {
      type oc-yang:counter64;
      description
        "nan";
    }
    leaf counter_slice4_ifg_ifgbe_ra_rx_undersize_pkt_drop_counter26_rx_port26_undersize_pkt_drop_cnt {
      type oc-yang:counter64;
      description
        "nan";
    }
    leaf counter_slice5_ifg_ifgbe_ra_rx_undersize_pkt_drop_counter26_rx_port26_undersize_pkt_drop_cnt {
      type oc-yang:counter64;
      description
        "nan";
    }
    leaf counter_slice6_ifg_ifgbe_ra_rx_undersize_pkt_drop_counter26_rx_port26_undersize_pkt_drop_cnt {
      type oc-yang:counter64;
      description
        "nan";
    }
    leaf counter_slice7_ifg_ifgbe_ra_rx_undersize_pkt_drop_counter26_rx_port26_undersize_pkt_drop_cnt {
      type oc-yang:counter64;
      description
        "nan";
    }
    leaf counter_slice8_ifg_ifgbe_ra_rx_undersize_pkt_drop_counter26_rx_port26_undersize_pkt_drop_cnt {
      type oc-yang:counter64;
      description
        "nan";
    }
    leaf counter_slice9_ifg_ifgbe_ra_rx_undersize_pkt_drop_counter26_rx_port26_undersize_pkt_drop_cnt {
      type oc-yang:counter64;
      description
        "nan";
    }
    leaf counter_slice10_ifg_ifgbe_ra_rx_undersize_pkt_drop_counter26_rx_port26_undersize_pkt_drop_cnt {
      type oc-yang:counter64;
      description
        "nan";
    }
    leaf counter_slice11_ifg_ifgbe_ra_rx_undersize_pkt_drop_counter26_rx_port26_undersize_pkt_drop_cnt {
      type oc-yang:counter64;
      description
        "nan";
    }
    leaf counter_slice12_ifg_ifgbe_ra_rx_undersize_pkt_drop_counter26_rx_port26_undersize_pkt_drop_cnt {
      type oc-yang:counter64;
      description
        "nan";
    }
    leaf counter_slice13_ifg_ifgbe_ra_rx_undersize_pkt_drop_counter26_rx_port26_undersize_pkt_drop_cnt {
      type oc-yang:counter64;
      description
        "nan";
    }
    leaf counter_slice14_ifg_ifgbe_ra_rx_undersize_pkt_drop_counter26_rx_port26_undersize_pkt_drop_cnt {
      type oc-yang:counter64;
      description
        "nan";
    }
    leaf counter_slice15_ifg_ifgbe_ra_rx_undersize_pkt_drop_counter26_rx_port26_undersize_pkt_drop_cnt {
      type oc-yang:counter64;
      description
        "nan";
    }
    leaf counter_slice0_ifg_ifgbe_ra_rx_undersize_pkt_drop_counter27_rx_port27_undersize_pkt_drop_cnt {
      type oc-yang:counter64;
      description
        "nan";
    }
    leaf counter_slice1_ifg_ifgbe_ra_rx_undersize_pkt_drop_counter27_rx_port27_undersize_pkt_drop_cnt {
      type oc-yang:counter64;
      description
        "nan";
    }
    leaf counter_slice2_ifg_ifgbe_ra_rx_undersize_pkt_drop_counter27_rx_port27_undersize_pkt_drop_cnt {
      type oc-yang:counter64;
      description
        "nan";
    }
    leaf counter_slice3_ifg_ifgbe_ra_rx_undersize_pkt_drop_counter27_rx_port27_undersize_pkt_drop_cnt {
      type oc-yang:counter64;
      description
        "nan";
    }
    leaf counter_slice4_ifg_ifgbe_ra_rx_undersize_pkt_drop_counter27_rx_port27_undersize_pkt_drop_cnt {
      type oc-yang:counter64;
      description
        "nan";
    }
    leaf counter_slice5_ifg_ifgbe_ra_rx_undersize_pkt_drop_counter27_rx_port27_undersize_pkt_drop_cnt {
      type oc-yang:counter64;
      description
        "nan";
    }
    leaf counter_slice6_ifg_ifgbe_ra_rx_undersize_pkt_drop_counter27_rx_port27_undersize_pkt_drop_cnt {
      type oc-yang:counter64;
      description
        "nan";
    }
    leaf counter_slice7_ifg_ifgbe_ra_rx_undersize_pkt_drop_counter27_rx_port27_undersize_pkt_drop_cnt {
      type oc-yang:counter64;
      description
        "nan";
    }
    leaf counter_slice8_ifg_ifgbe_ra_rx_undersize_pkt_drop_counter27_rx_port27_undersize_pkt_drop_cnt {
      type oc-yang:counter64;
      description
        "nan";
    }
    leaf counter_slice9_ifg_ifgbe_ra_rx_undersize_pkt_drop_counter27_rx_port27_undersize_pkt_drop_cnt {
      type oc-yang:counter64;
      description
        "nan";
    }
    leaf counter_slice10_ifg_ifgbe_ra_rx_undersize_pkt_drop_counter27_rx_port27_undersize_pkt_drop_cnt {
      type oc-yang:counter64;
      description
        "nan";
    }
    leaf counter_slice11_ifg_ifgbe_ra_rx_undersize_pkt_drop_counter27_rx_port27_undersize_pkt_drop_cnt {
      type oc-yang:counter64;
      description
        "nan";
    }
    leaf counter_slice12_ifg_ifgbe_ra_rx_undersize_pkt_drop_counter27_rx_port27_undersize_pkt_drop_cnt {
      type oc-yang:counter64;
      description
        "nan";
    }
    leaf counter_slice13_ifg_ifgbe_ra_rx_undersize_pkt_drop_counter27_rx_port27_undersize_pkt_drop_cnt {
      type oc-yang:counter64;
      description
        "nan";
    }
    leaf counter_slice14_ifg_ifgbe_ra_rx_undersize_pkt_drop_counter27_rx_port27_undersize_pkt_drop_cnt {
      type oc-yang:counter64;
      description
        "nan";
    }
    leaf counter_slice15_ifg_ifgbe_ra_rx_undersize_pkt_drop_counter27_rx_port27_undersize_pkt_drop_cnt {
      type oc-yang:counter64;
      description
        "nan";
    }
    leaf counter_slice0_ifg_ifgbe_ra_rx_undersize_pkt_drop_counter28_rx_port28_undersize_pkt_drop_cnt {
      type oc-yang:counter64;
      description
        "nan";
    }
    leaf counter_slice1_ifg_ifgbe_ra_rx_undersize_pkt_drop_counter28_rx_port28_undersize_pkt_drop_cnt {
      type oc-yang:counter64;
      description
        "nan";
    }
    leaf counter_slice2_ifg_ifgbe_ra_rx_undersize_pkt_drop_counter28_rx_port28_undersize_pkt_drop_cnt {
      type oc-yang:counter64;
      description
        "nan";
    }
    leaf counter_slice3_ifg_ifgbe_ra_rx_undersize_pkt_drop_counter28_rx_port28_undersize_pkt_drop_cnt {
      type oc-yang:counter64;
      description
        "nan";
    }
    leaf counter_slice4_ifg_ifgbe_ra_rx_undersize_pkt_drop_counter28_rx_port28_undersize_pkt_drop_cnt {
      type oc-yang:counter64;
      description
        "nan";
    }
    leaf counter_slice5_ifg_ifgbe_ra_rx_undersize_pkt_drop_counter28_rx_port28_undersize_pkt_drop_cnt {
      type oc-yang:counter64;
      description
        "nan";
    }
    leaf counter_slice6_ifg_ifgbe_ra_rx_undersize_pkt_drop_counter28_rx_port28_undersize_pkt_drop_cnt {
      type oc-yang:counter64;
      description
        "nan";
    }
    leaf counter_slice7_ifg_ifgbe_ra_rx_undersize_pkt_drop_counter28_rx_port28_undersize_pkt_drop_cnt {
      type oc-yang:counter64;
      description
        "nan";
    }
    leaf counter_slice8_ifg_ifgbe_ra_rx_undersize_pkt_drop_counter28_rx_port28_undersize_pkt_drop_cnt {
      type oc-yang:counter64;
      description
        "nan";
    }
    leaf counter_slice9_ifg_ifgbe_ra_rx_undersize_pkt_drop_counter28_rx_port28_undersize_pkt_drop_cnt {
      type oc-yang:counter64;
      description
        "nan";
    }
    leaf counter_slice10_ifg_ifgbe_ra_rx_undersize_pkt_drop_counter28_rx_port28_undersize_pkt_drop_cnt {
      type oc-yang:counter64;
      description
        "nan";
    }
    leaf counter_slice11_ifg_ifgbe_ra_rx_undersize_pkt_drop_counter28_rx_port28_undersize_pkt_drop_cnt {
      type oc-yang:counter64;
      description
        "nan";
    }
    leaf counter_slice12_ifg_ifgbe_ra_rx_undersize_pkt_drop_counter28_rx_port28_undersize_pkt_drop_cnt {
      type oc-yang:counter64;
      description
        "nan";
    }
    leaf counter_slice13_ifg_ifgbe_ra_rx_undersize_pkt_drop_counter28_rx_port28_undersize_pkt_drop_cnt {
      type oc-yang:counter64;
      description
        "nan";
    }
    leaf counter_slice14_ifg_ifgbe_ra_rx_undersize_pkt_drop_counter28_rx_port28_undersize_pkt_drop_cnt {
      type oc-yang:counter64;
      description
        "nan";
    }
    leaf counter_slice15_ifg_ifgbe_ra_rx_undersize_pkt_drop_counter28_rx_port28_undersize_pkt_drop_cnt {
      type oc-yang:counter64;
      description
        "nan";
    }
    leaf counter_slice0_ifg_ifgbe_ra_rx_undersize_pkt_drop_counter29_rx_port29_undersize_pkt_drop_cnt {
      type oc-yang:counter64;
      description
        "nan";
    }
    leaf counter_slice1_ifg_ifgbe_ra_rx_undersize_pkt_drop_counter29_rx_port29_undersize_pkt_drop_cnt {
      type oc-yang:counter64;
      description
        "nan";
    }
    leaf counter_slice2_ifg_ifgbe_ra_rx_undersize_pkt_drop_counter29_rx_port29_undersize_pkt_drop_cnt {
      type oc-yang:counter64;
      description
        "nan";
    }
    leaf counter_slice3_ifg_ifgbe_ra_rx_undersize_pkt_drop_counter29_rx_port29_undersize_pkt_drop_cnt {
      type oc-yang:counter64;
      description
        "nan";
    }
    leaf counter_slice4_ifg_ifgbe_ra_rx_undersize_pkt_drop_counter29_rx_port29_undersize_pkt_drop_cnt {
      type oc-yang:counter64;
      description
        "nan";
    }
    leaf counter_slice5_ifg_ifgbe_ra_rx_undersize_pkt_drop_counter29_rx_port29_undersize_pkt_drop_cnt {
      type oc-yang:counter64;
      description
        "nan";
    }
    leaf counter_slice6_ifg_ifgbe_ra_rx_undersize_pkt_drop_counter29_rx_port29_undersize_pkt_drop_cnt {
      type oc-yang:counter64;
      description
        "nan";
    }
    leaf counter_slice7_ifg_ifgbe_ra_rx_undersize_pkt_drop_counter29_rx_port29_undersize_pkt_drop_cnt {
      type oc-yang:counter64;
      description
        "nan";
    }
    leaf counter_slice8_ifg_ifgbe_ra_rx_undersize_pkt_drop_counter29_rx_port29_undersize_pkt_drop_cnt {
      type oc-yang:counter64;
      description
        "nan";
    }
    leaf counter_slice9_ifg_ifgbe_ra_rx_undersize_pkt_drop_counter29_rx_port29_undersize_pkt_drop_cnt {
      type oc-yang:counter64;
      description
        "nan";
    }
    leaf counter_slice10_ifg_ifgbe_ra_rx_undersize_pkt_drop_counter29_rx_port29_undersize_pkt_drop_cnt {
      type oc-yang:counter64;
      description
        "nan";
    }
    leaf counter_slice11_ifg_ifgbe_ra_rx_undersize_pkt_drop_counter29_rx_port29_undersize_pkt_drop_cnt {
      type oc-yang:counter64;
      description
        "nan";
    }
    leaf counter_slice12_ifg_ifgbe_ra_rx_undersize_pkt_drop_counter29_rx_port29_undersize_pkt_drop_cnt {
      type oc-yang:counter64;
      description
        "nan";
    }
    leaf counter_slice13_ifg_ifgbe_ra_rx_undersize_pkt_drop_counter29_rx_port29_undersize_pkt_drop_cnt {
      type oc-yang:counter64;
      description
        "nan";
    }
    leaf counter_slice14_ifg_ifgbe_ra_rx_undersize_pkt_drop_counter29_rx_port29_undersize_pkt_drop_cnt {
      type oc-yang:counter64;
      description
        "nan";
    }
    leaf counter_slice15_ifg_ifgbe_ra_rx_undersize_pkt_drop_counter29_rx_port29_undersize_pkt_drop_cnt {
      type oc-yang:counter64;
      description
        "nan";
    }
    leaf counter_slice0_ifg_ifgbe_ra_rx_undersize_pkt_drop_counter3_rx_port3_undersize_pkt_drop_cnt {
      type oc-yang:counter64;
      description
        "nan";
    }
    leaf counter_slice1_ifg_ifgbe_ra_rx_undersize_pkt_drop_counter3_rx_port3_undersize_pkt_drop_cnt {
      type oc-yang:counter64;
      description
        "nan";
    }
    leaf counter_slice2_ifg_ifgbe_ra_rx_undersize_pkt_drop_counter3_rx_port3_undersize_pkt_drop_cnt {
      type oc-yang:counter64;
      description
        "nan";
    }
    leaf counter_slice3_ifg_ifgbe_ra_rx_undersize_pkt_drop_counter3_rx_port3_undersize_pkt_drop_cnt {
      type oc-yang:counter64;
      description
        "nan";
    }
    leaf counter_slice4_ifg_ifgbe_ra_rx_undersize_pkt_drop_counter3_rx_port3_undersize_pkt_drop_cnt {
      type oc-yang:counter64;
      description
        "nan";
    }
    leaf counter_slice5_ifg_ifgbe_ra_rx_undersize_pkt_drop_counter3_rx_port3_undersize_pkt_drop_cnt {
      type oc-yang:counter64;
      description
        "nan";
    }
    leaf counter_slice6_ifg_ifgbe_ra_rx_undersize_pkt_drop_counter3_rx_port3_undersize_pkt_drop_cnt {
      type oc-yang:counter64;
      description
        "nan";
    }
    leaf counter_slice7_ifg_ifgbe_ra_rx_undersize_pkt_drop_counter3_rx_port3_undersize_pkt_drop_cnt {
      type oc-yang:counter64;
      description
        "nan";
    }
    leaf counter_slice8_ifg_ifgbe_ra_rx_undersize_pkt_drop_counter3_rx_port3_undersize_pkt_drop_cnt {
      type oc-yang:counter64;
      description
        "nan";
    }
    leaf counter_slice9_ifg_ifgbe_ra_rx_undersize_pkt_drop_counter3_rx_port3_undersize_pkt_drop_cnt {
      type oc-yang:counter64;
      description
        "nan";
    }
    leaf counter_slice10_ifg_ifgbe_ra_rx_undersize_pkt_drop_counter3_rx_port3_undersize_pkt_drop_cnt {
      type oc-yang:counter64;
      description
        "nan";
    }
    leaf counter_slice11_ifg_ifgbe_ra_rx_undersize_pkt_drop_counter3_rx_port3_undersize_pkt_drop_cnt {
      type oc-yang:counter64;
      description
        "nan";
    }
    leaf counter_slice12_ifg_ifgbe_ra_rx_undersize_pkt_drop_counter3_rx_port3_undersize_pkt_drop_cnt {
      type oc-yang:counter64;
      description
        "nan";
    }
    leaf counter_slice13_ifg_ifgbe_ra_rx_undersize_pkt_drop_counter3_rx_port3_undersize_pkt_drop_cnt {
      type oc-yang:counter64;
      description
        "nan";
    }
    leaf counter_slice14_ifg_ifgbe_ra_rx_undersize_pkt_drop_counter3_rx_port3_undersize_pkt_drop_cnt {
      type oc-yang:counter64;
      description
        "nan";
    }
    leaf counter_slice15_ifg_ifgbe_ra_rx_undersize_pkt_drop_counter3_rx_port3_undersize_pkt_drop_cnt {
      type oc-yang:counter64;
      description
        "nan";
    }
    leaf counter_slice0_ifg_ifgbe_ra_rx_undersize_pkt_drop_counter30_rx_port30_undersize_pkt_drop_cnt {
      type oc-yang:counter64;
      description
        "nan";
    }
    leaf counter_slice1_ifg_ifgbe_ra_rx_undersize_pkt_drop_counter30_rx_port30_undersize_pkt_drop_cnt {
      type oc-yang:counter64;
      description
        "nan";
    }
    leaf counter_slice2_ifg_ifgbe_ra_rx_undersize_pkt_drop_counter30_rx_port30_undersize_pkt_drop_cnt {
      type oc-yang:counter64;
      description
        "nan";
    }
    leaf counter_slice3_ifg_ifgbe_ra_rx_undersize_pkt_drop_counter30_rx_port30_undersize_pkt_drop_cnt {
      type oc-yang:counter64;
      description
        "nan";
    }
    leaf counter_slice4_ifg_ifgbe_ra_rx_undersize_pkt_drop_counter30_rx_port30_undersize_pkt_drop_cnt {
      type oc-yang:counter64;
      description
        "nan";
    }
    leaf counter_slice5_ifg_ifgbe_ra_rx_undersize_pkt_drop_counter30_rx_port30_undersize_pkt_drop_cnt {
      type oc-yang:counter64;
      description
        "nan";
    }
    leaf counter_slice6_ifg_ifgbe_ra_rx_undersize_pkt_drop_counter30_rx_port30_undersize_pkt_drop_cnt {
      type oc-yang:counter64;
      description
        "nan";
    }
    leaf counter_slice7_ifg_ifgbe_ra_rx_undersize_pkt_drop_counter30_rx_port30_undersize_pkt_drop_cnt {
      type oc-yang:counter64;
      description
        "nan";
    }
    leaf counter_slice8_ifg_ifgbe_ra_rx_undersize_pkt_drop_counter30_rx_port30_undersize_pkt_drop_cnt {
      type oc-yang:counter64;
      description
        "nan";
    }
    leaf counter_slice9_ifg_ifgbe_ra_rx_undersize_pkt_drop_counter30_rx_port30_undersize_pkt_drop_cnt {
      type oc-yang:counter64;
      description
        "nan";
    }
    leaf counter_slice10_ifg_ifgbe_ra_rx_undersize_pkt_drop_counter30_rx_port30_undersize_pkt_drop_cnt {
      type oc-yang:counter64;
      description
        "nan";
    }
    leaf counter_slice11_ifg_ifgbe_ra_rx_undersize_pkt_drop_counter30_rx_port30_undersize_pkt_drop_cnt {
      type oc-yang:counter64;
      description
        "nan";
    }
    leaf counter_slice12_ifg_ifgbe_ra_rx_undersize_pkt_drop_counter30_rx_port30_undersize_pkt_drop_cnt {
      type oc-yang:counter64;
      description
        "nan";
    }
    leaf counter_slice13_ifg_ifgbe_ra_rx_undersize_pkt_drop_counter30_rx_port30_undersize_pkt_drop_cnt {
      type oc-yang:counter64;
      description
        "nan";
    }
    leaf counter_slice14_ifg_ifgbe_ra_rx_undersize_pkt_drop_counter30_rx_port30_undersize_pkt_drop_cnt {
      type oc-yang:counter64;
      description
        "nan";
    }
    leaf counter_slice15_ifg_ifgbe_ra_rx_undersize_pkt_drop_counter30_rx_port30_undersize_pkt_drop_cnt {
      type oc-yang:counter64;
      description
        "nan";
    }
    leaf counter_slice0_ifg_ifgbe_ra_rx_undersize_pkt_drop_counter31_rx_port31_undersize_pkt_drop_cnt {
      type oc-yang:counter64;
      description
        "nan";
    }
    leaf counter_slice1_ifg_ifgbe_ra_rx_undersize_pkt_drop_counter31_rx_port31_undersize_pkt_drop_cnt {
      type oc-yang:counter64;
      description
        "nan";
    }
    leaf counter_slice2_ifg_ifgbe_ra_rx_undersize_pkt_drop_counter31_rx_port31_undersize_pkt_drop_cnt {
      type oc-yang:counter64;
      description
        "nan";
    }
    leaf counter_slice3_ifg_ifgbe_ra_rx_undersize_pkt_drop_counter31_rx_port31_undersize_pkt_drop_cnt {
      type oc-yang:counter64;
      description
        "nan";
    }
    leaf counter_slice4_ifg_ifgbe_ra_rx_undersize_pkt_drop_counter31_rx_port31_undersize_pkt_drop_cnt {
      type oc-yang:counter64;
      description
        "nan";
    }
    leaf counter_slice5_ifg_ifgbe_ra_rx_undersize_pkt_drop_counter31_rx_port31_undersize_pkt_drop_cnt {
      type oc-yang:counter64;
      description
        "nan";
    }
    leaf counter_slice6_ifg_ifgbe_ra_rx_undersize_pkt_drop_counter31_rx_port31_undersize_pkt_drop_cnt {
      type oc-yang:counter64;
      description
        "nan";
    }
    leaf counter_slice7_ifg_ifgbe_ra_rx_undersize_pkt_drop_counter31_rx_port31_undersize_pkt_drop_cnt {
      type oc-yang:counter64;
      description
        "nan";
    }
    leaf counter_slice8_ifg_ifgbe_ra_rx_undersize_pkt_drop_counter31_rx_port31_undersize_pkt_drop_cnt {
      type oc-yang:counter64;
      description
        "nan";
    }
    leaf counter_slice9_ifg_ifgbe_ra_rx_undersize_pkt_drop_counter31_rx_port31_undersize_pkt_drop_cnt {
      type oc-yang:counter64;
      description
        "nan";
    }
    leaf counter_slice10_ifg_ifgbe_ra_rx_undersize_pkt_drop_counter31_rx_port31_undersize_pkt_drop_cnt {
      type oc-yang:counter64;
      description
        "nan";
    }
    leaf counter_slice11_ifg_ifgbe_ra_rx_undersize_pkt_drop_counter31_rx_port31_undersize_pkt_drop_cnt {
      type oc-yang:counter64;
      description
        "nan";
    }
    leaf counter_slice12_ifg_ifgbe_ra_rx_undersize_pkt_drop_counter31_rx_port31_undersize_pkt_drop_cnt {
      type oc-yang:counter64;
      description
        "nan";
    }
    leaf counter_slice13_ifg_ifgbe_ra_rx_undersize_pkt_drop_counter31_rx_port31_undersize_pkt_drop_cnt {
      type oc-yang:counter64;
      description
        "nan";
    }
    leaf counter_slice14_ifg_ifgbe_ra_rx_undersize_pkt_drop_counter31_rx_port31_undersize_pkt_drop_cnt {
      type oc-yang:counter64;
      description
        "nan";
    }
    leaf counter_slice15_ifg_ifgbe_ra_rx_undersize_pkt_drop_counter31_rx_port31_undersize_pkt_drop_cnt {
      type oc-yang:counter64;
      description
        "nan";
    }
    leaf counter_slice0_ifg_ifgbe_ra_rx_undersize_pkt_drop_counter4_rx_port4_undersize_pkt_drop_cnt {
      type oc-yang:counter64;
      description
        "nan";
    }
    leaf counter_slice1_ifg_ifgbe_ra_rx_undersize_pkt_drop_counter4_rx_port4_undersize_pkt_drop_cnt {
      type oc-yang:counter64;
      description
        "nan";
    }
    leaf counter_slice2_ifg_ifgbe_ra_rx_undersize_pkt_drop_counter4_rx_port4_undersize_pkt_drop_cnt {
      type oc-yang:counter64;
      description
        "nan";
    }
    leaf counter_slice3_ifg_ifgbe_ra_rx_undersize_pkt_drop_counter4_rx_port4_undersize_pkt_drop_cnt {
      type oc-yang:counter64;
      description
        "nan";
    }
    leaf counter_slice4_ifg_ifgbe_ra_rx_undersize_pkt_drop_counter4_rx_port4_undersize_pkt_drop_cnt {
      type oc-yang:counter64;
      description
        "nan";
    }
    leaf counter_slice5_ifg_ifgbe_ra_rx_undersize_pkt_drop_counter4_rx_port4_undersize_pkt_drop_cnt {
      type oc-yang:counter64;
      description
        "nan";
    }
    leaf counter_slice6_ifg_ifgbe_ra_rx_undersize_pkt_drop_counter4_rx_port4_undersize_pkt_drop_cnt {
      type oc-yang:counter64;
      description
        "nan";
    }
    leaf counter_slice7_ifg_ifgbe_ra_rx_undersize_pkt_drop_counter4_rx_port4_undersize_pkt_drop_cnt {
      type oc-yang:counter64;
      description
        "nan";
    }
    leaf counter_slice8_ifg_ifgbe_ra_rx_undersize_pkt_drop_counter4_rx_port4_undersize_pkt_drop_cnt {
      type oc-yang:counter64;
      description
        "nan";
    }
    leaf counter_slice9_ifg_ifgbe_ra_rx_undersize_pkt_drop_counter4_rx_port4_undersize_pkt_drop_cnt {
      type oc-yang:counter64;
      description
        "nan";
    }
    leaf counter_slice10_ifg_ifgbe_ra_rx_undersize_pkt_drop_counter4_rx_port4_undersize_pkt_drop_cnt {
      type oc-yang:counter64;
      description
        "nan";
    }
    leaf counter_slice11_ifg_ifgbe_ra_rx_undersize_pkt_drop_counter4_rx_port4_undersize_pkt_drop_cnt {
      type oc-yang:counter64;
      description
        "nan";
    }
    leaf counter_slice12_ifg_ifgbe_ra_rx_undersize_pkt_drop_counter4_rx_port4_undersize_pkt_drop_cnt {
      type oc-yang:counter64;
      description
        "nan";
    }
    leaf counter_slice13_ifg_ifgbe_ra_rx_undersize_pkt_drop_counter4_rx_port4_undersize_pkt_drop_cnt {
      type oc-yang:counter64;
      description
        "nan";
    }
    leaf counter_slice14_ifg_ifgbe_ra_rx_undersize_pkt_drop_counter4_rx_port4_undersize_pkt_drop_cnt {
      type oc-yang:counter64;
      description
        "nan";
    }
    leaf counter_slice15_ifg_ifgbe_ra_rx_undersize_pkt_drop_counter4_rx_port4_undersize_pkt_drop_cnt {
      type oc-yang:counter64;
      description
        "nan";
    }
    leaf counter_slice0_ifg_ifgbe_ra_rx_undersize_pkt_drop_counter5_rx_port5_undersize_pkt_drop_cnt {
      type oc-yang:counter64;
      description
        "nan";
    }
    leaf counter_slice1_ifg_ifgbe_ra_rx_undersize_pkt_drop_counter5_rx_port5_undersize_pkt_drop_cnt {
      type oc-yang:counter64;
      description
        "nan";
    }
    leaf counter_slice2_ifg_ifgbe_ra_rx_undersize_pkt_drop_counter5_rx_port5_undersize_pkt_drop_cnt {
      type oc-yang:counter64;
      description
        "nan";
    }
    leaf counter_slice3_ifg_ifgbe_ra_rx_undersize_pkt_drop_counter5_rx_port5_undersize_pkt_drop_cnt {
      type oc-yang:counter64;
      description
        "nan";
    }
    leaf counter_slice4_ifg_ifgbe_ra_rx_undersize_pkt_drop_counter5_rx_port5_undersize_pkt_drop_cnt {
      type oc-yang:counter64;
      description
        "nan";
    }
    leaf counter_slice5_ifg_ifgbe_ra_rx_undersize_pkt_drop_counter5_rx_port5_undersize_pkt_drop_cnt {
      type oc-yang:counter64;
      description
        "nan";
    }
    leaf counter_slice6_ifg_ifgbe_ra_rx_undersize_pkt_drop_counter5_rx_port5_undersize_pkt_drop_cnt {
      type oc-yang:counter64;
      description
        "nan";
    }
    leaf counter_slice7_ifg_ifgbe_ra_rx_undersize_pkt_drop_counter5_rx_port5_undersize_pkt_drop_cnt {
      type oc-yang:counter64;
      description
        "nan";
    }
    leaf counter_slice8_ifg_ifgbe_ra_rx_undersize_pkt_drop_counter5_rx_port5_undersize_pkt_drop_cnt {
      type oc-yang:counter64;
      description
        "nan";
    }
    leaf counter_slice9_ifg_ifgbe_ra_rx_undersize_pkt_drop_counter5_rx_port5_undersize_pkt_drop_cnt {
      type oc-yang:counter64;
      description
        "nan";
    }
    leaf counter_slice10_ifg_ifgbe_ra_rx_undersize_pkt_drop_counter5_rx_port5_undersize_pkt_drop_cnt {
      type oc-yang:counter64;
      description
        "nan";
    }
    leaf counter_slice11_ifg_ifgbe_ra_rx_undersize_pkt_drop_counter5_rx_port5_undersize_pkt_drop_cnt {
      type oc-yang:counter64;
      description
        "nan";
    }
    leaf counter_slice12_ifg_ifgbe_ra_rx_undersize_pkt_drop_counter5_rx_port5_undersize_pkt_drop_cnt {
      type oc-yang:counter64;
      description
        "nan";
    }
    leaf counter_slice13_ifg_ifgbe_ra_rx_undersize_pkt_drop_counter5_rx_port5_undersize_pkt_drop_cnt {
      type oc-yang:counter64;
      description
        "nan";
    }
    leaf counter_slice14_ifg_ifgbe_ra_rx_undersize_pkt_drop_counter5_rx_port5_undersize_pkt_drop_cnt {
      type oc-yang:counter64;
      description
        "nan";
    }
    leaf counter_slice15_ifg_ifgbe_ra_rx_undersize_pkt_drop_counter5_rx_port5_undersize_pkt_drop_cnt {
      type oc-yang:counter64;
      description
        "nan";
    }
    leaf counter_slice0_ifg_ifgbe_ra_rx_undersize_pkt_drop_counter6_rx_port6_undersize_pkt_drop_cnt {
      type oc-yang:counter64;
      description
        "nan";
    }
    leaf counter_slice1_ifg_ifgbe_ra_rx_undersize_pkt_drop_counter6_rx_port6_undersize_pkt_drop_cnt {
      type oc-yang:counter64;
      description
        "nan";
    }
    leaf counter_slice2_ifg_ifgbe_ra_rx_undersize_pkt_drop_counter6_rx_port6_undersize_pkt_drop_cnt {
      type oc-yang:counter64;
      description
        "nan";
    }
    leaf counter_slice3_ifg_ifgbe_ra_rx_undersize_pkt_drop_counter6_rx_port6_undersize_pkt_drop_cnt {
      type oc-yang:counter64;
      description
        "nan";
    }
    leaf counter_slice4_ifg_ifgbe_ra_rx_undersize_pkt_drop_counter6_rx_port6_undersize_pkt_drop_cnt {
      type oc-yang:counter64;
      description
        "nan";
    }
    leaf counter_slice5_ifg_ifgbe_ra_rx_undersize_pkt_drop_counter6_rx_port6_undersize_pkt_drop_cnt {
      type oc-yang:counter64;
      description
        "nan";
    }
    leaf counter_slice6_ifg_ifgbe_ra_rx_undersize_pkt_drop_counter6_rx_port6_undersize_pkt_drop_cnt {
      type oc-yang:counter64;
      description
        "nan";
    }
    leaf counter_slice7_ifg_ifgbe_ra_rx_undersize_pkt_drop_counter6_rx_port6_undersize_pkt_drop_cnt {
      type oc-yang:counter64;
      description
        "nan";
    }
    leaf counter_slice8_ifg_ifgbe_ra_rx_undersize_pkt_drop_counter6_rx_port6_undersize_pkt_drop_cnt {
      type oc-yang:counter64;
      description
        "nan";
    }
    leaf counter_slice9_ifg_ifgbe_ra_rx_undersize_pkt_drop_counter6_rx_port6_undersize_pkt_drop_cnt {
      type oc-yang:counter64;
      description
        "nan";
    }
    leaf counter_slice10_ifg_ifgbe_ra_rx_undersize_pkt_drop_counter6_rx_port6_undersize_pkt_drop_cnt {
      type oc-yang:counter64;
      description
        "nan";
    }
    leaf counter_slice11_ifg_ifgbe_ra_rx_undersize_pkt_drop_counter6_rx_port6_undersize_pkt_drop_cnt {
      type oc-yang:counter64;
      description
        "nan";
    }
    leaf counter_slice12_ifg_ifgbe_ra_rx_undersize_pkt_drop_counter6_rx_port6_undersize_pkt_drop_cnt {
      type oc-yang:counter64;
      description
        "nan";
    }
    leaf counter_slice13_ifg_ifgbe_ra_rx_undersize_pkt_drop_counter6_rx_port6_undersize_pkt_drop_cnt {
      type oc-yang:counter64;
      description
        "nan";
    }
    leaf counter_slice14_ifg_ifgbe_ra_rx_undersize_pkt_drop_counter6_rx_port6_undersize_pkt_drop_cnt {
      type oc-yang:counter64;
      description
        "nan";
    }
    leaf counter_slice15_ifg_ifgbe_ra_rx_undersize_pkt_drop_counter6_rx_port6_undersize_pkt_drop_cnt {
      type oc-yang:counter64;
      description
        "nan";
    }
    leaf counter_slice0_ifg_ifgbe_ra_rx_undersize_pkt_drop_counter7_rx_port7_undersize_pkt_drop_cnt {
      type oc-yang:counter64;
      description
        "nan";
    }
    leaf counter_slice1_ifg_ifgbe_ra_rx_undersize_pkt_drop_counter7_rx_port7_undersize_pkt_drop_cnt {
      type oc-yang:counter64;
      description
        "nan";
    }
    leaf counter_slice2_ifg_ifgbe_ra_rx_undersize_pkt_drop_counter7_rx_port7_undersize_pkt_drop_cnt {
      type oc-yang:counter64;
      description
        "nan";
    }
    leaf counter_slice3_ifg_ifgbe_ra_rx_undersize_pkt_drop_counter7_rx_port7_undersize_pkt_drop_cnt {
      type oc-yang:counter64;
      description
        "nan";
    }
    leaf counter_slice4_ifg_ifgbe_ra_rx_undersize_pkt_drop_counter7_rx_port7_undersize_pkt_drop_cnt {
      type oc-yang:counter64;
      description
        "nan";
    }
    leaf counter_slice5_ifg_ifgbe_ra_rx_undersize_pkt_drop_counter7_rx_port7_undersize_pkt_drop_cnt {
      type oc-yang:counter64;
      description
        "nan";
    }
    leaf counter_slice6_ifg_ifgbe_ra_rx_undersize_pkt_drop_counter7_rx_port7_undersize_pkt_drop_cnt {
      type oc-yang:counter64;
      description
        "nan";
    }
    leaf counter_slice7_ifg_ifgbe_ra_rx_undersize_pkt_drop_counter7_rx_port7_undersize_pkt_drop_cnt {
      type oc-yang:counter64;
      description
        "nan";
    }
    leaf counter_slice8_ifg_ifgbe_ra_rx_undersize_pkt_drop_counter7_rx_port7_undersize_pkt_drop_cnt {
      type oc-yang:counter64;
      description
        "nan";
    }
    leaf counter_slice9_ifg_ifgbe_ra_rx_undersize_pkt_drop_counter7_rx_port7_undersize_pkt_drop_cnt {
      type oc-yang:counter64;
      description
        "nan";
    }
    leaf counter_slice10_ifg_ifgbe_ra_rx_undersize_pkt_drop_counter7_rx_port7_undersize_pkt_drop_cnt {
      type oc-yang:counter64;
      description
        "nan";
    }
    leaf counter_slice11_ifg_ifgbe_ra_rx_undersize_pkt_drop_counter7_rx_port7_undersize_pkt_drop_cnt {
      type oc-yang:counter64;
      description
        "nan";
    }
    leaf counter_slice12_ifg_ifgbe_ra_rx_undersize_pkt_drop_counter7_rx_port7_undersize_pkt_drop_cnt {
      type oc-yang:counter64;
      description
        "nan";
    }
    leaf counter_slice13_ifg_ifgbe_ra_rx_undersize_pkt_drop_counter7_rx_port7_undersize_pkt_drop_cnt {
      type oc-yang:counter64;
      description
        "nan";
    }
    leaf counter_slice14_ifg_ifgbe_ra_rx_undersize_pkt_drop_counter7_rx_port7_undersize_pkt_drop_cnt {
      type oc-yang:counter64;
      description
        "nan";
    }
    leaf counter_slice15_ifg_ifgbe_ra_rx_undersize_pkt_drop_counter7_rx_port7_undersize_pkt_drop_cnt {
      type oc-yang:counter64;
      description
        "nan";
    }
    leaf counter_slice0_ifg_ifgbe_ra_rx_undersize_pkt_drop_counter8_rx_port8_undersize_pkt_drop_cnt {
      type oc-yang:counter64;
      description
        "nan";
    }
    leaf counter_slice1_ifg_ifgbe_ra_rx_undersize_pkt_drop_counter8_rx_port8_undersize_pkt_drop_cnt {
      type oc-yang:counter64;
      description
        "nan";
    }
    leaf counter_slice2_ifg_ifgbe_ra_rx_undersize_pkt_drop_counter8_rx_port8_undersize_pkt_drop_cnt {
      type oc-yang:counter64;
      description
        "nan";
    }
    leaf counter_slice3_ifg_ifgbe_ra_rx_undersize_pkt_drop_counter8_rx_port8_undersize_pkt_drop_cnt {
      type oc-yang:counter64;
      description
        "nan";
    }
    leaf counter_slice4_ifg_ifgbe_ra_rx_undersize_pkt_drop_counter8_rx_port8_undersize_pkt_drop_cnt {
      type oc-yang:counter64;
      description
        "nan";
    }
    leaf counter_slice5_ifg_ifgbe_ra_rx_undersize_pkt_drop_counter8_rx_port8_undersize_pkt_drop_cnt {
      type oc-yang:counter64;
      description
        "nan";
    }
    leaf counter_slice6_ifg_ifgbe_ra_rx_undersize_pkt_drop_counter8_rx_port8_undersize_pkt_drop_cnt {
      type oc-yang:counter64;
      description
        "nan";
    }
    leaf counter_slice7_ifg_ifgbe_ra_rx_undersize_pkt_drop_counter8_rx_port8_undersize_pkt_drop_cnt {
      type oc-yang:counter64;
      description
        "nan";
    }
    leaf counter_slice8_ifg_ifgbe_ra_rx_undersize_pkt_drop_counter8_rx_port8_undersize_pkt_drop_cnt {
      type oc-yang:counter64;
      description
        "nan";
    }
    leaf counter_slice9_ifg_ifgbe_ra_rx_undersize_pkt_drop_counter8_rx_port8_undersize_pkt_drop_cnt {
      type oc-yang:counter64;
      description
        "nan";
    }
    leaf counter_slice10_ifg_ifgbe_ra_rx_undersize_pkt_drop_counter8_rx_port8_undersize_pkt_drop_cnt {
      type oc-yang:counter64;
      description
        "nan";
    }
    leaf counter_slice11_ifg_ifgbe_ra_rx_undersize_pkt_drop_counter8_rx_port8_undersize_pkt_drop_cnt {
      type oc-yang:counter64;
      description
        "nan";
    }
    leaf counter_slice12_ifg_ifgbe_ra_rx_undersize_pkt_drop_counter8_rx_port8_undersize_pkt_drop_cnt {
      type oc-yang:counter64;
      description
        "nan";
    }
    leaf counter_slice13_ifg_ifgbe_ra_rx_undersize_pkt_drop_counter8_rx_port8_undersize_pkt_drop_cnt {
      type oc-yang:counter64;
      description
        "nan";
    }
    leaf counter_slice14_ifg_ifgbe_ra_rx_undersize_pkt_drop_counter8_rx_port8_undersize_pkt_drop_cnt {
      type oc-yang:counter64;
      description
        "nan";
    }
    leaf counter_slice15_ifg_ifgbe_ra_rx_undersize_pkt_drop_counter8_rx_port8_undersize_pkt_drop_cnt {
      type oc-yang:counter64;
      description
        "nan";
    }
    leaf counter_slice0_ifg_ifgbe_ra_rx_undersize_pkt_drop_counter9_rx_port9_undersize_pkt_drop_cnt {
      type oc-yang:counter64;
      description
        "nan";
    }
    leaf counter_slice1_ifg_ifgbe_ra_rx_undersize_pkt_drop_counter9_rx_port9_undersize_pkt_drop_cnt {
      type oc-yang:counter64;
      description
        "nan";
    }
    leaf counter_slice2_ifg_ifgbe_ra_rx_undersize_pkt_drop_counter9_rx_port9_undersize_pkt_drop_cnt {
      type oc-yang:counter64;
      description
        "nan";
    }
    leaf counter_slice3_ifg_ifgbe_ra_rx_undersize_pkt_drop_counter9_rx_port9_undersize_pkt_drop_cnt {
      type oc-yang:counter64;
      description
        "nan";
    }
    leaf counter_slice4_ifg_ifgbe_ra_rx_undersize_pkt_drop_counter9_rx_port9_undersize_pkt_drop_cnt {
      type oc-yang:counter64;
      description
        "nan";
    }
    leaf counter_slice5_ifg_ifgbe_ra_rx_undersize_pkt_drop_counter9_rx_port9_undersize_pkt_drop_cnt {
      type oc-yang:counter64;
      description
        "nan";
    }
    leaf counter_slice6_ifg_ifgbe_ra_rx_undersize_pkt_drop_counter9_rx_port9_undersize_pkt_drop_cnt {
      type oc-yang:counter64;
      description
        "nan";
    }
    leaf counter_slice7_ifg_ifgbe_ra_rx_undersize_pkt_drop_counter9_rx_port9_undersize_pkt_drop_cnt {
      type oc-yang:counter64;
      description
        "nan";
    }
    leaf counter_slice8_ifg_ifgbe_ra_rx_undersize_pkt_drop_counter9_rx_port9_undersize_pkt_drop_cnt {
      type oc-yang:counter64;
      description
        "nan";
    }
    leaf counter_slice9_ifg_ifgbe_ra_rx_undersize_pkt_drop_counter9_rx_port9_undersize_pkt_drop_cnt {
      type oc-yang:counter64;
      description
        "nan";
    }
    leaf counter_slice10_ifg_ifgbe_ra_rx_undersize_pkt_drop_counter9_rx_port9_undersize_pkt_drop_cnt {
      type oc-yang:counter64;
      description
        "nan";
    }
    leaf counter_slice11_ifg_ifgbe_ra_rx_undersize_pkt_drop_counter9_rx_port9_undersize_pkt_drop_cnt {
      type oc-yang:counter64;
      description
        "nan";
    }
    leaf counter_slice12_ifg_ifgbe_ra_rx_undersize_pkt_drop_counter9_rx_port9_undersize_pkt_drop_cnt {
      type oc-yang:counter64;
      description
        "nan";
    }
    leaf counter_slice13_ifg_ifgbe_ra_rx_undersize_pkt_drop_counter9_rx_port9_undersize_pkt_drop_cnt {
      type oc-yang:counter64;
      description
        "nan";
    }
    leaf counter_slice14_ifg_ifgbe_ra_rx_undersize_pkt_drop_counter9_rx_port9_undersize_pkt_drop_cnt {
      type oc-yang:counter64;
      description
        "nan";
    }
    leaf counter_slice15_ifg_ifgbe_ra_rx_undersize_pkt_drop_counter9_rx_port9_undersize_pkt_drop_cnt {
      type oc-yang:counter64;
      description
        "nan";
    }
    leaf counter_slice0_ifg_ifgbi_rx_prot_frag_drop_counter_rx_prot_frag_drop_cnt {
      type oc-yang:counter64;
      description
        "RXPP interface protection fragments drop counter.";
    }
    leaf counter_slice1_ifg_ifgbi_rx_prot_frag_drop_counter_rx_prot_frag_drop_cnt {
      type oc-yang:counter64;
      description
        "RXPP interface protection fragments drop counter.";
    }
    leaf counter_slice2_ifg_ifgbi_rx_prot_frag_drop_counter_rx_prot_frag_drop_cnt {
      type oc-yang:counter64;
      description
        "RXPP interface protection fragments drop counter.";
    }
    leaf counter_slice3_ifg_ifgbi_rx_prot_frag_drop_counter_rx_prot_frag_drop_cnt {
      type oc-yang:counter64;
      description
        "RXPP interface protection fragments drop counter.";
    }
    leaf counter_slice4_ifg_ifgbi_rx_prot_frag_drop_counter_rx_prot_frag_drop_cnt {
      type oc-yang:counter64;
      description
        "RXPP interface protection fragments drop counter.";
    }
    leaf counter_slice5_ifg_ifgbi_rx_prot_frag_drop_counter_rx_prot_frag_drop_cnt {
      type oc-yang:counter64;
      description
        "RXPP interface protection fragments drop counter.";
    }
    leaf counter_slice6_ifg_ifgbi_rx_prot_frag_drop_counter_rx_prot_frag_drop_cnt {
      type oc-yang:counter64;
      description
        "RXPP interface protection fragments drop counter.";
    }
    leaf counter_slice7_ifg_ifgbi_rx_prot_frag_drop_counter_rx_prot_frag_drop_cnt {
      type oc-yang:counter64;
      description
        "RXPP interface protection fragments drop counter.";
    }
    leaf counter_slice8_ifg_ifgbi_rx_prot_frag_drop_counter_rx_prot_frag_drop_cnt {
      type oc-yang:counter64;
      description
        "RXPP interface protection fragments drop counter.";
    }
    leaf counter_slice9_ifg_ifgbi_rx_prot_frag_drop_counter_rx_prot_frag_drop_cnt {
      type oc-yang:counter64;
      description
        "RXPP interface protection fragments drop counter.";
    }
    leaf counter_slice10_ifg_ifgbi_rx_prot_frag_drop_counter_rx_prot_frag_drop_cnt {
      type oc-yang:counter64;
      description
        "RXPP interface protection fragments drop counter.";
    }
    leaf counter_slice11_ifg_ifgbi_rx_prot_frag_drop_counter_rx_prot_frag_drop_cnt {
      type oc-yang:counter64;
      description
        "RXPP interface protection fragments drop counter.";
    }
    leaf counter_slice12_ifg_ifgbi_rx_prot_frag_drop_counter_rx_prot_frag_drop_cnt {
      type oc-yang:counter64;
      description
        "RXPP interface protection fragments drop counter.";
    }
    leaf counter_slice13_ifg_ifgbi_rx_prot_frag_drop_counter_rx_prot_frag_drop_cnt {
      type oc-yang:counter64;
      description
        "RXPP interface protection fragments drop counter.";
    }
    leaf counter_slice14_ifg_ifgbi_rx_prot_frag_drop_counter_rx_prot_frag_drop_cnt {
      type oc-yang:counter64;
      description
        "RXPP interface protection fragments drop counter.";
    }
    leaf counter_slice15_ifg_ifgbi_rx_prot_frag_drop_counter_rx_prot_frag_drop_cnt {
      type oc-yang:counter64;
      description
        "RXPP interface protection fragments drop counter.";
    }
    leaf counter_slice0_ifg_ifgbi_rx_prot_pkt_drop_counter_rx_prot_pkt_drop_cnt {
      type oc-yang:counter64;
      description
        "RXPP interface protection packet drop counter.";
    }
    leaf counter_slice1_ifg_ifgbi_rx_prot_pkt_drop_counter_rx_prot_pkt_drop_cnt {
      type oc-yang:counter64;
      description
        "RXPP interface protection packet drop counter.";
    }
    leaf counter_slice2_ifg_ifgbi_rx_prot_pkt_drop_counter_rx_prot_pkt_drop_cnt {
      type oc-yang:counter64;
      description
        "RXPP interface protection packet drop counter.";
    }
    leaf counter_slice3_ifg_ifgbi_rx_prot_pkt_drop_counter_rx_prot_pkt_drop_cnt {
      type oc-yang:counter64;
      description
        "RXPP interface protection packet drop counter.";
    }
    leaf counter_slice4_ifg_ifgbi_rx_prot_pkt_drop_counter_rx_prot_pkt_drop_cnt {
      type oc-yang:counter64;
      description
        "RXPP interface protection packet drop counter.";
    }
    leaf counter_slice5_ifg_ifgbi_rx_prot_pkt_drop_counter_rx_prot_pkt_drop_cnt {
      type oc-yang:counter64;
      description
        "RXPP interface protection packet drop counter.";
    }
    leaf counter_slice6_ifg_ifgbi_rx_prot_pkt_drop_counter_rx_prot_pkt_drop_cnt {
      type oc-yang:counter64;
      description
        "RXPP interface protection packet drop counter.";
    }
    leaf counter_slice7_ifg_ifgbi_rx_prot_pkt_drop_counter_rx_prot_pkt_drop_cnt {
      type oc-yang:counter64;
      description
        "RXPP interface protection packet drop counter.";
    }
    leaf counter_slice8_ifg_ifgbi_rx_prot_pkt_drop_counter_rx_prot_pkt_drop_cnt {
      type oc-yang:counter64;
      description
        "RXPP interface protection packet drop counter.";
    }
    leaf counter_slice9_ifg_ifgbi_rx_prot_pkt_drop_counter_rx_prot_pkt_drop_cnt {
      type oc-yang:counter64;
      description
        "RXPP interface protection packet drop counter.";
    }
    leaf counter_slice10_ifg_ifgbi_rx_prot_pkt_drop_counter_rx_prot_pkt_drop_cnt {
      type oc-yang:counter64;
      description
        "RXPP interface protection packet drop counter.";
    }
    leaf counter_slice11_ifg_ifgbi_rx_prot_pkt_drop_counter_rx_prot_pkt_drop_cnt {
      type oc-yang:counter64;
      description
        "RXPP interface protection packet drop counter.";
    }
    leaf counter_slice12_ifg_ifgbi_rx_prot_pkt_drop_counter_rx_prot_pkt_drop_cnt {
      type oc-yang:counter64;
      description
        "RXPP interface protection packet drop counter.";
    }
    leaf counter_slice13_ifg_ifgbi_rx_prot_pkt_drop_counter_rx_prot_pkt_drop_cnt {
      type oc-yang:counter64;
      description
        "RXPP interface protection packet drop counter.";
    }
    leaf counter_slice14_ifg_ifgbi_rx_prot_pkt_drop_counter_rx_prot_pkt_drop_cnt {
      type oc-yang:counter64;
      description
        "RXPP interface protection packet drop counter.";
    }
    leaf counter_slice15_ifg_ifgbi_rx_prot_pkt_drop_counter_rx_prot_pkt_drop_cnt {
      type oc-yang:counter64;
      description
        "RXPP interface protection packet drop counter.";
    }
    leaf counter_dmc_pier_pier_oobe_drop_counter_reg0_oobe_drop_cnt {
      type oc-yang:counter64;
      description
        "This field counts the number of OOBE drop packets from a ring. It considers only the extracted packets that have error bit set.";
    }
    leaf counter_dmc_pier_pier_oobe_drop_counter_reg1_oobe_drop_cnt {
      type oc-yang:counter64;
      description
        "This field counts the number of OOBE drop packets from a ring. It considers only the extracted packets that have error bit set.";
    }
    leaf counter_dmc_pier_pier_oobe_drop_counter_reg2_oobe_drop_cnt {
      type oc-yang:counter64;
      description
        "This field counts the number of OOBE drop packets from a ring. It considers only the extracted packets that have error bit set.";
    }
    leaf counter_dmc_pier_pier_oobe_drop_counter_reg3_oobe_drop_cnt {
      type oc-yang:counter64;
      description
        "This field counts the number of OOBE drop packets from a ring. It considers only the extracted packets that have error bit set.";
    }
    leaf counter_slice0_npu_rxpp_fwd_post_npe_ifg_rxpp_output_counters0_ifg_drop_counter_due_destination {
      type oc-yang:counter64;
      description
        "Counts the number of packets the RxPP dropped due to drop destination";
    }
    leaf counter_slice1_npu_rxpp_fwd_post_npe_ifg_rxpp_output_counters0_ifg_drop_counter_due_destination {
      type oc-yang:counter64;
      description
        "Counts the number of packets the RxPP dropped due to drop destination";
    }
    leaf counter_slice2_npu_rxpp_fwd_post_npe_ifg_rxpp_output_counters0_ifg_drop_counter_due_destination {
      type oc-yang:counter64;
      description
        "Counts the number of packets the RxPP dropped due to drop destination";
    }
    leaf counter_slice3_npu_rxpp_fwd_post_npe_ifg_rxpp_output_counters0_ifg_drop_counter_due_destination {
      type oc-yang:counter64;
      description
        "Counts the number of packets the RxPP dropped due to drop destination";
    }
    leaf counter_slice4_npu_rxpp_fwd_post_npe_ifg_rxpp_output_counters0_ifg_drop_counter_due_destination {
      type oc-yang:counter64;
      description
        "Counts the number of packets the RxPP dropped due to drop destination";
    }
    leaf counter_slice5_npu_rxpp_fwd_post_npe_ifg_rxpp_output_counters0_ifg_drop_counter_due_destination {
      type oc-yang:counter64;
      description
        "Counts the number of packets the RxPP dropped due to drop destination";
    }
    leaf counter_slice6_npu_rxpp_fwd_post_npe_ifg_rxpp_output_counters0_ifg_drop_counter_due_destination {
      type oc-yang:counter64;
      description
        "Counts the number of packets the RxPP dropped due to drop destination";
    }
    leaf counter_slice7_npu_rxpp_fwd_post_npe_ifg_rxpp_output_counters0_ifg_drop_counter_due_destination {
      type oc-yang:counter64;
      description
        "Counts the number of packets the RxPP dropped due to drop destination";
    }
    leaf counter_slice8_npu_rxpp_fwd_post_npe_ifg_rxpp_output_counters0_ifg_drop_counter_due_destination {
      type oc-yang:counter64;
      description
        "Counts the number of packets the RxPP dropped due to drop destination";
    }
    leaf counter_slice9_npu_rxpp_fwd_post_npe_ifg_rxpp_output_counters0_ifg_drop_counter_due_destination {
      type oc-yang:counter64;
      description
        "Counts the number of packets the RxPP dropped due to drop destination";
    }
    leaf counter_slice10_npu_rxpp_fwd_post_npe_ifg_rxpp_output_counters0_ifg_drop_counter_due_destination {
      type oc-yang:counter64;
      description
        "Counts the number of packets the RxPP dropped due to drop destination";
    }
    leaf counter_slice11_npu_rxpp_fwd_post_npe_ifg_rxpp_output_counters0_ifg_drop_counter_due_destination {
      type oc-yang:counter64;
      description
        "Counts the number of packets the RxPP dropped due to drop destination";
    }
    leaf counter_slice12_npu_rxpp_fwd_post_npe_ifg_rxpp_output_counters0_ifg_drop_counter_due_destination {
      type oc-yang:counter64;
      description
        "Counts the number of packets the RxPP dropped due to drop destination";
    }
    leaf counter_slice13_npu_rxpp_fwd_post_npe_ifg_rxpp_output_counters0_ifg_drop_counter_due_destination {
      type oc-yang:counter64;
      description
        "Counts the number of packets the RxPP dropped due to drop destination";
    }
    leaf counter_slice14_npu_rxpp_fwd_post_npe_ifg_rxpp_output_counters0_ifg_drop_counter_due_destination {
      type oc-yang:counter64;
      description
        "Counts the number of packets the RxPP dropped due to drop destination";
    }
    leaf counter_slice15_npu_rxpp_fwd_post_npe_ifg_rxpp_output_counters0_ifg_drop_counter_due_destination {
      type oc-yang:counter64;
      description
        "Counts the number of packets the RxPP dropped due to drop destination";
    }
    leaf counter_slice0_npu_rxpp_fwd_post_npe_ifg_rxpp_output_counters0_ifg_drop_counter_due_ecc {
      type oc-yang:counter64;
      description
        "Counts the number of packets the RxPP dropped due to double ecc error from internal memories";
    }
    leaf counter_slice1_npu_rxpp_fwd_post_npe_ifg_rxpp_output_counters0_ifg_drop_counter_due_ecc {
      type oc-yang:counter64;
      description
        "Counts the number of packets the RxPP dropped due to double ecc error from internal memories";
    }
    leaf counter_slice2_npu_rxpp_fwd_post_npe_ifg_rxpp_output_counters0_ifg_drop_counter_due_ecc {
      type oc-yang:counter64;
      description
        "Counts the number of packets the RxPP dropped due to double ecc error from internal memories";
    }
    leaf counter_slice3_npu_rxpp_fwd_post_npe_ifg_rxpp_output_counters0_ifg_drop_counter_due_ecc {
      type oc-yang:counter64;
      description
        "Counts the number of packets the RxPP dropped due to double ecc error from internal memories";
    }
    leaf counter_slice4_npu_rxpp_fwd_post_npe_ifg_rxpp_output_counters0_ifg_drop_counter_due_ecc {
      type oc-yang:counter64;
      description
        "Counts the number of packets the RxPP dropped due to double ecc error from internal memories";
    }
    leaf counter_slice5_npu_rxpp_fwd_post_npe_ifg_rxpp_output_counters0_ifg_drop_counter_due_ecc {
      type oc-yang:counter64;
      description
        "Counts the number of packets the RxPP dropped due to double ecc error from internal memories";
    }
    leaf counter_slice6_npu_rxpp_fwd_post_npe_ifg_rxpp_output_counters0_ifg_drop_counter_due_ecc {
      type oc-yang:counter64;
      description
        "Counts the number of packets the RxPP dropped due to double ecc error from internal memories";
    }
    leaf counter_slice7_npu_rxpp_fwd_post_npe_ifg_rxpp_output_counters0_ifg_drop_counter_due_ecc {
      type oc-yang:counter64;
      description
        "Counts the number of packets the RxPP dropped due to double ecc error from internal memories";
    }
    leaf counter_slice8_npu_rxpp_fwd_post_npe_ifg_rxpp_output_counters0_ifg_drop_counter_due_ecc {
      type oc-yang:counter64;
      description
        "Counts the number of packets the RxPP dropped due to double ecc error from internal memories";
    }
    leaf counter_slice9_npu_rxpp_fwd_post_npe_ifg_rxpp_output_counters0_ifg_drop_counter_due_ecc {
      type oc-yang:counter64;
      description
        "Counts the number of packets the RxPP dropped due to double ecc error from internal memories";
    }
    leaf counter_slice10_npu_rxpp_fwd_post_npe_ifg_rxpp_output_counters0_ifg_drop_counter_due_ecc {
      type oc-yang:counter64;
      description
        "Counts the number of packets the RxPP dropped due to double ecc error from internal memories";
    }
    leaf counter_slice11_npu_rxpp_fwd_post_npe_ifg_rxpp_output_counters0_ifg_drop_counter_due_ecc {
      type oc-yang:counter64;
      description
        "Counts the number of packets the RxPP dropped due to double ecc error from internal memories";
    }
    leaf counter_slice12_npu_rxpp_fwd_post_npe_ifg_rxpp_output_counters0_ifg_drop_counter_due_ecc {
      type oc-yang:counter64;
      description
        "Counts the number of packets the RxPP dropped due to double ecc error from internal memories";
    }
    leaf counter_slice13_npu_rxpp_fwd_post_npe_ifg_rxpp_output_counters0_ifg_drop_counter_due_ecc {
      type oc-yang:counter64;
      description
        "Counts the number of packets the RxPP dropped due to double ecc error from internal memories";
    }
    leaf counter_slice14_npu_rxpp_fwd_post_npe_ifg_rxpp_output_counters0_ifg_drop_counter_due_ecc {
      type oc-yang:counter64;
      description
        "Counts the number of packets the RxPP dropped due to double ecc error from internal memories";
    }
    leaf counter_slice15_npu_rxpp_fwd_post_npe_ifg_rxpp_output_counters0_ifg_drop_counter_due_ecc {
      type oc-yang:counter64;
      description
        "Counts the number of packets the RxPP dropped due to double ecc error from internal memories";
    }
    leaf counter_slice0_npu_rxpp_fwd_post_npe_ifg_rxpp_output_counters0_ifg_drop_counter_due_err_flag {
      type oc-yang:counter64;
      description
        "Counts the number of packets the RxPP dropped due to error flag value of 1";
    }
    leaf counter_slice1_npu_rxpp_fwd_post_npe_ifg_rxpp_output_counters0_ifg_drop_counter_due_err_flag {
      type oc-yang:counter64;
      description
        "Counts the number of packets the RxPP dropped due to error flag value of 1";
    }
    leaf counter_slice2_npu_rxpp_fwd_post_npe_ifg_rxpp_output_counters0_ifg_drop_counter_due_err_flag {
      type oc-yang:counter64;
      description
        "Counts the number of packets the RxPP dropped due to error flag value of 1";
    }
    leaf counter_slice3_npu_rxpp_fwd_post_npe_ifg_rxpp_output_counters0_ifg_drop_counter_due_err_flag {
      type oc-yang:counter64;
      description
        "Counts the number of packets the RxPP dropped due to error flag value of 1";
    }
    leaf counter_slice4_npu_rxpp_fwd_post_npe_ifg_rxpp_output_counters0_ifg_drop_counter_due_err_flag {
      type oc-yang:counter64;
      description
        "Counts the number of packets the RxPP dropped due to error flag value of 1";
    }
    leaf counter_slice5_npu_rxpp_fwd_post_npe_ifg_rxpp_output_counters0_ifg_drop_counter_due_err_flag {
      type oc-yang:counter64;
      description
        "Counts the number of packets the RxPP dropped due to error flag value of 1";
    }
    leaf counter_slice6_npu_rxpp_fwd_post_npe_ifg_rxpp_output_counters0_ifg_drop_counter_due_err_flag {
      type oc-yang:counter64;
      description
        "Counts the number of packets the RxPP dropped due to error flag value of 1";
    }
    leaf counter_slice7_npu_rxpp_fwd_post_npe_ifg_rxpp_output_counters0_ifg_drop_counter_due_err_flag {
      type oc-yang:counter64;
      description
        "Counts the number of packets the RxPP dropped due to error flag value of 1";
    }
    leaf counter_slice8_npu_rxpp_fwd_post_npe_ifg_rxpp_output_counters0_ifg_drop_counter_due_err_flag {
      type oc-yang:counter64;
      description
        "Counts the number of packets the RxPP dropped due to error flag value of 1";
    }
    leaf counter_slice9_npu_rxpp_fwd_post_npe_ifg_rxpp_output_counters0_ifg_drop_counter_due_err_flag {
      type oc-yang:counter64;
      description
        "Counts the number of packets the RxPP dropped due to error flag value of 1";
    }
    leaf counter_slice10_npu_rxpp_fwd_post_npe_ifg_rxpp_output_counters0_ifg_drop_counter_due_err_flag {
      type oc-yang:counter64;
      description
        "Counts the number of packets the RxPP dropped due to error flag value of 1";
    }
    leaf counter_slice11_npu_rxpp_fwd_post_npe_ifg_rxpp_output_counters0_ifg_drop_counter_due_err_flag {
      type oc-yang:counter64;
      description
        "Counts the number of packets the RxPP dropped due to error flag value of 1";
    }
    leaf counter_slice12_npu_rxpp_fwd_post_npe_ifg_rxpp_output_counters0_ifg_drop_counter_due_err_flag {
      type oc-yang:counter64;
      description
        "Counts the number of packets the RxPP dropped due to error flag value of 1";
    }
    leaf counter_slice13_npu_rxpp_fwd_post_npe_ifg_rxpp_output_counters0_ifg_drop_counter_due_err_flag {
      type oc-yang:counter64;
      description
        "Counts the number of packets the RxPP dropped due to error flag value of 1";
    }
    leaf counter_slice14_npu_rxpp_fwd_post_npe_ifg_rxpp_output_counters0_ifg_drop_counter_due_err_flag {
      type oc-yang:counter64;
      description
        "Counts the number of packets the RxPP dropped due to error flag value of 1";
    }
    leaf counter_slice15_npu_rxpp_fwd_post_npe_ifg_rxpp_output_counters0_ifg_drop_counter_due_err_flag {
      type oc-yang:counter64;
      description
        "Counts the number of packets the RxPP dropped due to error flag value of 1";
    }
    leaf counter_slice0_npu_rxpp_fwd_post_npe_ifg_rxpp_output_counters0_ifg_drop_counter_due_frag_parity_err {
      type oc-yang:counter64;
      description
        "Counts the number of packets the RxPP dropped due to Fragment parity error.";
    }
    leaf counter_slice1_npu_rxpp_fwd_post_npe_ifg_rxpp_output_counters0_ifg_drop_counter_due_frag_parity_err {
      type oc-yang:counter64;
      description
        "Counts the number of packets the RxPP dropped due to Fragment parity error.";
    }
    leaf counter_slice2_npu_rxpp_fwd_post_npe_ifg_rxpp_output_counters0_ifg_drop_counter_due_frag_parity_err {
      type oc-yang:counter64;
      description
        "Counts the number of packets the RxPP dropped due to Fragment parity error.";
    }
    leaf counter_slice3_npu_rxpp_fwd_post_npe_ifg_rxpp_output_counters0_ifg_drop_counter_due_frag_parity_err {
      type oc-yang:counter64;
      description
        "Counts the number of packets the RxPP dropped due to Fragment parity error.";
    }
    leaf counter_slice4_npu_rxpp_fwd_post_npe_ifg_rxpp_output_counters0_ifg_drop_counter_due_frag_parity_err {
      type oc-yang:counter64;
      description
        "Counts the number of packets the RxPP dropped due to Fragment parity error.";
    }
    leaf counter_slice5_npu_rxpp_fwd_post_npe_ifg_rxpp_output_counters0_ifg_drop_counter_due_frag_parity_err {
      type oc-yang:counter64;
      description
        "Counts the number of packets the RxPP dropped due to Fragment parity error.";
    }
    leaf counter_slice6_npu_rxpp_fwd_post_npe_ifg_rxpp_output_counters0_ifg_drop_counter_due_frag_parity_err {
      type oc-yang:counter64;
      description
        "Counts the number of packets the RxPP dropped due to Fragment parity error.";
    }
    leaf counter_slice7_npu_rxpp_fwd_post_npe_ifg_rxpp_output_counters0_ifg_drop_counter_due_frag_parity_err {
      type oc-yang:counter64;
      description
        "Counts the number of packets the RxPP dropped due to Fragment parity error.";
    }
    leaf counter_slice8_npu_rxpp_fwd_post_npe_ifg_rxpp_output_counters0_ifg_drop_counter_due_frag_parity_err {
      type oc-yang:counter64;
      description
        "Counts the number of packets the RxPP dropped due to Fragment parity error.";
    }
    leaf counter_slice9_npu_rxpp_fwd_post_npe_ifg_rxpp_output_counters0_ifg_drop_counter_due_frag_parity_err {
      type oc-yang:counter64;
      description
        "Counts the number of packets the RxPP dropped due to Fragment parity error.";
    }
    leaf counter_slice10_npu_rxpp_fwd_post_npe_ifg_rxpp_output_counters0_ifg_drop_counter_due_frag_parity_err {
      type oc-yang:counter64;
      description
        "Counts the number of packets the RxPP dropped due to Fragment parity error.";
    }
    leaf counter_slice11_npu_rxpp_fwd_post_npe_ifg_rxpp_output_counters0_ifg_drop_counter_due_frag_parity_err {
      type oc-yang:counter64;
      description
        "Counts the number of packets the RxPP dropped due to Fragment parity error.";
    }
    leaf counter_slice12_npu_rxpp_fwd_post_npe_ifg_rxpp_output_counters0_ifg_drop_counter_due_frag_parity_err {
      type oc-yang:counter64;
      description
        "Counts the number of packets the RxPP dropped due to Fragment parity error.";
    }
    leaf counter_slice13_npu_rxpp_fwd_post_npe_ifg_rxpp_output_counters0_ifg_drop_counter_due_frag_parity_err {
      type oc-yang:counter64;
      description
        "Counts the number of packets the RxPP dropped due to Fragment parity error.";
    }
    leaf counter_slice14_npu_rxpp_fwd_post_npe_ifg_rxpp_output_counters0_ifg_drop_counter_due_frag_parity_err {
      type oc-yang:counter64;
      description
        "Counts the number of packets the RxPP dropped due to Fragment parity error.";
    }
    leaf counter_slice15_npu_rxpp_fwd_post_npe_ifg_rxpp_output_counters0_ifg_drop_counter_due_frag_parity_err {
      type oc-yang:counter64;
      description
        "Counts the number of packets the RxPP dropped due to Fragment parity error.";
    }
    leaf counter_slice0_ifg_sec_dec0_sta_undersize_filter0_sta_undersize_pkt_drop_cnt {
      type oc-yang:counter64;
      description
        "Per port RX undersize packet drop - counter for packets that were dropped because they were smaller than 57B.";
    }
    leaf counter_slice0_ifg_sec_dec0_sta_undersize_filter1_sta_undersize_pkt_drop_cnt {
      type oc-yang:counter64;
      description
        "Per port RX undersize packet drop - counter for packets that were dropped because they were smaller than 57B.";
    }
    leaf counter_slice0_ifg_sec_dec0_sta_undersize_filter2_sta_undersize_pkt_drop_cnt {
      type oc-yang:counter64;
      description
        "Per port RX undersize packet drop - counter for packets that were dropped because they were smaller than 57B.";
    }
    leaf counter_slice0_ifg_sec_dec0_sta_undersize_filter3_sta_undersize_pkt_drop_cnt {
      type oc-yang:counter64;
      description
        "Per port RX undersize packet drop - counter for packets that were dropped because they were smaller than 57B.";
    }
    leaf counter_slice0_ifg_sec_dec0_sta_undersize_filter4_sta_undersize_pkt_drop_cnt {
      type oc-yang:counter64;
      description
        "Per port RX undersize packet drop - counter for packets that were dropped because they were smaller than 57B.";
    }
    leaf counter_slice0_ifg_sec_dec0_sta_undersize_filter5_sta_undersize_pkt_drop_cnt {
      type oc-yang:counter64;
      description
        "Per port RX undersize packet drop - counter for packets that were dropped because they were smaller than 57B.";
    }
    leaf counter_slice0_ifg_sec_dec0_sta_undersize_filter6_sta_undersize_pkt_drop_cnt {
      type oc-yang:counter64;
      description
        "Per port RX undersize packet drop - counter for packets that were dropped because they were smaller than 57B.";
    }
    leaf counter_slice0_ifg_sec_dec0_sta_undersize_filter7_sta_undersize_pkt_drop_cnt {
      type oc-yang:counter64;
      description
        "Per port RX undersize packet drop - counter for packets that were dropped because they were smaller than 57B.";
    }
    leaf counter_slice0_ifg_sec_dec1_sta_undersize_filter0_sta_undersize_pkt_drop_cnt {
      type oc-yang:counter64;
      description
        "Per port RX undersize packet drop - counter for packets that were dropped because they were smaller than 57B.";
    }
    leaf counter_slice0_ifg_sec_dec1_sta_undersize_filter1_sta_undersize_pkt_drop_cnt {
      type oc-yang:counter64;
      description
        "Per port RX undersize packet drop - counter for packets that were dropped because they were smaller than 57B.";
    }
    leaf counter_slice0_ifg_sec_dec1_sta_undersize_filter2_sta_undersize_pkt_drop_cnt {
      type oc-yang:counter64;
      description
        "Per port RX undersize packet drop - counter for packets that were dropped because they were smaller than 57B.";
    }
    leaf counter_slice0_ifg_sec_dec1_sta_undersize_filter3_sta_undersize_pkt_drop_cnt {
      type oc-yang:counter64;
      description
        "Per port RX undersize packet drop - counter for packets that were dropped because they were smaller than 57B.";
    }
    leaf counter_slice0_ifg_sec_dec1_sta_undersize_filter4_sta_undersize_pkt_drop_cnt {
      type oc-yang:counter64;
      description
        "Per port RX undersize packet drop - counter for packets that were dropped because they were smaller than 57B.";
    }
    leaf counter_slice0_ifg_sec_dec1_sta_undersize_filter5_sta_undersize_pkt_drop_cnt {
      type oc-yang:counter64;
      description
        "Per port RX undersize packet drop - counter for packets that were dropped because they were smaller than 57B.";
    }
    leaf counter_slice0_ifg_sec_dec1_sta_undersize_filter6_sta_undersize_pkt_drop_cnt {
      type oc-yang:counter64;
      description
        "Per port RX undersize packet drop - counter for packets that were dropped because they were smaller than 57B.";
    }
    leaf counter_slice0_ifg_sec_dec1_sta_undersize_filter7_sta_undersize_pkt_drop_cnt {
      type oc-yang:counter64;
      description
        "Per port RX undersize packet drop - counter for packets that were dropped because they were smaller than 57B.";
    }
    leaf counter_slice0_ifg_sec_dec2_sta_undersize_filter0_sta_undersize_pkt_drop_cnt {
      type oc-yang:counter64;
      description
        "Per port RX undersize packet drop - counter for packets that were dropped because they were smaller than 57B.";
    }
    leaf counter_slice0_ifg_sec_dec2_sta_undersize_filter1_sta_undersize_pkt_drop_cnt {
      type oc-yang:counter64;
      description
        "Per port RX undersize packet drop - counter for packets that were dropped because they were smaller than 57B.";
    }
    leaf counter_slice0_ifg_sec_dec2_sta_undersize_filter2_sta_undersize_pkt_drop_cnt {
      type oc-yang:counter64;
      description
        "Per port RX undersize packet drop - counter for packets that were dropped because they were smaller than 57B.";
    }
    leaf counter_slice0_ifg_sec_dec2_sta_undersize_filter3_sta_undersize_pkt_drop_cnt {
      type oc-yang:counter64;
      description
        "Per port RX undersize packet drop - counter for packets that were dropped because they were smaller than 57B.";
    }
    leaf counter_slice0_ifg_sec_dec2_sta_undersize_filter4_sta_undersize_pkt_drop_cnt {
      type oc-yang:counter64;
      description
        "Per port RX undersize packet drop - counter for packets that were dropped because they were smaller than 57B.";
    }
    leaf counter_slice0_ifg_sec_dec2_sta_undersize_filter5_sta_undersize_pkt_drop_cnt {
      type oc-yang:counter64;
      description
        "Per port RX undersize packet drop - counter for packets that were dropped because they were smaller than 57B.";
    }
    leaf counter_slice0_ifg_sec_dec2_sta_undersize_filter6_sta_undersize_pkt_drop_cnt {
      type oc-yang:counter64;
      description
        "Per port RX undersize packet drop - counter for packets that were dropped because they were smaller than 57B.";
    }
    leaf counter_slice0_ifg_sec_dec2_sta_undersize_filter7_sta_undersize_pkt_drop_cnt {
      type oc-yang:counter64;
      description
        "Per port RX undersize packet drop - counter for packets that were dropped because they were smaller than 57B.";
    }
    leaf counter_slice0_ifg_sec_dec3_sta_undersize_filter0_sta_undersize_pkt_drop_cnt {
      type oc-yang:counter64;
      description
        "Per port RX undersize packet drop - counter for packets that were dropped because they were smaller than 57B.";
    }
    leaf counter_slice0_ifg_sec_dec3_sta_undersize_filter1_sta_undersize_pkt_drop_cnt {
      type oc-yang:counter64;
      description
        "Per port RX undersize packet drop - counter for packets that were dropped because they were smaller than 57B.";
    }
    leaf counter_slice0_ifg_sec_dec3_sta_undersize_filter2_sta_undersize_pkt_drop_cnt {
      type oc-yang:counter64;
      description
        "Per port RX undersize packet drop - counter for packets that were dropped because they were smaller than 57B.";
    }
    leaf counter_slice0_ifg_sec_dec3_sta_undersize_filter3_sta_undersize_pkt_drop_cnt {
      type oc-yang:counter64;
      description
        "Per port RX undersize packet drop - counter for packets that were dropped because they were smaller than 57B.";
    }
    leaf counter_slice0_ifg_sec_dec3_sta_undersize_filter4_sta_undersize_pkt_drop_cnt {
      type oc-yang:counter64;
      description
        "Per port RX undersize packet drop - counter for packets that were dropped because they were smaller than 57B.";
    }
    leaf counter_slice0_ifg_sec_dec3_sta_undersize_filter5_sta_undersize_pkt_drop_cnt {
      type oc-yang:counter64;
      description
        "Per port RX undersize packet drop - counter for packets that were dropped because they were smaller than 57B.";
    }
    leaf counter_slice0_ifg_sec_dec3_sta_undersize_filter6_sta_undersize_pkt_drop_cnt {
      type oc-yang:counter64;
      description
        "Per port RX undersize packet drop - counter for packets that were dropped because they were smaller than 57B.";
    }
    leaf counter_slice0_ifg_sec_dec3_sta_undersize_filter7_sta_undersize_pkt_drop_cnt {
      type oc-yang:counter64;
      description
        "Per port RX undersize packet drop - counter for packets that were dropped because they were smaller than 57B.";
    }
    leaf counter_slice1_ifg_sec_dec0_sta_undersize_filter0_sta_undersize_pkt_drop_cnt {
      type oc-yang:counter64;
      description
        "Per port RX undersize packet drop - counter for packets that were dropped because they were smaller than 57B.";
    }
    leaf counter_slice1_ifg_sec_dec0_sta_undersize_filter1_sta_undersize_pkt_drop_cnt {
      type oc-yang:counter64;
      description
        "Per port RX undersize packet drop - counter for packets that were dropped because they were smaller than 57B.";
    }
    leaf counter_slice1_ifg_sec_dec0_sta_undersize_filter2_sta_undersize_pkt_drop_cnt {
      type oc-yang:counter64;
      description
        "Per port RX undersize packet drop - counter for packets that were dropped because they were smaller than 57B.";
    }
    leaf counter_slice1_ifg_sec_dec0_sta_undersize_filter3_sta_undersize_pkt_drop_cnt {
      type oc-yang:counter64;
      description
        "Per port RX undersize packet drop - counter for packets that were dropped because they were smaller than 57B.";
    }
    leaf counter_slice1_ifg_sec_dec0_sta_undersize_filter4_sta_undersize_pkt_drop_cnt {
      type oc-yang:counter64;
      description
        "Per port RX undersize packet drop - counter for packets that were dropped because they were smaller than 57B.";
    }
    leaf counter_slice1_ifg_sec_dec0_sta_undersize_filter5_sta_undersize_pkt_drop_cnt {
      type oc-yang:counter64;
      description
        "Per port RX undersize packet drop - counter for packets that were dropped because they were smaller than 57B.";
    }
    leaf counter_slice1_ifg_sec_dec0_sta_undersize_filter6_sta_undersize_pkt_drop_cnt {
      type oc-yang:counter64;
      description
        "Per port RX undersize packet drop - counter for packets that were dropped because they were smaller than 57B.";
    }
    leaf counter_slice1_ifg_sec_dec0_sta_undersize_filter7_sta_undersize_pkt_drop_cnt {
      type oc-yang:counter64;
      description
        "Per port RX undersize packet drop - counter for packets that were dropped because they were smaller than 57B.";
    }
    leaf counter_slice1_ifg_sec_dec1_sta_undersize_filter0_sta_undersize_pkt_drop_cnt {
      type oc-yang:counter64;
      description
        "Per port RX undersize packet drop - counter for packets that were dropped because they were smaller than 57B.";
    }
    leaf counter_slice1_ifg_sec_dec1_sta_undersize_filter1_sta_undersize_pkt_drop_cnt {
      type oc-yang:counter64;
      description
        "Per port RX undersize packet drop - counter for packets that were dropped because they were smaller than 57B.";
    }
    leaf counter_slice1_ifg_sec_dec1_sta_undersize_filter2_sta_undersize_pkt_drop_cnt {
      type oc-yang:counter64;
      description
        "Per port RX undersize packet drop - counter for packets that were dropped because they were smaller than 57B.";
    }
    leaf counter_slice1_ifg_sec_dec1_sta_undersize_filter3_sta_undersize_pkt_drop_cnt {
      type oc-yang:counter64;
      description
        "Per port RX undersize packet drop - counter for packets that were dropped because they were smaller than 57B.";
    }
    leaf counter_slice1_ifg_sec_dec1_sta_undersize_filter4_sta_undersize_pkt_drop_cnt {
      type oc-yang:counter64;
      description
        "Per port RX undersize packet drop - counter for packets that were dropped because they were smaller than 57B.";
    }
    leaf counter_slice1_ifg_sec_dec1_sta_undersize_filter5_sta_undersize_pkt_drop_cnt {
      type oc-yang:counter64;
      description
        "Per port RX undersize packet drop - counter for packets that were dropped because they were smaller than 57B.";
    }
    leaf counter_slice1_ifg_sec_dec1_sta_undersize_filter6_sta_undersize_pkt_drop_cnt {
      type oc-yang:counter64;
      description
        "Per port RX undersize packet drop - counter for packets that were dropped because they were smaller than 57B.";
    }
    leaf counter_slice1_ifg_sec_dec1_sta_undersize_filter7_sta_undersize_pkt_drop_cnt {
      type oc-yang:counter64;
      description
        "Per port RX undersize packet drop - counter for packets that were dropped because they were smaller than 57B.";
    }
    leaf counter_slice1_ifg_sec_dec2_sta_undersize_filter0_sta_undersize_pkt_drop_cnt {
      type oc-yang:counter64;
      description
        "Per port RX undersize packet drop - counter for packets that were dropped because they were smaller than 57B.";
    }
    leaf counter_slice1_ifg_sec_dec2_sta_undersize_filter1_sta_undersize_pkt_drop_cnt {
      type oc-yang:counter64;
      description
        "Per port RX undersize packet drop - counter for packets that were dropped because they were smaller than 57B.";
    }
    leaf counter_slice1_ifg_sec_dec2_sta_undersize_filter2_sta_undersize_pkt_drop_cnt {
      type oc-yang:counter64;
      description
        "Per port RX undersize packet drop - counter for packets that were dropped because they were smaller than 57B.";
    }
    leaf counter_slice1_ifg_sec_dec2_sta_undersize_filter3_sta_undersize_pkt_drop_cnt {
      type oc-yang:counter64;
      description
        "Per port RX undersize packet drop - counter for packets that were dropped because they were smaller than 57B.";
    }
    leaf counter_slice1_ifg_sec_dec2_sta_undersize_filter4_sta_undersize_pkt_drop_cnt {
      type oc-yang:counter64;
      description
        "Per port RX undersize packet drop - counter for packets that were dropped because they were smaller than 57B.";
    }
    leaf counter_slice1_ifg_sec_dec2_sta_undersize_filter5_sta_undersize_pkt_drop_cnt {
      type oc-yang:counter64;
      description
        "Per port RX undersize packet drop - counter for packets that were dropped because they were smaller than 57B.";
    }
    leaf counter_slice1_ifg_sec_dec2_sta_undersize_filter6_sta_undersize_pkt_drop_cnt {
      type oc-yang:counter64;
      description
        "Per port RX undersize packet drop - counter for packets that were dropped because they were smaller than 57B.";
    }
    leaf counter_slice1_ifg_sec_dec2_sta_undersize_filter7_sta_undersize_pkt_drop_cnt {
      type oc-yang:counter64;
      description
        "Per port RX undersize packet drop - counter for packets that were dropped because they were smaller than 57B.";
    }
    leaf counter_slice1_ifg_sec_dec3_sta_undersize_filter0_sta_undersize_pkt_drop_cnt {
      type oc-yang:counter64;
      description
        "Per port RX undersize packet drop - counter for packets that were dropped because they were smaller than 57B.";
    }
    leaf counter_slice1_ifg_sec_dec3_sta_undersize_filter1_sta_undersize_pkt_drop_cnt {
      type oc-yang:counter64;
      description
        "Per port RX undersize packet drop - counter for packets that were dropped because they were smaller than 57B.";
    }
    leaf counter_slice1_ifg_sec_dec3_sta_undersize_filter2_sta_undersize_pkt_drop_cnt {
      type oc-yang:counter64;
      description
        "Per port RX undersize packet drop - counter for packets that were dropped because they were smaller than 57B.";
    }
    leaf counter_slice1_ifg_sec_dec3_sta_undersize_filter3_sta_undersize_pkt_drop_cnt {
      type oc-yang:counter64;
      description
        "Per port RX undersize packet drop - counter for packets that were dropped because they were smaller than 57B.";
    }
    leaf counter_slice1_ifg_sec_dec3_sta_undersize_filter4_sta_undersize_pkt_drop_cnt {
      type oc-yang:counter64;
      description
        "Per port RX undersize packet drop - counter for packets that were dropped because they were smaller than 57B.";
    }
    leaf counter_slice1_ifg_sec_dec3_sta_undersize_filter5_sta_undersize_pkt_drop_cnt {
      type oc-yang:counter64;
      description
        "Per port RX undersize packet drop - counter for packets that were dropped because they were smaller than 57B.";
    }
    leaf counter_slice1_ifg_sec_dec3_sta_undersize_filter6_sta_undersize_pkt_drop_cnt {
      type oc-yang:counter64;
      description
        "Per port RX undersize packet drop - counter for packets that were dropped because they were smaller than 57B.";
    }
    leaf counter_slice1_ifg_sec_dec3_sta_undersize_filter7_sta_undersize_pkt_drop_cnt {
      type oc-yang:counter64;
      description
        "Per port RX undersize packet drop - counter for packets that were dropped because they were smaller than 57B.";
    }
    leaf counter_slice2_ifg_sec_dec0_sta_undersize_filter0_sta_undersize_pkt_drop_cnt {
      type oc-yang:counter64;
      description
        "Per port RX undersize packet drop - counter for packets that were dropped because they were smaller than 57B.";
    }
    leaf counter_slice2_ifg_sec_dec0_sta_undersize_filter1_sta_undersize_pkt_drop_cnt {
      type oc-yang:counter64;
      description
        "Per port RX undersize packet drop - counter for packets that were dropped because they were smaller than 57B.";
    }
    leaf counter_slice2_ifg_sec_dec0_sta_undersize_filter2_sta_undersize_pkt_drop_cnt {
      type oc-yang:counter64;
      description
        "Per port RX undersize packet drop - counter for packets that were dropped because they were smaller than 57B.";
    }
    leaf counter_slice2_ifg_sec_dec0_sta_undersize_filter3_sta_undersize_pkt_drop_cnt {
      type oc-yang:counter64;
      description
        "Per port RX undersize packet drop - counter for packets that were dropped because they were smaller than 57B.";
    }
    leaf counter_slice2_ifg_sec_dec0_sta_undersize_filter4_sta_undersize_pkt_drop_cnt {
      type oc-yang:counter64;
      description
        "Per port RX undersize packet drop - counter for packets that were dropped because they were smaller than 57B.";
    }
    leaf counter_slice2_ifg_sec_dec0_sta_undersize_filter5_sta_undersize_pkt_drop_cnt {
      type oc-yang:counter64;
      description
        "Per port RX undersize packet drop - counter for packets that were dropped because they were smaller than 57B.";
    }
    leaf counter_slice2_ifg_sec_dec0_sta_undersize_filter6_sta_undersize_pkt_drop_cnt {
      type oc-yang:counter64;
      description
        "Per port RX undersize packet drop - counter for packets that were dropped because they were smaller than 57B.";
    }
    leaf counter_slice2_ifg_sec_dec0_sta_undersize_filter7_sta_undersize_pkt_drop_cnt {
      type oc-yang:counter64;
      description
        "Per port RX undersize packet drop - counter for packets that were dropped because they were smaller than 57B.";
    }
    leaf counter_slice2_ifg_sec_dec1_sta_undersize_filter0_sta_undersize_pkt_drop_cnt {
      type oc-yang:counter64;
      description
        "Per port RX undersize packet drop - counter for packets that were dropped because they were smaller than 57B.";
    }
    leaf counter_slice2_ifg_sec_dec1_sta_undersize_filter1_sta_undersize_pkt_drop_cnt {
      type oc-yang:counter64;
      description
        "Per port RX undersize packet drop - counter for packets that were dropped because they were smaller than 57B.";
    }
    leaf counter_slice2_ifg_sec_dec1_sta_undersize_filter2_sta_undersize_pkt_drop_cnt {
      type oc-yang:counter64;
      description
        "Per port RX undersize packet drop - counter for packets that were dropped because they were smaller than 57B.";
    }
    leaf counter_slice2_ifg_sec_dec1_sta_undersize_filter3_sta_undersize_pkt_drop_cnt {
      type oc-yang:counter64;
      description
        "Per port RX undersize packet drop - counter for packets that were dropped because they were smaller than 57B.";
    }
    leaf counter_slice2_ifg_sec_dec1_sta_undersize_filter4_sta_undersize_pkt_drop_cnt {
      type oc-yang:counter64;
      description
        "Per port RX undersize packet drop - counter for packets that were dropped because they were smaller than 57B.";
    }
    leaf counter_slice2_ifg_sec_dec1_sta_undersize_filter5_sta_undersize_pkt_drop_cnt {
      type oc-yang:counter64;
      description
        "Per port RX undersize packet drop - counter for packets that were dropped because they were smaller than 57B.";
    }
    leaf counter_slice2_ifg_sec_dec1_sta_undersize_filter6_sta_undersize_pkt_drop_cnt {
      type oc-yang:counter64;
      description
        "Per port RX undersize packet drop - counter for packets that were dropped because they were smaller than 57B.";
    }
    leaf counter_slice2_ifg_sec_dec1_sta_undersize_filter7_sta_undersize_pkt_drop_cnt {
      type oc-yang:counter64;
      description
        "Per port RX undersize packet drop - counter for packets that were dropped because they were smaller than 57B.";
    }
    leaf counter_slice2_ifg_sec_dec2_sta_undersize_filter0_sta_undersize_pkt_drop_cnt {
      type oc-yang:counter64;
      description
        "Per port RX undersize packet drop - counter for packets that were dropped because they were smaller than 57B.";
    }
    leaf counter_slice2_ifg_sec_dec2_sta_undersize_filter1_sta_undersize_pkt_drop_cnt {
      type oc-yang:counter64;
      description
        "Per port RX undersize packet drop - counter for packets that were dropped because they were smaller than 57B.";
    }
    leaf counter_slice2_ifg_sec_dec2_sta_undersize_filter2_sta_undersize_pkt_drop_cnt {
      type oc-yang:counter64;
      description
        "Per port RX undersize packet drop - counter for packets that were dropped because they were smaller than 57B.";
    }
    leaf counter_slice2_ifg_sec_dec2_sta_undersize_filter3_sta_undersize_pkt_drop_cnt {
      type oc-yang:counter64;
      description
        "Per port RX undersize packet drop - counter for packets that were dropped because they were smaller than 57B.";
    }
    leaf counter_slice2_ifg_sec_dec2_sta_undersize_filter4_sta_undersize_pkt_drop_cnt {
      type oc-yang:counter64;
      description
        "Per port RX undersize packet drop - counter for packets that were dropped because they were smaller than 57B.";
    }
    leaf counter_slice2_ifg_sec_dec2_sta_undersize_filter5_sta_undersize_pkt_drop_cnt {
      type oc-yang:counter64;
      description
        "Per port RX undersize packet drop - counter for packets that were dropped because they were smaller than 57B.";
    }
    leaf counter_slice2_ifg_sec_dec2_sta_undersize_filter6_sta_undersize_pkt_drop_cnt {
      type oc-yang:counter64;
      description
        "Per port RX undersize packet drop - counter for packets that were dropped because they were smaller than 57B.";
    }
    leaf counter_slice2_ifg_sec_dec2_sta_undersize_filter7_sta_undersize_pkt_drop_cnt {
      type oc-yang:counter64;
      description
        "Per port RX undersize packet drop - counter for packets that were dropped because they were smaller than 57B.";
    }
    leaf counter_slice2_ifg_sec_dec3_sta_undersize_filter0_sta_undersize_pkt_drop_cnt {
      type oc-yang:counter64;
      description
        "Per port RX undersize packet drop - counter for packets that were dropped because they were smaller than 57B.";
    }
    leaf counter_slice2_ifg_sec_dec3_sta_undersize_filter1_sta_undersize_pkt_drop_cnt {
      type oc-yang:counter64;
      description
        "Per port RX undersize packet drop - counter for packets that were dropped because they were smaller than 57B.";
    }
    leaf counter_slice2_ifg_sec_dec3_sta_undersize_filter2_sta_undersize_pkt_drop_cnt {
      type oc-yang:counter64;
      description
        "Per port RX undersize packet drop - counter for packets that were dropped because they were smaller than 57B.";
    }
    leaf counter_slice2_ifg_sec_dec3_sta_undersize_filter3_sta_undersize_pkt_drop_cnt {
      type oc-yang:counter64;
      description
        "Per port RX undersize packet drop - counter for packets that were dropped because they were smaller than 57B.";
    }
    leaf counter_slice2_ifg_sec_dec3_sta_undersize_filter4_sta_undersize_pkt_drop_cnt {
      type oc-yang:counter64;
      description
        "Per port RX undersize packet drop - counter for packets that were dropped because they were smaller than 57B.";
    }
    leaf counter_slice2_ifg_sec_dec3_sta_undersize_filter5_sta_undersize_pkt_drop_cnt {
      type oc-yang:counter64;
      description
        "Per port RX undersize packet drop - counter for packets that were dropped because they were smaller than 57B.";
    }
    leaf counter_slice2_ifg_sec_dec3_sta_undersize_filter6_sta_undersize_pkt_drop_cnt {
      type oc-yang:counter64;
      description
        "Per port RX undersize packet drop - counter for packets that were dropped because they were smaller than 57B.";
    }
    leaf counter_slice2_ifg_sec_dec3_sta_undersize_filter7_sta_undersize_pkt_drop_cnt {
      type oc-yang:counter64;
      description
        "Per port RX undersize packet drop - counter for packets that were dropped because they were smaller than 57B.";
    }
    leaf counter_slice3_ifg_sec_dec0_sta_undersize_filter0_sta_undersize_pkt_drop_cnt {
      type oc-yang:counter64;
      description
        "Per port RX undersize packet drop - counter for packets that were dropped because they were smaller than 57B.";
    }
    leaf counter_slice3_ifg_sec_dec0_sta_undersize_filter1_sta_undersize_pkt_drop_cnt {
      type oc-yang:counter64;
      description
        "Per port RX undersize packet drop - counter for packets that were dropped because they were smaller than 57B.";
    }
    leaf counter_slice3_ifg_sec_dec0_sta_undersize_filter2_sta_undersize_pkt_drop_cnt {
      type oc-yang:counter64;
      description
        "Per port RX undersize packet drop - counter for packets that were dropped because they were smaller than 57B.";
    }
    leaf counter_slice3_ifg_sec_dec0_sta_undersize_filter3_sta_undersize_pkt_drop_cnt {
      type oc-yang:counter64;
      description
        "Per port RX undersize packet drop - counter for packets that were dropped because they were smaller than 57B.";
    }
    leaf counter_slice3_ifg_sec_dec0_sta_undersize_filter4_sta_undersize_pkt_drop_cnt {
      type oc-yang:counter64;
      description
        "Per port RX undersize packet drop - counter for packets that were dropped because they were smaller than 57B.";
    }
    leaf counter_slice3_ifg_sec_dec0_sta_undersize_filter5_sta_undersize_pkt_drop_cnt {
      type oc-yang:counter64;
      description
        "Per port RX undersize packet drop - counter for packets that were dropped because they were smaller than 57B.";
    }
    leaf counter_slice3_ifg_sec_dec0_sta_undersize_filter6_sta_undersize_pkt_drop_cnt {
      type oc-yang:counter64;
      description
        "Per port RX undersize packet drop - counter for packets that were dropped because they were smaller than 57B.";
    }
    leaf counter_slice3_ifg_sec_dec0_sta_undersize_filter7_sta_undersize_pkt_drop_cnt {
      type oc-yang:counter64;
      description
        "Per port RX undersize packet drop - counter for packets that were dropped because they were smaller than 57B.";
    }
    leaf counter_slice3_ifg_sec_dec1_sta_undersize_filter0_sta_undersize_pkt_drop_cnt {
      type oc-yang:counter64;
      description
        "Per port RX undersize packet drop - counter for packets that were dropped because they were smaller than 57B.";
    }
    leaf counter_slice3_ifg_sec_dec1_sta_undersize_filter1_sta_undersize_pkt_drop_cnt {
      type oc-yang:counter64;
      description
        "Per port RX undersize packet drop - counter for packets that were dropped because they were smaller than 57B.";
    }
    leaf counter_slice3_ifg_sec_dec1_sta_undersize_filter2_sta_undersize_pkt_drop_cnt {
      type oc-yang:counter64;
      description
        "Per port RX undersize packet drop - counter for packets that were dropped because they were smaller than 57B.";
    }
    leaf counter_slice3_ifg_sec_dec1_sta_undersize_filter3_sta_undersize_pkt_drop_cnt {
      type oc-yang:counter64;
      description
        "Per port RX undersize packet drop - counter for packets that were dropped because they were smaller than 57B.";
    }
    leaf counter_slice3_ifg_sec_dec1_sta_undersize_filter4_sta_undersize_pkt_drop_cnt {
      type oc-yang:counter64;
      description
        "Per port RX undersize packet drop - counter for packets that were dropped because they were smaller than 57B.";
    }
    leaf counter_slice3_ifg_sec_dec1_sta_undersize_filter5_sta_undersize_pkt_drop_cnt {
      type oc-yang:counter64;
      description
        "Per port RX undersize packet drop - counter for packets that were dropped because they were smaller than 57B.";
    }
    leaf counter_slice3_ifg_sec_dec1_sta_undersize_filter6_sta_undersize_pkt_drop_cnt {
      type oc-yang:counter64;
      description
        "Per port RX undersize packet drop - counter for packets that were dropped because they were smaller than 57B.";
    }
    leaf counter_slice3_ifg_sec_dec1_sta_undersize_filter7_sta_undersize_pkt_drop_cnt {
      type oc-yang:counter64;
      description
        "Per port RX undersize packet drop - counter for packets that were dropped because they were smaller than 57B.";
    }
    leaf counter_slice3_ifg_sec_dec2_sta_undersize_filter0_sta_undersize_pkt_drop_cnt {
      type oc-yang:counter64;
      description
        "Per port RX undersize packet drop - counter for packets that were dropped because they were smaller than 57B.";
    }
    leaf counter_slice3_ifg_sec_dec2_sta_undersize_filter1_sta_undersize_pkt_drop_cnt {
      type oc-yang:counter64;
      description
        "Per port RX undersize packet drop - counter for packets that were dropped because they were smaller than 57B.";
    }
    leaf counter_slice3_ifg_sec_dec2_sta_undersize_filter2_sta_undersize_pkt_drop_cnt {
      type oc-yang:counter64;
      description
        "Per port RX undersize packet drop - counter for packets that were dropped because they were smaller than 57B.";
    }
    leaf counter_slice3_ifg_sec_dec2_sta_undersize_filter3_sta_undersize_pkt_drop_cnt {
      type oc-yang:counter64;
      description
        "Per port RX undersize packet drop - counter for packets that were dropped because they were smaller than 57B.";
    }
    leaf counter_slice3_ifg_sec_dec2_sta_undersize_filter4_sta_undersize_pkt_drop_cnt {
      type oc-yang:counter64;
      description
        "Per port RX undersize packet drop - counter for packets that were dropped because they were smaller than 57B.";
    }
    leaf counter_slice3_ifg_sec_dec2_sta_undersize_filter5_sta_undersize_pkt_drop_cnt {
      type oc-yang:counter64;
      description
        "Per port RX undersize packet drop - counter for packets that were dropped because they were smaller than 57B.";
    }
    leaf counter_slice3_ifg_sec_dec2_sta_undersize_filter6_sta_undersize_pkt_drop_cnt {
      type oc-yang:counter64;
      description
        "Per port RX undersize packet drop - counter for packets that were dropped because they were smaller than 57B.";
    }
    leaf counter_slice3_ifg_sec_dec2_sta_undersize_filter7_sta_undersize_pkt_drop_cnt {
      type oc-yang:counter64;
      description
        "Per port RX undersize packet drop - counter for packets that were dropped because they were smaller than 57B.";
    }
    leaf counter_slice3_ifg_sec_dec3_sta_undersize_filter0_sta_undersize_pkt_drop_cnt {
      type oc-yang:counter64;
      description
        "Per port RX undersize packet drop - counter for packets that were dropped because they were smaller than 57B.";
    }
    leaf counter_slice3_ifg_sec_dec3_sta_undersize_filter1_sta_undersize_pkt_drop_cnt {
      type oc-yang:counter64;
      description
        "Per port RX undersize packet drop - counter for packets that were dropped because they were smaller than 57B.";
    }
    leaf counter_slice3_ifg_sec_dec3_sta_undersize_filter2_sta_undersize_pkt_drop_cnt {
      type oc-yang:counter64;
      description
        "Per port RX undersize packet drop - counter for packets that were dropped because they were smaller than 57B.";
    }
    leaf counter_slice3_ifg_sec_dec3_sta_undersize_filter3_sta_undersize_pkt_drop_cnt {
      type oc-yang:counter64;
      description
        "Per port RX undersize packet drop - counter for packets that were dropped because they were smaller than 57B.";
    }
    leaf counter_slice3_ifg_sec_dec3_sta_undersize_filter4_sta_undersize_pkt_drop_cnt {
      type oc-yang:counter64;
      description
        "Per port RX undersize packet drop - counter for packets that were dropped because they were smaller than 57B.";
    }
    leaf counter_slice3_ifg_sec_dec3_sta_undersize_filter5_sta_undersize_pkt_drop_cnt {
      type oc-yang:counter64;
      description
        "Per port RX undersize packet drop - counter for packets that were dropped because they were smaller than 57B.";
    }
    leaf counter_slice3_ifg_sec_dec3_sta_undersize_filter6_sta_undersize_pkt_drop_cnt {
      type oc-yang:counter64;
      description
        "Per port RX undersize packet drop - counter for packets that were dropped because they were smaller than 57B.";
    }
    leaf counter_slice3_ifg_sec_dec3_sta_undersize_filter7_sta_undersize_pkt_drop_cnt {
      type oc-yang:counter64;
      description
        "Per port RX undersize packet drop - counter for packets that were dropped because they were smaller than 57B.";
    }
    leaf counter_slice4_ifg_sec_dec0_sta_undersize_filter0_sta_undersize_pkt_drop_cnt {
      type oc-yang:counter64;
      description
        "Per port RX undersize packet drop - counter for packets that were dropped because they were smaller than 57B.";
    }
    leaf counter_slice4_ifg_sec_dec0_sta_undersize_filter1_sta_undersize_pkt_drop_cnt {
      type oc-yang:counter64;
      description
        "Per port RX undersize packet drop - counter for packets that were dropped because they were smaller than 57B.";
    }
    leaf counter_slice4_ifg_sec_dec0_sta_undersize_filter2_sta_undersize_pkt_drop_cnt {
      type oc-yang:counter64;
      description
        "Per port RX undersize packet drop - counter for packets that were dropped because they were smaller than 57B.";
    }
    leaf counter_slice4_ifg_sec_dec0_sta_undersize_filter3_sta_undersize_pkt_drop_cnt {
      type oc-yang:counter64;
      description
        "Per port RX undersize packet drop - counter for packets that were dropped because they were smaller than 57B.";
    }
    leaf counter_slice4_ifg_sec_dec0_sta_undersize_filter4_sta_undersize_pkt_drop_cnt {
      type oc-yang:counter64;
      description
        "Per port RX undersize packet drop - counter for packets that were dropped because they were smaller than 57B.";
    }
    leaf counter_slice4_ifg_sec_dec0_sta_undersize_filter5_sta_undersize_pkt_drop_cnt {
      type oc-yang:counter64;
      description
        "Per port RX undersize packet drop - counter for packets that were dropped because they were smaller than 57B.";
    }
    leaf counter_slice4_ifg_sec_dec0_sta_undersize_filter6_sta_undersize_pkt_drop_cnt {
      type oc-yang:counter64;
      description
        "Per port RX undersize packet drop - counter for packets that were dropped because they were smaller than 57B.";
    }
    leaf counter_slice4_ifg_sec_dec0_sta_undersize_filter7_sta_undersize_pkt_drop_cnt {
      type oc-yang:counter64;
      description
        "Per port RX undersize packet drop - counter for packets that were dropped because they were smaller than 57B.";
    }
    leaf counter_slice4_ifg_sec_dec1_sta_undersize_filter0_sta_undersize_pkt_drop_cnt {
      type oc-yang:counter64;
      description
        "Per port RX undersize packet drop - counter for packets that were dropped because they were smaller than 57B.";
    }
    leaf counter_slice4_ifg_sec_dec1_sta_undersize_filter1_sta_undersize_pkt_drop_cnt {
      type oc-yang:counter64;
      description
        "Per port RX undersize packet drop - counter for packets that were dropped because they were smaller than 57B.";
    }
    leaf counter_slice4_ifg_sec_dec1_sta_undersize_filter2_sta_undersize_pkt_drop_cnt {
      type oc-yang:counter64;
      description
        "Per port RX undersize packet drop - counter for packets that were dropped because they were smaller than 57B.";
    }
    leaf counter_slice4_ifg_sec_dec1_sta_undersize_filter3_sta_undersize_pkt_drop_cnt {
      type oc-yang:counter64;
      description
        "Per port RX undersize packet drop - counter for packets that were dropped because they were smaller than 57B.";
    }
    leaf counter_slice4_ifg_sec_dec1_sta_undersize_filter4_sta_undersize_pkt_drop_cnt {
      type oc-yang:counter64;
      description
        "Per port RX undersize packet drop - counter for packets that were dropped because they were smaller than 57B.";
    }
    leaf counter_slice4_ifg_sec_dec1_sta_undersize_filter5_sta_undersize_pkt_drop_cnt {
      type oc-yang:counter64;
      description
        "Per port RX undersize packet drop - counter for packets that were dropped because they were smaller than 57B.";
    }
    leaf counter_slice4_ifg_sec_dec1_sta_undersize_filter6_sta_undersize_pkt_drop_cnt {
      type oc-yang:counter64;
      description
        "Per port RX undersize packet drop - counter for packets that were dropped because they were smaller than 57B.";
    }
    leaf counter_slice4_ifg_sec_dec1_sta_undersize_filter7_sta_undersize_pkt_drop_cnt {
      type oc-yang:counter64;
      description
        "Per port RX undersize packet drop - counter for packets that were dropped because they were smaller than 57B.";
    }
    leaf counter_slice4_ifg_sec_dec2_sta_undersize_filter0_sta_undersize_pkt_drop_cnt {
      type oc-yang:counter64;
      description
        "Per port RX undersize packet drop - counter for packets that were dropped because they were smaller than 57B.";
    }
    leaf counter_slice4_ifg_sec_dec2_sta_undersize_filter1_sta_undersize_pkt_drop_cnt {
      type oc-yang:counter64;
      description
        "Per port RX undersize packet drop - counter for packets that were dropped because they were smaller than 57B.";
    }
    leaf counter_slice4_ifg_sec_dec2_sta_undersize_filter2_sta_undersize_pkt_drop_cnt {
      type oc-yang:counter64;
      description
        "Per port RX undersize packet drop - counter for packets that were dropped because they were smaller than 57B.";
    }
    leaf counter_slice4_ifg_sec_dec2_sta_undersize_filter3_sta_undersize_pkt_drop_cnt {
      type oc-yang:counter64;
      description
        "Per port RX undersize packet drop - counter for packets that were dropped because they were smaller than 57B.";
    }
    leaf counter_slice4_ifg_sec_dec2_sta_undersize_filter4_sta_undersize_pkt_drop_cnt {
      type oc-yang:counter64;
      description
        "Per port RX undersize packet drop - counter for packets that were dropped because they were smaller than 57B.";
    }
    leaf counter_slice4_ifg_sec_dec2_sta_undersize_filter5_sta_undersize_pkt_drop_cnt {
      type oc-yang:counter64;
      description
        "Per port RX undersize packet drop - counter for packets that were dropped because they were smaller than 57B.";
    }
    leaf counter_slice4_ifg_sec_dec2_sta_undersize_filter6_sta_undersize_pkt_drop_cnt {
      type oc-yang:counter64;
      description
        "Per port RX undersize packet drop - counter for packets that were dropped because they were smaller than 57B.";
    }
    leaf counter_slice4_ifg_sec_dec2_sta_undersize_filter7_sta_undersize_pkt_drop_cnt {
      type oc-yang:counter64;
      description
        "Per port RX undersize packet drop - counter for packets that were dropped because they were smaller than 57B.";
    }
    leaf counter_slice4_ifg_sec_dec3_sta_undersize_filter0_sta_undersize_pkt_drop_cnt {
      type oc-yang:counter64;
      description
        "Per port RX undersize packet drop - counter for packets that were dropped because they were smaller than 57B.";
    }
    leaf counter_slice4_ifg_sec_dec3_sta_undersize_filter1_sta_undersize_pkt_drop_cnt {
      type oc-yang:counter64;
      description
        "Per port RX undersize packet drop - counter for packets that were dropped because they were smaller than 57B.";
    }
    leaf counter_slice4_ifg_sec_dec3_sta_undersize_filter2_sta_undersize_pkt_drop_cnt {
      type oc-yang:counter64;
      description
        "Per port RX undersize packet drop - counter for packets that were dropped because they were smaller than 57B.";
    }
    leaf counter_slice4_ifg_sec_dec3_sta_undersize_filter3_sta_undersize_pkt_drop_cnt {
      type oc-yang:counter64;
      description
        "Per port RX undersize packet drop - counter for packets that were dropped because they were smaller than 57B.";
    }
    leaf counter_slice4_ifg_sec_dec3_sta_undersize_filter4_sta_undersize_pkt_drop_cnt {
      type oc-yang:counter64;
      description
        "Per port RX undersize packet drop - counter for packets that were dropped because they were smaller than 57B.";
    }
    leaf counter_slice4_ifg_sec_dec3_sta_undersize_filter5_sta_undersize_pkt_drop_cnt {
      type oc-yang:counter64;
      description
        "Per port RX undersize packet drop - counter for packets that were dropped because they were smaller than 57B.";
    }
    leaf counter_slice4_ifg_sec_dec3_sta_undersize_filter6_sta_undersize_pkt_drop_cnt {
      type oc-yang:counter64;
      description
        "Per port RX undersize packet drop - counter for packets that were dropped because they were smaller than 57B.";
    }
    leaf counter_slice4_ifg_sec_dec3_sta_undersize_filter7_sta_undersize_pkt_drop_cnt {
      type oc-yang:counter64;
      description
        "Per port RX undersize packet drop - counter for packets that were dropped because they were smaller than 57B.";
    }
    leaf counter_slice5_ifg_sec_dec0_sta_undersize_filter0_sta_undersize_pkt_drop_cnt {
      type oc-yang:counter64;
      description
        "Per port RX undersize packet drop - counter for packets that were dropped because they were smaller than 57B.";
    }
    leaf counter_slice5_ifg_sec_dec0_sta_undersize_filter1_sta_undersize_pkt_drop_cnt {
      type oc-yang:counter64;
      description
        "Per port RX undersize packet drop - counter for packets that were dropped because they were smaller than 57B.";
    }
    leaf counter_slice5_ifg_sec_dec0_sta_undersize_filter2_sta_undersize_pkt_drop_cnt {
      type oc-yang:counter64;
      description
        "Per port RX undersize packet drop - counter for packets that were dropped because they were smaller than 57B.";
    }
    leaf counter_slice5_ifg_sec_dec0_sta_undersize_filter3_sta_undersize_pkt_drop_cnt {
      type oc-yang:counter64;
      description
        "Per port RX undersize packet drop - counter for packets that were dropped because they were smaller than 57B.";
    }
    leaf counter_slice5_ifg_sec_dec0_sta_undersize_filter4_sta_undersize_pkt_drop_cnt {
      type oc-yang:counter64;
      description
        "Per port RX undersize packet drop - counter for packets that were dropped because they were smaller than 57B.";
    }
    leaf counter_slice5_ifg_sec_dec0_sta_undersize_filter5_sta_undersize_pkt_drop_cnt {
      type oc-yang:counter64;
      description
        "Per port RX undersize packet drop - counter for packets that were dropped because they were smaller than 57B.";
    }
    leaf counter_slice5_ifg_sec_dec0_sta_undersize_filter6_sta_undersize_pkt_drop_cnt {
      type oc-yang:counter64;
      description
        "Per port RX undersize packet drop - counter for packets that were dropped because they were smaller than 57B.";
    }
    leaf counter_slice5_ifg_sec_dec0_sta_undersize_filter7_sta_undersize_pkt_drop_cnt {
      type oc-yang:counter64;
      description
        "Per port RX undersize packet drop - counter for packets that were dropped because they were smaller than 57B.";
    }
    leaf counter_slice5_ifg_sec_dec1_sta_undersize_filter0_sta_undersize_pkt_drop_cnt {
      type oc-yang:counter64;
      description
        "Per port RX undersize packet drop - counter for packets that were dropped because they were smaller than 57B.";
    }
    leaf counter_slice5_ifg_sec_dec1_sta_undersize_filter1_sta_undersize_pkt_drop_cnt {
      type oc-yang:counter64;
      description
        "Per port RX undersize packet drop - counter for packets that were dropped because they were smaller than 57B.";
    }
    leaf counter_slice5_ifg_sec_dec1_sta_undersize_filter2_sta_undersize_pkt_drop_cnt {
      type oc-yang:counter64;
      description
        "Per port RX undersize packet drop - counter for packets that were dropped because they were smaller than 57B.";
    }
    leaf counter_slice5_ifg_sec_dec1_sta_undersize_filter3_sta_undersize_pkt_drop_cnt {
      type oc-yang:counter64;
      description
        "Per port RX undersize packet drop - counter for packets that were dropped because they were smaller than 57B.";
    }
    leaf counter_slice5_ifg_sec_dec1_sta_undersize_filter4_sta_undersize_pkt_drop_cnt {
      type oc-yang:counter64;
      description
        "Per port RX undersize packet drop - counter for packets that were dropped because they were smaller than 57B.";
    }
    leaf counter_slice5_ifg_sec_dec1_sta_undersize_filter5_sta_undersize_pkt_drop_cnt {
      type oc-yang:counter64;
      description
        "Per port RX undersize packet drop - counter for packets that were dropped because they were smaller than 57B.";
    }
    leaf counter_slice5_ifg_sec_dec1_sta_undersize_filter6_sta_undersize_pkt_drop_cnt {
      type oc-yang:counter64;
      description
        "Per port RX undersize packet drop - counter for packets that were dropped because they were smaller than 57B.";
    }
    leaf counter_slice5_ifg_sec_dec1_sta_undersize_filter7_sta_undersize_pkt_drop_cnt {
      type oc-yang:counter64;
      description
        "Per port RX undersize packet drop - counter for packets that were dropped because they were smaller than 57B.";
    }
    leaf counter_slice5_ifg_sec_dec2_sta_undersize_filter0_sta_undersize_pkt_drop_cnt {
      type oc-yang:counter64;
      description
        "Per port RX undersize packet drop - counter for packets that were dropped because they were smaller than 57B.";
    }
    leaf counter_slice5_ifg_sec_dec2_sta_undersize_filter1_sta_undersize_pkt_drop_cnt {
      type oc-yang:counter64;
      description
        "Per port RX undersize packet drop - counter for packets that were dropped because they were smaller than 57B.";
    }
    leaf counter_slice5_ifg_sec_dec2_sta_undersize_filter2_sta_undersize_pkt_drop_cnt {
      type oc-yang:counter64;
      description
        "Per port RX undersize packet drop - counter for packets that were dropped because they were smaller than 57B.";
    }
    leaf counter_slice5_ifg_sec_dec2_sta_undersize_filter3_sta_undersize_pkt_drop_cnt {
      type oc-yang:counter64;
      description
        "Per port RX undersize packet drop - counter for packets that were dropped because they were smaller than 57B.";
    }
    leaf counter_slice5_ifg_sec_dec2_sta_undersize_filter4_sta_undersize_pkt_drop_cnt {
      type oc-yang:counter64;
      description
        "Per port RX undersize packet drop - counter for packets that were dropped because they were smaller than 57B.";
    }
    leaf counter_slice5_ifg_sec_dec2_sta_undersize_filter5_sta_undersize_pkt_drop_cnt {
      type oc-yang:counter64;
      description
        "Per port RX undersize packet drop - counter for packets that were dropped because they were smaller than 57B.";
    }
    leaf counter_slice5_ifg_sec_dec2_sta_undersize_filter6_sta_undersize_pkt_drop_cnt {
      type oc-yang:counter64;
      description
        "Per port RX undersize packet drop - counter for packets that were dropped because they were smaller than 57B.";
    }
    leaf counter_slice5_ifg_sec_dec2_sta_undersize_filter7_sta_undersize_pkt_drop_cnt {
      type oc-yang:counter64;
      description
        "Per port RX undersize packet drop - counter for packets that were dropped because they were smaller than 57B.";
    }
    leaf counter_slice5_ifg_sec_dec3_sta_undersize_filter0_sta_undersize_pkt_drop_cnt {
      type oc-yang:counter64;
      description
        "Per port RX undersize packet drop - counter for packets that were dropped because they were smaller than 57B.";
    }
    leaf counter_slice5_ifg_sec_dec3_sta_undersize_filter1_sta_undersize_pkt_drop_cnt {
      type oc-yang:counter64;
      description
        "Per port RX undersize packet drop - counter for packets that were dropped because they were smaller than 57B.";
    }
    leaf counter_slice5_ifg_sec_dec3_sta_undersize_filter2_sta_undersize_pkt_drop_cnt {
      type oc-yang:counter64;
      description
        "Per port RX undersize packet drop - counter for packets that were dropped because they were smaller than 57B.";
    }
    leaf counter_slice5_ifg_sec_dec3_sta_undersize_filter3_sta_undersize_pkt_drop_cnt {
      type oc-yang:counter64;
      description
        "Per port RX undersize packet drop - counter for packets that were dropped because they were smaller than 57B.";
    }
    leaf counter_slice5_ifg_sec_dec3_sta_undersize_filter4_sta_undersize_pkt_drop_cnt {
      type oc-yang:counter64;
      description
        "Per port RX undersize packet drop - counter for packets that were dropped because they were smaller than 57B.";
    }
    leaf counter_slice5_ifg_sec_dec3_sta_undersize_filter5_sta_undersize_pkt_drop_cnt {
      type oc-yang:counter64;
      description
        "Per port RX undersize packet drop - counter for packets that were dropped because they were smaller than 57B.";
    }
    leaf counter_slice5_ifg_sec_dec3_sta_undersize_filter6_sta_undersize_pkt_drop_cnt {
      type oc-yang:counter64;
      description
        "Per port RX undersize packet drop - counter for packets that were dropped because they were smaller than 57B.";
    }
    leaf counter_slice5_ifg_sec_dec3_sta_undersize_filter7_sta_undersize_pkt_drop_cnt {
      type oc-yang:counter64;
      description
        "Per port RX undersize packet drop - counter for packets that were dropped because they were smaller than 57B.";
    }
    leaf counter_slice6_ifg_sec_dec0_sta_undersize_filter0_sta_undersize_pkt_drop_cnt {
      type oc-yang:counter64;
      description
        "Per port RX undersize packet drop - counter for packets that were dropped because they were smaller than 57B.";
    }
    leaf counter_slice6_ifg_sec_dec0_sta_undersize_filter1_sta_undersize_pkt_drop_cnt {
      type oc-yang:counter64;
      description
        "Per port RX undersize packet drop - counter for packets that were dropped because they were smaller than 57B.";
    }
    leaf counter_slice6_ifg_sec_dec0_sta_undersize_filter2_sta_undersize_pkt_drop_cnt {
      type oc-yang:counter64;
      description
        "Per port RX undersize packet drop - counter for packets that were dropped because they were smaller than 57B.";
    }
    leaf counter_slice6_ifg_sec_dec0_sta_undersize_filter3_sta_undersize_pkt_drop_cnt {
      type oc-yang:counter64;
      description
        "Per port RX undersize packet drop - counter for packets that were dropped because they were smaller than 57B.";
    }
    leaf counter_slice6_ifg_sec_dec0_sta_undersize_filter4_sta_undersize_pkt_drop_cnt {
      type oc-yang:counter64;
      description
        "Per port RX undersize packet drop - counter for packets that were dropped because they were smaller than 57B.";
    }
    leaf counter_slice6_ifg_sec_dec0_sta_undersize_filter5_sta_undersize_pkt_drop_cnt {
      type oc-yang:counter64;
      description
        "Per port RX undersize packet drop - counter for packets that were dropped because they were smaller than 57B.";
    }
    leaf counter_slice6_ifg_sec_dec0_sta_undersize_filter6_sta_undersize_pkt_drop_cnt {
      type oc-yang:counter64;
      description
        "Per port RX undersize packet drop - counter for packets that were dropped because they were smaller than 57B.";
    }
    leaf counter_slice6_ifg_sec_dec0_sta_undersize_filter7_sta_undersize_pkt_drop_cnt {
      type oc-yang:counter64;
      description
        "Per port RX undersize packet drop - counter for packets that were dropped because they were smaller than 57B.";
    }
    leaf counter_slice6_ifg_sec_dec1_sta_undersize_filter0_sta_undersize_pkt_drop_cnt {
      type oc-yang:counter64;
      description
        "Per port RX undersize packet drop - counter for packets that were dropped because they were smaller than 57B.";
    }
    leaf counter_slice6_ifg_sec_dec1_sta_undersize_filter1_sta_undersize_pkt_drop_cnt {
      type oc-yang:counter64;
      description
        "Per port RX undersize packet drop - counter for packets that were dropped because they were smaller than 57B.";
    }
    leaf counter_slice6_ifg_sec_dec1_sta_undersize_filter2_sta_undersize_pkt_drop_cnt {
      type oc-yang:counter64;
      description
        "Per port RX undersize packet drop - counter for packets that were dropped because they were smaller than 57B.";
    }
    leaf counter_slice6_ifg_sec_dec1_sta_undersize_filter3_sta_undersize_pkt_drop_cnt {
      type oc-yang:counter64;
      description
        "Per port RX undersize packet drop - counter for packets that were dropped because they were smaller than 57B.";
    }
    leaf counter_slice6_ifg_sec_dec1_sta_undersize_filter4_sta_undersize_pkt_drop_cnt {
      type oc-yang:counter64;
      description
        "Per port RX undersize packet drop - counter for packets that were dropped because they were smaller than 57B.";
    }
    leaf counter_slice6_ifg_sec_dec1_sta_undersize_filter5_sta_undersize_pkt_drop_cnt {
      type oc-yang:counter64;
      description
        "Per port RX undersize packet drop - counter for packets that were dropped because they were smaller than 57B.";
    }
    leaf counter_slice6_ifg_sec_dec1_sta_undersize_filter6_sta_undersize_pkt_drop_cnt {
      type oc-yang:counter64;
      description
        "Per port RX undersize packet drop - counter for packets that were dropped because they were smaller than 57B.";
    }
    leaf counter_slice6_ifg_sec_dec1_sta_undersize_filter7_sta_undersize_pkt_drop_cnt {
      type oc-yang:counter64;
      description
        "Per port RX undersize packet drop - counter for packets that were dropped because they were smaller than 57B.";
    }
    leaf counter_slice6_ifg_sec_dec2_sta_undersize_filter0_sta_undersize_pkt_drop_cnt {
      type oc-yang:counter64;
      description
        "Per port RX undersize packet drop - counter for packets that were dropped because they were smaller than 57B.";
    }
    leaf counter_slice6_ifg_sec_dec2_sta_undersize_filter1_sta_undersize_pkt_drop_cnt {
      type oc-yang:counter64;
      description
        "Per port RX undersize packet drop - counter for packets that were dropped because they were smaller than 57B.";
    }
    leaf counter_slice6_ifg_sec_dec2_sta_undersize_filter2_sta_undersize_pkt_drop_cnt {
      type oc-yang:counter64;
      description
        "Per port RX undersize packet drop - counter for packets that were dropped because they were smaller than 57B.";
    }
    leaf counter_slice6_ifg_sec_dec2_sta_undersize_filter3_sta_undersize_pkt_drop_cnt {
      type oc-yang:counter64;
      description
        "Per port RX undersize packet drop - counter for packets that were dropped because they were smaller than 57B.";
    }
    leaf counter_slice6_ifg_sec_dec2_sta_undersize_filter4_sta_undersize_pkt_drop_cnt {
      type oc-yang:counter64;
      description
        "Per port RX undersize packet drop - counter for packets that were dropped because they were smaller than 57B.";
    }
    leaf counter_slice6_ifg_sec_dec2_sta_undersize_filter5_sta_undersize_pkt_drop_cnt {
      type oc-yang:counter64;
      description
        "Per port RX undersize packet drop - counter for packets that were dropped because they were smaller than 57B.";
    }
    leaf counter_slice6_ifg_sec_dec2_sta_undersize_filter6_sta_undersize_pkt_drop_cnt {
      type oc-yang:counter64;
      description
        "Per port RX undersize packet drop - counter for packets that were dropped because they were smaller than 57B.";
    }
    leaf counter_slice6_ifg_sec_dec2_sta_undersize_filter7_sta_undersize_pkt_drop_cnt {
      type oc-yang:counter64;
      description
        "Per port RX undersize packet drop - counter for packets that were dropped because they were smaller than 57B.";
    }
    leaf counter_slice6_ifg_sec_dec3_sta_undersize_filter0_sta_undersize_pkt_drop_cnt {
      type oc-yang:counter64;
      description
        "Per port RX undersize packet drop - counter for packets that were dropped because they were smaller than 57B.";
    }
    leaf counter_slice6_ifg_sec_dec3_sta_undersize_filter1_sta_undersize_pkt_drop_cnt {
      type oc-yang:counter64;
      description
        "Per port RX undersize packet drop - counter for packets that were dropped because they were smaller than 57B.";
    }
    leaf counter_slice6_ifg_sec_dec3_sta_undersize_filter2_sta_undersize_pkt_drop_cnt {
      type oc-yang:counter64;
      description
        "Per port RX undersize packet drop - counter for packets that were dropped because they were smaller than 57B.";
    }
    leaf counter_slice6_ifg_sec_dec3_sta_undersize_filter3_sta_undersize_pkt_drop_cnt {
      type oc-yang:counter64;
      description
        "Per port RX undersize packet drop - counter for packets that were dropped because they were smaller than 57B.";
    }
    leaf counter_slice6_ifg_sec_dec3_sta_undersize_filter4_sta_undersize_pkt_drop_cnt {
      type oc-yang:counter64;
      description
        "Per port RX undersize packet drop - counter for packets that were dropped because they were smaller than 57B.";
    }
    leaf counter_slice6_ifg_sec_dec3_sta_undersize_filter5_sta_undersize_pkt_drop_cnt {
      type oc-yang:counter64;
      description
        "Per port RX undersize packet drop - counter for packets that were dropped because they were smaller than 57B.";
    }
    leaf counter_slice6_ifg_sec_dec3_sta_undersize_filter6_sta_undersize_pkt_drop_cnt {
      type oc-yang:counter64;
      description
        "Per port RX undersize packet drop - counter for packets that were dropped because they were smaller than 57B.";
    }
    leaf counter_slice6_ifg_sec_dec3_sta_undersize_filter7_sta_undersize_pkt_drop_cnt {
      type oc-yang:counter64;
      description
        "Per port RX undersize packet drop - counter for packets that were dropped because they were smaller than 57B.";
    }
    leaf counter_slice7_ifg_sec_dec0_sta_undersize_filter0_sta_undersize_pkt_drop_cnt {
      type oc-yang:counter64;
      description
        "Per port RX undersize packet drop - counter for packets that were dropped because they were smaller than 57B.";
    }
    leaf counter_slice7_ifg_sec_dec0_sta_undersize_filter1_sta_undersize_pkt_drop_cnt {
      type oc-yang:counter64;
      description
        "Per port RX undersize packet drop - counter for packets that were dropped because they were smaller than 57B.";
    }
    leaf counter_slice7_ifg_sec_dec0_sta_undersize_filter2_sta_undersize_pkt_drop_cnt {
      type oc-yang:counter64;
      description
        "Per port RX undersize packet drop - counter for packets that were dropped because they were smaller than 57B.";
    }
    leaf counter_slice7_ifg_sec_dec0_sta_undersize_filter3_sta_undersize_pkt_drop_cnt {
      type oc-yang:counter64;
      description
        "Per port RX undersize packet drop - counter for packets that were dropped because they were smaller than 57B.";
    }
    leaf counter_slice7_ifg_sec_dec0_sta_undersize_filter4_sta_undersize_pkt_drop_cnt {
      type oc-yang:counter64;
      description
        "Per port RX undersize packet drop - counter for packets that were dropped because they were smaller than 57B.";
    }
    leaf counter_slice7_ifg_sec_dec0_sta_undersize_filter5_sta_undersize_pkt_drop_cnt {
      type oc-yang:counter64;
      description
        "Per port RX undersize packet drop - counter for packets that were dropped because they were smaller than 57B.";
    }
    leaf counter_slice7_ifg_sec_dec0_sta_undersize_filter6_sta_undersize_pkt_drop_cnt {
      type oc-yang:counter64;
      description
        "Per port RX undersize packet drop - counter for packets that were dropped because they were smaller than 57B.";
    }
    leaf counter_slice7_ifg_sec_dec0_sta_undersize_filter7_sta_undersize_pkt_drop_cnt {
      type oc-yang:counter64;
      description
        "Per port RX undersize packet drop - counter for packets that were dropped because they were smaller than 57B.";
    }
    leaf counter_slice7_ifg_sec_dec1_sta_undersize_filter0_sta_undersize_pkt_drop_cnt {
      type oc-yang:counter64;
      description
        "Per port RX undersize packet drop - counter for packets that were dropped because they were smaller than 57B.";
    }
    leaf counter_slice7_ifg_sec_dec1_sta_undersize_filter1_sta_undersize_pkt_drop_cnt {
      type oc-yang:counter64;
      description
        "Per port RX undersize packet drop - counter for packets that were dropped because they were smaller than 57B.";
    }
    leaf counter_slice7_ifg_sec_dec1_sta_undersize_filter2_sta_undersize_pkt_drop_cnt {
      type oc-yang:counter64;
      description
        "Per port RX undersize packet drop - counter for packets that were dropped because they were smaller than 57B.";
    }
    leaf counter_slice7_ifg_sec_dec1_sta_undersize_filter3_sta_undersize_pkt_drop_cnt {
      type oc-yang:counter64;
      description
        "Per port RX undersize packet drop - counter for packets that were dropped because they were smaller than 57B.";
    }
    leaf counter_slice7_ifg_sec_dec1_sta_undersize_filter4_sta_undersize_pkt_drop_cnt {
      type oc-yang:counter64;
      description
        "Per port RX undersize packet drop - counter for packets that were dropped because they were smaller than 57B.";
    }
    leaf counter_slice7_ifg_sec_dec1_sta_undersize_filter5_sta_undersize_pkt_drop_cnt {
      type oc-yang:counter64;
      description
        "Per port RX undersize packet drop - counter for packets that were dropped because they were smaller than 57B.";
    }
    leaf counter_slice7_ifg_sec_dec1_sta_undersize_filter6_sta_undersize_pkt_drop_cnt {
      type oc-yang:counter64;
      description
        "Per port RX undersize packet drop - counter for packets that were dropped because they were smaller than 57B.";
    }
    leaf counter_slice7_ifg_sec_dec1_sta_undersize_filter7_sta_undersize_pkt_drop_cnt {
      type oc-yang:counter64;
      description
        "Per port RX undersize packet drop - counter for packets that were dropped because they were smaller than 57B.";
    }
    leaf counter_slice7_ifg_sec_dec2_sta_undersize_filter0_sta_undersize_pkt_drop_cnt {
      type oc-yang:counter64;
      description
        "Per port RX undersize packet drop - counter for packets that were dropped because they were smaller than 57B.";
    }
    leaf counter_slice7_ifg_sec_dec2_sta_undersize_filter1_sta_undersize_pkt_drop_cnt {
      type oc-yang:counter64;
      description
        "Per port RX undersize packet drop - counter for packets that were dropped because they were smaller than 57B.";
    }
    leaf counter_slice7_ifg_sec_dec2_sta_undersize_filter2_sta_undersize_pkt_drop_cnt {
      type oc-yang:counter64;
      description
        "Per port RX undersize packet drop - counter for packets that were dropped because they were smaller than 57B.";
    }
    leaf counter_slice7_ifg_sec_dec2_sta_undersize_filter3_sta_undersize_pkt_drop_cnt {
      type oc-yang:counter64;
      description
        "Per port RX undersize packet drop - counter for packets that were dropped because they were smaller than 57B.";
    }
    leaf counter_slice7_ifg_sec_dec2_sta_undersize_filter4_sta_undersize_pkt_drop_cnt {
      type oc-yang:counter64;
      description
        "Per port RX undersize packet drop - counter for packets that were dropped because they were smaller than 57B.";
    }
    leaf counter_slice7_ifg_sec_dec2_sta_undersize_filter5_sta_undersize_pkt_drop_cnt {
      type oc-yang:counter64;
      description
        "Per port RX undersize packet drop - counter for packets that were dropped because they were smaller than 57B.";
    }
    leaf counter_slice7_ifg_sec_dec2_sta_undersize_filter6_sta_undersize_pkt_drop_cnt {
      type oc-yang:counter64;
      description
        "Per port RX undersize packet drop - counter for packets that were dropped because they were smaller than 57B.";
    }
    leaf counter_slice7_ifg_sec_dec2_sta_undersize_filter7_sta_undersize_pkt_drop_cnt {
      type oc-yang:counter64;
      description
        "Per port RX undersize packet drop - counter for packets that were dropped because they were smaller than 57B.";
    }
    leaf counter_slice7_ifg_sec_dec3_sta_undersize_filter0_sta_undersize_pkt_drop_cnt {
      type oc-yang:counter64;
      description
        "Per port RX undersize packet drop - counter for packets that were dropped because they were smaller than 57B.";
    }
    leaf counter_slice7_ifg_sec_dec3_sta_undersize_filter1_sta_undersize_pkt_drop_cnt {
      type oc-yang:counter64;
      description
        "Per port RX undersize packet drop - counter for packets that were dropped because they were smaller than 57B.";
    }
    leaf counter_slice7_ifg_sec_dec3_sta_undersize_filter2_sta_undersize_pkt_drop_cnt {
      type oc-yang:counter64;
      description
        "Per port RX undersize packet drop - counter for packets that were dropped because they were smaller than 57B.";
    }
    leaf counter_slice7_ifg_sec_dec3_sta_undersize_filter3_sta_undersize_pkt_drop_cnt {
      type oc-yang:counter64;
      description
        "Per port RX undersize packet drop - counter for packets that were dropped because they were smaller than 57B.";
    }
    leaf counter_slice7_ifg_sec_dec3_sta_undersize_filter4_sta_undersize_pkt_drop_cnt {
      type oc-yang:counter64;
      description
        "Per port RX undersize packet drop - counter for packets that were dropped because they were smaller than 57B.";
    }
    leaf counter_slice7_ifg_sec_dec3_sta_undersize_filter5_sta_undersize_pkt_drop_cnt {
      type oc-yang:counter64;
      description
        "Per port RX undersize packet drop - counter for packets that were dropped because they were smaller than 57B.";
    }
    leaf counter_slice7_ifg_sec_dec3_sta_undersize_filter6_sta_undersize_pkt_drop_cnt {
      type oc-yang:counter64;
      description
        "Per port RX undersize packet drop - counter for packets that were dropped because they were smaller than 57B.";
    }
    leaf counter_slice7_ifg_sec_dec3_sta_undersize_filter7_sta_undersize_pkt_drop_cnt {
      type oc-yang:counter64;
      description
        "Per port RX undersize packet drop - counter for packets that were dropped because they were smaller than 57B.";
    }
    leaf counter_slice8_ifg_sec_dec0_sta_undersize_filter0_sta_undersize_pkt_drop_cnt {
      type oc-yang:counter64;
      description
        "Per port RX undersize packet drop - counter for packets that were dropped because they were smaller than 57B.";
    }
    leaf counter_slice8_ifg_sec_dec0_sta_undersize_filter1_sta_undersize_pkt_drop_cnt {
      type oc-yang:counter64;
      description
        "Per port RX undersize packet drop - counter for packets that were dropped because they were smaller than 57B.";
    }
    leaf counter_slice8_ifg_sec_dec0_sta_undersize_filter2_sta_undersize_pkt_drop_cnt {
      type oc-yang:counter64;
      description
        "Per port RX undersize packet drop - counter for packets that were dropped because they were smaller than 57B.";
    }
    leaf counter_slice8_ifg_sec_dec0_sta_undersize_filter3_sta_undersize_pkt_drop_cnt {
      type oc-yang:counter64;
      description
        "Per port RX undersize packet drop - counter for packets that were dropped because they were smaller than 57B.";
    }
    leaf counter_slice8_ifg_sec_dec0_sta_undersize_filter4_sta_undersize_pkt_drop_cnt {
      type oc-yang:counter64;
      description
        "Per port RX undersize packet drop - counter for packets that were dropped because they were smaller than 57B.";
    }
    leaf counter_slice8_ifg_sec_dec0_sta_undersize_filter5_sta_undersize_pkt_drop_cnt {
      type oc-yang:counter64;
      description
        "Per port RX undersize packet drop - counter for packets that were dropped because they were smaller than 57B.";
    }
    leaf counter_slice8_ifg_sec_dec0_sta_undersize_filter6_sta_undersize_pkt_drop_cnt {
      type oc-yang:counter64;
      description
        "Per port RX undersize packet drop - counter for packets that were dropped because they were smaller than 57B.";
    }
    leaf counter_slice8_ifg_sec_dec0_sta_undersize_filter7_sta_undersize_pkt_drop_cnt {
      type oc-yang:counter64;
      description
        "Per port RX undersize packet drop - counter for packets that were dropped because they were smaller than 57B.";
    }
    leaf counter_slice8_ifg_sec_dec1_sta_undersize_filter0_sta_undersize_pkt_drop_cnt {
      type oc-yang:counter64;
      description
        "Per port RX undersize packet drop - counter for packets that were dropped because they were smaller than 57B.";
    }
    leaf counter_slice8_ifg_sec_dec1_sta_undersize_filter1_sta_undersize_pkt_drop_cnt {
      type oc-yang:counter64;
      description
        "Per port RX undersize packet drop - counter for packets that were dropped because they were smaller than 57B.";
    }
    leaf counter_slice8_ifg_sec_dec1_sta_undersize_filter2_sta_undersize_pkt_drop_cnt {
      type oc-yang:counter64;
      description
        "Per port RX undersize packet drop - counter for packets that were dropped because they were smaller than 57B.";
    }
    leaf counter_slice8_ifg_sec_dec1_sta_undersize_filter3_sta_undersize_pkt_drop_cnt {
      type oc-yang:counter64;
      description
        "Per port RX undersize packet drop - counter for packets that were dropped because they were smaller than 57B.";
    }
    leaf counter_slice8_ifg_sec_dec1_sta_undersize_filter4_sta_undersize_pkt_drop_cnt {
      type oc-yang:counter64;
      description
        "Per port RX undersize packet drop - counter for packets that were dropped because they were smaller than 57B.";
    }
    leaf counter_slice8_ifg_sec_dec1_sta_undersize_filter5_sta_undersize_pkt_drop_cnt {
      type oc-yang:counter64;
      description
        "Per port RX undersize packet drop - counter for packets that were dropped because they were smaller than 57B.";
    }
    leaf counter_slice8_ifg_sec_dec1_sta_undersize_filter6_sta_undersize_pkt_drop_cnt {
      type oc-yang:counter64;
      description
        "Per port RX undersize packet drop - counter for packets that were dropped because they were smaller than 57B.";
    }
    leaf counter_slice8_ifg_sec_dec1_sta_undersize_filter7_sta_undersize_pkt_drop_cnt {
      type oc-yang:counter64;
      description
        "Per port RX undersize packet drop - counter for packets that were dropped because they were smaller than 57B.";
    }
    leaf counter_slice8_ifg_sec_dec2_sta_undersize_filter0_sta_undersize_pkt_drop_cnt {
      type oc-yang:counter64;
      description
        "Per port RX undersize packet drop - counter for packets that were dropped because they were smaller than 57B.";
    }
    leaf counter_slice8_ifg_sec_dec2_sta_undersize_filter1_sta_undersize_pkt_drop_cnt {
      type oc-yang:counter64;
      description
        "Per port RX undersize packet drop - counter for packets that were dropped because they were smaller than 57B.";
    }
    leaf counter_slice8_ifg_sec_dec2_sta_undersize_filter2_sta_undersize_pkt_drop_cnt {
      type oc-yang:counter64;
      description
        "Per port RX undersize packet drop - counter for packets that were dropped because they were smaller than 57B.";
    }
    leaf counter_slice8_ifg_sec_dec2_sta_undersize_filter3_sta_undersize_pkt_drop_cnt {
      type oc-yang:counter64;
      description
        "Per port RX undersize packet drop - counter for packets that were dropped because they were smaller than 57B.";
    }
    leaf counter_slice8_ifg_sec_dec2_sta_undersize_filter4_sta_undersize_pkt_drop_cnt {
      type oc-yang:counter64;
      description
        "Per port RX undersize packet drop - counter for packets that were dropped because they were smaller than 57B.";
    }
    leaf counter_slice8_ifg_sec_dec2_sta_undersize_filter5_sta_undersize_pkt_drop_cnt {
      type oc-yang:counter64;
      description
        "Per port RX undersize packet drop - counter for packets that were dropped because they were smaller than 57B.";
    }
    leaf counter_slice8_ifg_sec_dec2_sta_undersize_filter6_sta_undersize_pkt_drop_cnt {
      type oc-yang:counter64;
      description
        "Per port RX undersize packet drop - counter for packets that were dropped because they were smaller than 57B.";
    }
    leaf counter_slice8_ifg_sec_dec2_sta_undersize_filter7_sta_undersize_pkt_drop_cnt {
      type oc-yang:counter64;
      description
        "Per port RX undersize packet drop - counter for packets that were dropped because they were smaller than 57B.";
    }
    leaf counter_slice8_ifg_sec_dec3_sta_undersize_filter0_sta_undersize_pkt_drop_cnt {
      type oc-yang:counter64;
      description
        "Per port RX undersize packet drop - counter for packets that were dropped because they were smaller than 57B.";
    }
    leaf counter_slice8_ifg_sec_dec3_sta_undersize_filter1_sta_undersize_pkt_drop_cnt {
      type oc-yang:counter64;
      description
        "Per port RX undersize packet drop - counter for packets that were dropped because they were smaller than 57B.";
    }
    leaf counter_slice8_ifg_sec_dec3_sta_undersize_filter2_sta_undersize_pkt_drop_cnt {
      type oc-yang:counter64;
      description
        "Per port RX undersize packet drop - counter for packets that were dropped because they were smaller than 57B.";
    }
    leaf counter_slice8_ifg_sec_dec3_sta_undersize_filter3_sta_undersize_pkt_drop_cnt {
      type oc-yang:counter64;
      description
        "Per port RX undersize packet drop - counter for packets that were dropped because they were smaller than 57B.";
    }
    leaf counter_slice8_ifg_sec_dec3_sta_undersize_filter4_sta_undersize_pkt_drop_cnt {
      type oc-yang:counter64;
      description
        "Per port RX undersize packet drop - counter for packets that were dropped because they were smaller than 57B.";
    }
    leaf counter_slice8_ifg_sec_dec3_sta_undersize_filter5_sta_undersize_pkt_drop_cnt {
      type oc-yang:counter64;
      description
        "Per port RX undersize packet drop - counter for packets that were dropped because they were smaller than 57B.";
    }
    leaf counter_slice8_ifg_sec_dec3_sta_undersize_filter6_sta_undersize_pkt_drop_cnt {
      type oc-yang:counter64;
      description
        "Per port RX undersize packet drop - counter for packets that were dropped because they were smaller than 57B.";
    }
    leaf counter_slice8_ifg_sec_dec3_sta_undersize_filter7_sta_undersize_pkt_drop_cnt {
      type oc-yang:counter64;
      description
        "Per port RX undersize packet drop - counter for packets that were dropped because they were smaller than 57B.";
    }
    leaf counter_slice9_ifg_sec_dec0_sta_undersize_filter0_sta_undersize_pkt_drop_cnt {
      type oc-yang:counter64;
      description
        "Per port RX undersize packet drop - counter for packets that were dropped because they were smaller than 57B.";
    }
    leaf counter_slice9_ifg_sec_dec0_sta_undersize_filter1_sta_undersize_pkt_drop_cnt {
      type oc-yang:counter64;
      description
        "Per port RX undersize packet drop - counter for packets that were dropped because they were smaller than 57B.";
    }
    leaf counter_slice9_ifg_sec_dec0_sta_undersize_filter2_sta_undersize_pkt_drop_cnt {
      type oc-yang:counter64;
      description
        "Per port RX undersize packet drop - counter for packets that were dropped because they were smaller than 57B.";
    }
    leaf counter_slice9_ifg_sec_dec0_sta_undersize_filter3_sta_undersize_pkt_drop_cnt {
      type oc-yang:counter64;
      description
        "Per port RX undersize packet drop - counter for packets that were dropped because they were smaller than 57B.";
    }
    leaf counter_slice9_ifg_sec_dec0_sta_undersize_filter4_sta_undersize_pkt_drop_cnt {
      type oc-yang:counter64;
      description
        "Per port RX undersize packet drop - counter for packets that were dropped because they were smaller than 57B.";
    }
    leaf counter_slice9_ifg_sec_dec0_sta_undersize_filter5_sta_undersize_pkt_drop_cnt {
      type oc-yang:counter64;
      description
        "Per port RX undersize packet drop - counter for packets that were dropped because they were smaller than 57B.";
    }
    leaf counter_slice9_ifg_sec_dec0_sta_undersize_filter6_sta_undersize_pkt_drop_cnt {
      type oc-yang:counter64;
      description
        "Per port RX undersize packet drop - counter for packets that were dropped because they were smaller than 57B.";
    }
    leaf counter_slice9_ifg_sec_dec0_sta_undersize_filter7_sta_undersize_pkt_drop_cnt {
      type oc-yang:counter64;
      description
        "Per port RX undersize packet drop - counter for packets that were dropped because they were smaller than 57B.";
    }
    leaf counter_slice9_ifg_sec_dec1_sta_undersize_filter0_sta_undersize_pkt_drop_cnt {
      type oc-yang:counter64;
      description
        "Per port RX undersize packet drop - counter for packets that were dropped because they were smaller than 57B.";
    }
    leaf counter_slice9_ifg_sec_dec1_sta_undersize_filter1_sta_undersize_pkt_drop_cnt {
      type oc-yang:counter64;
      description
        "Per port RX undersize packet drop - counter for packets that were dropped because they were smaller than 57B.";
    }
    leaf counter_slice9_ifg_sec_dec1_sta_undersize_filter2_sta_undersize_pkt_drop_cnt {
      type oc-yang:counter64;
      description
        "Per port RX undersize packet drop - counter for packets that were dropped because they were smaller than 57B.";
    }
    leaf counter_slice9_ifg_sec_dec1_sta_undersize_filter3_sta_undersize_pkt_drop_cnt {
      type oc-yang:counter64;
      description
        "Per port RX undersize packet drop - counter for packets that were dropped because they were smaller than 57B.";
    }
    leaf counter_slice9_ifg_sec_dec1_sta_undersize_filter4_sta_undersize_pkt_drop_cnt {
      type oc-yang:counter64;
      description
        "Per port RX undersize packet drop - counter for packets that were dropped because they were smaller than 57B.";
    }
    leaf counter_slice9_ifg_sec_dec1_sta_undersize_filter5_sta_undersize_pkt_drop_cnt {
      type oc-yang:counter64;
      description
        "Per port RX undersize packet drop - counter for packets that were dropped because they were smaller than 57B.";
    }
    leaf counter_slice9_ifg_sec_dec1_sta_undersize_filter6_sta_undersize_pkt_drop_cnt {
      type oc-yang:counter64;
      description
        "Per port RX undersize packet drop - counter for packets that were dropped because they were smaller than 57B.";
    }
    leaf counter_slice9_ifg_sec_dec1_sta_undersize_filter7_sta_undersize_pkt_drop_cnt {
      type oc-yang:counter64;
      description
        "Per port RX undersize packet drop - counter for packets that were dropped because they were smaller than 57B.";
    }
    leaf counter_slice9_ifg_sec_dec2_sta_undersize_filter0_sta_undersize_pkt_drop_cnt {
      type oc-yang:counter64;
      description
        "Per port RX undersize packet drop - counter for packets that were dropped because they were smaller than 57B.";
    }
    leaf counter_slice9_ifg_sec_dec2_sta_undersize_filter1_sta_undersize_pkt_drop_cnt {
      type oc-yang:counter64;
      description
        "Per port RX undersize packet drop - counter for packets that were dropped because they were smaller than 57B.";
    }
    leaf counter_slice9_ifg_sec_dec2_sta_undersize_filter2_sta_undersize_pkt_drop_cnt {
      type oc-yang:counter64;
      description
        "Per port RX undersize packet drop - counter for packets that were dropped because they were smaller than 57B.";
    }
    leaf counter_slice9_ifg_sec_dec2_sta_undersize_filter3_sta_undersize_pkt_drop_cnt {
      type oc-yang:counter64;
      description
        "Per port RX undersize packet drop - counter for packets that were dropped because they were smaller than 57B.";
    }
    leaf counter_slice9_ifg_sec_dec2_sta_undersize_filter4_sta_undersize_pkt_drop_cnt {
      type oc-yang:counter64;
      description
        "Per port RX undersize packet drop - counter for packets that were dropped because they were smaller than 57B.";
    }
    leaf counter_slice9_ifg_sec_dec2_sta_undersize_filter5_sta_undersize_pkt_drop_cnt {
      type oc-yang:counter64;
      description
        "Per port RX undersize packet drop - counter for packets that were dropped because they were smaller than 57B.";
    }
    leaf counter_slice9_ifg_sec_dec2_sta_undersize_filter6_sta_undersize_pkt_drop_cnt {
      type oc-yang:counter64;
      description
        "Per port RX undersize packet drop - counter for packets that were dropped because they were smaller than 57B.";
    }
    leaf counter_slice9_ifg_sec_dec2_sta_undersize_filter7_sta_undersize_pkt_drop_cnt {
      type oc-yang:counter64;
      description
        "Per port RX undersize packet drop - counter for packets that were dropped because they were smaller than 57B.";
    }
    leaf counter_slice9_ifg_sec_dec3_sta_undersize_filter0_sta_undersize_pkt_drop_cnt {
      type oc-yang:counter64;
      description
        "Per port RX undersize packet drop - counter for packets that were dropped because they were smaller than 57B.";
    }
    leaf counter_slice9_ifg_sec_dec3_sta_undersize_filter1_sta_undersize_pkt_drop_cnt {
      type oc-yang:counter64;
      description
        "Per port RX undersize packet drop - counter for packets that were dropped because they were smaller than 57B.";
    }
    leaf counter_slice9_ifg_sec_dec3_sta_undersize_filter2_sta_undersize_pkt_drop_cnt {
      type oc-yang:counter64;
      description
        "Per port RX undersize packet drop - counter for packets that were dropped because they were smaller than 57B.";
    }
    leaf counter_slice9_ifg_sec_dec3_sta_undersize_filter3_sta_undersize_pkt_drop_cnt {
      type oc-yang:counter64;
      description
        "Per port RX undersize packet drop - counter for packets that were dropped because they were smaller than 57B.";
    }
    leaf counter_slice9_ifg_sec_dec3_sta_undersize_filter4_sta_undersize_pkt_drop_cnt {
      type oc-yang:counter64;
      description
        "Per port RX undersize packet drop - counter for packets that were dropped because they were smaller than 57B.";
    }
    leaf counter_slice9_ifg_sec_dec3_sta_undersize_filter5_sta_undersize_pkt_drop_cnt {
      type oc-yang:counter64;
      description
        "Per port RX undersize packet drop - counter for packets that were dropped because they were smaller than 57B.";
    }
    leaf counter_slice9_ifg_sec_dec3_sta_undersize_filter6_sta_undersize_pkt_drop_cnt {
      type oc-yang:counter64;
      description
        "Per port RX undersize packet drop - counter for packets that were dropped because they were smaller than 57B.";
    }
    leaf counter_slice9_ifg_sec_dec3_sta_undersize_filter7_sta_undersize_pkt_drop_cnt {
      type oc-yang:counter64;
      description
        "Per port RX undersize packet drop - counter for packets that were dropped because they were smaller than 57B.";
    }
    leaf counter_slice10_ifg_sec_dec0_sta_undersize_filter0_sta_undersize_pkt_drop_cnt {
      type oc-yang:counter64;
      description
        "Per port RX undersize packet drop - counter for packets that were dropped because they were smaller than 57B.";
    }
    leaf counter_slice10_ifg_sec_dec0_sta_undersize_filter1_sta_undersize_pkt_drop_cnt {
      type oc-yang:counter64;
      description
        "Per port RX undersize packet drop - counter for packets that were dropped because they were smaller than 57B.";
    }
    leaf counter_slice10_ifg_sec_dec0_sta_undersize_filter2_sta_undersize_pkt_drop_cnt {
      type oc-yang:counter64;
      description
        "Per port RX undersize packet drop - counter for packets that were dropped because they were smaller than 57B.";
    }
    leaf counter_slice10_ifg_sec_dec0_sta_undersize_filter3_sta_undersize_pkt_drop_cnt {
      type oc-yang:counter64;
      description
        "Per port RX undersize packet drop - counter for packets that were dropped because they were smaller than 57B.";
    }
    leaf counter_slice10_ifg_sec_dec0_sta_undersize_filter4_sta_undersize_pkt_drop_cnt {
      type oc-yang:counter64;
      description
        "Per port RX undersize packet drop - counter for packets that were dropped because they were smaller than 57B.";
    }
    leaf counter_slice10_ifg_sec_dec0_sta_undersize_filter5_sta_undersize_pkt_drop_cnt {
      type oc-yang:counter64;
      description
        "Per port RX undersize packet drop - counter for packets that were dropped because they were smaller than 57B.";
    }
    leaf counter_slice10_ifg_sec_dec0_sta_undersize_filter6_sta_undersize_pkt_drop_cnt {
      type oc-yang:counter64;
      description
        "Per port RX undersize packet drop - counter for packets that were dropped because they were smaller than 57B.";
    }
    leaf counter_slice10_ifg_sec_dec0_sta_undersize_filter7_sta_undersize_pkt_drop_cnt {
      type oc-yang:counter64;
      description
        "Per port RX undersize packet drop - counter for packets that were dropped because they were smaller than 57B.";
    }
    leaf counter_slice10_ifg_sec_dec1_sta_undersize_filter0_sta_undersize_pkt_drop_cnt {
      type oc-yang:counter64;
      description
        "Per port RX undersize packet drop - counter for packets that were dropped because they were smaller than 57B.";
    }
    leaf counter_slice10_ifg_sec_dec1_sta_undersize_filter1_sta_undersize_pkt_drop_cnt {
      type oc-yang:counter64;
      description
        "Per port RX undersize packet drop - counter for packets that were dropped because they were smaller than 57B.";
    }
    leaf counter_slice10_ifg_sec_dec1_sta_undersize_filter2_sta_undersize_pkt_drop_cnt {
      type oc-yang:counter64;
      description
        "Per port RX undersize packet drop - counter for packets that were dropped because they were smaller than 57B.";
    }
    leaf counter_slice10_ifg_sec_dec1_sta_undersize_filter3_sta_undersize_pkt_drop_cnt {
      type oc-yang:counter64;
      description
        "Per port RX undersize packet drop - counter for packets that were dropped because they were smaller than 57B.";
    }
    leaf counter_slice10_ifg_sec_dec1_sta_undersize_filter4_sta_undersize_pkt_drop_cnt {
      type oc-yang:counter64;
      description
        "Per port RX undersize packet drop - counter for packets that were dropped because they were smaller than 57B.";
    }
    leaf counter_slice10_ifg_sec_dec1_sta_undersize_filter5_sta_undersize_pkt_drop_cnt {
      type oc-yang:counter64;
      description
        "Per port RX undersize packet drop - counter for packets that were dropped because they were smaller than 57B.";
    }
    leaf counter_slice10_ifg_sec_dec1_sta_undersize_filter6_sta_undersize_pkt_drop_cnt {
      type oc-yang:counter64;
      description
        "Per port RX undersize packet drop - counter for packets that were dropped because they were smaller than 57B.";
    }
    leaf counter_slice10_ifg_sec_dec1_sta_undersize_filter7_sta_undersize_pkt_drop_cnt {
      type oc-yang:counter64;
      description
        "Per port RX undersize packet drop - counter for packets that were dropped because they were smaller than 57B.";
    }
    leaf counter_slice10_ifg_sec_dec2_sta_undersize_filter0_sta_undersize_pkt_drop_cnt {
      type oc-yang:counter64;
      description
        "Per port RX undersize packet drop - counter for packets that were dropped because they were smaller than 57B.";
    }
    leaf counter_slice10_ifg_sec_dec2_sta_undersize_filter1_sta_undersize_pkt_drop_cnt {
      type oc-yang:counter64;
      description
        "Per port RX undersize packet drop - counter for packets that were dropped because they were smaller than 57B.";
    }
    leaf counter_slice10_ifg_sec_dec2_sta_undersize_filter2_sta_undersize_pkt_drop_cnt {
      type oc-yang:counter64;
      description
        "Per port RX undersize packet drop - counter for packets that were dropped because they were smaller than 57B.";
    }
    leaf counter_slice10_ifg_sec_dec2_sta_undersize_filter3_sta_undersize_pkt_drop_cnt {
      type oc-yang:counter64;
      description
        "Per port RX undersize packet drop - counter for packets that were dropped because they were smaller than 57B.";
    }
    leaf counter_slice10_ifg_sec_dec2_sta_undersize_filter4_sta_undersize_pkt_drop_cnt {
      type oc-yang:counter64;
      description
        "Per port RX undersize packet drop - counter for packets that were dropped because they were smaller than 57B.";
    }
    leaf counter_slice10_ifg_sec_dec2_sta_undersize_filter5_sta_undersize_pkt_drop_cnt {
      type oc-yang:counter64;
      description
        "Per port RX undersize packet drop - counter for packets that were dropped because they were smaller than 57B.";
    }
    leaf counter_slice10_ifg_sec_dec2_sta_undersize_filter6_sta_undersize_pkt_drop_cnt {
      type oc-yang:counter64;
      description
        "Per port RX undersize packet drop - counter for packets that were dropped because they were smaller than 57B.";
    }
    leaf counter_slice10_ifg_sec_dec2_sta_undersize_filter7_sta_undersize_pkt_drop_cnt {
      type oc-yang:counter64;
      description
        "Per port RX undersize packet drop - counter for packets that were dropped because they were smaller than 57B.";
    }
    leaf counter_slice10_ifg_sec_dec3_sta_undersize_filter0_sta_undersize_pkt_drop_cnt {
      type oc-yang:counter64;
      description
        "Per port RX undersize packet drop - counter for packets that were dropped because they were smaller than 57B.";
    }
    leaf counter_slice10_ifg_sec_dec3_sta_undersize_filter1_sta_undersize_pkt_drop_cnt {
      type oc-yang:counter64;
      description
        "Per port RX undersize packet drop - counter for packets that were dropped because they were smaller than 57B.";
    }
    leaf counter_slice10_ifg_sec_dec3_sta_undersize_filter2_sta_undersize_pkt_drop_cnt {
      type oc-yang:counter64;
      description
        "Per port RX undersize packet drop - counter for packets that were dropped because they were smaller than 57B.";
    }
    leaf counter_slice10_ifg_sec_dec3_sta_undersize_filter3_sta_undersize_pkt_drop_cnt {
      type oc-yang:counter64;
      description
        "Per port RX undersize packet drop - counter for packets that were dropped because they were smaller than 57B.";
    }
    leaf counter_slice10_ifg_sec_dec3_sta_undersize_filter4_sta_undersize_pkt_drop_cnt {
      type oc-yang:counter64;
      description
        "Per port RX undersize packet drop - counter for packets that were dropped because they were smaller than 57B.";
    }
    leaf counter_slice10_ifg_sec_dec3_sta_undersize_filter5_sta_undersize_pkt_drop_cnt {
      type oc-yang:counter64;
      description
        "Per port RX undersize packet drop - counter for packets that were dropped because they were smaller than 57B.";
    }
    leaf counter_slice10_ifg_sec_dec3_sta_undersize_filter6_sta_undersize_pkt_drop_cnt {
      type oc-yang:counter64;
      description
        "Per port RX undersize packet drop - counter for packets that were dropped because they were smaller than 57B.";
    }
    leaf counter_slice10_ifg_sec_dec3_sta_undersize_filter7_sta_undersize_pkt_drop_cnt {
      type oc-yang:counter64;
      description
        "Per port RX undersize packet drop - counter for packets that were dropped because they were smaller than 57B.";
    }
    leaf counter_slice11_ifg_sec_dec0_sta_undersize_filter0_sta_undersize_pkt_drop_cnt {
      type oc-yang:counter64;
      description
        "Per port RX undersize packet drop - counter for packets that were dropped because they were smaller than 57B.";
    }
    leaf counter_slice11_ifg_sec_dec0_sta_undersize_filter1_sta_undersize_pkt_drop_cnt {
      type oc-yang:counter64;
      description
        "Per port RX undersize packet drop - counter for packets that were dropped because they were smaller than 57B.";
    }
    leaf counter_slice11_ifg_sec_dec0_sta_undersize_filter2_sta_undersize_pkt_drop_cnt {
      type oc-yang:counter64;
      description
        "Per port RX undersize packet drop - counter for packets that were dropped because they were smaller than 57B.";
    }
    leaf counter_slice11_ifg_sec_dec0_sta_undersize_filter3_sta_undersize_pkt_drop_cnt {
      type oc-yang:counter64;
      description
        "Per port RX undersize packet drop - counter for packets that were dropped because they were smaller than 57B.";
    }
    leaf counter_slice11_ifg_sec_dec0_sta_undersize_filter4_sta_undersize_pkt_drop_cnt {
      type oc-yang:counter64;
      description
        "Per port RX undersize packet drop - counter for packets that were dropped because they were smaller than 57B.";
    }
    leaf counter_slice11_ifg_sec_dec0_sta_undersize_filter5_sta_undersize_pkt_drop_cnt {
      type oc-yang:counter64;
      description
        "Per port RX undersize packet drop - counter for packets that were dropped because they were smaller than 57B.";
    }
    leaf counter_slice11_ifg_sec_dec0_sta_undersize_filter6_sta_undersize_pkt_drop_cnt {
      type oc-yang:counter64;
      description
        "Per port RX undersize packet drop - counter for packets that were dropped because they were smaller than 57B.";
    }
    leaf counter_slice11_ifg_sec_dec0_sta_undersize_filter7_sta_undersize_pkt_drop_cnt {
      type oc-yang:counter64;
      description
        "Per port RX undersize packet drop - counter for packets that were dropped because they were smaller than 57B.";
    }
    leaf counter_slice11_ifg_sec_dec1_sta_undersize_filter0_sta_undersize_pkt_drop_cnt {
      type oc-yang:counter64;
      description
        "Per port RX undersize packet drop - counter for packets that were dropped because they were smaller than 57B.";
    }
    leaf counter_slice11_ifg_sec_dec1_sta_undersize_filter1_sta_undersize_pkt_drop_cnt {
      type oc-yang:counter64;
      description
        "Per port RX undersize packet drop - counter for packets that were dropped because they were smaller than 57B.";
    }
    leaf counter_slice11_ifg_sec_dec1_sta_undersize_filter2_sta_undersize_pkt_drop_cnt {
      type oc-yang:counter64;
      description
        "Per port RX undersize packet drop - counter for packets that were dropped because they were smaller than 57B.";
    }
    leaf counter_slice11_ifg_sec_dec1_sta_undersize_filter3_sta_undersize_pkt_drop_cnt {
      type oc-yang:counter64;
      description
        "Per port RX undersize packet drop - counter for packets that were dropped because they were smaller than 57B.";
    }
    leaf counter_slice11_ifg_sec_dec1_sta_undersize_filter4_sta_undersize_pkt_drop_cnt {
      type oc-yang:counter64;
      description
        "Per port RX undersize packet drop - counter for packets that were dropped because they were smaller than 57B.";
    }
    leaf counter_slice11_ifg_sec_dec1_sta_undersize_filter5_sta_undersize_pkt_drop_cnt {
      type oc-yang:counter64;
      description
        "Per port RX undersize packet drop - counter for packets that were dropped because they were smaller than 57B.";
    }
    leaf counter_slice11_ifg_sec_dec1_sta_undersize_filter6_sta_undersize_pkt_drop_cnt {
      type oc-yang:counter64;
      description
        "Per port RX undersize packet drop - counter for packets that were dropped because they were smaller than 57B.";
    }
    leaf counter_slice11_ifg_sec_dec1_sta_undersize_filter7_sta_undersize_pkt_drop_cnt {
      type oc-yang:counter64;
      description
        "Per port RX undersize packet drop - counter for packets that were dropped because they were smaller than 57B.";
    }
    leaf counter_slice11_ifg_sec_dec2_sta_undersize_filter0_sta_undersize_pkt_drop_cnt {
      type oc-yang:counter64;
      description
        "Per port RX undersize packet drop - counter for packets that were dropped because they were smaller than 57B.";
    }
    leaf counter_slice11_ifg_sec_dec2_sta_undersize_filter1_sta_undersize_pkt_drop_cnt {
      type oc-yang:counter64;
      description
        "Per port RX undersize packet drop - counter for packets that were dropped because they were smaller than 57B.";
    }
    leaf counter_slice11_ifg_sec_dec2_sta_undersize_filter2_sta_undersize_pkt_drop_cnt {
      type oc-yang:counter64;
      description
        "Per port RX undersize packet drop - counter for packets that were dropped because they were smaller than 57B.";
    }
    leaf counter_slice11_ifg_sec_dec2_sta_undersize_filter3_sta_undersize_pkt_drop_cnt {
      type oc-yang:counter64;
      description
        "Per port RX undersize packet drop - counter for packets that were dropped because they were smaller than 57B.";
    }
    leaf counter_slice11_ifg_sec_dec2_sta_undersize_filter4_sta_undersize_pkt_drop_cnt {
      type oc-yang:counter64;
      description
        "Per port RX undersize packet drop - counter for packets that were dropped because they were smaller than 57B.";
    }
    leaf counter_slice11_ifg_sec_dec2_sta_undersize_filter5_sta_undersize_pkt_drop_cnt {
      type oc-yang:counter64;
      description
        "Per port RX undersize packet drop - counter for packets that were dropped because they were smaller than 57B.";
    }
    leaf counter_slice11_ifg_sec_dec2_sta_undersize_filter6_sta_undersize_pkt_drop_cnt {
      type oc-yang:counter64;
      description
        "Per port RX undersize packet drop - counter for packets that were dropped because they were smaller than 57B.";
    }
    leaf counter_slice11_ifg_sec_dec2_sta_undersize_filter7_sta_undersize_pkt_drop_cnt {
      type oc-yang:counter64;
      description
        "Per port RX undersize packet drop - counter for packets that were dropped because they were smaller than 57B.";
    }
    leaf counter_slice11_ifg_sec_dec3_sta_undersize_filter0_sta_undersize_pkt_drop_cnt {
      type oc-yang:counter64;
      description
        "Per port RX undersize packet drop - counter for packets that were dropped because they were smaller than 57B.";
    }
    leaf counter_slice11_ifg_sec_dec3_sta_undersize_filter1_sta_undersize_pkt_drop_cnt {
      type oc-yang:counter64;
      description
        "Per port RX undersize packet drop - counter for packets that were dropped because they were smaller than 57B.";
    }
    leaf counter_slice11_ifg_sec_dec3_sta_undersize_filter2_sta_undersize_pkt_drop_cnt {
      type oc-yang:counter64;
      description
        "Per port RX undersize packet drop - counter for packets that were dropped because they were smaller than 57B.";
    }
    leaf counter_slice11_ifg_sec_dec3_sta_undersize_filter3_sta_undersize_pkt_drop_cnt {
      type oc-yang:counter64;
      description
        "Per port RX undersize packet drop - counter for packets that were dropped because they were smaller than 57B.";
    }
    leaf counter_slice11_ifg_sec_dec3_sta_undersize_filter4_sta_undersize_pkt_drop_cnt {
      type oc-yang:counter64;
      description
        "Per port RX undersize packet drop - counter for packets that were dropped because they were smaller than 57B.";
    }
    leaf counter_slice11_ifg_sec_dec3_sta_undersize_filter5_sta_undersize_pkt_drop_cnt {
      type oc-yang:counter64;
      description
        "Per port RX undersize packet drop - counter for packets that were dropped because they were smaller than 57B.";
    }
    leaf counter_slice11_ifg_sec_dec3_sta_undersize_filter6_sta_undersize_pkt_drop_cnt {
      type oc-yang:counter64;
      description
        "Per port RX undersize packet drop - counter for packets that were dropped because they were smaller than 57B.";
    }
    leaf counter_slice11_ifg_sec_dec3_sta_undersize_filter7_sta_undersize_pkt_drop_cnt {
      type oc-yang:counter64;
      description
        "Per port RX undersize packet drop - counter for packets that were dropped because they were smaller than 57B.";
    }
    leaf counter_slice12_ifg_sec_dec0_sta_undersize_filter0_sta_undersize_pkt_drop_cnt {
      type oc-yang:counter64;
      description
        "Per port RX undersize packet drop - counter for packets that were dropped because they were smaller than 57B.";
    }
    leaf counter_slice12_ifg_sec_dec0_sta_undersize_filter1_sta_undersize_pkt_drop_cnt {
      type oc-yang:counter64;
      description
        "Per port RX undersize packet drop - counter for packets that were dropped because they were smaller than 57B.";
    }
    leaf counter_slice12_ifg_sec_dec0_sta_undersize_filter2_sta_undersize_pkt_drop_cnt {
      type oc-yang:counter64;
      description
        "Per port RX undersize packet drop - counter for packets that were dropped because they were smaller than 57B.";
    }
    leaf counter_slice12_ifg_sec_dec0_sta_undersize_filter3_sta_undersize_pkt_drop_cnt {
      type oc-yang:counter64;
      description
        "Per port RX undersize packet drop - counter for packets that were dropped because they were smaller than 57B.";
    }
    leaf counter_slice12_ifg_sec_dec0_sta_undersize_filter4_sta_undersize_pkt_drop_cnt {
      type oc-yang:counter64;
      description
        "Per port RX undersize packet drop - counter for packets that were dropped because they were smaller than 57B.";
    }
    leaf counter_slice12_ifg_sec_dec0_sta_undersize_filter5_sta_undersize_pkt_drop_cnt {
      type oc-yang:counter64;
      description
        "Per port RX undersize packet drop - counter for packets that were dropped because they were smaller than 57B.";
    }
    leaf counter_slice12_ifg_sec_dec0_sta_undersize_filter6_sta_undersize_pkt_drop_cnt {
      type oc-yang:counter64;
      description
        "Per port RX undersize packet drop - counter for packets that were dropped because they were smaller than 57B.";
    }
    leaf counter_slice12_ifg_sec_dec0_sta_undersize_filter7_sta_undersize_pkt_drop_cnt {
      type oc-yang:counter64;
      description
        "Per port RX undersize packet drop - counter for packets that were dropped because they were smaller than 57B.";
    }
    leaf counter_slice12_ifg_sec_dec1_sta_undersize_filter0_sta_undersize_pkt_drop_cnt {
      type oc-yang:counter64;
      description
        "Per port RX undersize packet drop - counter for packets that were dropped because they were smaller than 57B.";
    }
    leaf counter_slice12_ifg_sec_dec1_sta_undersize_filter1_sta_undersize_pkt_drop_cnt {
      type oc-yang:counter64;
      description
        "Per port RX undersize packet drop - counter for packets that were dropped because they were smaller than 57B.";
    }
    leaf counter_slice12_ifg_sec_dec1_sta_undersize_filter2_sta_undersize_pkt_drop_cnt {
      type oc-yang:counter64;
      description
        "Per port RX undersize packet drop - counter for packets that were dropped because they were smaller than 57B.";
    }
    leaf counter_slice12_ifg_sec_dec1_sta_undersize_filter3_sta_undersize_pkt_drop_cnt {
      type oc-yang:counter64;
      description
        "Per port RX undersize packet drop - counter for packets that were dropped because they were smaller than 57B.";
    }
    leaf counter_slice12_ifg_sec_dec1_sta_undersize_filter4_sta_undersize_pkt_drop_cnt {
      type oc-yang:counter64;
      description
        "Per port RX undersize packet drop - counter for packets that were dropped because they were smaller than 57B.";
    }
    leaf counter_slice12_ifg_sec_dec1_sta_undersize_filter5_sta_undersize_pkt_drop_cnt {
      type oc-yang:counter64;
      description
        "Per port RX undersize packet drop - counter for packets that were dropped because they were smaller than 57B.";
    }
    leaf counter_slice12_ifg_sec_dec1_sta_undersize_filter6_sta_undersize_pkt_drop_cnt {
      type oc-yang:counter64;
      description
        "Per port RX undersize packet drop - counter for packets that were dropped because they were smaller than 57B.";
    }
    leaf counter_slice12_ifg_sec_dec1_sta_undersize_filter7_sta_undersize_pkt_drop_cnt {
      type oc-yang:counter64;
      description
        "Per port RX undersize packet drop - counter for packets that were dropped because they were smaller than 57B.";
    }
    leaf counter_slice12_ifg_sec_dec2_sta_undersize_filter0_sta_undersize_pkt_drop_cnt {
      type oc-yang:counter64;
      description
        "Per port RX undersize packet drop - counter for packets that were dropped because they were smaller than 57B.";
    }
    leaf counter_slice12_ifg_sec_dec2_sta_undersize_filter1_sta_undersize_pkt_drop_cnt {
      type oc-yang:counter64;
      description
        "Per port RX undersize packet drop - counter for packets that were dropped because they were smaller than 57B.";
    }
    leaf counter_slice12_ifg_sec_dec2_sta_undersize_filter2_sta_undersize_pkt_drop_cnt {
      type oc-yang:counter64;
      description
        "Per port RX undersize packet drop - counter for packets that were dropped because they were smaller than 57B.";
    }
    leaf counter_slice12_ifg_sec_dec2_sta_undersize_filter3_sta_undersize_pkt_drop_cnt {
      type oc-yang:counter64;
      description
        "Per port RX undersize packet drop - counter for packets that were dropped because they were smaller than 57B.";
    }
    leaf counter_slice12_ifg_sec_dec2_sta_undersize_filter4_sta_undersize_pkt_drop_cnt {
      type oc-yang:counter64;
      description
        "Per port RX undersize packet drop - counter for packets that were dropped because they were smaller than 57B.";
    }
    leaf counter_slice12_ifg_sec_dec2_sta_undersize_filter5_sta_undersize_pkt_drop_cnt {
      type oc-yang:counter64;
      description
        "Per port RX undersize packet drop - counter for packets that were dropped because they were smaller than 57B.";
    }
    leaf counter_slice12_ifg_sec_dec2_sta_undersize_filter6_sta_undersize_pkt_drop_cnt {
      type oc-yang:counter64;
      description
        "Per port RX undersize packet drop - counter for packets that were dropped because they were smaller than 57B.";
    }
    leaf counter_slice12_ifg_sec_dec2_sta_undersize_filter7_sta_undersize_pkt_drop_cnt {
      type oc-yang:counter64;
      description
        "Per port RX undersize packet drop - counter for packets that were dropped because they were smaller than 57B.";
    }
    leaf counter_slice12_ifg_sec_dec3_sta_undersize_filter0_sta_undersize_pkt_drop_cnt {
      type oc-yang:counter64;
      description
        "Per port RX undersize packet drop - counter for packets that were dropped because they were smaller than 57B.";
    }
    leaf counter_slice12_ifg_sec_dec3_sta_undersize_filter1_sta_undersize_pkt_drop_cnt {
      type oc-yang:counter64;
      description
        "Per port RX undersize packet drop - counter for packets that were dropped because they were smaller than 57B.";
    }
    leaf counter_slice12_ifg_sec_dec3_sta_undersize_filter2_sta_undersize_pkt_drop_cnt {
      type oc-yang:counter64;
      description
        "Per port RX undersize packet drop - counter for packets that were dropped because they were smaller than 57B.";
    }
    leaf counter_slice12_ifg_sec_dec3_sta_undersize_filter3_sta_undersize_pkt_drop_cnt {
      type oc-yang:counter64;
      description
        "Per port RX undersize packet drop - counter for packets that were dropped because they were smaller than 57B.";
    }
    leaf counter_slice12_ifg_sec_dec3_sta_undersize_filter4_sta_undersize_pkt_drop_cnt {
      type oc-yang:counter64;
      description
        "Per port RX undersize packet drop - counter for packets that were dropped because they were smaller than 57B.";
    }
    leaf counter_slice12_ifg_sec_dec3_sta_undersize_filter5_sta_undersize_pkt_drop_cnt {
      type oc-yang:counter64;
      description
        "Per port RX undersize packet drop - counter for packets that were dropped because they were smaller than 57B.";
    }
    leaf counter_slice12_ifg_sec_dec3_sta_undersize_filter6_sta_undersize_pkt_drop_cnt {
      type oc-yang:counter64;
      description
        "Per port RX undersize packet drop - counter for packets that were dropped because they were smaller than 57B.";
    }
    leaf counter_slice12_ifg_sec_dec3_sta_undersize_filter7_sta_undersize_pkt_drop_cnt {
      type oc-yang:counter64;
      description
        "Per port RX undersize packet drop - counter for packets that were dropped because they were smaller than 57B.";
    }
    leaf counter_slice13_ifg_sec_dec0_sta_undersize_filter0_sta_undersize_pkt_drop_cnt {
      type oc-yang:counter64;
      description
        "Per port RX undersize packet drop - counter for packets that were dropped because they were smaller than 57B.";
    }
    leaf counter_slice13_ifg_sec_dec0_sta_undersize_filter1_sta_undersize_pkt_drop_cnt {
      type oc-yang:counter64;
      description
        "Per port RX undersize packet drop - counter for packets that were dropped because they were smaller than 57B.";
    }
    leaf counter_slice13_ifg_sec_dec0_sta_undersize_filter2_sta_undersize_pkt_drop_cnt {
      type oc-yang:counter64;
      description
        "Per port RX undersize packet drop - counter for packets that were dropped because they were smaller than 57B.";
    }
    leaf counter_slice13_ifg_sec_dec0_sta_undersize_filter3_sta_undersize_pkt_drop_cnt {
      type oc-yang:counter64;
      description
        "Per port RX undersize packet drop - counter for packets that were dropped because they were smaller than 57B.";
    }
    leaf counter_slice13_ifg_sec_dec0_sta_undersize_filter4_sta_undersize_pkt_drop_cnt {
      type oc-yang:counter64;
      description
        "Per port RX undersize packet drop - counter for packets that were dropped because they were smaller than 57B.";
    }
    leaf counter_slice13_ifg_sec_dec0_sta_undersize_filter5_sta_undersize_pkt_drop_cnt {
      type oc-yang:counter64;
      description
        "Per port RX undersize packet drop - counter for packets that were dropped because they were smaller than 57B.";
    }
    leaf counter_slice13_ifg_sec_dec0_sta_undersize_filter6_sta_undersize_pkt_drop_cnt {
      type oc-yang:counter64;
      description
        "Per port RX undersize packet drop - counter for packets that were dropped because they were smaller than 57B.";
    }
    leaf counter_slice13_ifg_sec_dec0_sta_undersize_filter7_sta_undersize_pkt_drop_cnt {
      type oc-yang:counter64;
      description
        "Per port RX undersize packet drop - counter for packets that were dropped because they were smaller than 57B.";
    }
    leaf counter_slice13_ifg_sec_dec1_sta_undersize_filter0_sta_undersize_pkt_drop_cnt {
      type oc-yang:counter64;
      description
        "Per port RX undersize packet drop - counter for packets that were dropped because they were smaller than 57B.";
    }
    leaf counter_slice13_ifg_sec_dec1_sta_undersize_filter1_sta_undersize_pkt_drop_cnt {
      type oc-yang:counter64;
      description
        "Per port RX undersize packet drop - counter for packets that were dropped because they were smaller than 57B.";
    }
    leaf counter_slice13_ifg_sec_dec1_sta_undersize_filter2_sta_undersize_pkt_drop_cnt {
      type oc-yang:counter64;
      description
        "Per port RX undersize packet drop - counter for packets that were dropped because they were smaller than 57B.";
    }
    leaf counter_slice13_ifg_sec_dec1_sta_undersize_filter3_sta_undersize_pkt_drop_cnt {
      type oc-yang:counter64;
      description
        "Per port RX undersize packet drop - counter for packets that were dropped because they were smaller than 57B.";
    }
    leaf counter_slice13_ifg_sec_dec1_sta_undersize_filter4_sta_undersize_pkt_drop_cnt {
      type oc-yang:counter64;
      description
        "Per port RX undersize packet drop - counter for packets that were dropped because they were smaller than 57B.";
    }
    leaf counter_slice13_ifg_sec_dec1_sta_undersize_filter5_sta_undersize_pkt_drop_cnt {
      type oc-yang:counter64;
      description
        "Per port RX undersize packet drop - counter for packets that were dropped because they were smaller than 57B.";
    }
    leaf counter_slice13_ifg_sec_dec1_sta_undersize_filter6_sta_undersize_pkt_drop_cnt {
      type oc-yang:counter64;
      description
        "Per port RX undersize packet drop - counter for packets that were dropped because they were smaller than 57B.";
    }
    leaf counter_slice13_ifg_sec_dec1_sta_undersize_filter7_sta_undersize_pkt_drop_cnt {
      type oc-yang:counter64;
      description
        "Per port RX undersize packet drop - counter for packets that were dropped because they were smaller than 57B.";
    }
    leaf counter_slice13_ifg_sec_dec2_sta_undersize_filter0_sta_undersize_pkt_drop_cnt {
      type oc-yang:counter64;
      description
        "Per port RX undersize packet drop - counter for packets that were dropped because they were smaller than 57B.";
    }
    leaf counter_slice13_ifg_sec_dec2_sta_undersize_filter1_sta_undersize_pkt_drop_cnt {
      type oc-yang:counter64;
      description
        "Per port RX undersize packet drop - counter for packets that were dropped because they were smaller than 57B.";
    }
    leaf counter_slice13_ifg_sec_dec2_sta_undersize_filter2_sta_undersize_pkt_drop_cnt {
      type oc-yang:counter64;
      description
        "Per port RX undersize packet drop - counter for packets that were dropped because they were smaller than 57B.";
    }
    leaf counter_slice13_ifg_sec_dec2_sta_undersize_filter3_sta_undersize_pkt_drop_cnt {
      type oc-yang:counter64;
      description
        "Per port RX undersize packet drop - counter for packets that were dropped because they were smaller than 57B.";
    }
    leaf counter_slice13_ifg_sec_dec2_sta_undersize_filter4_sta_undersize_pkt_drop_cnt {
      type oc-yang:counter64;
      description
        "Per port RX undersize packet drop - counter for packets that were dropped because they were smaller than 57B.";
    }
    leaf counter_slice13_ifg_sec_dec2_sta_undersize_filter5_sta_undersize_pkt_drop_cnt {
      type oc-yang:counter64;
      description
        "Per port RX undersize packet drop - counter for packets that were dropped because they were smaller than 57B.";
    }
    leaf counter_slice13_ifg_sec_dec2_sta_undersize_filter6_sta_undersize_pkt_drop_cnt {
      type oc-yang:counter64;
      description
        "Per port RX undersize packet drop - counter for packets that were dropped because they were smaller than 57B.";
    }
    leaf counter_slice13_ifg_sec_dec2_sta_undersize_filter7_sta_undersize_pkt_drop_cnt {
      type oc-yang:counter64;
      description
        "Per port RX undersize packet drop - counter for packets that were dropped because they were smaller than 57B.";
    }
    leaf counter_slice13_ifg_sec_dec3_sta_undersize_filter0_sta_undersize_pkt_drop_cnt {
      type oc-yang:counter64;
      description
        "Per port RX undersize packet drop - counter for packets that were dropped because they were smaller than 57B.";
    }
    leaf counter_slice13_ifg_sec_dec3_sta_undersize_filter1_sta_undersize_pkt_drop_cnt {
      type oc-yang:counter64;
      description
        "Per port RX undersize packet drop - counter for packets that were dropped because they were smaller than 57B.";
    }
    leaf counter_slice13_ifg_sec_dec3_sta_undersize_filter2_sta_undersize_pkt_drop_cnt {
      type oc-yang:counter64;
      description
        "Per port RX undersize packet drop - counter for packets that were dropped because they were smaller than 57B.";
    }
    leaf counter_slice13_ifg_sec_dec3_sta_undersize_filter3_sta_undersize_pkt_drop_cnt {
      type oc-yang:counter64;
      description
        "Per port RX undersize packet drop - counter for packets that were dropped because they were smaller than 57B.";
    }
    leaf counter_slice13_ifg_sec_dec3_sta_undersize_filter4_sta_undersize_pkt_drop_cnt {
      type oc-yang:counter64;
      description
        "Per port RX undersize packet drop - counter for packets that were dropped because they were smaller than 57B.";
    }
    leaf counter_slice13_ifg_sec_dec3_sta_undersize_filter5_sta_undersize_pkt_drop_cnt {
      type oc-yang:counter64;
      description
        "Per port RX undersize packet drop - counter for packets that were dropped because they were smaller than 57B.";
    }
    leaf counter_slice13_ifg_sec_dec3_sta_undersize_filter6_sta_undersize_pkt_drop_cnt {
      type oc-yang:counter64;
      description
        "Per port RX undersize packet drop - counter for packets that were dropped because they were smaller than 57B.";
    }
    leaf counter_slice13_ifg_sec_dec3_sta_undersize_filter7_sta_undersize_pkt_drop_cnt {
      type oc-yang:counter64;
      description
        "Per port RX undersize packet drop - counter for packets that were dropped because they were smaller than 57B.";
    }
    leaf counter_slice14_ifg_sec_dec0_sta_undersize_filter0_sta_undersize_pkt_drop_cnt {
      type oc-yang:counter64;
      description
        "Per port RX undersize packet drop - counter for packets that were dropped because they were smaller than 57B.";
    }
    leaf counter_slice14_ifg_sec_dec0_sta_undersize_filter1_sta_undersize_pkt_drop_cnt {
      type oc-yang:counter64;
      description
        "Per port RX undersize packet drop - counter for packets that were dropped because they were smaller than 57B.";
    }
    leaf counter_slice14_ifg_sec_dec0_sta_undersize_filter2_sta_undersize_pkt_drop_cnt {
      type oc-yang:counter64;
      description
        "Per port RX undersize packet drop - counter for packets that were dropped because they were smaller than 57B.";
    }
    leaf counter_slice14_ifg_sec_dec0_sta_undersize_filter3_sta_undersize_pkt_drop_cnt {
      type oc-yang:counter64;
      description
        "Per port RX undersize packet drop - counter for packets that were dropped because they were smaller than 57B.";
    }
    leaf counter_slice14_ifg_sec_dec0_sta_undersize_filter4_sta_undersize_pkt_drop_cnt {
      type oc-yang:counter64;
      description
        "Per port RX undersize packet drop - counter for packets that were dropped because they were smaller than 57B.";
    }
    leaf counter_slice14_ifg_sec_dec0_sta_undersize_filter5_sta_undersize_pkt_drop_cnt {
      type oc-yang:counter64;
      description
        "Per port RX undersize packet drop - counter for packets that were dropped because they were smaller than 57B.";
    }
    leaf counter_slice14_ifg_sec_dec0_sta_undersize_filter6_sta_undersize_pkt_drop_cnt {
      type oc-yang:counter64;
      description
        "Per port RX undersize packet drop - counter for packets that were dropped because they were smaller than 57B.";
    }
    leaf counter_slice14_ifg_sec_dec0_sta_undersize_filter7_sta_undersize_pkt_drop_cnt {
      type oc-yang:counter64;
      description
        "Per port RX undersize packet drop - counter for packets that were dropped because they were smaller than 57B.";
    }
    leaf counter_slice14_ifg_sec_dec1_sta_undersize_filter0_sta_undersize_pkt_drop_cnt {
      type oc-yang:counter64;
      description
        "Per port RX undersize packet drop - counter for packets that were dropped because they were smaller than 57B.";
    }
    leaf counter_slice14_ifg_sec_dec1_sta_undersize_filter1_sta_undersize_pkt_drop_cnt {
      type oc-yang:counter64;
      description
        "Per port RX undersize packet drop - counter for packets that were dropped because they were smaller than 57B.";
    }
    leaf counter_slice14_ifg_sec_dec1_sta_undersize_filter2_sta_undersize_pkt_drop_cnt {
      type oc-yang:counter64;
      description
        "Per port RX undersize packet drop - counter for packets that were dropped because they were smaller than 57B.";
    }
    leaf counter_slice14_ifg_sec_dec1_sta_undersize_filter3_sta_undersize_pkt_drop_cnt {
      type oc-yang:counter64;
      description
        "Per port RX undersize packet drop - counter for packets that were dropped because they were smaller than 57B.";
    }
    leaf counter_slice14_ifg_sec_dec1_sta_undersize_filter4_sta_undersize_pkt_drop_cnt {
      type oc-yang:counter64;
      description
        "Per port RX undersize packet drop - counter for packets that were dropped because they were smaller than 57B.";
    }
    leaf counter_slice14_ifg_sec_dec1_sta_undersize_filter5_sta_undersize_pkt_drop_cnt {
      type oc-yang:counter64;
      description
        "Per port RX undersize packet drop - counter for packets that were dropped because they were smaller than 57B.";
    }
    leaf counter_slice14_ifg_sec_dec1_sta_undersize_filter6_sta_undersize_pkt_drop_cnt {
      type oc-yang:counter64;
      description
        "Per port RX undersize packet drop - counter for packets that were dropped because they were smaller than 57B.";
    }
    leaf counter_slice14_ifg_sec_dec1_sta_undersize_filter7_sta_undersize_pkt_drop_cnt {
      type oc-yang:counter64;
      description
        "Per port RX undersize packet drop - counter for packets that were dropped because they were smaller than 57B.";
    }
    leaf counter_slice14_ifg_sec_dec2_sta_undersize_filter0_sta_undersize_pkt_drop_cnt {
      type oc-yang:counter64;
      description
        "Per port RX undersize packet drop - counter for packets that were dropped because they were smaller than 57B.";
    }
    leaf counter_slice14_ifg_sec_dec2_sta_undersize_filter1_sta_undersize_pkt_drop_cnt {
      type oc-yang:counter64;
      description
        "Per port RX undersize packet drop - counter for packets that were dropped because they were smaller than 57B.";
    }
    leaf counter_slice14_ifg_sec_dec2_sta_undersize_filter2_sta_undersize_pkt_drop_cnt {
      type oc-yang:counter64;
      description
        "Per port RX undersize packet drop - counter for packets that were dropped because they were smaller than 57B.";
    }
    leaf counter_slice14_ifg_sec_dec2_sta_undersize_filter3_sta_undersize_pkt_drop_cnt {
      type oc-yang:counter64;
      description
        "Per port RX undersize packet drop - counter for packets that were dropped because they were smaller than 57B.";
    }
    leaf counter_slice14_ifg_sec_dec2_sta_undersize_filter4_sta_undersize_pkt_drop_cnt {
      type oc-yang:counter64;
      description
        "Per port RX undersize packet drop - counter for packets that were dropped because they were smaller than 57B.";
    }
    leaf counter_slice14_ifg_sec_dec2_sta_undersize_filter5_sta_undersize_pkt_drop_cnt {
      type oc-yang:counter64;
      description
        "Per port RX undersize packet drop - counter for packets that were dropped because they were smaller than 57B.";
    }
    leaf counter_slice14_ifg_sec_dec2_sta_undersize_filter6_sta_undersize_pkt_drop_cnt {
      type oc-yang:counter64;
      description
        "Per port RX undersize packet drop - counter for packets that were dropped because they were smaller than 57B.";
    }
    leaf counter_slice14_ifg_sec_dec2_sta_undersize_filter7_sta_undersize_pkt_drop_cnt {
      type oc-yang:counter64;
      description
        "Per port RX undersize packet drop - counter for packets that were dropped because they were smaller than 57B.";
    }
    leaf counter_slice14_ifg_sec_dec3_sta_undersize_filter0_sta_undersize_pkt_drop_cnt {
      type oc-yang:counter64;
      description
        "Per port RX undersize packet drop - counter for packets that were dropped because they were smaller than 57B.";
    }
    leaf counter_slice14_ifg_sec_dec3_sta_undersize_filter1_sta_undersize_pkt_drop_cnt {
      type oc-yang:counter64;
      description
        "Per port RX undersize packet drop - counter for packets that were dropped because they were smaller than 57B.";
    }
    leaf counter_slice14_ifg_sec_dec3_sta_undersize_filter2_sta_undersize_pkt_drop_cnt {
      type oc-yang:counter64;
      description
        "Per port RX undersize packet drop - counter for packets that were dropped because they were smaller than 57B.";
    }
    leaf counter_slice14_ifg_sec_dec3_sta_undersize_filter3_sta_undersize_pkt_drop_cnt {
      type oc-yang:counter64;
      description
        "Per port RX undersize packet drop - counter for packets that were dropped because they were smaller than 57B.";
    }
    leaf counter_slice14_ifg_sec_dec3_sta_undersize_filter4_sta_undersize_pkt_drop_cnt {
      type oc-yang:counter64;
      description
        "Per port RX undersize packet drop - counter for packets that were dropped because they were smaller than 57B.";
    }
    leaf counter_slice14_ifg_sec_dec3_sta_undersize_filter5_sta_undersize_pkt_drop_cnt {
      type oc-yang:counter64;
      description
        "Per port RX undersize packet drop - counter for packets that were dropped because they were smaller than 57B.";
    }
    leaf counter_slice14_ifg_sec_dec3_sta_undersize_filter6_sta_undersize_pkt_drop_cnt {
      type oc-yang:counter64;
      description
        "Per port RX undersize packet drop - counter for packets that were dropped because they were smaller than 57B.";
    }
    leaf counter_slice14_ifg_sec_dec3_sta_undersize_filter7_sta_undersize_pkt_drop_cnt {
      type oc-yang:counter64;
      description
        "Per port RX undersize packet drop - counter for packets that were dropped because they were smaller than 57B.";
    }
    leaf counter_slice15_ifg_sec_dec0_sta_undersize_filter0_sta_undersize_pkt_drop_cnt {
      type oc-yang:counter64;
      description
        "Per port RX undersize packet drop - counter for packets that were dropped because they were smaller than 57B.";
    }
    leaf counter_slice15_ifg_sec_dec0_sta_undersize_filter1_sta_undersize_pkt_drop_cnt {
      type oc-yang:counter64;
      description
        "Per port RX undersize packet drop - counter for packets that were dropped because they were smaller than 57B.";
    }
    leaf counter_slice15_ifg_sec_dec0_sta_undersize_filter2_sta_undersize_pkt_drop_cnt {
      type oc-yang:counter64;
      description
        "Per port RX undersize packet drop - counter for packets that were dropped because they were smaller than 57B.";
    }
    leaf counter_slice15_ifg_sec_dec0_sta_undersize_filter3_sta_undersize_pkt_drop_cnt {
      type oc-yang:counter64;
      description
        "Per port RX undersize packet drop - counter for packets that were dropped because they were smaller than 57B.";
    }
    leaf counter_slice15_ifg_sec_dec0_sta_undersize_filter4_sta_undersize_pkt_drop_cnt {
      type oc-yang:counter64;
      description
        "Per port RX undersize packet drop - counter for packets that were dropped because they were smaller than 57B.";
    }
    leaf counter_slice15_ifg_sec_dec0_sta_undersize_filter5_sta_undersize_pkt_drop_cnt {
      type oc-yang:counter64;
      description
        "Per port RX undersize packet drop - counter for packets that were dropped because they were smaller than 57B.";
    }
    leaf counter_slice15_ifg_sec_dec0_sta_undersize_filter6_sta_undersize_pkt_drop_cnt {
      type oc-yang:counter64;
      description
        "Per port RX undersize packet drop - counter for packets that were dropped because they were smaller than 57B.";
    }
    leaf counter_slice15_ifg_sec_dec0_sta_undersize_filter7_sta_undersize_pkt_drop_cnt {
      type oc-yang:counter64;
      description
        "Per port RX undersize packet drop - counter for packets that were dropped because they were smaller than 57B.";
    }
    leaf counter_slice15_ifg_sec_dec1_sta_undersize_filter0_sta_undersize_pkt_drop_cnt {
      type oc-yang:counter64;
      description
        "Per port RX undersize packet drop - counter for packets that were dropped because they were smaller than 57B.";
    }
    leaf counter_slice15_ifg_sec_dec1_sta_undersize_filter1_sta_undersize_pkt_drop_cnt {
      type oc-yang:counter64;
      description
        "Per port RX undersize packet drop - counter for packets that were dropped because they were smaller than 57B.";
    }
    leaf counter_slice15_ifg_sec_dec1_sta_undersize_filter2_sta_undersize_pkt_drop_cnt {
      type oc-yang:counter64;
      description
        "Per port RX undersize packet drop - counter for packets that were dropped because they were smaller than 57B.";
    }
    leaf counter_slice15_ifg_sec_dec1_sta_undersize_filter3_sta_undersize_pkt_drop_cnt {
      type oc-yang:counter64;
      description
        "Per port RX undersize packet drop - counter for packets that were dropped because they were smaller than 57B.";
    }
    leaf counter_slice15_ifg_sec_dec1_sta_undersize_filter4_sta_undersize_pkt_drop_cnt {
      type oc-yang:counter64;
      description
        "Per port RX undersize packet drop - counter for packets that were dropped because they were smaller than 57B.";
    }
    leaf counter_slice15_ifg_sec_dec1_sta_undersize_filter5_sta_undersize_pkt_drop_cnt {
      type oc-yang:counter64;
      description
        "Per port RX undersize packet drop - counter for packets that were dropped because they were smaller than 57B.";
    }
    leaf counter_slice15_ifg_sec_dec1_sta_undersize_filter6_sta_undersize_pkt_drop_cnt {
      type oc-yang:counter64;
      description
        "Per port RX undersize packet drop - counter for packets that were dropped because they were smaller than 57B.";
    }
    leaf counter_slice15_ifg_sec_dec1_sta_undersize_filter7_sta_undersize_pkt_drop_cnt {
      type oc-yang:counter64;
      description
        "Per port RX undersize packet drop - counter for packets that were dropped because they were smaller than 57B.";
    }
    leaf counter_slice15_ifg_sec_dec2_sta_undersize_filter0_sta_undersize_pkt_drop_cnt {
      type oc-yang:counter64;
      description
        "Per port RX undersize packet drop - counter for packets that were dropped because they were smaller than 57B.";
    }
    leaf counter_slice15_ifg_sec_dec2_sta_undersize_filter1_sta_undersize_pkt_drop_cnt {
      type oc-yang:counter64;
      description
        "Per port RX undersize packet drop - counter for packets that were dropped because they were smaller than 57B.";
    }
    leaf counter_slice15_ifg_sec_dec2_sta_undersize_filter2_sta_undersize_pkt_drop_cnt {
      type oc-yang:counter64;
      description
        "Per port RX undersize packet drop - counter for packets that were dropped because they were smaller than 57B.";
    }
    leaf counter_slice15_ifg_sec_dec2_sta_undersize_filter3_sta_undersize_pkt_drop_cnt {
      type oc-yang:counter64;
      description
        "Per port RX undersize packet drop - counter for packets that were dropped because they were smaller than 57B.";
    }
    leaf counter_slice15_ifg_sec_dec2_sta_undersize_filter4_sta_undersize_pkt_drop_cnt {
      type oc-yang:counter64;
      description
        "Per port RX undersize packet drop - counter for packets that were dropped because they were smaller than 57B.";
    }
    leaf counter_slice15_ifg_sec_dec2_sta_undersize_filter5_sta_undersize_pkt_drop_cnt {
      type oc-yang:counter64;
      description
        "Per port RX undersize packet drop - counter for packets that were dropped because they were smaller than 57B.";
    }
    leaf counter_slice15_ifg_sec_dec2_sta_undersize_filter6_sta_undersize_pkt_drop_cnt {
      type oc-yang:counter64;
      description
        "Per port RX undersize packet drop - counter for packets that were dropped because they were smaller than 57B.";
    }
    leaf counter_slice15_ifg_sec_dec2_sta_undersize_filter7_sta_undersize_pkt_drop_cnt {
      type oc-yang:counter64;
      description
        "Per port RX undersize packet drop - counter for packets that were dropped because they were smaller than 57B.";
    }
    leaf counter_slice15_ifg_sec_dec3_sta_undersize_filter0_sta_undersize_pkt_drop_cnt {
      type oc-yang:counter64;
      description
        "Per port RX undersize packet drop - counter for packets that were dropped because they were smaller than 57B.";
    }
    leaf counter_slice15_ifg_sec_dec3_sta_undersize_filter1_sta_undersize_pkt_drop_cnt {
      type oc-yang:counter64;
      description
        "Per port RX undersize packet drop - counter for packets that were dropped because they were smaller than 57B.";
    }
    leaf counter_slice15_ifg_sec_dec3_sta_undersize_filter2_sta_undersize_pkt_drop_cnt {
      type oc-yang:counter64;
      description
        "Per port RX undersize packet drop - counter for packets that were dropped because they were smaller than 57B.";
    }
    leaf counter_slice15_ifg_sec_dec3_sta_undersize_filter3_sta_undersize_pkt_drop_cnt {
      type oc-yang:counter64;
      description
        "Per port RX undersize packet drop - counter for packets that were dropped because they were smaller than 57B.";
    }
    leaf counter_slice15_ifg_sec_dec3_sta_undersize_filter4_sta_undersize_pkt_drop_cnt {
      type oc-yang:counter64;
      description
        "Per port RX undersize packet drop - counter for packets that were dropped because they were smaller than 57B.";
    }
    leaf counter_slice15_ifg_sec_dec3_sta_undersize_filter5_sta_undersize_pkt_drop_cnt {
      type oc-yang:counter64;
      description
        "Per port RX undersize packet drop - counter for packets that were dropped because they were smaller than 57B.";
    }
    leaf counter_slice15_ifg_sec_dec3_sta_undersize_filter6_sta_undersize_pkt_drop_cnt {
      type oc-yang:counter64;
      description
        "Per port RX undersize packet drop - counter for packets that were dropped because they were smaller than 57B.";
    }
    leaf counter_slice15_ifg_sec_dec3_sta_undersize_filter7_sta_undersize_pkt_drop_cnt {
      type oc-yang:counter64;
      description
        "Per port RX undersize packet drop - counter for packets that were dropped because they were smaller than 57B.";
    }
    leaf counter_slice0_ts_mon_drop_packets0_drop_fte_test {
      type oc-yang:counter64;
      description
        "FTE test caused drops for {MC, UCL, UCH}";
    }
    leaf counter_slice1_ts_mon_drop_packets0_drop_fte_test {
      type oc-yang:counter64;
      description
        "FTE test caused drops for {MC, UCL, UCH}";
    }
    leaf counter_slice2_ts_mon_drop_packets0_drop_fte_test {
      type oc-yang:counter64;
      description
        "FTE test caused drops for {MC, UCL, UCH}";
    }
    leaf counter_slice3_ts_mon_drop_packets0_drop_fte_test {
      type oc-yang:counter64;
      description
        "FTE test caused drops for {MC, UCL, UCH}";
    }
    leaf counter_slice4_ts_mon_drop_packets0_drop_fte_test {
      type oc-yang:counter64;
      description
        "FTE test caused drops for {MC, UCL, UCH}";
    }
    leaf counter_slice5_ts_mon_drop_packets0_drop_fte_test {
      type oc-yang:counter64;
      description
        "FTE test caused drops for {MC, UCL, UCH}";
    }
    leaf counter_slice6_ts_mon_drop_packets0_drop_fte_test {
      type oc-yang:counter64;
      description
        "FTE test caused drops for {MC, UCL, UCH}";
    }
    leaf counter_slice7_ts_mon_drop_packets0_drop_fte_test {
      type oc-yang:counter64;
      description
        "FTE test caused drops for {MC, UCL, UCH}";
    }
    leaf counter_slice8_ts_mon_drop_packets0_drop_fte_test {
      type oc-yang:counter64;
      description
        "FTE test caused drops for {MC, UCL, UCH}";
    }
    leaf counter_slice9_ts_mon_drop_packets0_drop_fte_test {
      type oc-yang:counter64;
      description
        "FTE test caused drops for {MC, UCL, UCH}";
    }
    leaf counter_slice10_ts_mon_drop_packets0_drop_fte_test {
      type oc-yang:counter64;
      description
        "FTE test caused drops for {MC, UCL, UCH}";
    }
    leaf counter_slice11_ts_mon_drop_packets0_drop_fte_test {
      type oc-yang:counter64;
      description
        "FTE test caused drops for {MC, UCL, UCH}";
    }
    leaf counter_slice12_ts_mon_drop_packets0_drop_fte_test {
      type oc-yang:counter64;
      description
        "FTE test caused drops for {MC, UCL, UCH}";
    }
    leaf counter_slice13_ts_mon_drop_packets0_drop_fte_test {
      type oc-yang:counter64;
      description
        "FTE test caused drops for {MC, UCL, UCH}";
    }
    leaf counter_slice14_ts_mon_drop_packets0_drop_fte_test {
      type oc-yang:counter64;
      description
        "FTE test caused drops for {MC, UCL, UCH}";
    }
    leaf counter_slice15_ts_mon_drop_packets0_drop_fte_test {
      type oc-yang:counter64;
      description
        "FTE test caused drops for {MC, UCL, UCH}";
    }
    leaf counter_slice0_ts_mon_drop_packets0_drop_monotonic_test {
      type oc-yang:counter64;
      description
        "Monotonic test caused drops for {MC, UCL, UCH} and the drops during the first 128 to 256 cycles of link_status up time. Both regular and keepalive packets are included in this counter.";
    }
    leaf counter_slice1_ts_mon_drop_packets0_drop_monotonic_test {
      type oc-yang:counter64;
      description
        "Monotonic test caused drops for {MC, UCL, UCH} and the drops during the first 128 to 256 cycles of link_status up time. Both regular and keepalive packets are included in this counter.";
    }
    leaf counter_slice2_ts_mon_drop_packets0_drop_monotonic_test {
      type oc-yang:counter64;
      description
        "Monotonic test caused drops for {MC, UCL, UCH} and the drops during the first 128 to 256 cycles of link_status up time. Both regular and keepalive packets are included in this counter.";
    }
    leaf counter_slice3_ts_mon_drop_packets0_drop_monotonic_test {
      type oc-yang:counter64;
      description
        "Monotonic test caused drops for {MC, UCL, UCH} and the drops during the first 128 to 256 cycles of link_status up time. Both regular and keepalive packets are included in this counter.";
    }
    leaf counter_slice4_ts_mon_drop_packets0_drop_monotonic_test {
      type oc-yang:counter64;
      description
        "Monotonic test caused drops for {MC, UCL, UCH} and the drops during the first 128 to 256 cycles of link_status up time. Both regular and keepalive packets are included in this counter.";
    }
    leaf counter_slice5_ts_mon_drop_packets0_drop_monotonic_test {
      type oc-yang:counter64;
      description
        "Monotonic test caused drops for {MC, UCL, UCH} and the drops during the first 128 to 256 cycles of link_status up time. Both regular and keepalive packets are included in this counter.";
    }
    leaf counter_slice6_ts_mon_drop_packets0_drop_monotonic_test {
      type oc-yang:counter64;
      description
        "Monotonic test caused drops for {MC, UCL, UCH} and the drops during the first 128 to 256 cycles of link_status up time. Both regular and keepalive packets are included in this counter.";
    }
    leaf counter_slice7_ts_mon_drop_packets0_drop_monotonic_test {
      type oc-yang:counter64;
      description
        "Monotonic test caused drops for {MC, UCL, UCH} and the drops during the first 128 to 256 cycles of link_status up time. Both regular and keepalive packets are included in this counter.";
    }
    leaf counter_slice8_ts_mon_drop_packets0_drop_monotonic_test {
      type oc-yang:counter64;
      description
        "Monotonic test caused drops for {MC, UCL, UCH} and the drops during the first 128 to 256 cycles of link_status up time. Both regular and keepalive packets are included in this counter.";
    }
    leaf counter_slice9_ts_mon_drop_packets0_drop_monotonic_test {
      type oc-yang:counter64;
      description
        "Monotonic test caused drops for {MC, UCL, UCH} and the drops during the first 128 to 256 cycles of link_status up time. Both regular and keepalive packets are included in this counter.";
    }
    leaf counter_slice10_ts_mon_drop_packets0_drop_monotonic_test {
      type oc-yang:counter64;
      description
        "Monotonic test caused drops for {MC, UCL, UCH} and the drops during the first 128 to 256 cycles of link_status up time. Both regular and keepalive packets are included in this counter.";
    }
    leaf counter_slice11_ts_mon_drop_packets0_drop_monotonic_test {
      type oc-yang:counter64;
      description
        "Monotonic test caused drops for {MC, UCL, UCH} and the drops during the first 128 to 256 cycles of link_status up time. Both regular and keepalive packets are included in this counter.";
    }
    leaf counter_slice12_ts_mon_drop_packets0_drop_monotonic_test {
      type oc-yang:counter64;
      description
        "Monotonic test caused drops for {MC, UCL, UCH} and the drops during the first 128 to 256 cycles of link_status up time. Both regular and keepalive packets are included in this counter.";
    }
    leaf counter_slice13_ts_mon_drop_packets0_drop_monotonic_test {
      type oc-yang:counter64;
      description
        "Monotonic test caused drops for {MC, UCL, UCH} and the drops during the first 128 to 256 cycles of link_status up time. Both regular and keepalive packets are included in this counter.";
    }
    leaf counter_slice14_ts_mon_drop_packets0_drop_monotonic_test {
      type oc-yang:counter64;
      description
        "Monotonic test caused drops for {MC, UCL, UCH} and the drops during the first 128 to 256 cycles of link_status up time. Both regular and keepalive packets are included in this counter.";
    }
    leaf counter_slice15_ts_mon_drop_packets0_drop_monotonic_test {
      type oc-yang:counter64;
      description
        "Monotonic test caused drops for {MC, UCL, UCH} and the drops during the first 128 to 256 cycles of link_status up time. Both regular and keepalive packets are included in this counter.";
    }
    leaf counter_slice0_ts_mon_drop_packets0_drop_skew_test {
      type oc-yang:counter64;
      description
        "Skew test caused drops for {MC, UCL, UCH}";
    }
    leaf counter_slice1_ts_mon_drop_packets0_drop_skew_test {
      type oc-yang:counter64;
      description
        "Skew test caused drops for {MC, UCL, UCH}";
    }
    leaf counter_slice2_ts_mon_drop_packets0_drop_skew_test {
      type oc-yang:counter64;
      description
        "Skew test caused drops for {MC, UCL, UCH}";
    }
    leaf counter_slice3_ts_mon_drop_packets0_drop_skew_test {
      type oc-yang:counter64;
      description
        "Skew test caused drops for {MC, UCL, UCH}";
    }
    leaf counter_slice4_ts_mon_drop_packets0_drop_skew_test {
      type oc-yang:counter64;
      description
        "Skew test caused drops for {MC, UCL, UCH}";
    }
    leaf counter_slice5_ts_mon_drop_packets0_drop_skew_test {
      type oc-yang:counter64;
      description
        "Skew test caused drops for {MC, UCL, UCH}";
    }
    leaf counter_slice6_ts_mon_drop_packets0_drop_skew_test {
      type oc-yang:counter64;
      description
        "Skew test caused drops for {MC, UCL, UCH}";
    }
    leaf counter_slice7_ts_mon_drop_packets0_drop_skew_test {
      type oc-yang:counter64;
      description
        "Skew test caused drops for {MC, UCL, UCH}";
    }
    leaf counter_slice8_ts_mon_drop_packets0_drop_skew_test {
      type oc-yang:counter64;
      description
        "Skew test caused drops for {MC, UCL, UCH}";
    }
    leaf counter_slice9_ts_mon_drop_packets0_drop_skew_test {
      type oc-yang:counter64;
      description
        "Skew test caused drops for {MC, UCL, UCH}";
    }
    leaf counter_slice10_ts_mon_drop_packets0_drop_skew_test {
      type oc-yang:counter64;
      description
        "Skew test caused drops for {MC, UCL, UCH}";
    }
    leaf counter_slice11_ts_mon_drop_packets0_drop_skew_test {
      type oc-yang:counter64;
      description
        "Skew test caused drops for {MC, UCL, UCH}";
    }
    leaf counter_slice12_ts_mon_drop_packets0_drop_skew_test {
      type oc-yang:counter64;
      description
        "Skew test caused drops for {MC, UCL, UCH}";
    }
    leaf counter_slice13_ts_mon_drop_packets0_drop_skew_test {
      type oc-yang:counter64;
      description
        "Skew test caused drops for {MC, UCL, UCH}";
    }
    leaf counter_slice14_ts_mon_drop_packets0_drop_skew_test {
      type oc-yang:counter64;
      description
        "Skew test caused drops for {MC, UCL, UCH}";
    }
    leaf counter_slice15_ts_mon_drop_packets0_drop_skew_test {
      type oc-yang:counter64;
      description
        "Skew test caused drops for {MC, UCL, UCH}";
    }
    leaf counter_slice0_ts_mon_drop_packets0_mc_drop_packet_cnt {
      type oc-yang:counter64;
      description
        "Counter of MC dropped packets";
    }
    leaf counter_slice1_ts_mon_drop_packets0_mc_drop_packet_cnt {
      type oc-yang:counter64;
      description
        "Counter of MC dropped packets";
    }
    leaf counter_slice2_ts_mon_drop_packets0_mc_drop_packet_cnt {
      type oc-yang:counter64;
      description
        "Counter of MC dropped packets";
    }
    leaf counter_slice3_ts_mon_drop_packets0_mc_drop_packet_cnt {
      type oc-yang:counter64;
      description
        "Counter of MC dropped packets";
    }
    leaf counter_slice4_ts_mon_drop_packets0_mc_drop_packet_cnt {
      type oc-yang:counter64;
      description
        "Counter of MC dropped packets";
    }
    leaf counter_slice5_ts_mon_drop_packets0_mc_drop_packet_cnt {
      type oc-yang:counter64;
      description
        "Counter of MC dropped packets";
    }
    leaf counter_slice6_ts_mon_drop_packets0_mc_drop_packet_cnt {
      type oc-yang:counter64;
      description
        "Counter of MC dropped packets";
    }
    leaf counter_slice7_ts_mon_drop_packets0_mc_drop_packet_cnt {
      type oc-yang:counter64;
      description
        "Counter of MC dropped packets";
    }
    leaf counter_slice8_ts_mon_drop_packets0_mc_drop_packet_cnt {
      type oc-yang:counter64;
      description
        "Counter of MC dropped packets";
    }
    leaf counter_slice9_ts_mon_drop_packets0_mc_drop_packet_cnt {
      type oc-yang:counter64;
      description
        "Counter of MC dropped packets";
    }
    leaf counter_slice10_ts_mon_drop_packets0_mc_drop_packet_cnt {
      type oc-yang:counter64;
      description
        "Counter of MC dropped packets";
    }
    leaf counter_slice11_ts_mon_drop_packets0_mc_drop_packet_cnt {
      type oc-yang:counter64;
      description
        "Counter of MC dropped packets";
    }
    leaf counter_slice12_ts_mon_drop_packets0_mc_drop_packet_cnt {
      type oc-yang:counter64;
      description
        "Counter of MC dropped packets";
    }
    leaf counter_slice13_ts_mon_drop_packets0_mc_drop_packet_cnt {
      type oc-yang:counter64;
      description
        "Counter of MC dropped packets";
    }
    leaf counter_slice14_ts_mon_drop_packets0_mc_drop_packet_cnt {
      type oc-yang:counter64;
      description
        "Counter of MC dropped packets";
    }
    leaf counter_slice15_ts_mon_drop_packets0_mc_drop_packet_cnt {
      type oc-yang:counter64;
      description
        "Counter of MC dropped packets";
    }
    leaf counter_slice0_ts_mon_drop_packets0_uch_drop_packet_cnt {
      type oc-yang:counter64;
      description
        "Counter of UCH dropped packets";
    }
    leaf counter_slice1_ts_mon_drop_packets0_uch_drop_packet_cnt {
      type oc-yang:counter64;
      description
        "Counter of UCH dropped packets";
    }
    leaf counter_slice2_ts_mon_drop_packets0_uch_drop_packet_cnt {
      type oc-yang:counter64;
      description
        "Counter of UCH dropped packets";
    }
    leaf counter_slice3_ts_mon_drop_packets0_uch_drop_packet_cnt {
      type oc-yang:counter64;
      description
        "Counter of UCH dropped packets";
    }
    leaf counter_slice4_ts_mon_drop_packets0_uch_drop_packet_cnt {
      type oc-yang:counter64;
      description
        "Counter of UCH dropped packets";
    }
    leaf counter_slice5_ts_mon_drop_packets0_uch_drop_packet_cnt {
      type oc-yang:counter64;
      description
        "Counter of UCH dropped packets";
    }
    leaf counter_slice6_ts_mon_drop_packets0_uch_drop_packet_cnt {
      type oc-yang:counter64;
      description
        "Counter of UCH dropped packets";
    }
    leaf counter_slice7_ts_mon_drop_packets0_uch_drop_packet_cnt {
      type oc-yang:counter64;
      description
        "Counter of UCH dropped packets";
    }
    leaf counter_slice8_ts_mon_drop_packets0_uch_drop_packet_cnt {
      type oc-yang:counter64;
      description
        "Counter of UCH dropped packets";
    }
    leaf counter_slice9_ts_mon_drop_packets0_uch_drop_packet_cnt {
      type oc-yang:counter64;
      description
        "Counter of UCH dropped packets";
    }
    leaf counter_slice10_ts_mon_drop_packets0_uch_drop_packet_cnt {
      type oc-yang:counter64;
      description
        "Counter of UCH dropped packets";
    }
    leaf counter_slice11_ts_mon_drop_packets0_uch_drop_packet_cnt {
      type oc-yang:counter64;
      description
        "Counter of UCH dropped packets";
    }
    leaf counter_slice12_ts_mon_drop_packets0_uch_drop_packet_cnt {
      type oc-yang:counter64;
      description
        "Counter of UCH dropped packets";
    }
    leaf counter_slice13_ts_mon_drop_packets0_uch_drop_packet_cnt {
      type oc-yang:counter64;
      description
        "Counter of UCH dropped packets";
    }
    leaf counter_slice14_ts_mon_drop_packets0_uch_drop_packet_cnt {
      type oc-yang:counter64;
      description
        "Counter of UCH dropped packets";
    }
    leaf counter_slice15_ts_mon_drop_packets0_uch_drop_packet_cnt {
      type oc-yang:counter64;
      description
        "Counter of UCH dropped packets";
    }
    leaf counter_slice0_ts_mon_drop_packets0_ucl_drop_packet_cnt {
      type oc-yang:counter64;
      description
        "Counter of UCL dropped packets";
    }
    leaf counter_slice1_ts_mon_drop_packets0_ucl_drop_packet_cnt {
      type oc-yang:counter64;
      description
        "Counter of UCL dropped packets";
    }
    leaf counter_slice2_ts_mon_drop_packets0_ucl_drop_packet_cnt {
      type oc-yang:counter64;
      description
        "Counter of UCL dropped packets";
    }
    leaf counter_slice3_ts_mon_drop_packets0_ucl_drop_packet_cnt {
      type oc-yang:counter64;
      description
        "Counter of UCL dropped packets";
    }
    leaf counter_slice4_ts_mon_drop_packets0_ucl_drop_packet_cnt {
      type oc-yang:counter64;
      description
        "Counter of UCL dropped packets";
    }
    leaf counter_slice5_ts_mon_drop_packets0_ucl_drop_packet_cnt {
      type oc-yang:counter64;
      description
        "Counter of UCL dropped packets";
    }
    leaf counter_slice6_ts_mon_drop_packets0_ucl_drop_packet_cnt {
      type oc-yang:counter64;
      description
        "Counter of UCL dropped packets";
    }
    leaf counter_slice7_ts_mon_drop_packets0_ucl_drop_packet_cnt {
      type oc-yang:counter64;
      description
        "Counter of UCL dropped packets";
    }
    leaf counter_slice8_ts_mon_drop_packets0_ucl_drop_packet_cnt {
      type oc-yang:counter64;
      description
        "Counter of UCL dropped packets";
    }
    leaf counter_slice9_ts_mon_drop_packets0_ucl_drop_packet_cnt {
      type oc-yang:counter64;
      description
        "Counter of UCL dropped packets";
    }
    leaf counter_slice10_ts_mon_drop_packets0_ucl_drop_packet_cnt {
      type oc-yang:counter64;
      description
        "Counter of UCL dropped packets";
    }
    leaf counter_slice11_ts_mon_drop_packets0_ucl_drop_packet_cnt {
      type oc-yang:counter64;
      description
        "Counter of UCL dropped packets";
    }
    leaf counter_slice12_ts_mon_drop_packets0_ucl_drop_packet_cnt {
      type oc-yang:counter64;
      description
        "Counter of UCL dropped packets";
    }
    leaf counter_slice13_ts_mon_drop_packets0_ucl_drop_packet_cnt {
      type oc-yang:counter64;
      description
        "Counter of UCL dropped packets";
    }
    leaf counter_slice14_ts_mon_drop_packets0_ucl_drop_packet_cnt {
      type oc-yang:counter64;
      description
        "Counter of UCL dropped packets";
    }
    leaf counter_slice15_ts_mon_drop_packets0_ucl_drop_packet_cnt {
      type oc-yang:counter64;
      description
        "Counter of UCL dropped packets";
    }
  }

  augment "/oc-platform:components/oc-platform:component/oc-platform:integrated-circuit/oc-ppc:pipeline-counters/oc-ppc:drop/oc-ppc:vendor/cisco:cisco" {
    description
      "Cisco container";
    container p200 {
      description
        "Si-One p200 Drop container";
      uses oc-ppc:pipeline-vendor-drop-containers;
    }
  }
  augment "/oc-platform:components/oc-platform:component/oc-platform:integrated-circuit/oc-ppc:pipeline-counters/oc-ppc:drop/oc-ppc:vendor/cisco:cisco/p200:p200/p200:adverse/p200:state" {
    description
      "Adverse drop container for p200";
    uses cisco-p200-adverse-drop-counters;
  }
  augment "/oc-platform:components/oc-platform:component/oc-platform:integrated-circuit/oc-ppc:pipeline-counters/oc-ppc:drop/oc-ppc:vendor/cisco:cisco/p200:p200/p200:congestion/p200:state" {
    description
      "Congestion drop container for p200";
    uses cisco-p200-congestion-drop-counters;
  }
  augment "/oc-platform:components/oc-platform:component/oc-platform:integrated-circuit/oc-ppc:pipeline-counters/oc-ppc:drop/oc-ppc:vendor/cisco:cisco/p200:p200/p200:packet-processing/p200:state" {
    description
      "Packet Processing drop container for p200";
    uses cisco-p200-packet-processing-drop-counters;
  }
  oc-ext:openconfig-version "0.1.0";
  oc-ext:catalog-organization "openconfig";
  oc-ext:origin "openconfig";
}
