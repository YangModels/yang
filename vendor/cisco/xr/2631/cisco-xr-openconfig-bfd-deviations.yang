module cisco-xr-openconfig-bfd-deviations {

  namespace "http://cisco.com/ns/yang/cisco-xr-openconfig-bfd-deviations";

  prefix  "oc-bfddevs";

  // import some basic types
  import openconfig-bfd { prefix oc-bfd; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-bfd.yang@2022-06-28 

     on Cisco IOS-XR devices.

     Copyright (c) 2016-2017, 2019,2023,2024 by Cisco Systems, Inc.
     All rights reserved.";

  revision "2025-05-21" {
    description
      "Deviation updated for leaf oc-bfd:member-interface";
  }

  revision "2024-10-14" {
    description
      "Deviation updated after Micro-bfd support applicable to IOS-XR 25.1.1";
  }

  revision "2023-03-17" {
    description
      "Initial revision applicable to IOS-XR 7.1.1";
  }

  deviation /oc-bfd:bfd/oc-bfd:interfaces/oc-bfd:interface/oc-bfd:config/oc-bfd:enable-per-member-link {
    deviate not-supported;
  }

  deviation /oc-bfd:bfd/oc-bfd:interfaces/oc-bfd:interface/oc-bfd:state/oc-bfd:enable-per-member-link {
    deviate not-supported;
  }

  deviation /oc-bfd:bfd/oc-bfd:interfaces/oc-bfd:interface/oc-bfd:interface-ref {
    deviate not-supported;
  }

  deviation /oc-bfd:bfd/oc-bfd:interfaces/oc-bfd:interface/oc-bfd:micro-bfd-sessions/oc-bfd:micro-bfd-session/oc-bfd:config {
    deviate not-supported;
  }

  deviation /oc-bfd:bfd/oc-bfd:interfaces/oc-bfd:interface/oc-bfd:micro-bfd-sessions/oc-bfd:micro-bfd-session/oc-bfd:member-interface {
    deviate replace {
      type "string";
    }
  }
}
//total deviations:5
