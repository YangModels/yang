module Cisco-IOS-XR-gated-shell-access-act {
  namespace "http://cisco.com/ns/yang/Cisco-IOS-XR-gated-shell-access-act";
  prefix gsh-act;

  import Cisco-IOS-XR-types {
    prefix csc;
  }

  organization
    "Cisco Systems, Inc.";
  contact
    "Cisco Systems, Inc.
     Customer Service
     Postal: 170 West Tasman Drive
     San Jose, CA 95134
     Tel: +1 800 553-NETS
     E-mail: cs-yang@cisco.com";
  description
    "This module defines procedures to manage shell access.
     
     Copyright (c) 2017 IETF Trust and the persons identified
     as authors of the code. All rights reserved.
     
     Redistribution and use in source and binary forms, with
     or without modification, is permitted pursuant to, and
     subject to the license terms contained in, the Simplified
     BSD License set forth in Section 4.c of the IETF Trust''s
     Legal Provisions Relating to IETF Documents
     (http://trustee.ietf.org/license-info).
     
     This version of this YANG module is part of RFC VVVV; see
     the RFC itself for full legal notices.";

  revision 2026-02-23 {
    description
      "Initial revision.";
  }

  typedef Bool-Input {
    type enumeration {
      enum "false" {
        value 0;
        description
          "No";
      }
      enum "true" {
        value 1;
        description
          "Yes";
      }
    }
    description
      "Input true or false";
  }

  rpc shell-access-restrict-challenge {
    description
      "Restrict shell access - Challenge";
    input {
      leaf signer {
        type enumeration {
          enum "cisco" {
            value 1;
            description
              "Use Cisco consent token key for challenge";
          }
          enum "owner" {
            value 2;
            description
              "Use owner consent token key for challenge";
          }
        }
        mandatory true;
        description
          "Generate challenge string";
      }
    }
    output {
      leaf challenge-string {
        type string;
        description
          "Challenge string output";
      }
    }
    csc:xr-task "system";
    csc:cli-command "platform security shell-access restrict challenge <signer>";
    csc:xr-task "system";
  }
  rpc shell-access-unrestrict-challenge {
    description
      "Unrestrict shell access - Challenge";
    output {
      leaf challenge-string {
        type string;
        description
          "Challenge string output";
      }
    }
    csc:xr-task "system";
    csc:cli-command "platform security shell-access unrestrict challenge";
    csc:xr-task "system";
  }
  rpc shell-access-response {
    description
      "Restrict or unrestrict shell access - Response";
    input {
      leaf shell-access {
        type enumeration {
          enum "restrict" {
            value 1;
            description
              "Restrict shell access";
          }
          enum "unrestrict" {
            value 2;
            description
              "Unrestrict shell access";
          }
        }
        mandatory true;
        description
          "Restricted shell access operation";
      }
      leaf challenge-response {
        type string;
        mandatory true;
        description
          "Accept challenge response string";
      }
    }
    csc:xr-task "system";
    csc:cli-command "platform security shell-access <shell-access> response";
  }
  rpc shell-access-session-terminate {
    description
      "Terminate an existing shell access authentication session.";
    input {
      leaf shell-access {
        type enumeration {
          enum "restrict" {
            value 1;
            description
              "Restrict shell access";
          }
          enum "unrestrict" {
            value 2;
            description
              "Unrestrict shell access";
          }
        }
        mandatory true;
        description
          "Restricted shell access operation";
      }
    }
    csc:xr-task "system";
    csc:cli-command "platform security shell-access <shell-access> terminate-auth";
  }
}
