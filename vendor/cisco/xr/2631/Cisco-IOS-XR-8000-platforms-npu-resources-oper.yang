module Cisco-IOS-XR-8000-platforms-npu-resources-oper {
  namespace "http://cisco.com/ns/yang/Cisco-IOS-XR-8000-platforms-npu-resources-oper";
  prefix xr-8000-platforms-npu-resources-oper;

  import cisco-semver {
    prefix semver;
  }
  import Cisco-IOS-XR-platforms-ofa-oper {
    prefix a1;
  }
  include Cisco-IOS-XR-8000-platforms-npu-resources-oper-sub1 {
    revision-date 2026-07-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-resources package operational data.
     
     This YANG module augments the
       Cisco-IOS-XR-platforms-ofa-oper
     module with state data.
     
     Copyright (c) 2013-2026 by Cisco Systems, Inc.
     All rights reserved.";

  revision 2026-07-03 {
    description
      "Restored support for quering the stage_lb resources";
    semver:module-version "5.0.0";
  }
  revision 2025-04-17 {
    description
      "Support new HW descriptors (PBTS Group Max Offset)
       2023-09-19
          Added high watermark for each resource
       2022-11-29
          Updated yang structure to include keyed lists
       2022-09-26
          Updated to remove unused fields
       2022-08-16
          Added new hwdb resources.";
    semver:module-version "4.0.0";
  }
  revision 2020-10-07 {
    description
      "Updated leaf fields and container stats";
    semver:module-version "3.0.0";
  }
  revision 2019-04-05 {
    description
      "Establish semantic version baseline.";
    semver:module-version "1.0.0";
  }
  revision 2015-11-09 {
    description
      "IOS XR 6.0 revision.";
  }

  typedef Resource {
    type enumeration {
      enum "counter-bank" {
        value 0;
        description
          "counter bank";
      }
      enum "l3-ac-port" {
        value 1;
        description
          "l3 ac port";
      }
      enum "native-fec-entry" {
        value 2;
        description
          "native fec entry";
      }
      enum "next-hop-gid" {
        value 3;
        description
          "nexthopgid";
      }
      enum "stage1-lb-group" {
        value 4;
        description
          "stage1 lb group";
      }
      enum "stage1-lb-member" {
        value 5;
        description
          "stage1 lb member";
      }
      enum "stage2-lb-group" {
        value 6;
        description
          "stage2 lb group";
      }
      enum "stage2-lb-member" {
        value 7;
        description
          "stage2 lb member";
      }
      enum "mp-group-stage0" {
        value 8;
        description
          "mp group stage0";
      }
      enum "mp-member-stage0" {
        value 9;
        description
          "mp member stage0";
      }
      enum "mp-group-stage1" {
        value 10;
        description
          "mp group stage1";
      }
      enum "mp-member-stage1" {
        value 11;
        description
          "mp member stage1";
      }
      enum "protection-monitor-stage1" {
        value 12;
        description
          "protection monitor stage1";
      }
      enum "mp-member-stage2" {
        value 13;
        description
          "mp member stage2";
      }
      enum "v4-lpts" {
        value 14;
        description
          "v4 lpts";
      }
      enum "v6-lpts" {
        value 15;
        description
          "v6 lpts";
      }
      enum "lpts-meters" {
        value 16;
        description
          "lpts meters";
      }
      enum "central-em" {
        value 17;
        description
          "central em";
      }
      enum "egress-acl-tcam" {
        value 18;
        description
          "egress acl tcam";
      }
      enum "ingress-acl-tcam" {
        value 19;
        description
          "ingress acl tcam";
      }
      enum "lpm-tcam" {
        value 20;
        description
          "lpm tcam";
      }
      enum "mc-emdb" {
        value 21;
        description
          "mc emdb";
      }
      enum "ipv6-compressed-sips" {
        value 22;
        description
          "ipv6 compressed sips";
      }
      enum "egress-large-encap" {
        value 23;
        description
          "egress large encap";
      }
      enum "egress-small-encap" {
        value 24;
        description
          "egress small encap";
      }
      enum "tunnel-termination" {
        value 25;
        description
          "tunnel termination";
      }
      enum "sipidxtbl" {
        value 26;
        description
          "sipidxtbl";
      }
      enum "myipv4tbl" {
        value 27;
        description
          "myipv4tbl";
      }
      enum "l2-service-port" {
        value 28;
        description
          "l2 service port";
      }
      enum "egress-l3-dlp" {
        value 29;
        description
          "egress l3 dlp";
      }
      enum "protection-group" {
        value 30;
        description
          "protection group";
      }
      enum "tunnel-termination-1" {
        value 31;
        description
          "tunnel termination 1";
      }
      enum "dip-index" {
        value 32;
        description
          "dip index";
      }
      enum "mac-service-map-ping" {
        value 33;
        description
          "mac service mapping";
      }
      enum "mac-service-map-ping-1" {
        value 34;
        description
          "mac service mapping 1";
      }
      enum "mac-termination-em-table" {
        value 35;
        description
          "mac termination em table";
      }
      enum "egress-enc-em0" {
        value 36;
        description
          "egress enc em0";
      }
      enum "egress-enc-em1" {
        value 37;
        description
          "egress enc em1";
      }
      enum "egress-enc-em2" {
        value 38;
        description
          "egress enc em2";
      }
      enum "egress-enc-em3" {
        value 39;
        description
          "egress enc em3";
      }
      enum "egress-enc-em4" {
        value 40;
        description
          "egress enc em4";
      }
      enum "egress-enc-em5" {
        value 41;
        description
          "egress enc em5";
      }
      enum "service-lp-attributes-table" {
        value 42;
        description
          "service lp attributes table";
      }
      enum "additional-labels-table" {
        value 43;
        description
          "additional labels table";
      }
      enum "myipv6tbl" {
        value 44;
        description
          "myipv6tbl";
      }
      enum "vxlan-termination-vni-tbl" {
        value 45;
        description
          "vxlan termination vni tbl";
      }
      enum "vxlan-l2-dlp-tbl" {
        value 46;
        description
          "vxlan l2 dlp tbl";
      }
      enum "ipv6-vxlan-l2-dlp-tbl" {
        value 47;
        description
          "ipv6 vxlan l2 dlp tbl";
      }
      enum "l3-vxlan-overlay-mac-tbl" {
        value 48;
        description
          "l3 vxlan overlay mac tbl";
      }
      enum "ip-relay-to-vni-tbl" {
        value 49;
        description
          "ip relay to vni tbl";
      }
      enum "ipv6-relay-to-vni-tbl" {
        value 50;
        description
          "ipv6 relay to vni tbl";
      }
      enum "associate-data-table-stage0" {
        value 51;
        description
          "associate data table stage0";
      }
      enum "associate-data-table-stage1" {
        value 52;
        description
          "associate data table stage1";
      }
      enum "associate-data-table-stage2" {
        value 53;
        description
          "associate data table stage2";
      }
      enum "associate-data-table-stage3" {
        value 54;
        description
          "associate data table stage3";
      }
      enum "pbts-group-max-off-set-2-stage0-tbl" {
        value 55;
        description
          "pbts group max offset 2 stage0 tbl";
      }
      enum "pbts-group-max-off-set-4-stage0-tbl" {
        value 56;
        description
          "pbts group max offset 4 stage0 tbl";
      }
      enum "pbts-group-max-off-set-8-stage0-tbl" {
        value 57;
        description
          "pbts group max offset 8 stage0 tbl";
      }
      enum "pbts-group-max-off-set-2-stage1-tbl" {
        value 58;
        description
          "pbts group max offset 2 stage1 tbl";
      }
      enum "pbts-group-max-off-set-4-stage1-tbl" {
        value 59;
        description
          "pbts group max offset 4 stage1 tbl";
      }
      enum "pbts-group-max-off-set-8-stage1-tbl" {
        value 60;
        description
          "pbts group max offset 8 stage1 tbl";
      }
    }
    description
      "Resource";
  }

  augment "/a1:ofa/a1:stats/a1:nodes/a1:node" {
    description
      "This augment extends the operational data of
       'Cisco-IOS-XR-platforms-ofa-oper'";
    container hw-resources-datas {
      description
        "OFA HW resources stats ";
      list hw-resources-data {
        key "resource";
        description
          "Hardware resources table";
        leaf resource {
          type Resource;
          description
            "Resource type";
        }
        uses OFA-SYSDB-HW-RESOURCE;
      }
    }
  }
}
