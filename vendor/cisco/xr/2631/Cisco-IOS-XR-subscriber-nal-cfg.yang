module Cisco-IOS-XR-subscriber-nal-cfg {
  namespace "http://cisco.com/ns/yang/Cisco-IOS-XR-subscriber-nal-cfg";
  prefix subscriber-nal-cfg;

  import ietf-inet-types {
    prefix inet;
  }
  import ietf-yang-types {
    prefix yang;
  }
  import Cisco-IOS-XR-types {
    prefix xr;
  }
  import Cisco-IOS-XR-config-mda-cfg {
    prefix node;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-nal package configuration.
     
     This YANG module augments the
       Cisco-IOS-XR-ifmgr-cfg,
       Cisco-IOS-XR-config-mda-cfg
     modules with configuration data.
     
     Copyright (c) 2013-2026 by Cisco Systems, Inc.
     All rights reserved.";

  revision 2026-01-12 {
    description
      "Added config for up-instance-id description.
       2025-12-17
         Added up-instance configuration under cnbng_nal config.
       2025-12-16
         Added configuration to add ipv4 access control route for L3 routed subs
       2025-09-22
         Updated cnbng ipsubscriber initiator configuration to distinguish P-BNG and cnBNG access interface";
    semver:module-version "3.1.0";
  }
  revision 2025-07-03 {
    description
      "Added configuration to enable tracking of L2TP tunnel Ns (Next sent) and Nr (Next received) values.
       2025-06-27
          Added config to use metric as distance for framed routes
       2025-03-28
          Added config for max warm standby infilight subscriber bringup.
       2024-10-14
          Added ipv6 capability enable support for auto loopback
       2024-09-28
          Config support for routed subscriber support initiators.
       2024-06-10
          Config support for slaac enable config.
       2024-03-10
          Added afi leaf under cp-server and up-server configuration
       2024-02-10
          Added tunnel local end point to loopback mapping configuration
       2023-06-28
          Updated l2tp tcp mss configuration sysdb path.
       2023-06-16
          Added the sub-intf-range support config under the cnbng-nal.
       2023-03-24
          Deleted the group config under the cnbng-nal config.
       2022-12-16
          Config support for IPv6 ND related configurations for access interface.
       2022-04-04
          Added stats batch timer interval config CLI
       2022-03-03
          Removed headless timer interval config CLI
       2022-02-10
          Added SRG related configurations.
       2022-01-20
          Moved in-flight configurations from CMD file to ui file";
    semver:module-version "3.0.0";
  }
  revision 2021-09-28 {
    description
      "Augmented MDA common config schema
       2021-08-18
           Added support for tcp mss adjust config
       2021-07-13
           Added support for l2tp enable CLI
       2021-07-07
           Added support for pre-configuration.
       2021-05-05
           Added support for storing tr459 mode.
       2021-04-01
           NAL access interface config for LNS.";
    semver:module-version "2.0.0";
  }
  revision 2020-12-01 {
    description
      "NAL access interface config.";
    semver:module-version "1.0.0";
  }
  revision 2020-11-24 {
    description
      "Auto loopback primary address.";
  }
  revision 2019-04-05 {
    description
      "Establish semantic version baseline.";
  }
  revision 2015-11-09 {
    description
      "IOS XR 6.0 revision.";
  }

  typedef Nal-addr-family {
    type enumeration {
      enum "ipv4" {
        value 2;
        description
          "IPv4";
      }
      enum "ipv6" {
        value 10;
        description
          "IPv6";
      }
    }
    description
      "Nal addr family";
  }

  typedef Ipv6nd-router-preference {
    type enumeration {
      enum "high" {
        value 1;
        description
          "Preference high";
      }
      enum "medium" {
        value 2;
        description
          "Preference medium";
      }
      enum "low" {
        value 3;
        description
          "Preference low";
      }
    }
    description
      "Ipv6nd router preference";
  }

  grouping NODE-CFG {
    description
      "active/preconfigured nodes configuration";
    container subscriber-cnbng-nal-loc {
      presence "Indicates a subscriber-cnbng-nal-loc node is configured.";
      description
        "Table of SubscriberCnbngNalLoc";
      container nal-auto-lb-classes {
        description
          "Table of NALAutoLBClass";
        list nal-auto-lb-class {
          key "vrf-name";
          description
            "NAL Auto-Loopback configurations";
          container nal-auto-lb-int-classes {
            description
              "Table of NALAutoLBIntClass";
            list nal-auto-lb-int-class {
              key "nal-auto-lb-int-name";
              description
                "None";
              leaf nal-auto-lb-int-addr-class {
                type inet:ipv4-address-no-zone;
                description
                  "NAL auto-loopback Interface Primary-IP
                   address";
              }
              leaf nal-auto-lb-ipv6-enable {
                type uint32;
                description
                  "Constant integer value";
              }
              leaf nal-auto-lb-int-name {
                type xr:Interface-name;
                description
                  "NAL auto-loopback Interface";
              }
            }
          }
          leaf auto-lb-description {
            type string {
              length "1..256";
            }
            description
              "Description of autoloopback interfaces";
          }
          leaf vrf-name {
            type xr:Cisco-ios-xr-string;
            description
              "Constant string value";
          }
        }
      }
      container subscriber-redundancy {
        presence "Indicates a subscriber-redundancy node is configured.";
        description
          "Subscriber redundancy configuration";
        container srg-groups {
          description
            "Table of SRGGroup";
          list srg-group {
            key "srg-group-name";
            description
              "SRG group configuration";
            container access-interfaces {
              presence "Indicates a access-interfaces node is configured.";
              description
                "Access interface list for this SRG Group";
              container interface-ranges {
                description
                  "Table of InterfaceRange";
                list interface-range {
                  key "interface-name sub-interface-range-start sub-interface-range-end";
                  description
                    "Access interface";
                  leaf interface-name {
                    type xr:Interface-name;
                    description
                      "Interface name";
                  }
                  leaf sub-interface-range-start {
                    type uint32 {
                      range "0..2147483646";
                    }
                    description
                      "Sub Interface Start Index";
                  }
                  leaf sub-interface-range-end {
                    type uint32 {
                      range "0..2147483646";
                    }
                    description
                      "Sub Interface End Index";
                  }
                  leaf interface-name-xr {
                    type xr:Interface-name;
                    description
                      "Interface";
                  }
                  leaf sub-interface-range-start-xr {
                    type uint32 {
                      range "0..2147483646";
                    }
                    description
                      "Interface range start";
                  }
                  leaf sub-interface-range-end-xr {
                    type uint32 {
                      range "0..2147483646";
                    }
                    description
                      "Interface range end";
                  }
                }
              }
              leaf enable {
                type empty;
                mandatory true;
                description
                  "Enable Access interface list for this SRG
                   Group. Deletion of this object also causes
                   deletion of all associated objects under
                   SRGGroupAccessIntfList.";
              }
              list access-interface {
                key "intf-name";
                description
                  "Access interface";
                leaf intf-name {
                  type xr:Interface-name;
                  description
                    "Interface name";
                }
                leaf intf-name-xr {
                  type xr:Interface-name;
                  mandatory true;
                  description
                    "Interface name";
                }
              }
            }
            leaf description {
              type string {
                length "1..256";
              }
              description
                "Description of srg group";
            }
            leaf core-tracking-object {
              type xr:Cisco-ios-xr-string {
                length "1..32";
              }
              description
                "Core Tracking Object for this SRG Group";
            }
            leaf damping-timer {
              type uint32 {
                range "60..600";
              }
              units "second";
              description
                "Damping timer value for this SRG Group";
            }
            leaf route-tag {
              type uint32 {
                range "1..4294967295";
              }
              description
                "Route tag for subnets belonging to this
                 group";
            }
            leaf up-instance-id {
              type uint32 {
                range "1..15";
              }
              description
                "Instance ID for this group";
            }
            leaf fast-switchover-disable {
              type uint32;
              description
                "Disable fast switchover for this SRG group";
            }
            leaf access-tracking-object {
              type xr:Cisco-ios-xr-string {
                length "1..32";
              }
              description
                "Access Tracking Object for this SRG Group";
            }
            leaf vmac-address {
              type yang:mac-address;
              description
                "Virtual MAC address for this SRG Group";
            }
            leaf srg-group-name {
              type xr:Cisco-ios-xr-string {
                length "1..64";
              }
              description
                "SRG Group ID";
            }
            list access-control-route {
              key "afi";
              description
                "Access control route for this group";
              leaf afi {
                type Nal-addr-family;
                description
                  "Constant integer value";
              }
              leaf prefix-string {
                type inet:ip-address-no-zone;
                description
                  "IPv6 prefix value";
              }
              leaf prefix-mask {
                type uint32;
                description
                  "Prefix of the IP Address";
              }
              leaf vrf-name {
                type xr:Cisco-ios-xr-string {
                  length "1..32";
                }
                description
                  "VRF Name";
              }
              leaf next-hop-vrf-name {
                type xr:Cisco-ios-xr-string {
                  length "1..32";
                }
                description
                  "VRF name";
              }
              leaf next-hop-ip {
                type inet:ip-address-no-zone;
                description
                  "Next-hop address";
              }
              leaf active-tag {
                type uint32 {
                  range "1..4294967295";
                }
                description
                  "Route tag value";
              }
              leaf standby-tag {
                type uint32 {
                  range "1..4294967295";
                }
                description
                  "Route tag value";
              }
            }
            list state-control-next-hop-ip {
              key "afi";
              description
                "State control next hop ip for this group";
              leaf afi {
                type Nal-addr-family;
                description
                  "Constant integer value";
              }
              leaf next-hop-ip {
                type inet:ip-address-no-zone;
                mandatory true;
                description
                  "Next-hop address";
              }
            }
          }
        }
        leaf srg-damping-timer {
          type uint32 {
            range "60..600";
          }
          units "second";
          description
            "Timer value (in secs)";
        }
        leaf nal-stats-request-rate-timeout {
          type uint32 {
            range "10..8000";
          }
          description
            "Timeout rate of stats request(Restricted to
             development)";
        }
        leaf enable {
          type empty;
          mandatory true;
          description
            "Enable Subscriber redundancy configuration.
             Deletion of this object also causes deletion
             of all associated objects under
             SubscriberRedundancy.";
        }
        leaf nal-stats-request-rate {
          type uint32 {
            range "10..8000";
          }
          description
            "rate of stats request(Restricted to
             development)";
        }
        leaf nal-stats-request-svm-timeout {
          type uint32 {
            range "10..8000";
          }
          description
            "SVM timeout of stats request(Restricted to
             development)";
        }
      }
      container up-instance-ids {
        description
          "Table of UpInstanceId";
        list up-instance-id {
          key "up-instance-id";
          description
            "UP Instance configuration";
          container nal-trans-up-server-cfg {
            description
              "None";
            leaf afi {
              type Nal-addr-family;
              description
                "Constant integer value";
            }
            leaf prefix-string {
              type inet:ip-address-no-zone;
              description
                "IP address for the UP-Server source
                 connection";
            }
            leaf intf-name {
              type xr:Interface-name;
              description
                "Source Interface";
            }
            leaf gtp-port-num {
              type uint32 {
                range "15002..15051";
              }
              description
                "UP-server source GTP port-number";
            }
            leaf pfcp-port-num {
              type uint32 {
                range "15002..15051";
              }
              description
                "UP-server source PFCP port-number";
            }
            leaf vrf-name {
              type xr:Cisco-ios-xr-string {
                length "1..32";
              }
              description
                "UP server's VRF Name";
            }
          }
          container nal-trans-cp-server-cfg {
            description
              "None";
            container nal-cp-primary-srv-cfg {
              description
                "None";
              leaf afi {
                type Nal-addr-family;
                description
                  "Constant integer value";
              }
              leaf prefix-string {
                type inet:ip-address-no-zone;
                description
                  "IPv4 address of the CP's primary-server";
              }
            }
          }
          leaf nal-host-name {
            type xr:Cisco-ios-xr-string {
              length "1..64";
            }
            description
              "NAL Host Identifier for selected UP instance";
          }
          leaf nal-up-cp-stats-flow-ctrl {
            type uint32 {
              range "20..500";
            }
            description
              "limit";
          }
          leaf nal-instance-description {
            type string {
              length "1..256";
            }
            description
              "Description of up-instance-id";
          }
          leaf nal-up-cp-notif-flow-ctrl {
            type uint32 {
              range "20..400";
            }
            description
              "limit";
          }
          leaf nal-cp-assoc-retry-cnt {
            type uint32 {
              range "5..20";
            }
            description
              "Retry count";
          }
          leaf up-instance-id {
            type uint32 {
              range "1..15";
            }
            description
              "UP Instance ID";
          }
        }
      }
      container nal-trans-cp-server-cfg {
        description
          "None";
        container nal-cp-primary-srv-cfg {
          description
            "None";
          leaf afi {
            type Nal-addr-family;
            description
              "Constant integer value";
          }
          leaf prefix-string {
            type inet:ip-address-no-zone;
            description
              "IP address of the CP's primary-server";
          }
        }
      }
      container nal-trans-up-server-cfg {
        description
          "None";
        leaf afi {
          type Nal-addr-family;
          description
            "Constant integer value";
        }
        leaf prefix-string {
          type inet:ip-address-no-zone;
          description
            "IP address for the UP-Server source connection";
        }
        leaf intf-name {
          type xr:Interface-name;
          description
            "Source Interface";
        }
        leaf gtp-port-num {
          type uint32 {
            range "15002..15051";
          }
          description
            "UP-server source GTP port-number";
        }
        leaf pcfp-port-num {
          type uint32 {
            range "15002..15051";
          }
          description
            "UP-server source PFCP port-number";
        }
        leaf vrf-name {
          type xr:Cisco-ios-xr-string {
            length "1..32";
          }
          description
            "UP server's VRF Name";
        }
      }
      leaf nal-host-name {
        type xr:Cisco-ios-xr-string {
          length "1..64";
        }
        description
          "NAL Host-name";
      }
      leaf nal-ipoe-fsol-flow-ctrl {
        type uint32 {
          range "50..400";
        }
        description
          "None";
      }
      leaf nal-max-sub-create-in-progress {
        type uint32 {
          range "200..800";
        }
        description
          "Create request range";
      }
      leaf nal-up-cp-stats-global-flow-ctrl {
        type uint32 {
          range "150..1300";
        }
        description
          "global limit";
      }
      leaf nal-framed-route-metric-as-distance {
        type uint32;
        description
          "Constant integer value";
      }
      leaf nal-pppoe-fsol-flow-ctrl {
        type uint32 {
          range "50..400";
        }
        description
          "None";
      }
      leaf nal-route-summary-tag {
        type uint32 {
          range "1..4294967295";
        }
        description
          "Tag value";
      }
      leaf enable-tr459-mode {
        type uint32;
        description
          "Constant integer value";
      }
      leaf nal-max-delete-batch-timer {
        type uint32 {
          range "200..600";
        }
        description
          "Subscriber bulk disconnect timer timeout range";
      }
      leaf enable-l2tp-nsnr-tracking {
        type uint32;
        description
          "Constant integer value";
      }
      leaf nal-enable-sec-addr-upd {
        type uint32;
        description
          "Enable secondary address update";
      }
      leaf description {
        type string {
          length "1..256";
        }
        description
          "Config User-description";
      }
      leaf nal-up-cp-stats-flow-ctrl {
        type uint32 {
          range "20..500";
        }
        description
          "limit";
      }
      leaf nall2tp-tcp-mss-config {
        type uint32 {
          range "1280..1460";
        }
        description
          "Tcp mss adjust range";
      }
      leaf nal-trace-level {
        type uint32;
        description
          "Constant integer value";
      }
      leaf nal-disconnect-history-file-logging {
        type uint32;
        description
          "Constant integer value";
      }
      leaf nal-max-warm-sub-create-in-progress {
        type uint32 {
          range "50..200";
        }
        description
          "Create request range";
      }
      leaf disable-secondary-address-notification {
        type uint32;
        description
          "Constant integer value";
      }
      leaf nal-max-delete-batch-size {
        type uint32 {
          range "600..1000";
        }
        description
          "Subscriber bulk disconnect range";
      }
      leaf nall2tp-tunnel-lb {
        type uint32;
        description
          "Constant integer value";
      }
      leaf nal-cp-assoc-retry-cnt {
        type uint32 {
          range "5..20";
        }
        description
          "Retry count";
      }
      leaf nall2tp-subscriber-config {
        type uint32;
        description
          "Constant integer value";
      }
      leaf spa-request-response-history-file-logging {
        type uint32;
        description
          "Constant integer value";
      }
      leaf nal-max-sub-delete-in-progress {
        type uint32 {
          range "2000..4000";
        }
        description
          "Delete request range";
      }
      leaf nal-max-sub-update-in-progress {
        type uint32 {
          range "600..1400";
        }
        description
          "Update request range";
      }
      leaf nal-up-cp-notif-flow-ctrl {
        type uint32 {
          range "20..400";
        }
        description
          "limit";
      }
      leaf nal-up-cp-notif-global-flow-ctrl {
        type uint32 {
          range "100..1200";
        }
        description
          "global limit";
      }
      leaf enable {
        type empty;
        mandatory true;
        description
          "Enable Location Specification. Deletion of this
           object also causes deletion of all associated
           objects under SubscriberCnbngNalLoc.";
      }
    }
  }

  augment "/a1:interface-configurations/a1:interface-configuration" {
    description
      "This augment extends the configuration data of
       'Cisco-IOS-XR-ifmgr-cfg'";
    list interface-cnbng-nal {
      key "cnbng-intf";
      description
        "None";
      leaf enable {
        type empty;
        description
          "Enable None. Deletion of this object also
           causes deletion of all associated objects under
           InterfaceCnbngNal.";
      }
      leaf cnbng-intf {
        type xr:Cisco-ios-xr-string;
        description
          "String value";
      }
      list cnbng-nal-ip-subscriber {
        key "ip-sub";
        description
          "None";
        leaf enable {
          type empty;
          description
            "Enable None. Deletion of this object also
             causes deletion of all associated objects
             under CnbngNalIpSubscriber.";
        }
        leaf ip-sub {
          type xr:Cisco-ios-xr-string;
          description
            "String value";
        }
        list cnbng-nal-ipv4-routed-sub-enable {
          key "ipv4 ipv4-routed";
          description
            "None";
          leaf enable {
            type empty;
            description
              "Enable None. Deletion of this object also
               causes deletion of all associated objects
               under CnbngNalIpv4RoutedSubEnable.";
          }
          leaf cnbng-nal-ipv4-routed-sub-init-dhcp {
            type empty;
            description
              "Enable";
          }
          leaf ipv4 {
            type xr:Cisco-ios-xr-string;
            description
              "String value";
          }
          leaf ipv4-routed {
            type xr:Cisco-ios-xr-string;
            description
              "String value";
          }
        }
        list cnbng-nal-ipv6-routed-sub-enable {
          key "ipv6 ipv6-routed";
          description
            "None";
          container cnbng-nal-ipv6-routed-sub-init-dhcp {
            description
              "None";
            leaf prefix-len {
              type uint32 {
                range "1..127";
              }
              description
                "Prefix length";
            }
            leaf src-ip-dual-lookup {
              type uint32;
              description
                "Constant integer value";
            }
          }
          leaf enable {
            type empty;
            description
              "Enable None. Deletion of this object also
               causes deletion of all associated objects
               under CnbngNalIpv6RoutedSubEnable.";
          }
          leaf ipv6 {
            type xr:Cisco-ios-xr-string;
            description
              "String value";
          }
          leaf ipv6-routed {
            type xr:Cisco-ios-xr-string;
            description
              "String value";
          }
        }
        list cnbng-nal-ipv4-sub-enable {
          key "ipv4 ipv4l2-conn";
          description
            "None";
          leaf enable {
            type empty;
            description
              "Enable None. Deletion of this object also
               causes deletion of all associated objects
               under CnbngNalIpv4SubEnable.";
          }
          leaf cnbng-nal-ipv4-sub-init-dhcp {
            type empty;
            description
              "Enable";
          }
          leaf ipv4 {
            type xr:Cisco-ios-xr-string;
            description
              "String value";
          }
          leaf ipv4l2-conn {
            type xr:Cisco-ios-xr-string;
            description
              "String value";
          }
        }
        list cnbng-nal-ipv6-sub-enable {
          key "ipv6 ipv6l2-conn";
          description
            "None";
          leaf cnbng-nal-ipv6-sub-init-dhcp {
            type empty;
            description
              "Enable";
          }
          leaf enable {
            type empty;
            description
              "Enable None. Deletion of this object also
               causes deletion of all associated objects
               under CnbngNalIpv6SubEnable.";
          }
          leaf ipv6 {
            type xr:Cisco-ios-xr-string;
            description
              "String value";
          }
          leaf ipv6l2-conn {
            type xr:Cisco-ios-xr-string;
            description
              "String value";
          }
        }
      }
      list cnbng-nal-nd-config {
        key "ipv6-conf";
        description
          "None";
        container ra-initial {
          description
            "None";
          leaf ra-initial-count {
            type uint32 {
              range "0..32";
            }
            description
              "Initial number of Router Advertisements(RA)";
          }
          leaf ra-initial-interval {
            type uint32 {
              range "4..1800";
            }
            description
              "Initial Router Advertisement(RA) Interval
               (sec)";
          }
        }
        container ra-interval {
          description
            "None";
          leaf ra-interval-max {
            type uint32 {
              range "4..1800";
            }
            description
              "Maximum RA Interval (sec)";
          }
          leaf ra-interval-min {
            type uint32 {
              range "3..1800";
            }
            description
              "Minimum RA Interval (sec). Must be less than
               0.75 * maximum interval";
          }
        }
        leaf slaac {
          type empty;
          description
            "Enable";
        }
        leaf nud-enable {
          type empty;
          description
            "Enable";
        }
        leaf hop-limit-unspecified {
          type empty;
          description
            "Enable";
        }
        leaf managed-config {
          type empty;
          description
            "Enable";
        }
        leaf ra-lifetime {
          type uint32 {
            range "0..9000";
          }
          description
            "RA Lifetime (seconds)";
        }
        leaf mtu-suppress {
          type empty;
          description
            "Enable";
        }
        leaf ra-unicast {
          type empty;
          description
            "Enable";
        }
        leaf suppress-ra {
          type empty;
          description
            "Enable";
        }
        leaf ns-interval {
          type uint32 {
            range "1000..4294967295";
          }
          description
            "Retransmission interval in milliseconds";
        }
        leaf enable {
          type empty;
          description
            "Enable None. Deletion of this object also
             causes deletion of all associated objects
             under CnbngNalNdConfig.";
        }
        leaf other-config {
          type empty;
          description
            "Enable";
        }
        leaf start-ra-on-ipv6-enable {
          type empty;
          description
            "Enable";
        }
        leaf suppress-cache-learning {
          type empty;
          description
            "Enable";
        }
        leaf router-preference {
          type Ipv6nd-router-preference;
          description
            "Set router preference";
        }
        leaf reachable-time {
          type uint32 {
            range "0..3600000";
          }
          description
            "Reachability time in milliseconds";
        }
        leaf ipv6-conf {
          type xr:Cisco-ios-xr-string;
          description
            "String value";
        }
      }
    }
  }
  augment "/a1:interface-configurations/a1:interface-configuration" {
    description
      "This augment extends the configuration data of
       'Cisco-IOS-XR-ifmgr-cfg'";
    container cnbng-nal-pppoe-subscriber {
      description
        "None";
      leaf pppoe {
        type uint32;
        description
          "Constant integer value";
      }
      leaf bba-group {
        type string;
        description
          "The bba-group to use";
      }
    }
  }
  augment "/a1:interface-configurations/a1:interface-configuration" {
    description
      "This augment extends the configuration data of
       'Cisco-IOS-XR-ifmgr-cfg'";
    leaf cnbng-nal-lns-subscriber {
      type empty;
      description
        "Enable";
    }
  }
  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
