submodule Cisco-IOS-XR-dnx-driver-oper-sub2 {
  belongs-to Cisco-IOS-XR-dnx-driver-oper {
    prefix Cisco-IOS-XR-dnx-driver-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR dnx-driver package operational data.
     
     Copyright (c) 2013-2025 by Cisco Systems, Inc.
     All rights reserved.";

  revision 2025-12-10 {
    description
      "added L2 and L3 forwarding table operational data.";
    semver:module-version "1.3.0";
  }
  revision 2020-04-29 {
    description
      "added bundle_id and lane_id to get bundle port information.";
    semver:module-version "1.2.0";
  }
  revision 2019-04-05 {
    description
      "Establish semantic version baseline.";
    semver:module-version "1.1.0";
  }
  revision 2017-08-29 {
    description
      "Changed blk and field info to be dynamic.";
  }
  revision 2015-11-09 {
    description
      "IOS XR 6.0 revision.";
  }

  grouping BCM-TABLE-METADATA {
    description
      "BCM TABLE METADATA";
    leaf magic {
      type uint32;
      description
        "Protocol Marker (0x46574454 = 'FWDT')";
    }
    leaf sdk-version {
      type uint32;
      description
        "BCM SDK Version (major<<16 | minor<<8 | patch)";
    }
    leaf table-type {
      type uint32;
      description
        "Table Type (see bcm_table_type)";
    }
    leaf entry-struct-size {
      type uint32;
      units "byte";
      description
        "Size of Each Entry Structure (bytes)";
    }
    leaf entry-count {
      type uint32;
      description
        "Number of Entries in This Chunk";
    }
    leaf total-hw-entries {
      type uint32;
      description
        "Total Entries in Hardware (all chunks)";
    }
    leaf timestamp-ns {
      type uint64;
      units "nanosecond";
      description
        "Collection Timestamp (nanoseconds since Unix
         epoch)";
    }
    leaf session-timestamp-ns {
      type uint64;
      units "nanosecond";
      description
        "Session Timestamp - Common across related tables
         (nanoseconds since Unix epoch)";
    }
    leaf sequence-number {
      type uint32;
      description
        "Chunk Sequence Number (0-based)";
    }
    leaf chunk-count {
      type uint32;
      description
        "Total Number of Chunks";
    }
    leaf checksum {
      type uint32;
      description
        "CRC32 of Entry Data";
    }
    leaf node-id {
      type uint16;
      description
        "Node ID (numeric)";
    }
    leaf asic-instance {
      type uint16;
      description
        "ASIC/NPU Instance Number";
    }
    leaf hw-type {
      type uint8;
      description
        "Hardware Type: 0=Unknown, 1=Jericho, 2=Jericho+,
         3=Jericho2, 4=Jericho2C";
    }
    leaf padding {
      type uint8;
      description
        "Padding for 8-byte alignment";
    }
  }

  grouping BCM-TABLE-CHUNK {
    description
      "BCM TABLE CHUNK";
    container metadata {
      description
        "Table and Chunk Metadata";
      uses BCM-TABLE-METADATA;
    }
    leaf entries {
      type yang:hex-string;
      description
        "Variable-Length Entry Array (size = entry_count
         * entry_struct_size)";
    }
  }
}
