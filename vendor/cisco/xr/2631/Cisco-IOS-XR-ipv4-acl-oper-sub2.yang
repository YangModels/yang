submodule Cisco-IOS-XR-ipv4-acl-oper-sub2 {
  belongs-to Cisco-IOS-XR-ipv4-acl-oper {
    prefix Cisco-IOS-XR-ipv4-acl-oper;
  }

  import cisco-semver {
    prefix semver;
  }
  include Cisco-IOS-XR-ipv4-acl-oper-sub1 {
    revision-date 2025-05-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-acl package operational data.
     
     Copyright (c) 2013-2025 by Cisco Systems, Inc.
     All rights reserved.";

  revision 2025-05-05 {
    description
      "Removing the unused seqeunce string leaf";
    semver:module-version "2.0.0";
  }
  revision 2021-03-05 {
    description
      "Adding a new policer stats field.CSCvx54997";
    semver:module-version "1.2.0";
  }
  revision 2020-11-13 {
    description
      "Adding policer and priority.";
    semver:module-version "1.1.0";
  }
  revision 2019-04-05 {
    description
      "Establish semantic version baseline.";
    semver:module-version "1.0.1";
  }
  revision 2019-02-12 {
    description
      "Fixing CSCvn61905.";
  }
  revision 2017-05-01 {
    description
      "Fixing backward compatibility error in module.";
  }
  revision 2015-11-09 {
    description
      "IOS XR 6.0 revision.";
  }

  grouping MPLS-ACL-EDM-OOR-DETAIL {
    description
      "mpls Oor detail config BAG";
    leaf current-configured-ac-ls {
      type uint32;
      description
        "Current configured mpls acls";
    }
    leaf current-configured-ac-es {
      type uint32;
      description
        "Current configured mpls aces";
    }
  }

  grouping MPLS-ACL-EDM-ACE {
    description
      "MPLS bag";
    leaf sequence {
      type uint32;
      description
        "ACLE sequence number";
    }
    leaf grant {
      type Acl-action;
      description
        "Permit/deny";
    }
    leaf exp1 {
      type uint8;
      description
        "MPLS Exp1";
    }
    leaf exp2 {
      type uint8;
      description
        "MPLS Exp2";
    }
    leaf exp3 {
      type uint8;
      description
        "MPLS Exp3";
    }
    leaf label1-value1 {
      type uint32;
      description
        "Label1 Value1";
    }
    leaf label1-value2 {
      type uint32;
      description
        "Label1 Value2";
    }
    leaf label1-operator {
      type uint8;
      description
        "Label1 Operator";
    }
    leaf label2-value1 {
      type uint32;
      description
        "Label2 Value1";
    }
    leaf label2-value2 {
      type uint32;
      description
        "Label2 Value2";
    }
    leaf label2-operator {
      type uint8;
      description
        "Label2 Operator";
    }
    leaf label3-value1 {
      type uint32;
      description
        "Label3 Value1";
    }
    leaf label3-value2 {
      type uint32;
      description
        "Label3 Value2";
    }
    leaf label3-operator {
      type uint8;
      description
        "Label3 Operator";
    }
    leaf acl-name {
      type string;
      description
        "ACL Name";
    }
    leaf exp1-present {
      type boolean;
      description
        "Exp1 Present";
    }
    leaf exp2-present {
      type boolean;
      description
        "Exp2 Present";
    }
    leaf exp3-present {
      type boolean;
      description
        "Exp3 Present";
    }
  }
}
