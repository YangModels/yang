//*************  DO-NOT EDIT  **************
//*********** Auto-generated file ********** 

 module cisco-xr-openconfig-platform-fabric-deviations {

  prefix  "oc-fabricdevs";

  namespace "http://cisco.com/ns/yang/cisco-xr-openconfig-platform-fabric-deviations";

  import openconfig-platform-fabric { prefix oc-fabric; }
  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-platform-fabric.yang@2022-07-28 

     on Cisco IOS-XR devices.

     Copyright (c) 2017 by Cisco Systems, Inc.
     All rights reserved.";

  revision "2023-06-07" {
    description
      "Initial revision applicable to IOS-XR 6.4.1";
  }


  deviation /oc-platform:components/oc-platform:component/oc-platform:fabric/oc-platform:config/oc-fabric:power-admin-state {
    deviate delete {
      default POWER_ENABLED;
    }
  }

  deviation /oc-platform:components/oc-platform:component/oc-platform:fabric/oc-platform:state/oc-fabric:power-admin-state {
    deviate delete {
      default POWER_ENABLED;
    }
  }


}
//total deviations:2
