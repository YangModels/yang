module Cisco-IOS-XR-um-ssm-cfg {
  yang-version 1.1;
  namespace "http://cisco.com/ns/yang/Cisco-IOS-XR-um-ssm-cfg";
  prefix um-ssm-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     Service State Manager (SSM) configuration.
     
     Copyright (c) 2021-2026 by Cisco Systems, Inc., and/or its affiliates.
     All rights reserved.";

  revision 2026-03-24 {
    description
      "Update to align with latest IOS-XR YANG quality guidelines.";
    semver:module-version "2.0.0";
  }
  revision 2021-01-18 {
    description
      "Initial release";
    semver:module-version "1.0.0";
  }

  container ssm {
    description
      "Service availability specific configuration";
    container monitor {
      description
        "Enabling/disabling monitoring at an SDR scope";
      container service {
        description
          "Service availability";
        leaf disable {
          type empty;
          description
            "Disable service monitoring";
        }
      }
    }
  }
}
