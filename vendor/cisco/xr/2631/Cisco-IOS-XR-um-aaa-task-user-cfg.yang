module Cisco-IOS-XR-um-aaa-task-user-cfg {
  namespace "http://cisco.com/ns/yang/Cisco-IOS-XR-um-aaa-task-user-cfg";
  prefix um-aaa-task-user-cfg;

  import Cisco-IOS-XR-types {
    prefix xr;
  }
  import Cisco-IOS-XR-um-line-cfg {
    prefix a1;
  }
  import Cisco-IOS-XR-um-aaa-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-task-user package configuration.
     
     This YANG module augments the
     modules with configuration data.
     
     Copyright (c) 2020-2025 by Cisco Systems, Inc., and/or its affiliates.
     All rights reserved.";

  revision 2024-10-18 {
    description
      "Restored container password-policy with deprecation note, as its cli is also restored. Added deprecation note to 3 password policy options.";
    semver:module-version "2.0.0";
  }
  revision 2021-01-05 {
    description
      "Initial release";
    semver:module-version "1.0.0";
  }

  feature pslib_check_password {
    description
      "pslib check password";
  }

  augment "/a1:line/a1:console" {
    description
      "This augment extends line console nodes configuration";
    container login {
      description
        "Line login configuration";
      leaf authentication {
        type union {
          type string {
            pattern "default" {
              description
                "Use the default authentication list";
            }
          }
          type xr:Cisco-ios-xr-string {
            length "1..1024" {
              description
                "Use an authentication list with this name";
            }
          }
        }
        description
          "Authentication parameters";
      }
    }
    container authorization {
      description
        "Authorization parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf eventmanager {
        type union {
          type string {
            pattern "default" {
              description
                "Use the default authorization list";
            }
          }
          type xr:Cisco-ios-xr-string {
            length "1..1024" {
              description
                "Use an authorization list with this name";
            }
          }
        }
        description
          "Set eventmanager authorization method";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container accounting {
      description
        "Accounting parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container password {
      description
        "Specify the password for the user";
      leaf seven {
        type xr:Proprietary-password;
        description
          "Specifies that an encrypted password";
      }
    }
    container secret {
      description
        "Provide a secure one way encrypted password";
      leaf five {
        type xr:Proprietary-password;
        description
          "The encrypted user password string";
      }
    }
    container timeout {
      description
        "Timeouts for the line";
      container login {
        description
          "Timeouts related to the login sequence";
        leaf response {
          type uint32 {
            range "0..300" {
              description
                "Timeout in seconds (default 30 seconds)";
            }
          }
          description
            "Timeouts for any user input during login sequence";
        }
      }
    }
    container users {
      description
        "Users characteristics";
      list group {
        key "group-name";
        description
          "Name of the user group";
        leaf group-name {
          type union {
            type string {
              pattern "cisco-support" {
                description
                  "Cisco support personnel";
              }
            }
            type string {
              pattern "netadmin" {
                description
                  "Network administrators group";
              }
            }
            type string {
              pattern "operator" {
                description
                  "Operator group";
              }
            }
            type string {
              pattern "root-lr" {
                description
                  "Root LR group";
              }
            }
            type string {
              pattern "serviceadmin" {
                description
                  "Service administrators group";
              }
            }
            type string {
              pattern "sysadmin" {
                description
                  "System administrators group";
              }
            }
            type xr:Cisco-ios-xr-string {
              length "1..1024" {
                description
                  "Name of the user group";
              }
            }
          }
          description
            "Name of the user group";
        }
      }
    }
  }
  augment "/a1:line/a1:default" {
    description
      "This augment extends line default nodes configuration";
    container login {
      description
        "Line login configuration";
      leaf authentication {
        type union {
          type string {
            pattern "default" {
              description
                "Use the default authentication list";
            }
          }
          type xr:Cisco-ios-xr-string {
            length "1..1024" {
              description
                "Use an authentication list with this name";
            }
          }
        }
        description
          "Authentication parameters";
      }
    }
    container authorization {
      description
        "Authorization parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf eventmanager {
        type union {
          type string {
            pattern "default" {
              description
                "Use the default authorization list";
            }
          }
          type xr:Cisco-ios-xr-string {
            length "1..1024" {
              description
                "Use an authorization list with this name";
            }
          }
        }
        description
          "Set eventmanager authorization method";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container accounting {
      description
        "Accounting parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container password {
      description
        "Specify the password for the user";
      leaf seven {
        type xr:Proprietary-password;
        description
          "Specifies that an encrypted password";
      }
    }
    container secret {
      description
        "Provide a secure one way encrypted password";
      leaf five {
        type xr:Proprietary-password;
        description
          "The encrypted user password string";
      }
    }
    container timeout {
      description
        "Timeouts for the line";
      container login {
        description
          "Timeouts related to the login sequence";
        leaf response {
          type uint32 {
            range "0..300" {
              description
                "Timeout in seconds (default 30 seconds)";
            }
          }
          description
            "Timeouts for any user input during login sequence";
        }
      }
    }
    container users {
      description
        "Users characteristics";
      list group {
        key "group-name";
        description
          "Name of the user group";
        leaf group-name {
          type union {
            type string {
              pattern "cisco-support" {
                description
                  "Cisco support personnel";
              }
            }
            type string {
              pattern "netadmin" {
                description
                  "Network administrators group";
              }
            }
            type string {
              pattern "operator" {
                description
                  "Operator group";
              }
            }
            type string {
              pattern "root-lr" {
                description
                  "Root LR group";
              }
            }
            type string {
              pattern "serviceadmin" {
                description
                  "Service administrators group";
              }
            }
            type string {
              pattern "sysadmin" {
                description
                  "System administrators group";
              }
            }
            type xr:Cisco-ios-xr-string {
              length "1..1024" {
                description
                  "Name of the user group";
              }
            }
          }
          description
            "Name of the user group";
        }
      }
    }
  }
  augment "/a1:line/a1:templates/a1:template" {
    description
      "This augment extends line template nodes configuration";
    container login {
      description
        "Line login configuration";
      leaf authentication {
        type union {
          type string {
            pattern "default" {
              description
                "Use the default authentication list";
            }
          }
          type xr:Cisco-ios-xr-string {
            length "1..1024" {
              description
                "Use an authentication list with this name";
            }
          }
        }
        description
          "Authentication parameters";
      }
    }
    container authorization {
      description
        "Authorization parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf eventmanager {
        type union {
          type string {
            pattern "default" {
              description
                "Use the default authorization list";
            }
          }
          type xr:Cisco-ios-xr-string {
            length "1..1024" {
              description
                "Use an authorization list with this name";
            }
          }
        }
        description
          "Set eventmanager authorization method";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container accounting {
      description
        "Accounting parameters";
      leaf exec {
        type union {
          type string {
            pattern "default" {
              description
                "Use the default authorization list";
            }
          }
          type xr:Cisco-ios-xr-string {
            length "1..1024" {
              description
                "Use an authorization list with this name";
            }
          }
        }
        description
          "For starting an exec (shell)";
      }
      leaf commands {
        type union {
          type string {
            pattern "default" {
              description
                "Use the default authorization list";
            }
          }
          type xr:Cisco-ios-xr-string {
            length "1..1024" {
              description
                "Use an authorization list with this name";
            }
          }
        }
        description
          "For exec (shell) commands";
      }
    }
    container password {
      description
        "Specify the password for the user";
      leaf seven {
        type xr:Proprietary-password;
        description
          "Specifies that an encrypted password";
      }
    }
    container secret {
      description
        "Provide a secure one way encrypted password";
      leaf five {
        type xr:Proprietary-password;
        description
          "The encrypted user password string";
      }
    }
    container timeout {
      description
        "Timeouts for the line";
      container login {
        description
          "Timeouts related to the login sequence";
        leaf response {
          type uint32 {
            range "0..300" {
              description
                "Timeout in seconds (default 30 seconds)";
            }
          }
          description
            "Timeouts for any user input during login sequence";
        }
      }
    }
    container users {
      description
        "Users characteristics";
      list group {
        key "group-name";
        description
          "Name of the user group";
        leaf group-name {
          type union {
            type string {
              pattern "cisco-support" {
                description
                  "Cisco support personnel";
              }
            }
            type string {
              pattern "netadmin" {
                description
                  "Network administrators group";
              }
            }
            type string {
              pattern "operator" {
                description
                  "Operator group";
              }
            }
            type string {
              pattern "root-lr" {
                description
                  "Root LR group";
              }
            }
            type string {
              pattern "serviceadmin" {
                description
                  "Service administrators group";
              }
            }
            type string {
              pattern "sysadmin" {
                description
                  "System administrators group";
              }
            }
            type xr:Cisco-ios-xr-string {
              length "1..1024" {
                description
                  "Name of the user group";
              }
            }
          }
          description
            "Name of the user group";
        }
      }
    }
  }
  augment "/a2:aaa" {
    description
      "This augment extends aaa nodes configuration";
    container admin-accounting {
      description
        "Admin Accounting Enable/Disable";
      container enable {
        must "not(../disable)";
        presence "Indicates a enable node is configured.";
        description
          "enable calvados accounting";
      }
      container disable {
        must "not(../enable)";
        presence "Indicates a disable node is configured.";
        description
          "disable calvados accounting";
      }
    }
    leaf default-taskgroup {
      type xr:Cisco-ios-xr-string {
        length "1..800" {
          description
            "Name of the taskgroup to be used";
        }
      }
      description
        "Default taskgroup to be used for remote authentication";
    }
    container password-policies {
      description
        "AAA password Policy";
      list password-policy {
        key "password-policy-name";
        description
          "Password Policy name";
        leaf password-policy-name {
          type string {
            length "1..253" {
              description
                "Password Policy name.
                 Allowed special chars for password policy are _,-,.,;,:,$,#,space allowed with backslash";
            }
          }
          description
            "Password Policy name";
        }
        leaf min-length {
          type uint32 {
            range "2..253" {
              description
                "Minimum length <2-253>, default is 2";
            }
          }
          description
            "Specify the minimum length of the password/secret";
        }
        leaf max-length {
          type uint32 {
            range "2..253" {
              description
                "Maximum length <2-253>, default is 253";
            }
          }
          description
            "Specify the maximum length of the password/secret";
        }
        leaf upper-case {
          type uint32 {
            range "0..253" {
              description
                "Number of upper-case characters <0-253>, default is 0.";
            }
          }
          description
            "Number of upper-case characters required in password/secret";
        }
        leaf lower-case {
          type uint32 {
            range "0..253" {
              description
                "Number of lower-case characters <0-253>, default is 0.";
            }
          }
          description
            "Number of lower-case characters required in password/secret";
        }
        leaf special-char {
          type uint32 {
            range "0..253" {
              description
                "Number of special characters <0-253>, default is 0.";
            }
          }
          description
            "Number of special characters required in password/secret";
        }
        leaf numeric {
          type uint32 {
            range "0..253" {
              description
                "Number of numeric characters <0-253>, default is 0.";
            }
          }
          description
            "Number of numeric characters required in password/secret";
        }
        leaf min-char-change {
          type uint32 {
            range "0..253" {
              description
                "Number of characters change required <0-253>, default is 4.";
            }
          }
          status deprecated;
          description
            "Number of characters change required between old and new passwords (deprecated, will be removed in 25.3.1)";
        }
        leaf max-char-repetition {
          type uint32 {
            range "2..5" {
              description
                "Number of times a character can repeat <2-5>, default is 0.";
            }
          }
          description
            "Number of times consecutively a character can repeat in the password";
        }
        leaf restrict-old-count {
          type uint32 {
            range "0..10" {
              description
                "Represents the history of passwords/secrets that cannot be reused now";
            }
          }
          description
            "Count for the number of old passwords/secrets that cannot be reused";
        }
        container restrict-old-time {
          description
            "Time for which any old password/secret is considered as valid history";
          leaf years {
            type uint32 {
              range "0..99" {
                description
                  "Number of years";
              }
            }
            description
              "Number of years";
          }
          leaf months {
            type uint32 {
              range "0..11" {
                description
                  "Number of months";
              }
            }
            description
              "Number of months";
          }
          leaf days {
            type uint32 {
              range "0..30" {
                description
                  "Number of days";
              }
            }
            description
              "Number of days";
          }
        }
        container restrict-username {
          presence "Indicates a restrict-username node is configured.";
          description
            "Restricts the usage of associated username as password/secret";
        }
        container restrict-username-reverse {
          presence "Indicates a restrict-username-reverse node is configured.";
          description
            "Restricts the usage of associated username reversed as password/secret";
        }
        container restrict-password-reverse {
          presence "Indicates a restrict-password-reverse node is configured.";
          status deprecated;
          description
            "Restricts the password to be same as reversed old password (deprecated, will be removed in 25.3.1)";
        }
        container restrict-password-advanced {
          presence "Indicates a restrict-password-advanced node is configured.";
          status deprecated;
          description
            "Advanced restrictions on new password (deprecated, will be removed in 25.3.1)";
        }
        container lifetime {
          description
            "Lifetime of the password/secret";
          leaf years {
            type uint32 {
              range "0..99" {
                description
                  "Number of years";
              }
            }
            description
              "Number of years";
          }
          leaf months {
            type uint32 {
              range "0..11" {
                description
                  "Number of months";
              }
            }
            description
              "Number of months";
          }
          leaf days {
            type uint32 {
              range "0..30" {
                description
                  "Number of days";
              }
            }
            description
              "Number of days";
          }
          leaf hours {
            type uint32 {
              range "0..23" {
                description
                  "Number of hours";
              }
            }
            description
              "Number of hours";
          }
          leaf minutes {
            type uint32 {
              range "0..59" {
                description
                  "Number of minutes";
              }
            }
            description
              "Number of minutes";
          }
          leaf seconds {
            type uint32 {
              range "30..59" {
                description
                  "Number of seconds";
              }
            }
            description
              "Number of seconds";
          }
        }
        container lockout-time {
          description
            "Lockout time for the maximum authentication failures";
          leaf days {
            type uint32 {
              range "0..255" {
                description
                  "Number of days";
              }
            }
            description
              "Number of days";
          }
          leaf hours {
            type uint32 {
              range "0..23" {
                description
                  "Number of hours";
              }
            }
            description
              "Number of hours";
          }
          leaf minutes {
            type uint32 {
              range "0..59" {
                description
                  "Number of minutes";
              }
            }
            description
              "Number of minutes";
          }
          leaf seconds {
            type uint32 {
              range "0..59" {
                description
                  "Number of seconds";
              }
            }
            description
              "Number of seconds";
          }
        }
        container warn-interval {
          description
            "Warning interval to notify about expiring password/secret";
          leaf years {
            type uint32 {
              range "0..99" {
                description
                  "Number of years";
              }
            }
            description
              "Number of years";
          }
          leaf months {
            type uint32 {
              range "0..11" {
                description
                  "Number of months";
              }
            }
            description
              "Number of months";
          }
          leaf days {
            type uint32 {
              range "0..30" {
                description
                  "Number of days";
              }
            }
            description
              "Number of days";
          }
          leaf hours {
            type uint32 {
              range "0..23" {
                description
                  "Number of hours";
              }
            }
            description
              "Number of hours";
          }
          leaf minutes {
            type uint32 {
              range "0..59" {
                description
                  "Number of minutes";
              }
            }
            description
              "Number of minutes";
          }
          leaf seconds {
            type uint32 {
              range "30..59" {
                description
                  "Number of seconds";
              }
            }
            description
              "Number of seconds";
          }
        }
        leaf authen-max-attempts {
          type uint32 {
            range "1..24" {
              description
                "Number of attempts, default is 0.";
            }
          }
          description
            "Maximum authentication failures to be allowed.";
        }
        container restrict-consecutive-characters {
          description
            "Restrict consecutive letters and decimal numbers from English alphabet and qwerty keyboard";
          leaf english-alphabet {
            type uint32 {
              range "2..26" {
                description
                  "Number of characters";
              }
            }
            description
              "Restrict consecutive letters from English alphabet";
          }
          container cyclic-wrap-en {
            must "../english-alphabet";
            presence "Indicates a cyclic-wrap node is configured.";
            description
              "Restrict consecutive English letters from cyclic wrapping, e.g. yzab";
          }
          leaf qwerty-keyboard {
            type uint32 {
              range "2..10" {
                description
                  "Number of characters";
              }
            }
            description
              "Restrict consecutive alphanumeric characters from qwerty keyboard";
          }
          container cyclic-wrap-qt {
            must "../qwerty-keyboard";
            presence "Indicates a cyclic-wrap node is configured.";
            description
              "Restrict alphanumeric characters on the qwerty keyboard from cyclic wrapping, e.g. opqw, 9012";
          }
        }
      }
    }
    container enable-cert-authentication {
      presence "Indicates a enable-cert-authentication node is configured.";
      description
        "Enables OpenSSH Certificate based authentication for TACACS+ users. Mandates exec authorization configuration with TACACS+";
    }
    container display-login-failed-users {
      presence "Indicates a display-login-failed-users node is configured.";
      description
        "Enable to display login failed usernames in syslog after failure attempt";
    }
    container map-to {
      description
        "AAA username map-to SPIFFE ID";
      container usernames {
        description
          "Configure username to be mapped with SPIFFE ID";
        list username {
          key "name";
          description
            "Configure username to be mapped with SPIFFE ID";
          leaf name {
            type string {
              length "1..255" {
                description
                  "Specify user name";
              }
            }
            description
              "Configure username to be mapped with SPIFFE ID";
          }
          container spiffe-id {
            description
              "Spiffe-id to mapped with the user";
            container any {
              presence "Indicates a any node is configured.";
              description
                "Any spiffe-id";
            }
          }
        }
      }
    }
    container usergroups {
      description
        "Configure user group";
      list usergroup {
        key "usergroup-name";
        description
          "Usergroup name";
        leaf usergroup-name {
          type string {
            length "1..253" {
              description
                "Usergroup name.
                 Allowed special chars for usergroup name are _-.";
            }
          }
          description
            "Usergroup name";
        }
        leaf description {
          type string {
            length "1..800" {
              description
                "Description for this group";
            }
          }
          description
            "Description for the user group";
        }
        container taskgroup {
          description
            "Task group associated with this group";
          container root-lr {
            presence "Indicates a root-lr node is configured.";
            description
              "Root LR group";
          }
          container netadmin {
            presence "Indicates a netadmin node is configured.";
            description
              "Network administrators group";
          }
          container sysadmin {
            presence "Indicates a sysadmin node is configured.";
            description
              "System administrators group";
          }
          container serviceadmin {
            presence "Indicates a serviceadmin node is configured.";
            description
              "Service administrators group";
          }
          container operator {
            presence "Indicates a operator node is configured.";
            description
              "Operator group";
          }
          container cisco-support {
            presence "Indicates a cisco-support node is configured.";
            description
              "Technical support group";
          }
          container maintenance {
            presence "Indicates a maintenance node is configured.";
            description
              "Maintenance group";
          }
          container provisioning {
            presence "Indicates a provisioning node is configured.";
            description
              "Provisioning group";
          }
          container retrieve {
            presence "Indicates a retrieve node is configured.";
            description
              "Retrieve group";
          }
          container read-only-tg {
            presence "Indicates a read-only-tg node is configured.";
            description
              "Read only group";
          }
          container task-groups {
            description
              "Name of the task group";
            list task-group {
              key "task-group-name";
              description
                "Name of the task group";
              leaf task-group-name {
                type string {
                  length "1..800" {
                    description
                      "Name of the task group";
                  }
                }
                description
                  "Name of the task group";
              }
            }
          }
        }
        container inherit {
          description
            "Inherit to this user group";
          list usergroup {
            key "usergroup-name";
            description
              "User group to be inherited by this group";
            leaf usergroup-name {
              type string {
                length "1..253" {
                  description
                    "Name of the user group.
                     Allowed special chars for usergroup name are _-.";
                }
              }
              description
                "User group to be inherited by this group";
            }
          }
        }
      }
    }
    container taskgroups {
      description
        "Configure task group";
      list taskgroup {
        key "taskgroup-name";
        description
          "Taskgroup name";
        leaf taskgroup-name {
          type string {
            length "1..253" {
              description
                "Taskgroup name.
                 Allowed all special chars except ? without prepended backslash and space without prepended backslash";
            }
          }
          description
            "Taskgroup name";
        }
        leaf description {
          type string {
            length "1..800" {
              description
                "Description for this group";
            }
          }
          description
            "Description for the task group";
        }
        container task {
          description
            "Specify a task ID to be part of this group";
          container read {
            description
              "Specify a read-type task ID";
            container bgp {
              presence "Indicates a bgp node is configured.";
              description
                "Border Gateway Protocol";
            }
            container ospf {
              presence "Indicates a ospf node is configured.";
              description
                "Open Shortest Pathway First";
            }
            container hsrp {
              presence "Indicates a hsrp node is configured.";
              description
                "Hot Standby Routing Protocol";
            }
            container isis {
              presence "Indicates a isis node is configured.";
              description
                "Intermediate System-Intermediate System";
            }
            container route-map {
              presence "Indicates a route-map node is configured.";
              description
                "Policy filtering and redistribution of routes";
            }
            container route-policy {
              presence "Indicates a route-policy node is configured.";
              description
                "Route Policy";
            }
            container static {
              presence "Indicates a static node is configured.";
              description
                "Static Routing";
            }
            container vrrp {
              presence "Indicates a vrrp node is configured.";
              description
                "Virtual Router Redundancy Protocol";
            }
            container cef {
              presence "Indicates a cef node is configured.";
              description
                "Cisco Express Forwarding/FIB";
            }
            container lpts {
              presence "Indicates a lpts node is configured.";
              description
                "Local Packet Transport Service";
            }
            container ipv4 {
              presence "Indicates a ipv4 node is configured.";
              description
                "IPv4";
            }
            container rib {
              presence "Indicates a rib node is configured.";
              description
                "Controls and monitors the routing table (RIB)";
            }
            container multicast {
              presence "Indicates a multicast node is configured.";
              description
                "Multicast management including PIM, IGMP, etc.";
            }
            container mpls-te {
              presence "Indicates a mpls-te node is configured.";
              description
                "Multi-protocol Label Switching - Traffic Engineering";
            }
            container mpls-ldp {
              presence "Indicates a mpls-ldp node is configured.";
              description
                "Multi-protocol Label Switching - Label Distribution Protocol";
            }
            container mpls-static {
              presence "Indicates a mpls-static node is configured.";
              description
                "Multi-protocol Label Switching - Static configuration";
            }
            container ouni {
              presence "Indicates a ouni node is configured.";
              description
                "Optical UNI";
            }
            container fabric {
              presence "Indicates a fabric node is configured.";
              description
                "Fabric Management";
            }
            container bundle {
              presence "Indicates a bundle node is configured.";
              description
                "Bundles";
            }
            container network {
              presence "Indicates a network node is configured.";
              description
                "IPv4, IPv6, ICMP, CLNS, ...";
            }
            container transport {
              presence "Indicates a transport node is configured.";
              description
                "TCP/UDP";
            }
            container ppp {
              presence "Indicates a ppp node is configured.";
              description
                "Point-to-Point Protocol";
            }
            container hdlc {
              presence "Indicates a hdlc node is configured.";
              description
                "High-level Data Link Control";
            }
            container pos-dpt {
              presence "Indicates a pos-dpt node is configured.";
              description
                "Packet-Over-SONET/Dynamic Packet Transport";
            }
            container sonet-sdh {
              presence "Indicates a sonet-sdh node is configured.";
              description
                "SONET/SDH Transport including APS/MSP";
            }
            container dwdm {
              presence "Indicates a dwdm node is configured.";
              description
                "DWDM Transport";
            }
            container tunnel {
              presence "Indicates a tunnel node is configured.";
              description
                "GRE, UTI";
            }
            container vlan {
              presence "Indicates a vlan node is configured.";
              description
                "Virtual Local Area Network";
            }
            container qos {
              presence "Indicates a qos node is configured.";
              description
                "Quality of Service";
            }
            container acl {
              presence "Indicates a acl node is configured.";
              description
                "Access Control List";
            }
            container aaa {
              presence "Indicates a aaa node is configured.";
              description
                "AAA";
            }
            container crypto {
              presence "Indicates a crypto node is configured.";
              description
                "ipsec, ssl";
            }
            container snmp {
              presence "Indicates a snmp node is configured.";
              description
                "Simple Network Management Protocol";
            }
            container config-mgmt {
              presence "Indicates a config-mgmt node is configured.";
              description
                "Create/copy/delete configuration checkpoints";
            }
            container config-services {
              presence "Indicates a config-services node is configured.";
              description
                "Configure/monitor web server, ORB, SSH, XML Agent.";
            }
            container host-services {
              presence "Indicates a host-services node is configured.";
              description
                "Configure/monitor hostname, clock, timestamps, etc.";
            }
            container boot {
              presence "Indicates a boot node is configured.";
              description
                "reload, boot";
            }
            container fault-mgr {
              presence "Indicates a fault-mgr node is configured.";
              description
                "Configure/monitor fault manager settings";
            }
            container filesystem {
              presence "Indicates a filesystem node is configured.";
              description
                "Execute rcs, erase, format, fsck, etc.";
            }
            container interface {
              presence "Indicates a interface node is configured.";
              description
                "Configure/monitor basic (or common) interface characteristics";
            }
            container ip-services {
              presence "Indicates a ip-services node is configured.";
              description
                "Configure/monitor DNS, DHCP, ARP, NTP, ARM, Domain services";
            }
            container pkg-mgmt {
              presence "Indicates a pkg-mgmt node is configured.";
              description
                "Install operations, SAM";
            }
            container system {
              presence "Indicates a system node is configured.";
              description
                "LR Redundancy/pairing, logical interface/node grouping, LACP";
            }
            container tty-access {
              presence "Indicates a tty-access node is configured.";
              description
                "Configure/monitor Line (tty/vty), banner, etc.";
            }
            container basic-services {
              presence "Indicates a basic-services node is configured.";
              description
                "Ping, show version/privileges, etc.";
            }
            container cdp {
              presence "Indicates a cdp node is configured.";
              description
                "Cisco Discovery Protocol";
            }
            container diag {
              presence "Indicates a diag node is configured.";
              description
                "exception, coredump, itrace, monitor, stats";
            }
            container ext-access {
              presence "Indicates a ext-access node is configured.";
              description
                "Execute RCP, RSH, FTP, TFTP, rlogin, telnet, ...";
            }
            container bcdl {
              presence "Indicates a bcdl node is configured.";
              description
                "Bulk Content Downloader";
            }
            container sysmgr {
              presence "Indicates a sysmgr node is configured.";
              description
                "Placement/process, chkpt, mbus, gsp, netio, qnet, SysDB, qsm, driver infrastructure";
            }
            container logging {
              presence "Indicates a logging node is configured.";
              description
                "logging, alarm";
            }
            container netflow {
              presence "Indicates a netflow node is configured.";
              description
                "Netflow application";
            }
            container drivers {
              presence "Indicates a drivers node is configured.";
              description
                "Driver related functions";
            }
            container fr {
              presence "Indicates a fr node is configured.";
              description
                "Frame-Relay";
            }
            container monitor {
              presence "Indicates a monitor node is configured.";
              description
                "Monitor system resource/performance characteristics";
            }
            container inventory {
              presence "Indicates a inventory node is configured.";
              description
                "Inventory information management";
            }
            container ipv6 {
              presence "Indicates a ipv6 node is configured.";
              description
                "IPv6";
            }
            container admin {
              presence "Indicates a admin node is configured.";
              description
                "Admin plane functions";
            }
            container atm {
              presence "Indicates a atm node is configured.";
              description
                "Asynchronous Transfer Mode";
            }
            container bfd {
              presence "Indicates a bfd node is configured.";
              description
                "Bidirectional Forwarding Protocol";
            }
            container rip {
              presence "Indicates a rip node is configured.";
              description
                "Routing Information Protocol";
            }
            container eigrp {
              presence "Indicates a eigrp node is configured.";
              description
                "Enhanced Interior Gateway Routing Protocol";
            }
            container sbc {
              presence "Indicates a sbc node is configured.";
              description
                "Session Border Controller";
            }
            container firewall {
              presence "Indicates a firewall node is configured.";
              description
                "Firewall operations";
            }
            container l2vpn {
              presence "Indicates a l2vpn node is configured.";
              description
                "Layer 2 VPN";
            }
            container ethernet-services {
              presence "Indicates a ethernet-services node is configured.";
              description
                "Ethernet Services and OAM";
            }
            container eem {
              presence "Indicates a eem node is configured.";
              description
                "Embedded Event Manager";
            }
            container li {
              presence "Indicates a li node is configured.";
              description
                "Lawful Intercept component";
            }
            container ancp {
              presence "Indicates a ancp node is configured.";
              description
                "Access Node Control Protocol";
            }
            container cgn {
              presence "Indicates a cgn node is configured.";
              description
                "Carrier Grade Nat";
            }
            container call-home {
              presence "Indicates a call-home node is configured.";
              description
                "call-home";
            }
            container rcmd {
              presence "Indicates a rcmd node is configured.";
              description
                "Routing Convergence Monitoring and Diagnostics";
            }
            container vpdn {
              presence "Indicates a vpdn node is configured.";
              description
                "Virtual Private Dial-up Network (VPDN)";
            }
            container nps {
              presence "Indicates a nps node is configured.";
              description
                "Network Positioning System (NPS)";
            }
            container lisp {
              presence "Indicates a lisp node is configured.";
              description
                "Locator/Identifier Separation Protocol";
            }
            container pbr {
              presence "Indicates a pbr node is configured.";
              description
                "Policy Based Routing";
            }
            container otn {
              presence "Indicates a otn node is configured.";
              description
                "Optical Transport Network";
            }
            container nacm {
              presence "Indicates a nacm node is configured.";
              description
                "Netconf Authorization Control Module";
            }
            container plat-mgr {
              presence "Indicates a plat-mgr node is configured.";
              description
                "Platform Mgr Module";
            }
            container cpri {
              presence "Indicates a cpri node is configured.";
              description
                "cpri controller taskid";
            }
            container lldp {
              presence "Indicates a lldp node is configured.";
              description
                "Support LLDP protocol";
            }
            container l2rib {
              presence "Indicates a l2rib node is configured.";
              description
                "Layer 2 RIB";
            }
            container dossier {
              presence "Indicates a dossier node is configured.";
              description
                "Support for dossier related collection/CLIs";
            }
            container fti {
              presence "Indicates a fti node is configured.";
              description
                "Support for FTI CLIs";
            }
            container fc {
              presence "Indicates a fc node is configured.";
              description
                "Fibre Channel controller taskid";
            }
          }
          container write {
            description
              "Specify a read-write-type task ID";
            container bgp {
              presence "Indicates a bgp node is configured.";
              description
                "Border Gateway Protocol";
            }
            container ospf {
              presence "Indicates a ospf node is configured.";
              description
                "Open Shortest Pathway First";
            }
            container hsrp {
              presence "Indicates a hsrp node is configured.";
              description
                "Hot Standby Routing Protocol";
            }
            container isis {
              presence "Indicates a isis node is configured.";
              description
                "Intermediate System-Intermediate System";
            }
            container route-map {
              presence "Indicates a route-map node is configured.";
              description
                "Policy filtering and redistribution of routes";
            }
            container route-policy {
              presence "Indicates a route-policy node is configured.";
              description
                "Route Policy";
            }
            container static {
              presence "Indicates a static node is configured.";
              description
                "Static Routing";
            }
            container vrrp {
              presence "Indicates a vrrp node is configured.";
              description
                "Virtual Router Redundancy Protocol";
            }
            container cef {
              presence "Indicates a cef node is configured.";
              description
                "Cisco Express Forwarding/FIB";
            }
            container lpts {
              presence "Indicates a lpts node is configured.";
              description
                "Local Packet Transport Service";
            }
            container ipv4 {
              presence "Indicates a ipv4 node is configured.";
              description
                "IPv4";
            }
            container rib {
              presence "Indicates a rib node is configured.";
              description
                "Controls and monitors the routing table (RIB)";
            }
            container multicast {
              presence "Indicates a multicast node is configured.";
              description
                "Multicast management including PIM, IGMP, etc.";
            }
            container mpls-te {
              presence "Indicates a mpls-te node is configured.";
              description
                "Multi-protocol Label Switching - Traffic Engineering";
            }
            container mpls-ldp {
              presence "Indicates a mpls-ldp node is configured.";
              description
                "Multi-protocol Label Switching - Label Distribution Protocol";
            }
            container mpls-static {
              presence "Indicates a mpls-static node is configured.";
              description
                "Multi-protocol Label Switching - Static configuration";
            }
            container ouni {
              presence "Indicates a ouni node is configured.";
              description
                "Optical UNI";
            }
            container fabric {
              presence "Indicates a fabric node is configured.";
              description
                "Fabric Management";
            }
            container bundle {
              presence "Indicates a bundle node is configured.";
              description
                "Bundles";
            }
            container network {
              presence "Indicates a network node is configured.";
              description
                "IPv4, IPv6, ICMP, CLNS, ...";
            }
            container transport {
              presence "Indicates a transport node is configured.";
              description
                "TCP/UDP";
            }
            container ppp {
              presence "Indicates a ppp node is configured.";
              description
                "Point-to-Point Protocol";
            }
            container hdlc {
              presence "Indicates a hdlc node is configured.";
              description
                "High-level Data Link Control";
            }
            container pos-dpt {
              presence "Indicates a pos-dpt node is configured.";
              description
                "Packet-Over-SONET/Dynamic Packet Transport";
            }
            container sonet-sdh {
              presence "Indicates a sonet-sdh node is configured.";
              description
                "SONET/SDH Transport including APS/MSP";
            }
            container dwdm {
              presence "Indicates a dwdm node is configured.";
              description
                "DWDM Transport";
            }
            container tunnel {
              presence "Indicates a tunnel node is configured.";
              description
                "GRE, UTI";
            }
            container vlan {
              presence "Indicates a vlan node is configured.";
              description
                "Virtual Local Area Network";
            }
            container qos {
              presence "Indicates a qos node is configured.";
              description
                "Quality of Service";
            }
            container acl {
              presence "Indicates a acl node is configured.";
              description
                "Access Control List";
            }
            container aaa {
              presence "Indicates a aaa node is configured.";
              description
                "AAA";
            }
            container crypto {
              presence "Indicates a crypto node is configured.";
              description
                "ipsec, ssl";
            }
            container snmp {
              presence "Indicates a snmp node is configured.";
              description
                "Simple Network Management Protocol";
            }
            container config-mgmt {
              presence "Indicates a config-mgmt node is configured.";
              description
                "Create/copy/delete configuration checkpoints";
            }
            container config-services {
              presence "Indicates a config-services node is configured.";
              description
                "Configure/monitor web server, ORB, SSH, XML Agent.";
            }
            container host-services {
              presence "Indicates a host-services node is configured.";
              description
                "Configure/monitor hostname, clock, timestamps, etc.";
            }
            container boot {
              presence "Indicates a boot node is configured.";
              description
                "reload, boot";
            }
            container fault-mgr {
              presence "Indicates a fault-mgr node is configured.";
              description
                "Configure/monitor fault manager settings";
            }
            container filesystem {
              presence "Indicates a filesystem node is configured.";
              description
                "Execute rcs, erase, format, fsck, etc.";
            }
            container interface {
              presence "Indicates a interface node is configured.";
              description
                "Configure/monitor basic (or common) interface characteristics";
            }
            container ip-services {
              presence "Indicates a ip-services node is configured.";
              description
                "Configure/monitor DNS, DHCP, ARP, NTP, ARM, Domain services";
            }
            container pkg-mgmt {
              presence "Indicates a pkg-mgmt node is configured.";
              description
                "Install operations, SAM";
            }
            container system {
              presence "Indicates a system node is configured.";
              description
                "LR Redundancy/pairing, logical interface/node grouping, LACP";
            }
            container tty-access {
              presence "Indicates a tty-access node is configured.";
              description
                "Configure/monitor Line (tty/vty), banner, etc.";
            }
            container basic-services {
              presence "Indicates a basic-services node is configured.";
              description
                "Ping, show version/privileges, etc.";
            }
            container cdp {
              presence "Indicates a cdp node is configured.";
              description
                "Cisco Discovery Protocol";
            }
            container diag {
              presence "Indicates a diag node is configured.";
              description
                "exception, coredump, itrace, monitor, stats";
            }
            container ext-access {
              presence "Indicates a ext-access node is configured.";
              description
                "Execute RCP, RSH, FTP, TFTP, rlogin, telnet, ...";
            }
            container bcdl {
              presence "Indicates a bcdl node is configured.";
              description
                "Bulk Content Downloader";
            }
            container sysmgr {
              presence "Indicates a sysmgr node is configured.";
              description
                "Placement/process, chkpt, mbus, gsp, netio, qnet, SysDB, qsm, driver infrastructure";
            }
            container logging {
              presence "Indicates a logging node is configured.";
              description
                "logging, alarm";
            }
            container netflow {
              presence "Indicates a netflow node is configured.";
              description
                "Netflow application";
            }
            container drivers {
              presence "Indicates a drivers node is configured.";
              description
                "Driver related functions";
            }
            container fr {
              presence "Indicates a fr node is configured.";
              description
                "Frame-Relay";
            }
            container monitor {
              presence "Indicates a monitor node is configured.";
              description
                "Monitor system resource/performance characteristics";
            }
            container inventory {
              presence "Indicates a inventory node is configured.";
              description
                "Inventory information management";
            }
            container ipv6 {
              presence "Indicates a ipv6 node is configured.";
              description
                "IPv6";
            }
            container admin {
              presence "Indicates a admin node is configured.";
              description
                "Admin plane functions";
            }
            container atm {
              presence "Indicates a atm node is configured.";
              description
                "Asynchronous Transfer Mode";
            }
            container bfd {
              presence "Indicates a bfd node is configured.";
              description
                "Bidirectional Forwarding Protocol";
            }
            container rip {
              presence "Indicates a rip node is configured.";
              description
                "Routing Information Protocol";
            }
            container eigrp {
              presence "Indicates a eigrp node is configured.";
              description
                "Enhanced Interior Gateway Routing Protocol";
            }
            container sbc {
              presence "Indicates a sbc node is configured.";
              description
                "Session Border Controller";
            }
            container firewall {
              presence "Indicates a firewall node is configured.";
              description
                "Firewall operations";
            }
            container l2vpn {
              presence "Indicates a l2vpn node is configured.";
              description
                "Layer 2 VPN";
            }
            container ethernet-services {
              presence "Indicates a ethernet-services node is configured.";
              description
                "Ethernet Services and OAM";
            }
            container eem {
              presence "Indicates a eem node is configured.";
              description
                "Embedded Event Manager";
            }
            container li {
              presence "Indicates a li node is configured.";
              description
                "Lawful Intercept component";
            }
            container ancp {
              presence "Indicates a ancp node is configured.";
              description
                "Access Node Control Protocol";
            }
            container cgn {
              presence "Indicates a cgn node is configured.";
              description
                "Carrier Grade Nat";
            }
            container call-home {
              presence "Indicates a call-home node is configured.";
              description
                "call-home";
            }
            container rcmd {
              presence "Indicates a rcmd node is configured.";
              description
                "Routing Convergence Monitoring and Diagnostics";
            }
            container vpdn {
              presence "Indicates a vpdn node is configured.";
              description
                "Virtual Private Dial-up Network (VPDN)";
            }
            container nps {
              presence "Indicates a nps node is configured.";
              description
                "Network Positioning System (NPS)";
            }
            container lisp {
              presence "Indicates a lisp node is configured.";
              description
                "Locator/Identifier Separation Protocol";
            }
            container pbr {
              presence "Indicates a pbr node is configured.";
              description
                "Policy Based Routing";
            }
            container otn {
              presence "Indicates a otn node is configured.";
              description
                "Optical Transport Network";
            }
            container nacm {
              presence "Indicates a nacm node is configured.";
              description
                "Netconf Authorization Control Module";
            }
            container plat-mgr {
              presence "Indicates a plat-mgr node is configured.";
              description
                "Platform Mgr Module";
            }
            container cpri {
              presence "Indicates a cpri node is configured.";
              description
                "cpri controller taskid";
            }
            container lldp {
              presence "Indicates a lldp node is configured.";
              description
                "Support LLDP protocol";
            }
            container l2rib {
              presence "Indicates a l2rib node is configured.";
              description
                "Layer 2 RIB";
            }
            container dossier {
              presence "Indicates a dossier node is configured.";
              description
                "Support for dossier related collection/CLIs";
            }
            container fti {
              presence "Indicates a fti node is configured.";
              description
                "Support for FTI CLIs";
            }
            container fc {
              presence "Indicates a fc node is configured.";
              description
                "Fibre Channel controller taskid";
            }
          }
          container execute {
            description
              "Specify a execute-type task ID";
            container bgp {
              presence "Indicates a bgp node is configured.";
              description
                "Border Gateway Protocol";
            }
            container ospf {
              presence "Indicates a ospf node is configured.";
              description
                "Open Shortest Pathway First";
            }
            container hsrp {
              presence "Indicates a hsrp node is configured.";
              description
                "Hot Standby Routing Protocol";
            }
            container isis {
              presence "Indicates a isis node is configured.";
              description
                "Intermediate System-Intermediate System";
            }
            container route-map {
              presence "Indicates a route-map node is configured.";
              description
                "Policy filtering and redistribution of routes";
            }
            container route-policy {
              presence "Indicates a route-policy node is configured.";
              description
                "Route Policy";
            }
            container static {
              presence "Indicates a static node is configured.";
              description
                "Static Routing";
            }
            container vrrp {
              presence "Indicates a vrrp node is configured.";
              description
                "Virtual Router Redundancy Protocol";
            }
            container cef {
              presence "Indicates a cef node is configured.";
              description
                "Cisco Express Forwarding/FIB";
            }
            container lpts {
              presence "Indicates a lpts node is configured.";
              description
                "Local Packet Transport Service";
            }
            container ipv4 {
              presence "Indicates a ipv4 node is configured.";
              description
                "IPv4";
            }
            container rib {
              presence "Indicates a rib node is configured.";
              description
                "Controls and monitors the routing table (RIB)";
            }
            container multicast {
              presence "Indicates a multicast node is configured.";
              description
                "Multicast management including PIM, IGMP, etc.";
            }
            container mpls-te {
              presence "Indicates a mpls-te node is configured.";
              description
                "Multi-protocol Label Switching - Traffic Engineering";
            }
            container mpls-ldp {
              presence "Indicates a mpls-ldp node is configured.";
              description
                "Multi-protocol Label Switching - Label Distribution Protocol";
            }
            container mpls-static {
              presence "Indicates a mpls-static node is configured.";
              description
                "Multi-protocol Label Switching - Static configuration";
            }
            container ouni {
              presence "Indicates a ouni node is configured.";
              description
                "Optical UNI";
            }
            container fabric {
              presence "Indicates a fabric node is configured.";
              description
                "Fabric Management";
            }
            container bundle {
              presence "Indicates a bundle node is configured.";
              description
                "Bundles";
            }
            container network {
              presence "Indicates a network node is configured.";
              description
                "IPv4, IPv6, ICMP, CLNS, ...";
            }
            container transport {
              presence "Indicates a transport node is configured.";
              description
                "TCP/UDP";
            }
            container ppp {
              presence "Indicates a ppp node is configured.";
              description
                "Point-to-Point Protocol";
            }
            container hdlc {
              presence "Indicates a hdlc node is configured.";
              description
                "High-level Data Link Control";
            }
            container pos-dpt {
              presence "Indicates a pos-dpt node is configured.";
              description
                "Packet-Over-SONET/Dynamic Packet Transport";
            }
            container sonet-sdh {
              presence "Indicates a sonet-sdh node is configured.";
              description
                "SONET/SDH Transport including APS/MSP";
            }
            container dwdm {
              presence "Indicates a dwdm node is configured.";
              description
                "DWDM Transport";
            }
            container tunnel {
              presence "Indicates a tunnel node is configured.";
              description
                "GRE, UTI";
            }
            container vlan {
              presence "Indicates a vlan node is configured.";
              description
                "Virtual Local Area Network";
            }
            container qos {
              presence "Indicates a qos node is configured.";
              description
                "Quality of Service";
            }
            container acl {
              presence "Indicates a acl node is configured.";
              description
                "Access Control List";
            }
            container aaa {
              presence "Indicates a aaa node is configured.";
              description
                "AAA";
            }
            container crypto {
              presence "Indicates a crypto node is configured.";
              description
                "ipsec, ssl";
            }
            container snmp {
              presence "Indicates a snmp node is configured.";
              description
                "Simple Network Management Protocol";
            }
            container config-mgmt {
              presence "Indicates a config-mgmt node is configured.";
              description
                "Create/copy/delete configuration checkpoints";
            }
            container config-services {
              presence "Indicates a config-services node is configured.";
              description
                "Configure/monitor web server, ORB, SSH, XML Agent.";
            }
            container host-services {
              presence "Indicates a host-services node is configured.";
              description
                "Configure/monitor hostname, clock, timestamps, etc.";
            }
            container boot {
              presence "Indicates a boot node is configured.";
              description
                "reload, boot";
            }
            container fault-mgr {
              presence "Indicates a fault-mgr node is configured.";
              description
                "Configure/monitor fault manager settings";
            }
            container filesystem {
              presence "Indicates a filesystem node is configured.";
              description
                "Execute rcs, erase, format, fsck, etc.";
            }
            container interface {
              presence "Indicates a interface node is configured.";
              description
                "Configure/monitor basic (or common) interface characteristics";
            }
            container ip-services {
              presence "Indicates a ip-services node is configured.";
              description
                "Configure/monitor DNS, DHCP, ARP, NTP, ARM, Domain services";
            }
            container pkg-mgmt {
              presence "Indicates a pkg-mgmt node is configured.";
              description
                "Install operations, SAM";
            }
            container system {
              presence "Indicates a system node is configured.";
              description
                "LR Redundancy/pairing, logical interface/node grouping, LACP";
            }
            container tty-access {
              presence "Indicates a tty-access node is configured.";
              description
                "Configure/monitor Line (tty/vty), banner, etc.";
            }
            container basic-services {
              presence "Indicates a basic-services node is configured.";
              description
                "Ping, show version/privileges, etc.";
            }
            container cdp {
              presence "Indicates a cdp node is configured.";
              description
                "Cisco Discovery Protocol";
            }
            container diag {
              presence "Indicates a diag node is configured.";
              description
                "exception, coredump, itrace, monitor, stats";
            }
            container ext-access {
              presence "Indicates a ext-access node is configured.";
              description
                "Execute RCP, RSH, FTP, TFTP, rlogin, telnet, ...";
            }
            container bcdl {
              presence "Indicates a bcdl node is configured.";
              description
                "Bulk Content Downloader";
            }
            container sysmgr {
              presence "Indicates a sysmgr node is configured.";
              description
                "Placement/process, chkpt, mbus, gsp, netio, qnet, SysDB, qsm, driver infrastructure";
            }
            container logging {
              presence "Indicates a logging node is configured.";
              description
                "logging, alarm";
            }
            container netflow {
              presence "Indicates a netflow node is configured.";
              description
                "Netflow application";
            }
            container drivers {
              presence "Indicates a drivers node is configured.";
              description
                "Driver related functions";
            }
            container fr {
              presence "Indicates a fr node is configured.";
              description
                "Frame-Relay";
            }
            container monitor {
              presence "Indicates a monitor node is configured.";
              description
                "Monitor system resource/performance characteristics";
            }
            container inventory {
              presence "Indicates a inventory node is configured.";
              description
                "Inventory information management";
            }
            container ipv6 {
              presence "Indicates a ipv6 node is configured.";
              description
                "IPv6";
            }
            container admin {
              presence "Indicates a admin node is configured.";
              description
                "Admin plane functions";
            }
            container atm {
              presence "Indicates a atm node is configured.";
              description
                "Asynchronous Transfer Mode";
            }
            container bfd {
              presence "Indicates a bfd node is configured.";
              description
                "Bidirectional Forwarding Protocol";
            }
            container rip {
              presence "Indicates a rip node is configured.";
              description
                "Routing Information Protocol";
            }
            container eigrp {
              presence "Indicates a eigrp node is configured.";
              description
                "Enhanced Interior Gateway Routing Protocol";
            }
            container sbc {
              presence "Indicates a sbc node is configured.";
              description
                "Session Border Controller";
            }
            container firewall {
              presence "Indicates a firewall node is configured.";
              description
                "Firewall operations";
            }
            container l2vpn {
              presence "Indicates a l2vpn node is configured.";
              description
                "Layer 2 VPN";
            }
            container ethernet-services {
              presence "Indicates a ethernet-services node is configured.";
              description
                "Ethernet Services and OAM";
            }
            container eem {
              presence "Indicates a eem node is configured.";
              description
                "Embedded Event Manager";
            }
            container li {
              presence "Indicates a li node is configured.";
              description
                "Lawful Intercept component";
            }
            container ancp {
              presence "Indicates a ancp node is configured.";
              description
                "Access Node Control Protocol";
            }
            container cgn {
              presence "Indicates a cgn node is configured.";
              description
                "Carrier Grade Nat";
            }
            container call-home {
              presence "Indicates a call-home node is configured.";
              description
                "call-home";
            }
            container rcmd {
              presence "Indicates a rcmd node is configured.";
              description
                "Routing Convergence Monitoring and Diagnostics";
            }
            container vpdn {
              presence "Indicates a vpdn node is configured.";
              description
                "Virtual Private Dial-up Network (VPDN)";
            }
            container nps {
              presence "Indicates a nps node is configured.";
              description
                "Network Positioning System (NPS)";
            }
            container lisp {
              presence "Indicates a lisp node is configured.";
              description
                "Locator/Identifier Separation Protocol";
            }
            container pbr {
              presence "Indicates a pbr node is configured.";
              description
                "Policy Based Routing";
            }
            container otn {
              presence "Indicates a otn node is configured.";
              description
                "Optical Transport Network";
            }
            container nacm {
              presence "Indicates a nacm node is configured.";
              description
                "Netconf Authorization Control Module";
            }
            container plat-mgr {
              presence "Indicates a plat-mgr node is configured.";
              description
                "Platform Mgr Module";
            }
            container cpri {
              presence "Indicates a cpri node is configured.";
              description
                "cpri controller taskid";
            }
            container lldp {
              presence "Indicates a lldp node is configured.";
              description
                "Support LLDP protocol";
            }
            container l2rib {
              presence "Indicates a l2rib node is configured.";
              description
                "Layer 2 RIB";
            }
            container dossier {
              presence "Indicates a dossier node is configured.";
              description
                "Support for dossier related collection/CLIs";
            }
            container fti {
              presence "Indicates a fti node is configured.";
              description
                "Support for FTI CLIs";
            }
            container fc {
              presence "Indicates a fc node is configured.";
              description
                "Fibre Channel controller taskid";
            }
          }
          container debug {
            description
              "Specify a debug-type task ID";
            container bgp {
              presence "Indicates a bgp node is configured.";
              description
                "Border Gateway Protocol";
            }
            container ospf {
              presence "Indicates a ospf node is configured.";
              description
                "Open Shortest Pathway First";
            }
            container hsrp {
              presence "Indicates a hsrp node is configured.";
              description
                "Hot Standby Routing Protocol";
            }
            container isis {
              presence "Indicates a isis node is configured.";
              description
                "Intermediate System-Intermediate System";
            }
            container route-map {
              presence "Indicates a route-map node is configured.";
              description
                "Policy filtering and redistribution of routes";
            }
            container route-policy {
              presence "Indicates a route-policy node is configured.";
              description
                "Route Policy";
            }
            container static {
              presence "Indicates a static node is configured.";
              description
                "Static Routing";
            }
            container vrrp {
              presence "Indicates a vrrp node is configured.";
              description
                "Virtual Router Redundancy Protocol";
            }
            container cef {
              presence "Indicates a cef node is configured.";
              description
                "Cisco Express Forwarding/FIB";
            }
            container lpts {
              presence "Indicates a lpts node is configured.";
              description
                "Local Packet Transport Service";
            }
            container ipv4 {
              presence "Indicates a ipv4 node is configured.";
              description
                "IPv4";
            }
            container rib {
              presence "Indicates a rib node is configured.";
              description
                "Controls and monitors the routing table (RIB)";
            }
            container multicast {
              presence "Indicates a multicast node is configured.";
              description
                "Multicast management including PIM, IGMP, etc.";
            }
            container mpls-te {
              presence "Indicates a mpls-te node is configured.";
              description
                "Multi-protocol Label Switching - Traffic Engineering";
            }
            container mpls-ldp {
              presence "Indicates a mpls-ldp node is configured.";
              description
                "Multi-protocol Label Switching - Label Distribution Protocol";
            }
            container mpls-static {
              presence "Indicates a mpls-static node is configured.";
              description
                "Multi-protocol Label Switching - Static configuration";
            }
            container ouni {
              presence "Indicates a ouni node is configured.";
              description
                "Optical UNI";
            }
            container fabric {
              presence "Indicates a fabric node is configured.";
              description
                "Fabric Management";
            }
            container bundle {
              presence "Indicates a bundle node is configured.";
              description
                "Bundles";
            }
            container network {
              presence "Indicates a network node is configured.";
              description
                "IPv4, IPv6, ICMP, CLNS, ...";
            }
            container transport {
              presence "Indicates a transport node is configured.";
              description
                "TCP/UDP";
            }
            container ppp {
              presence "Indicates a ppp node is configured.";
              description
                "Point-to-Point Protocol";
            }
            container hdlc {
              presence "Indicates a hdlc node is configured.";
              description
                "High-level Data Link Control";
            }
            container pos-dpt {
              presence "Indicates a pos-dpt node is configured.";
              description
                "Packet-Over-SONET/Dynamic Packet Transport";
            }
            container sonet-sdh {
              presence "Indicates a sonet-sdh node is configured.";
              description
                "SONET/SDH Transport including APS/MSP";
            }
            container dwdm {
              presence "Indicates a dwdm node is configured.";
              description
                "DWDM Transport";
            }
            container tunnel {
              presence "Indicates a tunnel node is configured.";
              description
                "GRE, UTI";
            }
            container vlan {
              presence "Indicates a vlan node is configured.";
              description
                "Virtual Local Area Network";
            }
            container qos {
              presence "Indicates a qos node is configured.";
              description
                "Quality of Service";
            }
            container acl {
              presence "Indicates a acl node is configured.";
              description
                "Access Control List";
            }
            container aaa {
              presence "Indicates a aaa node is configured.";
              description
                "AAA";
            }
            container crypto {
              presence "Indicates a crypto node is configured.";
              description
                "ipsec, ssl";
            }
            container snmp {
              presence "Indicates a snmp node is configured.";
              description
                "Simple Network Management Protocol";
            }
            container config-mgmt {
              presence "Indicates a config-mgmt node is configured.";
              description
                "Create/copy/delete configuration checkpoints";
            }
            container config-services {
              presence "Indicates a config-services node is configured.";
              description
                "Configure/monitor web server, ORB, SSH, XML Agent.";
            }
            container host-services {
              presence "Indicates a host-services node is configured.";
              description
                "Configure/monitor hostname, clock, timestamps, etc.";
            }
            container boot {
              presence "Indicates a boot node is configured.";
              description
                "reload, boot";
            }
            container fault-mgr {
              presence "Indicates a fault-mgr node is configured.";
              description
                "Configure/monitor fault manager settings";
            }
            container filesystem {
              presence "Indicates a filesystem node is configured.";
              description
                "Execute rcs, erase, format, fsck, etc.";
            }
            container interface {
              presence "Indicates a interface node is configured.";
              description
                "Configure/monitor basic (or common) interface characteristics";
            }
            container ip-services {
              presence "Indicates a ip-services node is configured.";
              description
                "Configure/monitor DNS, DHCP, ARP, NTP, ARM, Domain services";
            }
            container pkg-mgmt {
              presence "Indicates a pkg-mgmt node is configured.";
              description
                "Install operations, SAM";
            }
            container system {
              presence "Indicates a system node is configured.";
              description
                "LR Redundancy/pairing, logical interface/node grouping, LACP";
            }
            container tty-access {
              presence "Indicates a tty-access node is configured.";
              description
                "Configure/monitor Line (tty/vty), banner, etc.";
            }
            container basic-services {
              presence "Indicates a basic-services node is configured.";
              description
                "Ping, show version/privileges, etc.";
            }
            container cdp {
              presence "Indicates a cdp node is configured.";
              description
                "Cisco Discovery Protocol";
            }
            container diag {
              presence "Indicates a diag node is configured.";
              description
                "exception, coredump, itrace, monitor, stats";
            }
            container ext-access {
              presence "Indicates a ext-access node is configured.";
              description
                "Execute RCP, RSH, FTP, TFTP, rlogin, telnet, ...";
            }
            container bcdl {
              presence "Indicates a bcdl node is configured.";
              description
                "Bulk Content Downloader";
            }
            container sysmgr {
              presence "Indicates a sysmgr node is configured.";
              description
                "Placement/process, chkpt, mbus, gsp, netio, qnet, SysDB, qsm, driver infrastructure";
            }
            container logging {
              presence "Indicates a logging node is configured.";
              description
                "logging, alarm";
            }
            container netflow {
              presence "Indicates a netflow node is configured.";
              description
                "Netflow application";
            }
            container drivers {
              presence "Indicates a drivers node is configured.";
              description
                "Driver related functions";
            }
            container fr {
              presence "Indicates a fr node is configured.";
              description
                "Frame-Relay";
            }
            container monitor {
              presence "Indicates a monitor node is configured.";
              description
                "Monitor system resource/performance characteristics";
            }
            container inventory {
              presence "Indicates a inventory node is configured.";
              description
                "Inventory information management";
            }
            container ipv6 {
              presence "Indicates a ipv6 node is configured.";
              description
                "IPv6";
            }
            container admin {
              presence "Indicates a admin node is configured.";
              description
                "Admin plane functions";
            }
            container atm {
              presence "Indicates a atm node is configured.";
              description
                "Asynchronous Transfer Mode";
            }
            container bfd {
              presence "Indicates a bfd node is configured.";
              description
                "Bidirectional Forwarding Protocol";
            }
            container rip {
              presence "Indicates a rip node is configured.";
              description
                "Routing Information Protocol";
            }
            container eigrp {
              presence "Indicates a eigrp node is configured.";
              description
                "Enhanced Interior Gateway Routing Protocol";
            }
            container sbc {
              presence "Indicates a sbc node is configured.";
              description
                "Session Border Controller";
            }
            container firewall {
              presence "Indicates a firewall node is configured.";
              description
                "Firewall operations";
            }
            container l2vpn {
              presence "Indicates a l2vpn node is configured.";
              description
                "Layer 2 VPN";
            }
            container ethernet-services {
              presence "Indicates a ethernet-services node is configured.";
              description
                "Ethernet Services and OAM";
            }
            container eem {
              presence "Indicates a eem node is configured.";
              description
                "Embedded Event Manager";
            }
            container li {
              presence "Indicates a li node is configured.";
              description
                "Lawful Intercept component";
            }
            container ancp {
              presence "Indicates a ancp node is configured.";
              description
                "Access Node Control Protocol";
            }
            container cgn {
              presence "Indicates a cgn node is configured.";
              description
                "Carrier Grade Nat";
            }
            container call-home {
              presence "Indicates a call-home node is configured.";
              description
                "call-home";
            }
            container rcmd {
              presence "Indicates a rcmd node is configured.";
              description
                "Routing Convergence Monitoring and Diagnostics";
            }
            container vpdn {
              presence "Indicates a vpdn node is configured.";
              description
                "Virtual Private Dial-up Network (VPDN)";
            }
            container nps {
              presence "Indicates a nps node is configured.";
              description
                "Network Positioning System (NPS)";
            }
            container lisp {
              presence "Indicates a lisp node is configured.";
              description
                "Locator/Identifier Separation Protocol";
            }
            container pbr {
              presence "Indicates a pbr node is configured.";
              description
                "Policy Based Routing";
            }
            container otn {
              presence "Indicates a otn node is configured.";
              description
                "Optical Transport Network";
            }
            container nacm {
              presence "Indicates a nacm node is configured.";
              description
                "Netconf Authorization Control Module";
            }
            container plat-mgr {
              presence "Indicates a plat-mgr node is configured.";
              description
                "Platform Mgr Module";
            }
            container cpri {
              presence "Indicates a cpri node is configured.";
              description
                "cpri controller taskid";
            }
            container lldp {
              presence "Indicates a lldp node is configured.";
              description
                "Support LLDP protocol";
            }
            container l2rib {
              presence "Indicates a l2rib node is configured.";
              description
                "Layer 2 RIB";
            }
            container dossier {
              presence "Indicates a dossier node is configured.";
              description
                "Support for dossier related collection/CLIs";
            }
            container fti {
              presence "Indicates a fti node is configured.";
              description
                "Support for FTI CLIs";
            }
            container fc {
              presence "Indicates a fc node is configured.";
              description
                "Fibre Channel controller taskid";
            }
          }
        }
        container inherit {
          description
            "Inherit to include into this taskgroup";
          container taskgroup {
            description
              "Specify a taskgroup to inherit from";
            container root-lr {
              presence "Indicates a root-lr node is configured.";
              description
                "Root LR taskgroup";
            }
            container netadmin {
              presence "Indicates a netadmin node is configured.";
              description
                "Network administrators taskgroup";
            }
            container sysadmin {
              presence "Indicates a sysadmin node is configured.";
              description
                "System administrators taskgroup";
            }
            container serviceadmin {
              presence "Indicates a serviceadmin node is configured.";
              description
                "Service administrators taskgroup";
            }
            container operator {
              presence "Indicates a operator node is configured.";
              description
                "Operator taskgroup";
            }
            container cisco-support {
              presence "Indicates a cisco-support node is configured.";
              description
                "Technical support group";
            }
            container task-groups {
              description
                "Name of the task group to include";
              list task-group {
                key "task-group-name";
                description
                  "Name of the task group to include";
                leaf task-group-name {
                  type string {
                    length "1..253" {
                      description
                        "Name of the task group to include.
                         Allowed all special chars except ? without prepended backslash and space without prepended backslash";
                    }
                  }
                  description
                    "Name of the task group to include";
                }
              }
            }
          }
        }
      }
    }
    container usernames {
      description
        "Configure user name";
      list username {
        key "ordering-index name";
        description
          "User name";
        leaf ordering-index {
          type uint32;
          description
            "This is used to sort the users in the order of
             precedence";
        }
        leaf name {
          type string {
            length "2..253" {
              description
                "User name.
                 Allowed special chars for username are _-.<>()[]&^!~*%=,+|:#$ forward slash and back slash";
            }
          }
          description
            "User name";
        }
        leaf password {
          type xr:Proprietary-password;
          status deprecated;
          description
            "Specify the password for the user (deprecated, will be removed in 25.3.1, Please use 'secret')";
        }
        container secret {
          description
            "Specify the secure password for the user";
          leaf eight {
            type xr:Type8-password;
            must "not(../nine or ../ten)";
            description
              "Specifies that SHA-256 encrypted password will follow";
          }
          leaf nine {
            type xr:Type9-password;
            must "not(../eight or ../ten)";
            description
              "Specifies that scrypt encrypted password will follow";
          }
          leaf ten {
            type xr:Type10-password;
            must "not(../eight or ../nine)";
            description
              "Specifies that SHA512 encrypted password will follow";
          }
        }
        container login-history {
          description
            "Option to set whether to display previous login details";
          container enable {
            must "not(../disable)";
            presence "Indicates a enable node is configured.";
            description
              "Enable the display of login history.";
          }
          container disable {
            must "not(../enable)";
            presence "Indicates a disable node is configured.";
            description
              "Disable the display of login history.";
          }
        }
        leaf policy {
          type xr:Cisco-ios-xr-string {
            length "1..253" {
              description
                "Specify the password policy name";
            }
          }
          description
            "Specify the policy common to password and secret for the user";
        }
        container password-policy {
          status deprecated;
          description
            "Specify the password policy (Deprecated, will be removed in 25.3.1, Please use 'secret' & 'policy')";
          leaf policy-name {
            type xr:Cisco-ios-xr-string {
              length "1..253" {
                description
                  "Specify the password policy name";
              }
            }
            description
              "Specify the password policy name, deprecated, Please use 'policy'";
          }
          leaf password {
            type xr:Proprietary-password;
            description
              "Deprecated, will be removed in 25.3.1, Please use 'secret'";
          }
        }
        container group {
          description
            "User group in which this user will be a member of";
          container root-lr {
            presence "Indicates a root-lr node is configured.";
            description
              "Root LR group";
          }
          container netadmin {
            presence "Indicates a netadmin node is configured.";
            description
              "Network administrators group";
          }
          container sysadmin {
            presence "Indicates a sysadmin node is configured.";
            description
              "System administrators group";
          }
          container serviceadmin {
            presence "Indicates a serviceadmin node is configured.";
            description
              "Service administrators group";
          }
          container operator {
            presence "Indicates a operator node is configured.";
            description
              "Operator group";
          }
          container cisco-support {
            presence "Indicates a cisco-support node is configured.";
            description
              "Cisco support personnel";
          }
          container maintenance {
            presence "Indicates a maintenance node is configured.";
            description
              "Maintenance group";
          }
          container provisioning {
            presence "Indicates a provisioning node is configured.";
            description
              "Provisioning group";
          }
          container retrieve {
            presence "Indicates a retrieve node is configured.";
            description
              "Retrieve group";
          }
          container read-only-tg {
            presence "Indicates a read-only-tg node is configured.";
            description
              "Read only group";
          }
          container user-groups {
            description
              "Name of the user group";
            list user-group {
              key "user-group-name";
              description
                "Name of the user group";
              leaf user-group-name {
                type string {
                  length "1..253" {
                    description
                      "Name of the user group.
                       Allowed special chars for usergroup name are _-.";
                  }
                }
                description
                  "Name of the user group";
              }
            }
          }
        }
        leaf shell-type {
          type xr:Cisco-ios-xr-string {
            length "1..32" {
              description
                "Shell type of the user";
            }
          }
          description
            "Specify the shell type of the user";
        }
        leaf directory {
          type string {
            length "1..512" {
              description
                "Directory of the user";
            }
          }
          description
            "Specify the directory of the user";
        }
      }
    }
  }
}
