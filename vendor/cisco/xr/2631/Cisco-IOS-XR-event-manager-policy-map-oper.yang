module Cisco-IOS-XR-event-manager-policy-map-oper {
  namespace "http://cisco.com/ns/yang/Cisco-IOS-XR-event-manager-policy-map-oper";
  prefix event-manager-policy-map-oper;

  import Cisco-IOS-XR-types {
    prefix xr;
  }
  import cisco-semver {
    prefix semver;
  }
  import Cisco-IOS-XR-ha-eem-policy-oper {
    prefix a1;
  }
  include Cisco-IOS-XR-event-manager-policy-map-oper-sub1 {
    revision-date 2022-06-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR event-manager-policy-map package operational data.
     
     This YANG module augments the
       Cisco-IOS-XR-ha-eem-policy-oper
     module with state data.
     
     Copyright (c) 2013-2022 by Cisco Systems, Inc.
     All rights reserved.";

  revision 2022-06-16 {
    description
      "Added new options under policy-map and removed event reset time.";
    semver:module-version "1.0.0";
  }
  revision 2022-01-11 {
    description
      "IOS XR 7.7.1 revision.";
  }
  revision 2019-04-05 {
    description
      "Establish semantic version baseline.";
  }
  revision 2015-11-09 {
    description
      "IOS XR 6.0 revision.";
  }

  augment "/a1:eem" {
    description
      "This augment extends the operational data of
       'Cisco-IOS-XR-ha-eem-policy-oper'";
    container script-action-names {
      description
        "Event Manager script-action mapping parameters";
      list script-action-name {
        key "script-name";
        description
          "Name of the script-action mapping";
        leaf script-name {
          type xr:Cisco-ios-xr-string;
          description
            "Name of script";
        }
        uses EEM-SCRIPT-BAG;
      }
    }
  }
  augment "/a1:eem" {
    description
      "This augment extends the operational data of
       'Cisco-IOS-XR-ha-eem-policy-oper'";
    container action-names {
      description
        "Event Manager Action parameters";
      list action-name {
        key "action-name";
        description
          "Name of the action";
        leaf action-name {
          type xr:Cisco-ios-xr-string;
          description
            "Name of Action";
        }
        uses EEM-ACTION-DETAIL-BAG;
      }
    }
  }
  augment "/a1:eem" {
    description
      "This augment extends the operational data of
       'Cisco-IOS-XR-ha-eem-policy-oper'";
    container event-trigger-names {
      description
        "EEM Event-trigger parameters";
      list event-trigger-name {
        key "event-name";
        description
          "Name of the event trigger";
        leaf event-name {
          type xr:Cisco-ios-xr-string;
          description
            "Name of event-trigger";
        }
        uses EEM-EVENT-DETAIL-BAG;
      }
    }
  }
  augment "/a1:eem" {
    description
      "This augment extends the operational data of
       'Cisco-IOS-XR-ha-eem-policy-oper'";
    container policy-map-names {
      description
        "Event Manager policy-map parameters";
      list policy-map-name {
        key "policy-name";
        description
          "Name of the policy-map";
        leaf policy-name {
          type xr:Cisco-ios-xr-string;
          description
            "Name of Policy-Map";
        }
        uses EEM-POLICY-DETAIL-BAG;
      }
    }
  }
}
