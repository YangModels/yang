submodule Cisco-IOS-XR-ncs1001-ots-oper-sub1 {
  belongs-to Cisco-IOS-XR-ncs1001-ots-oper {
    prefix Cisco-IOS-XR-ncs1001-ots-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs1001-ots package operational data.
     
     Copyright (c) 2013-2025 by Cisco Systems, Inc.
     All rights reserved.";

  revision 2025-11-01 {
    description
      "added new channel-view-slot/trail_data/configured path to get only configured channels";
    semver:module-version "3.1.0";
  }
  revision 2022-09-28 {
    description
      "moved channel-view-slot and ampli-view-slot leaves under the new added parent leaf amplier";
    semver:module-version "3.0.0";
  }
  revision 2020-12-12 {
    description
      "XML query for CLI show hw-module ampli-trail-view/channel-trail-view does not return a response";
    semver:module-version "2.1.0";
  }
  revision 2019-04-05 {
    description
      "Establish semantic version baseline.";
    semver:module-version "1.0.0";
  }
  revision 2018-01-23 {
    description
      "first release.";
  }
  revision 2015-11-09 {
    description
      "IOS XR 6.0 revision.";
  }

  typedef Chfilter {
    type enumeration {
      enum "ch-filter-active" {
        value 0;
        description
          "Active";
      }
      enum "ch-filter-all" {
        value 1;
        description
          "All";
      }
      enum "ch-filter-active-psd" {
        value 2;
        description
          "ActivePsd";
      }
      enum "ch-filter-all-psd" {
        value 3;
        description
          "AllPsd";
      }
    }
    description
      "Chfilter";
  }

  typedef Trailview {
    type enumeration {
      enum "trail-view-all" {
        value 0;
        description
          "All";
      }
      enum "trail-view-bst" {
        value 1;
        description
          "Booster";
      }
      enum "trail-view-pre" {
        value 2;
        description
          "Pre";
      }
    }
    description
      "Trailview";
  }

  grouping HWMOD-AMPLI-TRAIL-INFO-PRE-B {
    description
      "HWMOD AMPLI TRAIL INFO PRE B";
    leaf eqpt-fail {
      type uint8;
      description
        "Eqpt fail";
    }
    leaf view {
      type Trailview;
      description
        "View";
    }
    leaf com-port-number {
      type uint8;
      description
        "ComPortNumber";
    }
    leaf com-port-name {
      type string {
        length "0..32";
      }
      description
        "ComPortName";
    }
    leaf line-port-number {
      type uint8;
      description
        "LinePortNumber";
    }
    leaf line-port-name {
      type string {
        length "0..32";
      }
      description
        "LinePortName";
    }
    leaf pre-in-rx-power {
      type int16;
      description
        "PreInRxPower";
    }
    leaf pre-in-rx-total-power {
      type int16;
      description
        "PreInRxTotalPower";
    }
    leaf pre-in-rx-power-th-low {
      type int16;
      description
        "PreInRxPowerThLow";
    }
    leaf pre-out-tx-power {
      type int16;
      description
        "PreOutTxPower";
    }
    leaf pre-out-tx-total-power {
      type int16;
      description
        "PreOutTxTotalPower";
    }
    leaf pre-out-tx-power-th-low {
      type int16;
      description
        "PreOutTxPowerThLow";
    }
    leaf pre-working-mode {
      type uint16;
      description
        "PreWorkingMode";
    }
    leaf pre-safety-mode {
      type uint16;
      description
        "PreSafetyMode";
    }
    leaf pre-gain-range {
      type uint16;
      description
        "PreGainRange";
    }
    leaf pre-osri {
      type uint16;
      description
        "PreOsri";
    }
    leaf pre-channel-power {
      type int16;
      description
        "PreChannelPower";
    }
    leaf pre-gain {
      type int16;
      description
        "PreGain";
    }
    leaf pre-tilt {
      type int16;
      description
        "PreTilt";
    }
  }

  grouping HWMOD-AMPLI-TRAIL-INFO-BST-B {
    description
      "HWMOD AMPLI TRAIL INFO BST B";
    leaf eqpt-fail {
      type uint8;
      description
        "Eqpt fail";
    }
    leaf view {
      type Trailview;
      description
        "View";
    }
    leaf com-port-number {
      type uint8;
      description
        "ComPortNumber";
    }
    leaf com-port-name {
      type string {
        length "0..32";
      }
      description
        "ComPortName";
    }
    leaf line-port-number {
      type uint8;
      description
        "LinePortNumber";
    }
    leaf line-port-name {
      type string {
        length "0..32";
      }
      description
        "LinePortName";
    }
    leaf bst-in-rx-power {
      type int16;
      description
        "BstInRxPower";
    }
    leaf bst-in-rx-total-power {
      type int16;
      description
        "BstInRxTotalPower";
    }
    leaf bst-in-rx-power-th-low {
      type int16;
      description
        "BstInRxPowerThLow";
    }
    leaf bst-out-tx-power {
      type int16;
      description
        "BstOutTxPower";
    }
    leaf bst-out-tx-total-power {
      type int16;
      description
        "BstOutTxTotalPower";
    }
    leaf bst-out-tx-power-th-low {
      type int16;
      description
        "BstOutTxPowerThLow";
    }
    leaf bst-working-mode {
      type uint16;
      description
        "BstWorkingMode";
    }
    leaf bst-safety-mode {
      type uint16;
      description
        "BstSafetyMode";
    }
    leaf bst-gain-range {
      type uint16;
      description
        "BstGainRange";
    }
    leaf bst-osri {
      type uint16;
      description
        "BstOsri";
    }
    leaf bst-channel-power {
      type int16;
      description
        "BstChannelPower";
    }
    leaf bst-gain {
      type int16;
      description
        "BstGain";
    }
    leaf bst-tilt {
      type int16;
      description
        "BstTilt";
    }
  }

  grouping HWMOD-CHANNEL-TRAIL-INFO-B {
    description
      "HWMOD CHANNEL TRAIL INFO B";
    leaf eqpt-fail {
      type uint8;
      description
        "Eqpt fail";
    }
    leaf filter {
      type Chfilter;
      description
        "Filter";
    }
    leaf och-name {
      type string {
        length "0..64";
      }
      description
        "OchName";
    }
    leaf wavelength {
      type uint32;
      description
        "Wavelength";
    }
    leaf frequency {
      type uint32;
      description
        "Frequency";
    }
    leaf com-port-number {
      type uint8;
      description
        "ComPortNumber";
    }
    leaf com-port-name {
      type string {
        length "0..32";
      }
      description
        "ComPortName";
    }
    leaf com-rx-power-th-low {
      type int16;
      description
        "ComRxPowerThLow";
    }
    leaf line-port-number {
      type uint8;
      description
        "LinePortNumber";
    }
    leaf line-port-name {
      type string {
        length "0..32";
      }
      description
        "LinePortName";
    }
    leaf line-rx-power-th-low {
      type int16;
      description
        "LineRxPowerThLow";
    }
    leaf bst-in-rx-power {
      type int32;
      description
        "BstInRxPower";
    }
    leaf bst-out-tx-power {
      type int32;
      description
        "BstOutTxPower";
    }
    leaf pre-in-rx-power {
      type int32;
      description
        "PreInRxPower";
    }
    leaf pre-out-tx-power {
      type int32;
      description
        "PreOutTxPower";
    }
    leaf width {
      type uint32;
      description
        "Width";
    }
    leaf no-channels-active {
      type boolean;
      description
        "NoChannelsActive";
    }
    leaf no-grid-mode {
      type boolean;
      description
        "NoGridMode";
    }
  }

  grouping HWMOD-AMPLI-TRAIL-INFO-B {
    description
      "HWMOD AMPLI TRAIL INFO B";
    leaf eqpt-fail {
      type uint8;
      description
        "Eqpt fail";
    }
    leaf view {
      type Trailview;
      description
        "View";
    }
    leaf com-port-number {
      type uint8;
      description
        "ComPortNumber";
    }
    leaf com-port-name {
      type string {
        length "0..32";
      }
      description
        "ComPortName";
    }
    leaf line-port-number {
      type uint8;
      description
        "LinePortNumber";
    }
    leaf line-port-name {
      type string {
        length "0..32";
      }
      description
        "LinePortName";
    }
    leaf bst-in-rx-power {
      type int16;
      description
        "BstInRxPower";
    }
    leaf bst-in-rx-total-power {
      type int16;
      description
        "BstInRxTotalPower";
    }
    leaf bst-in-rx-power-th-low {
      type int16;
      description
        "BstInRxPowerThLow";
    }
    leaf bst-out-tx-power {
      type int16;
      description
        "BstOutTxPower";
    }
    leaf bst-out-tx-total-power {
      type int16;
      description
        "BstOutTxTotalPower";
    }
    leaf bst-out-tx-power-th-low {
      type int16;
      description
        "BstOutTxPowerThLow";
    }
    leaf bst-working-mode {
      type uint16;
      description
        "BstWorkingMode";
    }
    leaf bst-safety-mode {
      type uint16;
      description
        "BstSafetyMode";
    }
    leaf bst-gain-range {
      type uint16;
      description
        "BstGainRange";
    }
    leaf bst-osri {
      type uint16;
      description
        "BstOsri";
    }
    leaf bst-channel-power {
      type int16;
      description
        "BstChannelPower";
    }
    leaf bst-gain {
      type int16;
      description
        "BstGain";
    }
    leaf bst-tilt {
      type int16;
      description
        "BstTilt";
    }
    leaf pre-in-rx-power {
      type int16;
      description
        "PreInRxPower";
    }
    leaf pre-in-rx-total-power {
      type int16;
      description
        "PreInRxTotalPower";
    }
    leaf pre-in-rx-power-th-low {
      type int16;
      description
        "PreInRxPowerThLow";
    }
    leaf pre-out-tx-power {
      type int16;
      description
        "PreOutTxPower";
    }
    leaf pre-out-tx-total-power {
      type int16;
      description
        "PreOutTxTotalPower";
    }
    leaf pre-out-tx-power-th-low {
      type int16;
      description
        "PreOutTxPowerThLow";
    }
    leaf pre-working-mode {
      type uint16;
      description
        "PreWorkingMode";
    }
    leaf pre-safety-mode {
      type uint16;
      description
        "PreSafetyMode";
    }
    leaf pre-gain-range {
      type uint16;
      description
        "PreGainRange";
    }
    leaf pre-osri {
      type uint16;
      description
        "PreOsri";
    }
    leaf pre-channel-power {
      type int16;
      description
        "PreChannelPower";
    }
    leaf pre-gain {
      type int16;
      description
        "PreGain";
    }
    leaf pre-tilt {
      type int16;
      description
        "PreTilt";
    }
  }

  grouping OTS-HWMOD-OP {
    description
      "hwmodule trail info";
    list ampli-trail-info {
      description
        "ampli trail info";
      uses HWMOD-AMPLI-TRAIL-INFO-B;
    }
    list channel-trail-info {
      description
        "channel trail info";
      uses HWMOD-CHANNEL-TRAIL-INFO-B;
    }
    list ampli-trail-info-bst {
      description
        "ampli trail info bst";
      uses HWMOD-AMPLI-TRAIL-INFO-BST-B;
    }
    list ampli-trail-info-pre {
      description
        "ampli trail info pre";
      uses HWMOD-AMPLI-TRAIL-INFO-PRE-B;
    }
  }
}
