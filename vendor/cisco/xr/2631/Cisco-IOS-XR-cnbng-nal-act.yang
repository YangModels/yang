module Cisco-IOS-XR-cnbng-nal-act {
  namespace "http://cisco.com/ns/yang/Cisco-IOS-XR-cnbng-nal-act";
  prefix cnbng-nal-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2018-2026 by Cisco Systems, Inc., and/or its affiliates.
     All rights reserved.";

  revision 2026-01-13 {
    description
      "IOS XR 26.2.1 revision updated clear cnbng subscriber warm-standby CLI filters";
    semver:module-version "1.3.0";
  }
  revision 2022-02-25 {
    description
      "IOS XR 7.7.1 revision updated clear dynamic route CLI filters
       2022-01-21
          IOS XR 7.7.1 revision added srg clear CLIs";
    semver:module-version "1.2.0";
  }
  revision 2021-08-29 {
    description
      "IOS XR 7.6.1 revision removing cnbng-nal task";
    semver:module-version "1.1.0";
  }
  revision 2021-02-11 {
    description
      "IOS XR 7.4.1 revision removing unused imports.";
    semver:module-version "1.0.0";
  }
  revision 2020-09-10 {
    description
      "IOS XR 7.3.1 revision.";
    semver:module-version "1.0.0";
  }

  rpc clear-cnbng-nal-cp-association {
    description
      "Clear cnBNG NAL CP server association";
    csc:cli-command "clear cnbng-nal cp-association";
  }
  rpc clear-cnbng-nal-cp-association-location {
    description
      "Clear cnBNG NAL CP server association for given node";
    input {
      leaf node-location {
        type string;
        mandatory true;
        description
          "Node location";
        csc:cli-name "*";
      }
    }
    csc:cli-command "clear cnbng-nal cp-association location <node-location>";
  }
  rpc clear-cnbng-nal-dynamic-routes-afi {
    description
      "Execute clear cnBNG NAL Dynamic-routes AFI-type";
    input {
      leaf afi-type {
        type string;
        mandatory true;
        description
          "Address-family";
        csc:cli-name "*";
      }
    }
    csc:cli-command "clear cnbng-nal dynamic-routes afi <afi-type>";
  }
  rpc clear-cnbng-nal-dynamic-routes-afi-location {
    description
      "Execute clear cnBNG NAL Dynamic-routes AFI for the given node";
    input {
      leaf afi-type {
        type string;
        mandatory true;
        description
          "Address-family";
        csc:cli-name "*";
      }
      leaf node-location {
        type string;
        mandatory true;
        description
          "Node location";
        csc:cli-name "*";
      }
    }
    csc:cli-command "clear cnbng-nal dynamic-routes afi <afi-type> location <node-location>";
  }
  rpc clear-cnbng-nal-dynamic-routes-afi-srg-group {
    description
      "Execute clear cnBNG NAL Dynamic-routes AFI-type srg-group";
    input {
      leaf afi-type {
        type string;
        mandatory true;
        description
          "Address-family";
        csc:cli-name "*";
      }
      leaf srg-group-name {
        type string;
        mandatory true;
        description
          "SRG group name";
        csc:cli-name "*";
      }
    }
    csc:cli-command "clear cnbng-nal dynamic-routes afi <afi-type> srg-group <srg-group-name>";
  }
  rpc clear-cnbng-nal-dynamic-routes-afi-srg-group-location {
    description
      "Execute clear cnBNG NAL Dynamic-routes AFI srg-group for the given node";
    input {
      leaf afi-type {
        type string;
        mandatory true;
        description
          "Address-family";
        csc:cli-name "*";
      }
      leaf srg-group-name {
        type string;
        mandatory true;
        description
          "SRG group name";
        csc:cli-name "*";
      }
      leaf node-location {
        type string;
        mandatory true;
        description
          "Node location";
        csc:cli-name "*";
      }
    }
    csc:cli-command "clear cnbng-nal dynamic-routes afi <afi-type> srg-group <srg-group-name> location <node-location>";
  }
  rpc clear-cnbng-nal-dynamic-routes-history {
    description
      "Clear cnBNG NAL Dynamic-routes history";
    csc:cli-command "clear cnbng-nal dynamic-routes history";
  }
  rpc clear-cnbng-nal-dynamic-routes-history-location {
    description
      "Clear cnBNG NAL Dynamic-routes history for given node";
    input {
      leaf node-location {
        type string;
        mandatory true;
        description
          "Node location";
        csc:cli-name "*";
      }
    }
    csc:cli-command "clear cnbng-nal dynamic-routes history location <node-location>";
  }
  rpc clear-cnbng-nal-subscriber-disconnect-history {
    description
      "Clear cnBNG NAL subscriber disconnect-history entries";
    csc:cli-command "clear cnbng-nal subscriber disconnect-history";
  }
  rpc clear-cnbng-nal-subscriber-disconnect-history-location {
    description
      "Clear cnBNG NAL subscriber disconnect-history entries for given node";
    input {
      leaf node-location {
        type string;
        mandatory true;
        description
          "Node location";
        csc:cli-name "*";
      }
    }
    csc:cli-command "clear cnbng-nal subscriber disconnect-history location <node-location>";
  }
  rpc clear-cnbng-nal-cp-srg-association-srg-group {
    description
      "Execute clear cnBNG NAL CP SRG association srg-group";
    input {
      leaf srg-group-name {
        type string;
        mandatory true;
        description
          "SRG group name";
        csc:cli-name "*";
      }
    }
    csc:cli-command "clear cnbng-nal cp-srg-association srg-group <srg-group-name>";
  }
  rpc clear-cnbng-nal-cp-srg-association-srg-group-location {
    description
      "Execute clear cnBNG NAL CP SRG association srg-group for the given node";
    input {
      leaf srg-group-name {
        type string;
        mandatory true;
        description
          "SRG group name";
        csc:cli-name "*";
      }
      leaf node-location {
        type string;
        mandatory true;
        description
          "Node location";
        csc:cli-name "*";
      }
    }
    csc:cli-command "clear cnbng-nal cp-srg-association srg-group <srg-group-name> location <node-location>";
  }
  rpc clear-cnbng-subscriber-warm-stby-access-intf-up-inst {
    description
      "Clear cnBNG NAL subscriber warm-standby access-interface entries";
    input {
      leaf access-interface {
        type string;
        mandatory true;
        description
          "access interface";
        csc:cli-name "*";
      }
      leaf up-instance-id {
        type string;
        mandatory true;
        description
          "up-instance-id";
        csc:cli-name "*";
      }
    }
    csc:cli-command "clear cnbng-nal subscriber warm-standby access-interface <access-interface> up-instance-id <up-instance-id>";
  }
  rpc clear-cnbng-subscriber-warm-stby-access-intf-up-inst-location {
    description
      "Clear cnBNG NAL subscriber warm-standby entries for given node";
    input {
      leaf access-interface {
        type string;
        mandatory true;
        description
          "access interface";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby access-interface <access-interface> up-instance-id <up-instance-id> location <node-location>";
  }
  rpc clear-cnbng-subscriber-warm-stby-all-up-inst {
    description
      "Clear cnBNG NAL subscriber warm-standby all entries";
    input {
      leaf all {
        type string;
        mandatory true;
        description
          "all";
        csc:cli-name "*";
      }
      leaf up-instance-id {
        type string;
        mandatory true;
        description
          "up-instance-id";
        csc:cli-name "*";
      }
    }
    csc:cli-command "clear cnbng-nal subscriber warm-standby all up-instance-id <up-instance-id>";
  }
  rpc clear-cnbng-subscriber-warm-stby-all-up-inst-location {
    description
      "Clear cnBNG NAL subscriber warm-standby all entries for given node";
    input {
      leaf all {
        type string;
        mandatory true;
        description
          "all";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby all up-instance-id <up-instance-id> location <node-location>";
  }
  rpc clear-cnbng-subscriber-warm-stby-cpid-up-inst {
    description
      "Clear cnBNG NAL subscriber warm-standby cpid entries";
    input {
      leaf cpid {
        type string;
        mandatory true;
        description
          "cpid";
        csc:cli-name "*";
      }
      leaf up-instance-id {
        type string;
        mandatory true;
        description
          "up-instance-id";
        csc:cli-name "*";
      }
    }
    csc:cli-command "clear cnbng-nal subscriber warm-standby cpid <cpid> up-instance-id <up-instance-id>";
  }
  rpc clear-cnbng-subscriber-warm-stby-cpid-up-inst-location {
    description
      "Clear cnBNG NAL subscriber warm-standby cpid entries for given node";
    input {
      leaf cpid {
        type string;
        mandatory true;
        description
          "cpid";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby cpid <cpid> up-instance-id <up-instance-id> location <node-location>";
  }
  rpc clear-cnbng-subscriber-warm-stby-disc-hist-up-inst {
    description
      "Clear cnBNG NAL subscriber warm-standby disconnect-history entries";
    input {
      leaf disconnect-history {
        type string;
        mandatory true;
        description
          "disconnect history";
        csc:cli-name "*";
      }
      leaf up-instance-id {
        type string;
        mandatory true;
        description
          "up-instance-id";
        csc:cli-name "*";
      }
    }
    csc:cli-command "clear cnbng-nal subscriber warm-standby disconnect-history <disconnect-history> up-instance-id <up-instance-id>";
  }
  rpc clear-cnbng-subscriber-warm-stby-disc-hist-up-inst-location {
    description
      "Clear cnBNG NAL subscriber warm-standby disconnect-history entries for given node";
    input {
      leaf disconnect-history {
        type string;
        mandatory true;
        description
          "disconnect history";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby disconnect-history <disconnect-history> up-instance-id <up-instance-id> location <node-location>";
  }
  rpc clear-cnbng-subscriber-warm-stby-srg-group-up-inst {
    description
      "Clear cnBNG NAL subscriber warm-standby srg-group entries";
    input {
      leaf srg-group {
        type string;
        mandatory true;
        description
          "srg-group";
        csc:cli-name "*";
      }
      leaf up-instance-id {
        type string;
        mandatory true;
        description
          "up-instance-id";
        csc:cli-name "*";
      }
    }
    csc:cli-command "clear cnbng-nal subscriber warm-standby srg-group <srg-group> up-instance-id <up-instance-id>";
  }
  rpc clear-cnbng-subscriber-warm-stby-srg-group-up-inst-location {
    description
      "Clear cnBNG NAL subscriber warm-standby entries for given node";
    input {
      leaf srg-group {
        type string;
        mandatory true;
        description
          "srg-group";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby srg-group <srg-group> up-instance-id <up-instance-id> location <node-location>";
  }
  rpc clear-cnbng-subscriber-warm-stby-sub-type-up-inst {
    description
      "Clear cnBNG NAL subscriber warm-standby sub-type entries";
    input {
      leaf sub-type {
        type string;
        mandatory true;
        description
          "sub-type";
        csc:cli-name "*";
      }
      leaf up-instance-id {
        type string;
        mandatory true;
        description
          "up-instance-id";
        csc:cli-name "*";
      }
    }
    csc:cli-command "clear cnbng-nal subscriber warm-standby sub-type <sub-type> up-instance-id <up-instance-id>";
  }
  rpc clear-cnbng-subscriber-warm-stby-sub-type-up-inst-location {
    description
      "Clear cnBNG NAL subscriber warm-standby sub-type entries for given node";
    input {
      leaf sub-type {
        type string;
        mandatory true;
        description
          "sub-type";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber warm-standby sub-type <sub-type> up-instance-id <up-instance-id> location <node-location>";
  }
  rpc clear-cnbng-subscriber-access-interface-up-inst {
    description
      "Clear cnBNG NAL subscriber access-interface entries";
    input {
      leaf access-interface {
        type string;
        mandatory true;
        description
          "access-interface";
        csc:cli-name "*";
      }
      leaf up-instance-id {
        type string;
        mandatory true;
        description
          "up-instance-id";
        csc:cli-name "*";
      }
    }
    csc:cli-command "clear cnbng-nal subscriber access-interface <access-interface> up-instance-id <up-instance-id>";
  }
  rpc clear-cnbng-subscriber-access-interface-up-inst-location {
    description
      "Clear cnBNG NAL subscriber access-interface entries for given node";
    input {
      leaf access-interface {
        type string;
        mandatory true;
        description
          "access-interface";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber access-interface <access-interface> up-instance-id <up-instance-id> location <node-location>";
  }
  rpc clear-cnbng-subscriber-all-up-inst {
    description
      "Clear cnBNG NAL subscriber all entries";
    input {
      leaf all {
        type string;
        mandatory true;
        description
          "all";
        csc:cli-name "*";
      }
      leaf up-instance-id {
        type string;
        mandatory true;
        description
          "up-instance-id";
        csc:cli-name "*";
      }
    }
    csc:cli-command "clear cnbng-nal subscriber all up-instance-id <up-instance-id>";
  }
  rpc clear-cnbng-subscriber-all-up-inst-location {
    description
      "Clear cnBNG NAL subscriber all entries for given node";
    input {
      leaf all {
        type string;
        mandatory true;
        description
          "all";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber all up-instance-id <up-instance-id> location <node-location>";
  }
  rpc clear-cnbng-subscriber-interface-up-inst {
    description
      "Clear cnBNG NAL subscriber interface entries";
    input {
      leaf interface {
        type string;
        mandatory true;
        description
          "interface";
        csc:cli-name "*";
      }
      leaf up-instance-id {
        type string;
        mandatory true;
        description
          "up-instance-id";
        csc:cli-name "*";
      }
    }
    csc:cli-command "clear cnbng-nal subscriber interface <interface> up-instance-id <up-instance-id>";
  }
  rpc clear-cnbng-subscriber-interface-up-inst-location {
    description
      "Clear cnBNG NAL subscriber interface entries for given node";
    input {
      leaf interface {
        type string;
        mandatory true;
        description
          "interface";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber interface <interface> up-instance-id <up-instance-id> location <node-location>";
  }
  rpc clear-cnbng-subscriber-srg-group-up-inst {
    description
      "Clear cnBNG NAL subscriber srg-group entries";
    input {
      leaf srg-group {
        type string;
        mandatory true;
        description
          "srg-group";
        csc:cli-name "*";
      }
      leaf up-instance-id {
        type string;
        mandatory true;
        description
          "up-instance-id";
        csc:cli-name "*";
      }
    }
    csc:cli-command "clear cnbng-nal subscriber srg-group <srg-group> up-instance-id <up-instance-id>";
  }
  rpc clear-cnbng-subscriber-srg-group-up-inst-location {
    description
      "Clear cnBNG NAL subscriber srg-group entries for given node";
    input {
      leaf srg-group {
        type string;
        mandatory true;
        description
          "srg-group";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber srg-group <srg-group> up-instance-id <up-instance-id> location <node-location>";
  }
  rpc clear-cnbng-subscriber-mac-address-up-inst {
    description
      "Clear cnBNG NAL subscriber mac-address entries";
    input {
      leaf mac-address {
        type string;
        mandatory true;
        description
          "mac-address";
        csc:cli-name "*";
      }
      leaf up-instance-id {
        type string;
        mandatory true;
        description
          "up-instance-id";
        csc:cli-name "*";
      }
    }
    csc:cli-command "clear cnbng-nal subscriber mac-address <mac-address> up-instance-id <up-instance-id>";
  }
  rpc clear-cnbng-subscriber-mac-address-up-inst-location {
    description
      "Clear cnBNG NAL subscriber mac-address entries for given node";
    input {
      leaf mac-address {
        type string;
        mandatory true;
        description
          "mac-address";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber mac-address <mac-address> up-instance-id <up-instance-id> location <node-location>";
  }
  rpc clear-cnbng-subscriber-upid-up-inst {
    description
      "Clear cnBNG NAL subscriber upid entries";
    input {
      leaf upid {
        type string;
        mandatory true;
        description
          "upid";
        csc:cli-name "*";
      }
      leaf up-instance-id {
        type string;
        mandatory true;
        description
          "up-instance-id";
        csc:cli-name "*";
      }
    }
    csc:cli-command "clear cnbng-nal subscriber upid <upid> up-instance-id <up-instance-id>";
  }
  rpc clear-cnbng-subscriber-upid-up-inst-location {
    description
      "Clear cnBNG NAL subscriber upid entries for given node";
    input {
      leaf upid {
        type string;
        mandatory true;
        description
          "upid";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber upid <upid> up-instance-id <up-instance-id> location <node-location>";
  }
  rpc clear-cnbng-subscriber-vrf-up-inst {
    description
      "Clear cnBNG NAL subscriber vrf entries";
    input {
      leaf vrf {
        type string;
        mandatory true;
        description
          "vrf";
        csc:cli-name "*";
      }
      leaf up-instance-id {
        type string;
        mandatory true;
        description
          "up-instance-id";
        csc:cli-name "*";
      }
    }
    csc:cli-command "clear cnbng-nal subscriber vrf <vrf> up-instance-id <up-instance-id>";
  }
  rpc clear-cnbng-subscriber-vrf-up-inst-location {
    description
      "Clear cnBNG NAL subscriber vrf entries for given node";
    input {
      leaf vrf {
        type string;
        mandatory true;
        description
          "vrf";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal subscriber vrf <vrf> up-instance-id <up-instance-id> location <node-location>";
  }
  rpc clear-cnbng-nal-cp-association-up-inst {
    description
      "Clear cnBNG NAL CP association for given up-instance-id";
    input {
      leaf up-instance-id {
        type string;
        mandatory true;
        description
          "up-instance-id";
        csc:cli-name "*";
      }
    }
    csc:cli-command "clear cnbng-nal cp-association up-instance-id <up-instance-id>";
  }
  rpc clear-cnbng-nal-cp-association-up-inst-location {
    description
      "Clear cnBNG NAL CP association for given up-instance-id and node";
    input {
      leaf up-instance-id {
        type string;
        mandatory true;
        description
          "up-instance-id";
        csc:cli-name "*";
      }
      leaf node-location {
        type string;
        mandatory true;
        description
          "Node location";
        csc:cli-name "*";
      }
    }
    csc:cli-command "clear cnbng-nal cp-association up-instance-id <up-instance-id> location <node-location>";
  }
  rpc clear-cnbng-nal-dynamic-routes-afi-up-inst {
    description
      "Execute clear cnBNG NAL Dynamic-routes AFI with up-instance-id";
    input {
      leaf afi-type {
        type string;
        mandatory true;
        description
          "Address-family";
        csc:cli-name "*";
      }
      leaf up-instance-id {
        type string;
        mandatory true;
        description
          "up-instance-id";
        csc:cli-name "*";
      }
    }
    csc:cli-command "clear cnbng-nal dynamic-routes afi <afi-type> up-instance-id <up-instance-id>";
  }
  rpc clear-cnbng-nal-dynamic-routes-afi-up-inst-location {
    description
      "Execute clear cnBNG NAL Dynamic-routes AFI with up-instance-id for the given node";
    input {
      leaf afi-type {
        type string;
        mandatory true;
        description
          "Address-family";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal dynamic-routes afi <afi-type> up-instance-id <up-instance-id> location <node-location>";
  }
  rpc clear-cnbng-nal-dynamic-routes-afi-srg-up-inst {
    description
      "Execute clear cnBNG NAL Dynamic-routes AFI srg-group with up-instance-id";
    input {
      leaf afi-type {
        type string;
        mandatory true;
        description
          "Address-family";
        csc:cli-name "*";
      }
      leaf srg-group-name {
        type string;
        mandatory true;
        description
          "SRG group name";
        csc:cli-name "*";
      }
      leaf up-instance-id {
        type string;
        mandatory true;
        description
          "up-instance-id";
        csc:cli-name "*";
      }
    }
    csc:cli-command "clear cnbng-nal dynamic-routes afi <afi-type> srg-group <srg-group-name> up-instance-id <up-instance-id>";
  }
  rpc clear-cnbng-nal-dynamic-routes-afi-srg-up-inst-location {
    description
      "Execute clear cnBNG NAL Dynamic-routes AFI srg-group with up-instance-id for the given node";
    input {
      leaf afi-type {
        type string;
        mandatory true;
        description
          "Address-family";
        csc:cli-name "*";
      }
      leaf srg-group-name {
        type string;
        mandatory true;
        description
          "SRG group name";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal dynamic-routes afi <afi-type> srg-group <srg-group-name> up-instance-id <up-instance-id> location <node-location>";
  }
  rpc clear-cnbng-nal-dynamic-routes-afi-force-up-inst {
    description
      "Execute clear cnBNG NAL Dynamic-routes AFI force with up-instance-id";
    input {
      leaf afi-type {
        type string;
        mandatory true;
        description
          "Address-family";
        csc:cli-name "*";
      }
      leaf up-instance-id {
        type string;
        mandatory true;
        description
          "up-instance-id";
        csc:cli-name "*";
      }
    }
    csc:cli-command "clear cnbng-nal dynamic-routes afi <afi-type> force up-instance-id <up-instance-id>";
  }
  rpc clear-cnbng-nal-dynamic-routes-afi-force-up-inst-location {
    description
      "Execute clear cnBNG NAL Dynamic-routes AFI force with up-instance-id for the given node";
    input {
      leaf afi-type {
        type string;
        mandatory true;
        description
          "Address-family";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal dynamic-routes afi <afi-type> force up-instance-id <up-instance-id> location <node-location>";
  }
  rpc clear-cnbng-nal-dynamic-routes-afi-srg-force-up-inst {
    description
      "Execute clear cnBNG NAL Dynamic-routes AFI srg-group force with up-instance-id";
    input {
      leaf afi-type {
        type string;
        mandatory true;
        description
          "Address-family";
        csc:cli-name "*";
      }
      leaf srg-group-name {
        type string;
        mandatory true;
        description
          "SRG group name";
        csc:cli-name "*";
      }
      leaf up-instance-id {
        type string;
        mandatory true;
        description
          "up-instance-id";
        csc:cli-name "*";
      }
    }
    csc:cli-command "clear cnbng-nal dynamic-routes afi <afi-type> srg-group <srg-group-name> force up-instance-id <up-instance-id>";
  }
  rpc clear-cnbng-nal-dynamic-routes-afi-srg-force-up-inst-location {
    description
      "Execute clear cnBNG NAL Dynamic-routes AFI srg-group force with up-instance-id for the given node";
    input {
      leaf afi-type {
        type string;
        mandatory true;
        description
          "Address-family";
        csc:cli-name "*";
      }
      leaf srg-group-name {
        type string;
        mandatory true;
        description
          "SRG group name";
        csc:cli-name "*";
      }
      leaf up-instance-id {
        type string;
        mandatory true;
        description
          "up-instance-id";
        csc:cli-name "*";
      }
      leaf node-location {
        type string;
        mandatory true;
        description
          "Node location";
        csc:cli-name "*";
      }
    }
    csc:cli-command "clear cnbng-nal dynamic-routes afi <afi-type> srg-group <srg-group-name> force up-instance-id <up-instance-id> location <node-location>";
  }
  rpc clear-cnbng-subscriber-sub-type {
    description
      "Clear cnBNG NAL subscriber sub-type";
    input {
      leaf sub-type {
        type string;
        mandatory true;
        description
          "sub-type";
        csc:cli-name "*";
      }
    }
    csc:cli-command "clear cnbng-nal subscriber sub-type <sub-type>";
  }
  rpc clear-cnbng-subscriber-sub-type-location {
    description
      "Clear cnBNG NAL subscriber sub-type for given node";
    input {
      leaf sub-type {
        type string;
        mandatory true;
        description
          "sub-type";
        csc:cli-name "*";
      }
      leaf node-location {
        type string;
        mandatory true;
        description
          "Node location";
        csc:cli-name "*";
      }
    }
    csc:cli-command "clear cnbng-nal subscriber sub-type <sub-type> location <node-location>";
  }
  rpc clear-cnbng-subscriber-warm-stby-access-intf {
    description
      "Clear cnBNG NAL subscriber warm-standby access-interface entries";
    input {
      leaf access-interface {
        type string;
        mandatory true;
        description
          "access interface";
        csc:cli-name "*";
      }
    }
    csc:cli-command "clear cnbng-nal subscriber warm-standby access-interface <access-interface>";
  }
  rpc clear-cnbng-subscriber-warm-stby-access-intf-location {
    description
      "Clear cnBNG NAL subscriber warm-standby access-interface entries for given node";
    input {
      leaf access-interface {
        type string;
        mandatory true;
        description
          "access interface";
        csc:cli-name "*";
      }
      leaf node-location {
        type string;
        mandatory true;
        description
          "Node location";
        csc:cli-name "*";
      }
    }
    csc:cli-command "clear cnbng-nal subscriber warm-standby access-interface <access-interface> location <node-location>";
  }
  rpc clear-cnbng-subscriber-warm-stby-all {
    description
      "Clear cnBNG NAL subscriber warm-standby all entries";
    input {
      leaf all {
        type string;
        mandatory true;
        description
          "all";
        csc:cli-name "*";
      }
    }
    csc:cli-command "clear cnbng-nal subscriber warm-standby all";
  }
  rpc clear-cnbng-subscriber-warm-stby-all-location {
    description
      "Clear cnBNG NAL subscriber warm-standby all entries for given node";
    input {
      leaf all {
        type string;
        mandatory true;
        description
          "all";
        csc:cli-name "*";
      }
      leaf node-location {
        type string;
        mandatory true;
        description
          "Node location";
        csc:cli-name "*";
      }
    }
    csc:cli-command "clear cnbng-nal subscriber warm-standby all location <node-location>";
  }
  rpc clear-cnbng-subscriber-warm-stby-cpid {
    description
      "Clear cnBNG NAL subscriber warm-standby cpid entries";
    input {
      leaf cpid {
        type string;
        mandatory true;
        description
          "cpid";
        csc:cli-name "*";
      }
    }
    csc:cli-command "clear cnbng-nal subscriber warm-standby cpid <cpid>";
  }
  rpc clear-cnbng-subscriber-warm-stby-cpid-location {
    description
      "Clear cnBNG NAL subscriber warm-standby cpid entries for given node";
    input {
      leaf cpid {
        type string;
        mandatory true;
        description
          "cpid";
        csc:cli-name "*";
      }
      leaf node-location {
        type string;
        mandatory true;
        description
          "Node location";
        csc:cli-name "*";
      }
    }
    csc:cli-command "clear cnbng-nal subscriber warm-standby cpid <cpid> location <node-location>";
  }
  rpc clear-cnbng-subscriber-warm-stby-disc-hist {
    description
      "Clear cnBNG NAL subscriber warm-standby disconnect-history entries";
    input {
      leaf disconnect-history {
        type string;
        mandatory true;
        description
          "disconnect history";
        csc:cli-name "*";
      }
    }
    csc:cli-command "clear cnbng-nal subscriber warm-standby disconnect-history <disconnect-history>";
  }
  rpc clear-cnbng-subscriber-warm-stby-disc-hist-location {
    description
      "Clear cnBNG NAL subscriber warm-standby disconnect-history entries for given node";
    input {
      leaf disconnect-history {
        type string;
        mandatory true;
        description
          "disconnect history";
        csc:cli-name "*";
      }
      leaf node-location {
        type string;
        mandatory true;
        description
          "Node location";
        csc:cli-name "*";
      }
    }
    csc:cli-command "clear cnbng-nal subscriber warm-standby disconnect-history <disconnect-history> location <node-location>";
  }
  rpc clear-cnbng-subscriber-warm-stby-srg-group {
    description
      "Clear cnBNG NAL subscriber warm-standby srg-group entries";
    input {
      leaf srg-group {
        type string;
        mandatory true;
        description
          "srg-group";
        csc:cli-name "*";
      }
    }
    csc:cli-command "clear cnbng-nal subscriber warm-standby srg-group <srg-group>";
  }
  rpc clear-cnbng-subscriber-warm-stby-srg-group-location {
    description
      "Clear cnBNG NAL subscriber warm-standby srg-group entries for given node";
    input {
      leaf srg-group {
        type string;
        mandatory true;
        description
          "srg-group";
        csc:cli-name "*";
      }
      leaf node-location {
        type string;
        mandatory true;
        description
          "Node location";
        csc:cli-name "*";
      }
    }
    csc:cli-command "clear cnbng-nal subscriber warm-standby srg-group <srg-group> location <node-location>";
  }
  rpc clear-cnbng-subscriber-warm-stby-sub-type {
    description
      "Clear cnBNG NAL subscriber warm-standby sub-type entries";
    input {
      leaf sub-type {
        type string;
        mandatory true;
        description
          "sub-type";
        csc:cli-name "*";
      }
    }
    csc:cli-command "clear cnbng-nal subscriber warm-standby sub-type <sub-type>";
  }
  rpc clear-cnbng-subscriber-warm-stby-sub-type-location {
    description
      "Clear cnBNG NAL subscriber warm-standby sub-type entries for given node";
    input {
      leaf sub-type {
        type string;
        mandatory true;
        description
          "sub-type";
        csc:cli-name "*";
      }
      leaf node-location {
        type string;
        mandatory true;
        description
          "Node location";
        csc:cli-name "*";
      }
    }
    csc:cli-command "clear cnbng-nal subscriber warm-standby sub-type <sub-type> location <node-location>";
  }
  rpc clear-cnbng-subscriber-access-interface {
    description
      "Clear cnBNG NAL subscriber access-interface entries";
    input {
      leaf access-interface {
        type string;
        mandatory true;
        description
          "access-interface";
        csc:cli-name "*";
      }
    }
    csc:cli-command "clear cnbng-nal subscriber access-interface <access-interface>";
  }
  rpc clear-cnbng-subscriber-access-interface-location {
    description
      "Clear cnBNG NAL subscriber access-interface entries for given node";
    input {
      leaf access-interface {
        type string;
        mandatory true;
        description
          "access-interface";
        csc:cli-name "*";
      }
      leaf node-location {
        type string;
        mandatory true;
        description
          "Node location";
        csc:cli-name "*";
      }
    }
    csc:cli-command "clear cnbng-nal subscriber access-interface <access-interface> location <node-location>";
  }
  rpc clear-cnbng-subscriber-all {
    description
      "Clear cnBNG NAL subscriber all entries";
    input {
      leaf all {
        type string;
        mandatory true;
        description
          "all";
        csc:cli-name "*";
      }
    }
    csc:cli-command "clear cnbng-nal subscriber all <all>";
  }
  rpc clear-cnbng-subscriber-all-location {
    description
      "Clear cnBNG NAL subscriber all entries for given node";
    input {
      leaf all {
        type string;
        mandatory true;
        description
          "all";
        csc:cli-name "*";
      }
      leaf node-location {
        type string;
        mandatory true;
        description
          "Node location";
        csc:cli-name "*";
      }
    }
    csc:cli-command "clear cnbng-nal subscriber all <all> location <node-location>";
  }
  rpc clear-cnbng-subscriber-interface {
    description
      "Clear cnBNG NAL subscriber interface entries";
    input {
      leaf interface {
        type string;
        mandatory true;
        description
          "interface";
        csc:cli-name "*";
      }
    }
    csc:cli-command "clear cnbng-nal subscriber interface <interface>";
  }
  rpc clear-cnbng-subscriber-interface-location {
    description
      "Clear cnBNG NAL subscriber interface entries for given node";
    input {
      leaf interface {
        type string;
        mandatory true;
        description
          "interface";
        csc:cli-name "*";
      }
      leaf node-location {
        type string;
        mandatory true;
        description
          "Node location";
        csc:cli-name "*";
      }
    }
    csc:cli-command "clear cnbng-nal subscriber interface <interface> location <node-location>";
  }
  rpc clear-cnbng-subscriber-srg-group {
    description
      "Clear cnBNG NAL subscriber srg-group entries";
    input {
      leaf srg-group {
        type string;
        mandatory true;
        description
          "srg-group";
        csc:cli-name "*";
      }
    }
    csc:cli-command "clear cnbng-nal subscriber srg-group <srg-group>";
  }
  rpc clear-cnbng-subscriber-srg-group-location {
    description
      "Clear cnBNG NAL subscriber srg-group entries for given node";
    input {
      leaf srg-group {
        type string;
        mandatory true;
        description
          "srg-group";
        csc:cli-name "*";
      }
      leaf node-location {
        type string;
        mandatory true;
        description
          "Node location";
        csc:cli-name "*";
      }
    }
    csc:cli-command "clear cnbng-nal subscriber srg-group <srg-group> location <node-location>";
  }
  rpc clear-cnbng-subscriber-mac-address {
    description
      "Clear cnBNG NAL subscriber mac-address entries";
    input {
      leaf mac-address {
        type string;
        mandatory true;
        description
          "mac-address";
        csc:cli-name "*";
      }
    }
    csc:cli-command "clear cnbng-nal subscriber mac-address <mac-address>";
  }
  rpc clear-cnbng-subscriber-mac-address-location {
    description
      "Clear cnBNG NAL subscriber mac-address entries for given node";
    input {
      leaf mac-address {
        type string;
        mandatory true;
        description
          "mac-address";
        csc:cli-name "*";
      }
      leaf node-location {
        type string;
        mandatory true;
        description
          "Node location";
        csc:cli-name "*";
      }
    }
    csc:cli-command "clear cnbng-nal subscriber mac-address <mac-address> location <node-location>";
  }
  rpc clear-cnbng-subscriber-upid {
    description
      "Clear cnBNG NAL subscriber upid entries";
    input {
      leaf upid {
        type string;
        mandatory true;
        description
          "upid";
        csc:cli-name "*";
      }
    }
    csc:cli-command "clear cnbng-nal subscriber upid <upid>";
  }
  rpc clear-cnbng-subscriber-upid-location {
    description
      "Clear cnBNG NAL subscriber upid entries for given node";
    input {
      leaf upid {
        type string;
        mandatory true;
        description
          "upid";
        csc:cli-name "*";
      }
      leaf node-location {
        type string;
        mandatory true;
        description
          "Node location";
        csc:cli-name "*";
      }
    }
    csc:cli-command "clear cnbng-nal subscriber upid <upid> location <node-location>";
  }
  rpc clear-cnbng-subscriber-vrf {
    description
      "Clear cnBNG NAL subscriber vrf entries";
    input {
      leaf vrf {
        type string;
        mandatory true;
        description
          "vrf";
        csc:cli-name "*";
      }
    }
    csc:cli-command "clear cnbng-nal subscriber vrf <vrf>";
  }
  rpc clear-cnbng-subscriber-vrf-location {
    description
      "Clear cnBNG NAL subscriber vrf entries for given node";
    input {
      leaf vrf {
        type string;
        mandatory true;
        description
          "vrf";
        csc:cli-name "*";
      }
      leaf node-location {
        type string;
        mandatory true;
        description
          "Node location";
        csc:cli-name "*";
      }
    }
    csc:cli-command "clear cnbng-nal subscriber vrf <vrf> location <node-location>";
  }
}
