module Cisco-IOS-XR-pbr-cfg {
  namespace "http://cisco.com/ns/yang/Cisco-IOS-XR-pbr-cfg";
  prefix pbr-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pbr package configuration.
     
     This YANG module augments the
       Cisco-IOS-XR-ifmgr-cfg
     module with configuration data.
     
     Copyright (c) 2013-2020 by Cisco Systems, Inc.
     All rights reserved.";

  revision 2020-11-19 {
    description
      "PBR Flowspec config rollback error in module.";
    semver:module-version "1.0.1";
  }
  revision 2019-04-05 {
    description
      "Establish semantic version baseline.";
    semver:module-version "1.0.1";
  }
  revision 2018-05-17 {
    description
      "CSCvi93168 PBR commit replace feature.";
  }
  revision 2016-03-08 {
    description
      "Moved augment statement to a separate file";
  }
  revision 2015-11-09 {
    description
      "IOS XR 6.0 revision.";
  }

  augment "/a1:interface-configurations/a1:interface-configuration" {
    description
      "This augment extends the configuration data of
       'Cisco-IOS-XR-ifmgr-cfg'";
    container pbr {
      description
        "Interface PBR configuration";
      container service-policies {
        description
          "Ingress service policy";
        list service-policy {
          key "service-policy";
          description
            "Service policy details";
          leaf service-policy {
            type string {
              length "1..64";
            }
            description
              "Name of policy-map";
          }
        }
      }
      leaf service-policy-in {
        type string;
        description
          "Class for subscriber ingress policy";
      }
    }
  }
}
