submodule Cisco-IOS-XR-bvi-gateway-ea-oper-sub1 {
  belongs-to Cisco-IOS-XR-bvi-gateway-ea-oper {
    prefix Cisco-IOS-XR-bvi-gateway-ea-oper;
  }

  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR bvi-gateway-ea package operational data.
     
     Copyright (c) 2013-2026 by Cisco Systems, Inc.
     All rights reserved.";

  revision 2026-04-08 {
    description
      "Initial revision.";
    semver:module-version "1.0.0";
  }
  revision 2019-04-05 {
    description
      "Establish semantic version baseline.";
  }
  revision 2015-11-09 {
    description
      "IOS XR 6.0 revision.";
  }

  typedef Im-state {
    type uint32;
    description
      "Im state";
  }

  grouping L3DAG-EA-IDB-UL-INTF {
    description
      "Underlying interface list member";
    leaf member-interface-name {
      type xr:Interface-name;
      description
        "Member Interface Handle";
    }
    leaf member-npu-mask {
      type uint32;
      description
        "Member NPU Mask";
    }
  }

  grouping L3DAG-EA-IDB {
    description
      "BVI-Gateway EA Interface Database";
    leaf bvi-gateway-name-xr {
      type xr:Interface-name;
      description
        "BVI-Gateway interface handle (canonical key)";
    }
    leaf interface-state {
      type Im-state;
      description
        "Interface state";
    }
    leaf interface-npu-mask {
      type uint32;
      description
        "Interface NPU mask";
    }
    leaf interface-type {
      type string;
      description
        "Interface Type";
    }
    leaf mac-address {
      type yang:mac-address;
      description
        "Effective MAC address";
    }
    list underlying-interface {
      key "member-interface-name";
      description
        "Underlying interfaces";
      uses L3DAG-EA-IDB-UL-INTF;
    }
    list base-underlying-interface {
      key "member-interface-name";
      description
        "Base underlying interfaces";
      uses L3DAG-EA-IDB-UL-INTF;
    }
  }
}
