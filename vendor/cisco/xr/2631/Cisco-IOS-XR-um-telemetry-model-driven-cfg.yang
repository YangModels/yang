module Cisco-IOS-XR-um-telemetry-model-driven-cfg {
  namespace "http://cisco.com/ns/yang/Cisco-IOS-XR-um-telemetry-model-driven-cfg";
  prefix um-telemetry-model-driven-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco telemetry package configuration.
     Copyright (c) 2024-2026 by Cisco Systems, Inc., and/or its affiliates.
     All rights reserved.";

  revision 2026-03-10 {
    description
      "Deprecated heartbeat/always leaf
       2026-01-23
         Deprecated the max-containers-per-path leaf";
    semver:module-version "4.1.0";
  }
  revision 2025-05-29 {
    description
      "Changed maximum string length of destination group, sensor group,
        subscription and sensor path
       2024-06-28
          Initial UM2 release
       2022-05-02
          Added gNMI bundling of telemetry updates";
    semver:module-version "4.0.0";
  }
  revision 2021-06-28 {
    description
      "added new leaf node mode";
    semver:module-version "3.1.0";
  }
  revision 2021-05-12 {
    description
      "added a must statement under sensor-group
       2020-12-10
            Changed string length of leaf nodes that set maximum as 1024
       2020-10-02
            Added heartbeat containers";
    semver:module-version "3.0.0";
  }
  revision 2020-05-08 {
    description
      "Added new containers, destinations under destination-group and
          tcp-send-timeout/gnmi-target-defined under top node
       2020-03-13
          Added new gzip option for grpc protocol";
    semver:module-version "2.0.0";
  }
  revision 2019-06-10 {
    description
      "Establish semantic version baseline.";
    semver:module-version "1.0.1";
  }
  revision 2019-03-30 {
    description
      "Initial version";
  }

  feature grpc {
    description
      "grpc";
  }

  container telemetry {
    description
      "Telemetry configuration";
    container model-driven {
      presence "Model Driven Telemetry configuration commands";
      description
        "Model Driven Telemetry configuration commands";
      leaf max-containers-per-path {
        type uint32 {
          range "0..1024" {
            description
              "This configuration has no effect as of release 26.2.1. This will be removed in release 27.1.1";
          }
        }
        status deprecated;
        description
          "This configuration has no effect as of release 26.2.1. This will be removed in release 27.1.1";
      }
      leaf max-sensor-paths {
        type uint32 {
          range "0..4000" {
            description
              "Maximum sensor paths, 0 disables the check";
          }
        }
        description
          "Maximum allowed sensor paths (default: 1000)";
      }
      leaf tcp-send-timeout {
        type uint32 {
          range "0..30" {
            description
              "TCP send timeout value, 0 disables the timeout";
          }
        }
        description
          "TCP send timeout value in seconds (default: 30)";
      }
      leaf strict-timer {
        type empty;
        description
          "use strict timer for all subscriptions, default is relative timer";
      }
      container gnmi-target-defined {
        description
          "GNMI target defined to select minimum cadence and cadence factor";
        leaf cadence-factor {
          type uint32 {
            range "1..10" {
              description
                "Multiplier factor of collection time for cadence for tgtdef mode";
            }
          }
          description
            "Multiplier factor for cadence of target defined subscriptions";
        }
        leaf minimum-cadence {
          type uint32 {
            range "1..65535" {
              description
                "Minimum cadence for target defined subscriptions in seconds";
            }
          }
          description
            "Minimum cadence for target defined subscriptions in secs";
        }
      }
      container include {
        description
          "Include fields with empty values in output";
        leaf select-leaves-on-events {
          type empty;
          description
            "Include only configured leafs on on-change event for the sensor-path";
        }
        container empty {
          description
            "Include fields with empty values in output";
          leaf values {
            type empty;
            description
              "Include fields with empty values in output";
          }
        }
      }
      container gnmi {
        description
          "GNMI subscribe";
        container heartbeat {
          description
            "gNMI heartbeat";
          leaf always {
            type empty;
            status deprecated;
            description
              "This configuration has no effect as of release 26.3.1. This will be removed in release 27.2.1";
          }
        }
        container bundling {
          presence "gNMI bundling of telemetry updates";
          description
            "gNMI bundling of telemetry updates";
          leaf size {
            type uint32 {
              range "1024..65536" {
                description
                  "gNMI bundling size (bytes)";
              }
            }
            description
              "gNMI bundling size (default: 32768)";
          }
        }
      }
      container destination-groups {
        description
          "Destination Group Id";
        list destination-group {
          key "destination-group-string";
          description
            "Destination Group Id";
          leaf destination-group-string {
            type xr:Cisco-ios-xr-string {
              length "1..64" {
                description
                  "Destination Group Id string";
              }
            }
            description
              "Destination Group Id string";
          }
          leaf vrf {
            type xr:Cisco-ios-xr-string {
              length "1..32" {
                description
                  "vrf-name for the dest grp";
              }
            }
            description
              "vrf for the dest grp";
          }
          container address-families {
            description
              "Destination address of the recepient of the telemetry information";
            list address-family {
              key "af-name destination-address port";
              description
                "Destination address of the recepient of the telemetry information";
              leaf af-name {
                type xr:Cisco-ios-xr-string {
                  length "1..1024" {
                    description
                      "af-name";
                  }
                }
                description
                  "af-name";
              }
              leaf destination-address {
                type inet:ip-address-no-zone;
                description
                  "destination-address";
              }
              leaf port {
                type uint32 {
                  range "1..65535" {
                    description
                      "Port Number";
                  }
                }
                description
                  "Destination Port configuration";
              }
              container protocol {
                description
                  "Transport protocol";
                choice PROTOCOL {
                  description
                    "Transport protocol";
                  case GRPC {
                    container grpc {
                      if-feature "grpc";
                      presence "gRPC";
                      description
                        "gRPC";
                      leaf no-tls {
                        type empty;
                        description
                          "No TLS";
                      }
                      leaf tls-hostname {
                        type xr:Cisco-ios-xr-string {
                          length "1..255" {
                            description
                              "hostname";
                          }
                        }
                        description
                          "TLS hostname";
                      }
                      leaf gzip {
                        type empty;
                        description
                          "gRPC gzip message compression";
                      }
                    }
                  }
                  case TCP {
                    leaf tcp {
                      type empty;
                      description
                        "TCP";
                    }
                  }
                  case UDP {
                    container udp {
                      presence "UDP";
                      description
                        "UDP";
                      leaf packetsize {
                        type uint32 {
                          range "484..65507" {
                            description
                              "UDP packet size";
                          }
                        }
                        description
                          "UDP packet size";
                      }
                    }
                  }
                }
              }
              leaf encoding {
                type enumeration {
                  enum "gpb" {
                    value 2;
                    description
                      "GPB encoding";
                  }
                  enum "self-describing-gpb" {
                    value 3;
                    description
                      "Self describing GPB encoding";
                  }
                  enum "json" {
                    value 4;
                    description
                      "JSON encoding";
                  }
                }
                description
                  "Transport protocol encoding";
              }
            }
          }
          container destinations {
            description
              "Destination IP address or fully qualified domain name";
            list destination {
              key "destination-string port";
              description
                "Destination IP address or fully qualified domain name";
              leaf destination-string {
                type xr:Cisco-ios-xr-string {
                  length "1..128" {
                    description
                      "IPv4/IPv6 address or domain name";
                  }
                }
                description
                  "IPv4/IPv6 address or domain name";
              }
              leaf port {
                type uint32 {
                  range "1..65535" {
                    description
                      "Port number";
                  }
                }
                description
                  "Destination port";
              }
              leaf address-family {
                type enumeration {
                  enum "ipv4" {
                    value 1;
                    description
                      "IPv4 address family";
                  }
                  enum "ipv6" {
                    value 2;
                    description
                      "IPv6 address family";
                  }
                }
                description
                  "Specify the desired address family for the returned addresses from DNS. Only applicable to FQDN";
              }
              container protocol {
                description
                  "Transport protocol";
                choice PROTOCOL {
                  description
                    "Transport protocol";
                  case GRPC {
                    container grpc {
                      presence "gRPC";
                      description
                        "gRPC";
                      leaf no-tls {
                        type empty;
                        description
                          "No TLS";
                      }
                      leaf tls-hostname {
                        type xr:Cisco-ios-xr-string {
                          length "1..255" {
                            description
                              "hostname";
                          }
                        }
                        description
                          "TLS hostname";
                      }
                      leaf gzip {
                        type empty;
                        description
                          "gRPC gzip message compression";
                      }
                    }
                  }
                  case TCP {
                    leaf tcp {
                      type empty;
                      description
                        "TCP";
                    }
                  }
                  case UDP {
                    container udp {
                      presence "UDP";
                      description
                        "UDP";
                      leaf packetsize {
                        type uint32 {
                          range "484..65507" {
                            description
                              "UDP packet size";
                          }
                        }
                        description
                          "UDP packet size";
                      }
                    }
                  }
                }
              }
              leaf encoding {
                type enumeration {
                  enum "gpb" {
                    value 2;
                    description
                      "GPB encoding";
                  }
                  enum "self-describing-gpb" {
                    value 3;
                    description
                      "Self describing GPB encoding";
                  }
                  enum "json" {
                    value 4;
                    description
                      "JSON encoding";
                  }
                }
                description
                  "Transport protocol encoding";
              }
            }
          }
        }
      }
      container subscriptions {
        description
          "Subscription Id";
        list subscription {
          key "subscription-string";
          description
            "Subscription Id";
          leaf subscription-string {
            type xr:Cisco-ios-xr-string {
              length "1..64" {
                description
                  "Subscription Id string";
              }
            }
            description
              "Subscription Id string";
          }
          leaf source-qos-marking {
            type enumeration {
              enum "default" {
                value 0;
                description
                  "Match packets with default dscp (000000)";
              }
              enum "af11" {
                value 10;
                description
                  "Match packets with AF11 dscp (001010)";
              }
              enum "af12" {
                value 12;
                description
                  "Match packets with AF12 dscp (001100)";
              }
              enum "af13" {
                value 14;
                description
                  "Match packets with AF13 dscp (001110)";
              }
              enum "af21" {
                value 18;
                description
                  "Match packets with AF21 dscp (010010)";
              }
              enum "af22" {
                value 20;
                description
                  "Match packets with AF22 dscp (010100)";
              }
              enum "af23" {
                value 22;
                description
                  "Match packets with AF23 dscp (010110)";
              }
              enum "af31" {
                value 26;
                description
                  "Match packets with AF31 dscp (011010)";
              }
              enum "af32" {
                value 28;
                description
                  "Match packets with AF32 dscp (011100)";
              }
              enum "af33" {
                value 30;
                description
                  "Match packets with AF33 dscp (011110)";
              }
              enum "af41" {
                value 34;
                description
                  "Match packets with AF41 dscp (100010)";
              }
              enum "af42" {
                value 36;
                description
                  "Match packets with AF42 dscp (100100)";
              }
              enum "af43" {
                value 38;
                description
                  "Match packets with AF43 dscp (100110)";
              }
              enum "cs1" {
                value 8;
                description
                  "Match packets with CS1 dscp (001000)";
              }
              enum "cs2" {
                value 16;
                description
                  "Match packets with CS2 dscp (010000)";
              }
              enum "cs3" {
                value 24;
                description
                  "Match packets with CS3 dscp (011000)";
              }
              enum "cs4" {
                value 32;
                description
                  "Match packets with CS4 dscp (100000)";
              }
              enum "cs5" {
                value 40;
                description
                  "Match packets with CS5 dscp (101000)";
              }
              enum "cs6" {
                value 48;
                description
                  "Match packets with CS6 dscp (110000)";
              }
              enum "cs7" {
                value 56;
                description
                  "Match packets with CS7 dscp (111000)";
              }
              enum "ef" {
                value 46;
                description
                  "Match packets with EF dscp (101110)";
              }
            }
            description
              "Outgoing DSCP value";
          }
          leaf source-interface {
            type xr:Interface-name;
            description
              "Source interface to use in the outgoing IP packets";
          }
          container sensor-group-ids {
            description
              "Association of one or more Sensor Groups with a Subscription Id";
            list sensor-group-id {
              must "mode or heartbeat/always or heartbeat/interval or strict-timer or sample-interval";
              key "sensor-group-id-string";
              description
                "Association of one or more Sensor Groups with a Subscription Id";
              leaf sensor-group-id-string {
                type xr:Cisco-ios-xr-string {
                  length "1..64" {
                    description
                      "Available Sensor Groups";
                  }
                }
                description
                  "Available Sensor Groups";
              }
              leaf mode {
                type enumeration {
                  enum "target-defined" {
                    value 0;
                    description
                      "Device selects one of sample/on-change for leaves to stream data";
                  }
                }
                description
                  "Subscription mode";
              }
              container heartbeat {
                description
                  "Heartbeat";
                leaf always {
                  type empty;
                  status deprecated;
                  description
                    "This configuration has no effect as of release 26.3.1. This will be removed in release 27.2.1";
                }
                leaf interval {
                  type uint32 {
                    range "1..4294967295" {
                      description
                        "Heartbeat interval in milliseconds";
                    }
                  }
                  description
                    "Send subscription data per heartbeat interval when no events have occurred within interval";
                }
              }
              leaf strict-timer {
                type empty;
                description
                  "use strict timer, default is relative timer";
              }
              leaf sample-interval {
                type uint32 {
                  range "0..4294967295" {
                    description
                      "Sample interval in milliseconds";
                  }
                }
                description
                  "Sample interval";
              }
            }
          }
          container destination-ids {
            description
              "Destination Group Id to associate with the current subscription id";
            list destination-id {
              key "destination-id-string";
              description
                "Destination Group Id to associate with the current subscription id";
              leaf destination-id-string {
                type xr:Cisco-ios-xr-string {
                  length "1..64" {
                    description
                      "Available Destination Group Ids";
                  }
                }
                description
                  "Available Destination Group Ids";
              }
            }
          }
          container send {
            description
              "Send retry";
            container retry {
              description
                "Number of send retries";
              leaf retry-number {
                type uint32 {
                  range "1..10" {
                    description
                      "Number of send retries";
                  }
                }
                must "../duration";
                description
                  "Number of send retries";
              }
              leaf duration {
                type uint32 {
                  range "0..10000" {
                    description
                      "Send retry wait duration in microseconds. 0 means yield.";
                  }
                }
                must "../retry-number";
                description
                  "Send retry wait duration in microseconds";
              }
            }
          }
        }
      }
      container sensor-groups {
        description
          "Sensor group configuration";
        list sensor-group {
          key "sensor-group-string";
          description
            "Sensor group configuration";
          leaf sensor-group-string {
            type xr:Cisco-ios-xr-string {
              length "1..64" {
                description
                  "Sensor Group Id";
              }
            }
            description
              "Sensor Group Id";
          }
          container sensor-paths {
            description
              "Sensor Path";
            list sensor-path {
              key "sensor-path-string";
              description
                "Sensor Path";
              leaf sensor-path-string {
                type string {
                  length "1..512" {
                    description
                      "Sensor Path";
                  }
                }
                description
                  "Sensor Path";
              }
            }
          }
        }
      }
    }
  }
}
