module Cisco-IOS-XR-openconfig-mpls-static-ext {
  yang-version 1;
  namespace "http://cisco.com/ns/yang/Cisco-IOS-XR-openconfig-mpls-static-ext";
  prefix oc-mpls-static-cisco-xr-ext;

  import openconfig-extensions {
    prefix oc-ext;
  }
  import openconfig-network-instance {
    prefix oc-ni;
  }
  import openconfig-mpls-types {
    prefix oc-mplst;
  }
  import openconfig-inet-types {
    prefix inet;
  }
  import openconfig-interfaces {
    prefix oc-if;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module adds extensions to the OpenConfig MPLS Static model to
     provide extensions which allow non-resolve nexthops to be adequately
     configured and operated. It augments the existing OpenConfig MPLS Static
     model where required.";

  revision 2023-02-22 {
    description
      "removed unused import";
    reference "1.0.0";
  }
  revision 2022-05-12 {
    description
      "Initial version";
    reference "0.1.0";
  }

  grouping mpls-static-interface-attributes-config {
    description
      "global level definitions for interfaces
       on which MPLS is run";
    leaf enabled-interface {
      type oc-if:interface-id;
      description
        "Indentifier for the MPLS interface";
    }
  }

  grouping mpls-static-interfaces-top {
    description
      "Top level grouping for attributes
       for MPLS static ingress-enabled interfaces.";
    container interface-attributes {
      description
        "Parameters related to MPLS interfaces";
      list interface {
        key "enabled-interface";
        description
          "List of MPLS static interfaces";
        leaf enabled-interface {
          type leafref {
            path "../config/enabled-interface";
          }
          description
            "Reference to the interface id list key";
        }
        container config {
          description
            "Configuration parameters related to MPLS interfaces:";
          uses mpls-static-interface-attributes-config;
        }
        container state {
          config false;
          description
            "State parameters related to MPLS static interfaces";
          uses mpls-static-interface-attributes-config;
        }
      }
    }
  }

  grouping static-lsp-extended-paths-path {
    description
      "common definitions for static LSPs with multiple out-going paths.";
    leaf path-id {
      type uint32;
      description
        "Path id key";
    }
    leaf next-hop {
      type inet:ip-address;
      description
        "next hop IP address for the LSP";
    }
    leaf push-label {
      type oc-mplst:mpls-label;
      description
        "label value to push at the current hop for the
         LSP";
    }
    leaf push-interface {
      type string;
      description
        "interface name of outgoing traffic";
    }
  }

  grouping static-lsp-ext-paths-top {
    description
      "common definitions for additional static LSP push paths";
    container paths {
      description
        "Additional push LSP paths";
      list path {
        key "path-id";
        description
          "list of additional static LSP push paths";
        leaf path-id {
          type leafref {
            path "../config/path-id";
          }
          description
            "Path id of the out-going path.";
        }
        container config {
          description
            "Configuration parameters relating push path.";
          uses static-lsp-extended-paths-path;
        }
        container state {
          config false;
          description
            "State parameters relating to push path";
          uses static-lsp-extended-paths-path;
        }
      }
    }
  }

  grouping static-lsp-ingress-interface-info {
    description
      "static lsp ingress interface enable info";
    container static-lsp-ingress-interfaces {
      description
        "static lsp enabled ingress interfaces ";
      uses mpls-static-interfaces-top;
    }
  }

  grouping static-lsp-ext-info {
    description
      "push interface option for non-resolve nexthops";
    leaf push-interface {
      type string;
      description
        "interface name of outgoing traffic";
    }
  }

  grouping static-lsp-ingress-ext-info {
    description
      "incoming-prefix and incoming-prefix-length values";
    leaf incoming-prefix {
      type inet:ip-address;
      description
        "incoming IP address for the LSP";
    }
    leaf incoming-prefix-length {
      type uint32;
      description
        "length of incoming IP address for the LSP";
    }
    uses static-lsp-ext-info;
  }

  augment "/oc-ni:network-instances/oc-ni:network-instance/oc-ni:mpls/oc-ni:lsps/oc-ni:static-lsps/oc-ni:static-lsp/oc-ni:ingress/oc-ni:config" {
    description
      "Add incoming-prefix, incomfing-prefix length,
       and push-interface to ingress
       configuration hierarchy.";
    uses static-lsp-ingress-ext-info;
  }
  augment "/oc-ni:network-instances/oc-ni:network-instance/oc-ni:mpls/oc-ni:lsps/oc-ni:static-lsps/oc-ni:static-lsp/oc-ni:transit/oc-ni:config" {
    description
      "Add push-interface to transit
       configuration hierarchy.";
    uses static-lsp-ext-info;
  }
  augment "/oc-ni:network-instances/oc-ni:network-instance/oc-ni:mpls/oc-ni:lsps/oc-ni:static-lsps/oc-ni:static-lsp/oc-ni:egress/oc-ni:config" {
    description
      "Add push-interface to egress
       configuration hierarchy.";
    uses static-lsp-ext-info;
  }
  augment "/oc-ni:network-instances/oc-ni:network-instance/oc-ni:mpls/oc-ni:lsps/oc-ni:static-lsps/oc-ni:static-lsp/oc-ni:ingress/oc-ni:state" {
    description
      "Add incoming-prefix, incomfing-prefix length,
       and push-interface to ingress
       state hierarchy.";
    uses static-lsp-ingress-ext-info;
  }
  augment "/oc-ni:network-instances/oc-ni:network-instance/oc-ni:mpls/oc-ni:lsps/oc-ni:static-lsps/oc-ni:static-lsp/oc-ni:transit/oc-ni:state" {
    description
      "Add push-interface to transit
       state hierarchy.";
    uses static-lsp-ext-info;
  }
  augment "/oc-ni:network-instances/oc-ni:network-instance/oc-ni:mpls/oc-ni:lsps/oc-ni:static-lsps/oc-ni:static-lsp/oc-ni:egress/oc-ni:state" {
    description
      "Add push-interface to egress
       state hierarchy.";
    uses static-lsp-ext-info;
  }
  augment "/oc-ni:network-instances/oc-ni:network-instance/oc-ni:mpls" {
    description
      "Add list of static lsp ingress interfaces to the
       mpls configuration hierarchy.";
    uses static-lsp-ingress-interface-info;
  }
  augment "/oc-ni:network-instances/oc-ni:network-instance/oc-ni:mpls/oc-ni:lsps/oc-ni:static-lsps/oc-ni:static-lsp/oc-ni:ingress" {
    description
      "Add incoming-prefix, incomfing-prefix length,
       and push-interface to ingress
       configuration hierarchy.";
    uses static-lsp-ext-paths-top;
  }
  augment "/oc-ni:network-instances/oc-ni:network-instance/oc-ni:mpls/oc-ni:lsps/oc-ni:static-lsps/oc-ni:static-lsp/oc-ni:transit" {
    description
      "Add push-interface to transit
       configuration hierarchy.";
    uses static-lsp-ext-paths-top;
  }
  augment "/oc-ni:network-instances/oc-ni:network-instance/oc-ni:mpls/oc-ni:lsps/oc-ni:static-lsps/oc-ni:static-lsp/oc-ni:egress" {
    description
      "Add push-interface to egress
       configuration hierarchy.";
    uses static-lsp-ext-paths-top;
  }
  oc-ext:openconfig-version "1.0.0";
}
