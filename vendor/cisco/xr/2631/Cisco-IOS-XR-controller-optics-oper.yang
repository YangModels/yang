module Cisco-IOS-XR-controller-optics-oper {
  namespace "http://cisco.com/ns/yang/Cisco-IOS-XR-controller-optics-oper";
  prefix controller-optics-oper;

  import Cisco-IOS-XR-types {
    prefix xr;
  }
  import cisco-semver {
    prefix semver;
  }
  include Cisco-IOS-XR-controller-optics-oper-sub2 {
    revision-date 2026-05-26;
  }
  include Cisco-IOS-XR-controller-optics-oper-sub1 {
    revision-date 2026-05-26;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-optics package operational data.
     
     This module contains definitions
     for the following management objects:
       optics-oper: Optics operational data
     
     Copyright (c) 2013-2026 by Cisco Systems, Inc.
     All rights reserved.";

  revision 2026-05-26 {
    description
      "Added support for Generic DCO module
       2026-04-28
         Changed unit of cfg-tx-powerm-w from 0.1mW to uW
       2026-04-11
         Added RX and TX hold-off timer operational data
       2026-03-16
         Added new Optics Phy Type: QDD_PSM
       2026-03-15
         Added 800GBASE-VR8 and 800GBASE-DR8 to Ethernet Compliance Type
       2026-03-09
         Corrected transposed TX mW threshold values (tx-high-thresholdm-w / tx-low-thresholdm-w).
       2026-01-16
         Added support for OSFP 800G VR8
       2025-12-16
         Added C+S Band support: new enum OPTICS_C_PLUS_S_BAND for operational data";
    semver:module-version "7.0.0";
  }
  revision 2025-11-25 {
    description
      "Converted voltage and temperature to pointer in optics_edm_info bag
       2025-09-15
          Added support for OSFP 800G FR4
       2025-08-28
          Added support for OSFP 800G DR8 and Removed LLH as it's considered as ULH L-Band
       2025-08-14
          Added support for Optics PRBS
       2025-07-17
          Added support for 400G LLH and 800G ZR
       2025-05-23
          Added support for OPTICS_PHY_TYPE_25G_50G_SL
       2025-04-15
          Added enum support OPTICS_PHY_TYPE_4x100G_CU and OPTICS_PHY_TYPE_100G_CR2 for new optics 4x100 CU and 100G CR2
       2025-02-11
          Added new leaves in active application selection information
       2024-12-16
          Added support for Application Selection Code
       2024-12-16
          Added support for Application Descriptor
       2024-11-28
          enum added for Optics Phy Type for 400G ULH module
       2024-10-24
          Added OPTICS_PHY_TYPE_100G_BX20_BD
       2024-10-15
          Added last link flap field
       2024-08-06
          Added new media type definination for 25G/50G LR-S optics
       2024-07-14
          enum added for Optics Phy Type for 400G ER1 module
       2024-06-30
          Added enum support OPTICS_PHY_TYPE_1G_T_X for new optics SFP-1G-T-X
       2024-06-26
          Added support for hardware version
       2024-06-10
          Added support for rx-voa gain-offset
       2024-05-31
          Added OPTICS_PHY_TYPE_100G_BX40_BD
       2024-05-27
          Added support for media linkdown prefec degrade
       2024-05-22
          Added support for firmware active and inactive version
       2024-04-16
          Added CS connector type
       2024-03-01
          Added SFP-50G-ER-I, SFP-50G-BX40U, SFP-50G-BX40D
       2024-02-15
          New form factor types CSFP, DSFP, QSFP28_DD added.
       2023-12-13
          Added QSFP-DD SR4-BD
       2023-11-21
          New form factor types QSFP56, QSFP56_DD, SFP_56, SFP_DD added.
       2023-07-31
          Added New PCS enum in modulation type
       2023-05-31
          New leaf nodes for dom status and power mode added for optics controller.
       2023-05-15
          Added support for FED and FDD thresholds.
       2023-03-23
          Added support for optics observable data.
       2023-03-20
          New OPTICS_ETH_400GBASE_LR4 added to EthernetPmdType
       2023-03-17
          New form factor type CIM8 added.
       2023-02-27
          New OPTICS_PHY_TYPE_25G_SL added to OpticsPhyType
       2023-02-24
          Leaf loopback-host and loopback-media added for optics controller.
       2023-01-18
          Support for squelch host and media
       2022-11-04
          enum OPTICS_FORM_FACTOR_OSFP added in Form Factor list for OSFP module
       2022-10-03
          enum added for new Optics Phy Type for 400G Bright ZRP module
       2022-10-02
          enum added for new Optics Phy Type for QSFP-DD DUAL EDFA module
       2022-09-10
          enum added for new Optics Phy Type for 2x400G LR4 module
       2022-05-10
          enum added for new Optics Phy Type for Credo 800G AEC
       2022-04-22
          enum added for new Optics Phy Type for 8x100G FR module
       2022-02-03
          Added power fields in mW unit in Grey lane data
       2022-01-28
          introducing lane0 alarm counters paramaters for those platforms which want to use lanes from 0-7
       2022-01-27
          Added power fields for mW unit in optics transponder information
       2022-01-20
          enum added for new QSA Adapter Cazadero28
       2022-01-07
          enum added for new Optics Phy Type for 400G SR8 module
       2022-01-06
          New Enum OPTICS_PHY_TYPE_1G_LH are added in enum OpticsPhyType
       2021-12-22
          enum added for new Optics Phy Type 100m FE FX
       2021-12-03
          enumadded for new Optics Phy Type for 200G FR4 modules
       2021-11-27
          Added Dac Rate field in optics_edm_info.
       2021-11-22
          Added threshold fields for mW unit in optics transponder information
       2021-10-08
          enum added for new Optics Phy Type for 800G ELB module
       2021-09-20
          enum added for new Optics Phy Type for 2x400G FR and 8x100 DR module";
    semver:module-version "6.0.0";
  }
  revision 2021-09-17 {
    description
      "enumadded for new Optics Phy Type for 200G Cu, 200G AOC, 2x200G CU and 2x200G AOC modules
       2021-07-30
           New Enum OPTICS_PHY_TYPE_100G_ERL are added in enum OpticsPhyType
       2021-07-06
           enum added for new Optics Phy Type for 4x100G LR module
       2021-06-22
           New OPTICS_PHY_TYPE_16G_FC,OPTICS_PHY_TYPE_32G_FC are added in enum OpticsPhyType
       2021-06-21
           New Enums added for FibreChannel 16G and 32G Optics Phy type
       2021-06-10
           New parameters added in bag
       2021-05-27
           DAC rate and Laser temperature and laser age Added for Optics Controller";
    semver:module-version "5.0.0";
  }
  revision 2021-04-14 {
    description
      "New Enums added for Multirate Optics Phy type
       2021-03-22
            New Enums added for Optics Phy type
       2021-02-23
            enum added for new Optics Phy Type for 400G LR4 module
       2021-02-19
            enum added for 1 new Optics Phy Type and new value added to enum EthernetPmdType
       2021-02-17
            New OPTICS_ETH_100GBASE_DR_S added to enum EthernetPmdType
       2021-01-18
            Added 2 enums for New FEC Type.
       2020-12-23
            New value added to enum EthernetPmdType
       2020-11-24
            Enum value in optics_modulation_type is changed from MODE_16QAM_32QAM to MOD_16QAM_32QAM
       2020-11-10
            enum added for 1 new Optics Phy Type for 100G DR-S optics module
       2020-09-10
            removed optics_edm_fastpoll_info and added new bag optics_edm_fastpoll_data
       2020-08-02
            New values added to enum FiberConnectorType
       2020-07-24
            New value added in optics yang for FastPollInfo
       2020-07-14
            New value added to enum EthernetPmdType";
    semver:module-version "4.0.0";
  }
  revision 2020-04-26 {
    description
      "New value added to enum EthernetPmdType
       2020-02-24
          enum added for OTN Application code.
       2020-02-19
          enum added for 1 new Optics Phy Type
       2020-01-31
          enum added for 1 new Optics Phy Type
       2020-01-27
          Added new parameters in optics bag to display parameters which are not configurable
       2019-12-05
          enum added for 2 new OTN Application codes.
       2019-11-30
          Back Reflection data field is added in bag.
       2019-09-30
          chan_num data field is added to support L-Band frequency range.";
    semver:module-version "3.0.0";
  }
  revision 2019-04-05 {
    description
      "Establish semantic version baseline.";
    semver:module-version "2.0.0";
  }
  revision 2017-09-07 {
    description
      "Fixed type translation error.";
  }
  revision 2017-05-01 {
    description
      "Fixing backward compatibility error in module.";
  }
  revision 2015-11-09 {
    description
      "IOS XR 6.0 revision.";
  }

  container optics-oper {
    config false;
    description
      "Optics operational data";
    container optics-ports {
      description
        "All Optics Port operational data";
      list optics-port {
        key "name";
        description
          "Optics operational data";
        container observable-lanes {
          description
            "Enclosing container for optics observables
             lane/module data";
          list observable-lane {
            key "lane-id";
            description
              "Optics observable lane/module level
               information";
            leaf lane-id {
              type uint32;
              description
                "Observable lane/module identifier";
            }
            uses OPTICS-OBSERVABLE-LANE-INFO;
          }
        }
        container prbs-capability-info {
          description
            "PRBS capabilities supported on the optics port";
          uses OPTICS-PRBS-CAPABILITY-INFO;
        }
        container application-code-info {
          description
            "Information on application codes supported on
             the optics";
          uses OPTICS-APP-CODE-INFO;
        }
        container prbs-info {
          description
            "PRBS test related information";
          uses OPTICS-PRBS-INFO;
        }
        container optics-dwdm-carrier-channel-map {
          description
            "Optics operational data";
          uses OPTICS-EDM-WAVE-INFO;
        }
        container fec-threshold {
          description
            "Optics FEC threshold information";
          uses OPTICS-FEC-THRESH-INFO;
        }
        container ots-spectrum-info {
          description
            "Ots Spectrum Operational data";
          uses OPTICS-EDM-SPECTRUM-INFO;
        }
        container optics-dwdm-carrier-channel-map-flexi {
          description
            "Optics operational data";
          uses OPTICS-EDM-WAVE-INFO;
        }
        container optics-info {
          description
            "Optics operational data";
          uses OPTICS-EDM-INFO;
        }
        container optics-reload-info {
          description
            "Optics operational data";
          uses OPTICS-TRANSCEIVER-RELOAD-INFO;
        }
        container optics-fastpolls {
          description
            "All Optics Fastpoll operational data";
          list optics-fastpoll {
            key "unique-id";
            description
              "Fastpoll Information";
            leaf unique-id {
              type uint32;
              description
                "Fastpoll Index";
            }
            uses OPTICS-EDM-FASTPOLL-DATA;
          }
        }
        container optics-lanes {
          description
            "All Optics Port operational data";
          list optics-lane {
            key "number";
            description
              "Lane Information";
            leaf number {
              type uint32;
              description
                "Lane Index";
            }
            uses OPTICS-EDM-LANE-DATA;
          }
        }
        container application-code-info-detail {
          description
            "Detailed information on application codes
             supported on the optics";
          uses OPTICS-APP-CODE-INFO;
        }
        container active-application-code-info {
          description
            "Optics operational data";
          uses OPTICS-ACTIVE-APPLICATION-CODE-INFO-ALL;
        }
        container optics-db-info {
          description
            "Optics operational data";
          uses OPTICS-DB-INFO;
        }
        leaf name {
          type xr:Interface-name;
          description
            "Port name";
        }
      }
    }
  }
}
