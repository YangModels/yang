module Cisco-IOS-XR-crypto-cepki-oper {
  namespace "http://cisco.com/ns/yang/Cisco-IOS-XR-crypto-cepki-oper";
  prefix crypto-cepki-oper;

  import Cisco-IOS-XR-types {
    prefix xr;
  }
  import cisco-semver {
    prefix semver;
  }
  include Cisco-IOS-XR-crypto-cepki-oper-sub1 {
    revision-date 2026-02-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-cepki package operational data.
     
     This module contains definitions
     for the following management objects:
       crypto-certificate-authority: Public Key Infrastructure
         Related Information
     
     Copyright (c) 2013-2026 by Cisco Systems, Inc.
     All rights reserved.";

  revision 2026-02-28 {
    description
      "Added telemetry support for x509 and openssh certificate info by implementing bags for the same.";
    semver:module-version "2.0.0";
  }
  revision 2022-07-22 {
    description
      "added multiple rsa authentication keys support.
       2022-04-06
          Added serial number and fingerprint for ca.
       2022-03-20
          OpenSSH certificate support.";
    semver:module-version "1.1.0";
  }
  revision 2019-04-05 {
    description
      "Establish semantic version baseline.";
    semver:module-version "1.0.0";
  }
  revision 2015-11-09 {
    description
      "IOS XR 6.0 revision.";
  }

  container crypto-certificate-authority {
    config false;
    description
      "Public Key Infrastructure Related Information";
    container trustpoints {
      description
        "CA Trustpoint Table Information";
      list trustpoint {
        key "name";
        description
          "Certificate Information for a particular
           Trustpoint";
        leaf name {
          type xr:Cisco-ios-xr-string;
          description
            "The Trustpoint to query";
        }
        uses CRYPTO-TRUSTPOINT;
      }
    }
    container openssh {
      description
        "Certificate Authority OpenSSH Trustpoint Table
         Information";
      container openssh-trustpoints {
        description
          "Certificate Authority OpenSSH Trustpoint Table
           Information";
        list openssh-trustpoint {
          key "name";
          description
            "Certificate Information for a particular
             OpenSSH Trustpoint";
          leaf name {
            type xr:Cisco-ios-xr-string;
            description
              "OpenSSH Trustpoint name";
          }
          uses OPENSSH-TRUSTPOINT;
        }
      }
    }
  }
}
