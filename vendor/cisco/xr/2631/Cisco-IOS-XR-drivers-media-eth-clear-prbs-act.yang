module Cisco-IOS-XR-drivers-media-eth-clear-prbs-act {
  namespace "http://cisco.com/ns/yang/Cisco-IOS-XR-drivers-media-eth-clear-prbs-act";
  prefix drivers-media-eth-clear-prbs-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clear prbs bit-errors counter and timestamps for
     Cisco-IOS-XR-drivers-media-eth module.
     
     Copyright (c) 2018-2024 by Cisco Systems, Inc.
     All rights reserved.";

  revision 2026-02-15 {
    description
      "Added controller type restriction to limit clear prbs-stats to
       Ethernet controllers only";
    semver:module-version "2.0.0";
  }
  revision 2024-07-10 {
    description
      "Clear prbs bit-errors counter and timestamps for ethernet controllers";
    semver:module-version "1.0.0";
  }

  rpc clear-controller-prbs-details {
    description
      "Clear prbs bit-errors counter and timestamps";
    input {
      leaf controller-name {
        type string {
          pattern "(GigabitEthCtrlr|TenGigECtrlr|TwentyFiveGigECtrlr|FortyGigECtrlr|FiftyGigECtrlr|HundredGigECtrlr|TwoHundredGigECtrlr|FourHundredGigECtrlr|EightHundredGigECtrlr)[0-9]+(/[0-9]+){3}";
        }
        description
          "Ethernet controller name in R/S/I/P format.
           Only Ethernet controllers are supported ";
      }
      leaf prbs-details {
        type empty;
        description
          "Clear prbs bit-errors counter and timestamps";
      }
    }
  }
}
