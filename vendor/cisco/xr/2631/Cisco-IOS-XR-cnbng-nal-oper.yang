module Cisco-IOS-XR-cnbng-nal-oper {
  namespace "http://cisco.com/ns/yang/Cisco-IOS-XR-cnbng-nal-oper";
  prefix cnbng-nal-oper;

  import Cisco-IOS-XR-types {
    prefix xr;
  }
  import cisco-semver {
    prefix semver;
  }
  include Cisco-IOS-XR-cnbng-nal-oper-sub3 {
    revision-date 2026-08-07;
  }
  include Cisco-IOS-XR-cnbng-nal-oper-sub2 {
    revision-date 2026-08-07;
  }
  include Cisco-IOS-XR-cnbng-nal-oper-sub1 {
    revision-date 2026-08-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cnbng-nal package operational data.
     
     This module contains definitions
     for the following management objects:
       cnbng-nal: cnBNG NAL operational data
     
     Copyright (c) 2013-2026 by Cisco Systems, Inc.
     All rights reserved.";

  revision 2026-08-07 {
    description
      "Added remaining damping time duration in SRG group operational data
       2026-05-05
         Added pending interim stats queue counters in show cnbng-nal process-info.
       2026-03-18
         Added support for retrieving subscribers belonging to cold SRG mode.
       2026-03-05
         Added new show cp connection summary command for configured up-instance.
       2026-03-04
         Updated CP connection status now lists only configured UP instances.
       2026-02-26
         Added schema support for show CLIs to display subscriber summary based on VRF and Access interface.
       2026-02-18
         Updated subscriber disconnect reason type from value to enumeration
       2026-02-11
         Add up instance id information
       2026-02-08
         Added SPA LIB multi-instance counters (global and per-instance)
       2026-01-20
         Removed dynamic-route-summary-tbl container
       2025-12-22
         Updated up-instance-id filter for subscriber, srg-group, dynamic routes and disconnect history.
       2025-12-22
         Updated subscriber detail for up-instance-id.
       2025-12-22
         Updated cp connection information in show command for up-instance-id.";
    semver:module-version "4.0.0";
  }
  revision 2025-09-08 {
    description
      "Added support for warm standby subscriber events
       2025-08-20
          Updated timestamp data type from unit32 to unit64
       2025-07-15
          Added new bag to display warm standby subscriber brief and detail
       2025-07-03
          Added support to get L2TP tunnel context
       2025-07-01
          Added distance leaf in dynamic framed route
       2025-06-30
          Added warm create inprogress and pending information
       2025-04-14
          Added oper support for warm standby feature
       2025-04-03
          Updated timestamp data type from unit32 to unit64
       2025-03-28
          Control-plane subscriber ID datatype updated to uint64
       2025-01-07
          Updated counter name string length in counters and recon history statistics
       2024-12-05
          Added Service params in NAL subscriber detail
       2024-11-15
          Added ipoe-l2-connected option in subscriber and parent interface CLIs
       2024-10-14
          Updated dynamic route summary to include v6 owner channel statistics
       2024-09-18
          Updated subscriber detail and dynamic route data to include next-hop IP information for routed subscribers
       2024-09-05
          Added SRG group subscriber count for keep alive start
       2024-08-28
          Added support to publish subscriber User-Plane, Control-Plane ,transaction id mapping
       2024-08-04
          Updated SLAAC prefix and prefix length fields in NAL subscriber brief and detail
       2024-06-18
          Added Rib statistics under srg group detail
       2024-06-10
          Added slaac counters support.
       2024-05-03
          Included SRG role change counters part of SRG group detail
       2024-02-10
          Updated subscriber detail and subscriber internal detail filtered based on UPID information
       2023-12-10
          Added support to publish CPS(Calls per second) stats
       2023-10-24
          Removed SRG role change counters.
       2023-10-12
          Updated CP-UP connection information to include PFCP and GTPu socket bind result.
       2023-10-03
          Interface name length size is updated.
       2023-07-24
          Annotated process readiness and control-plane/user-plane connection data for EDT support.
       2023-04-07
          Added field to display api-stats viz err status, last fail time, upid for all API used by cnbng nal.
       2023-03-30
          Changed String in dynamic route bag
       2023-03-28
          Reduced failed entry bag description length from 256 to 65 bytes.
       2023-01-11
          Added counters for cp-up spa recon stats.
       2022-12-14
          Added the new field desciption in auto-loopback vrf and srg group configuration.
       2022-12-02
          Updated the data type of node feature-id to String.
       2022-11-21
          Added block size in chunk statistics and session replay response as dynamic data in bag.
       2022-11-03
          Updated binary data associated with each event in event history entry as private.
       2022-10-20
          Changed readable strings like interface/vrf names from type char to string.
       2022-09-06
          Renamed structure in bag file.
       2022-08-31
          Migrated XR library event history to internal history library.
       2022-08-30
          Added key meta-data into oper yang lists.
       2022-08-08
          Added new element outstanding_ka_expiry_cnt in bag file.
       2022-08-04
          Removed dynamic route history query from schema.
       2022-07-27
          Updated SRG group admin state datatype
       2022-07-21
          Updated nal_subscriber_session_info gateway IP format from uint32_t to in_addr_t
       2022-05-16
          added new elements in bag
       2022-03-16
          Added SRG group summary support
       2022-03-15
          Counters arrays made dynamic.
       2022-03-15
          Added counter for fast switchover timer expiry.
       2022-03-10
          Added counters for SRG group recon start and end.
       2022-03-07
          Added additional NAL disconnect types
       2022-03-04
          Added counter for zero subscribers in recon replay request.
       2022-03-02
          Added new counters for SRG stats retry enqueue.
       2022-03-02
          Added new counter for SRG group state is not ready.
       2022-02-23
          Updated SRG show command bag with reconciliation information.
       2022-02-10
          Added SRG show commands.
       2022-01-27
          Updated length of interface name string length from 64 to 72
       2022-01-20
          Updated process info bag with in-flight configuration values
       2021-12-21
          Added access interface event history
       2021-12-01
          Updated xml tree definitions
       2021-11-11
          Dynamic Route info addition in route provision flow.
       2021-10-20
          AIPC server stats display command updated.
       2021-10-10
          Added schema support for multiple show CLIs
       2021-09-30
          Added new counter for tracking empty pulses in nal_main_edm_nal_counters lac_stats.
       2021-09-29
          Added batch counter for spio resync";
    semver:module-version "3.0.0";
  }
  revision 2021-09-27 {
    description
      "Updated transport and association status enum in yang model.
       2021-07-22
           Updated nal_main_edm_process_info to include SPIO connection information.
       2021-07-06
           Added schema support for all address family in show dynamic route command.
       2021-07-02
           Added connection status information and interface counters.
       2021-06-30
           Added process readiness and transaction pending flags in nal_main_edm_process_readiness.
       2021-06-26
           Updated nal_main_edm_process_info bag to include features supported from platform.
       2021-06-20
           Added new path for getting subscriber summary based on VRF name.
       2021-06-14
           Added tunnel vrf for LAC/LNS subscriber bag
       2021-06-11
           Updated subscriber brief bag with subscriber interface handle.
       2021-05-31
           Added new NAL counter type client api
       2021-05-29
           Added new bag for getting subscriber count and global routes installed.
       2021-05-05
           Added tr459 mode enable flag in bag structure.
       2021-04-01
           added LNS subcriber info in bag
       2021-03-15
           added details for LAC subcriber in bag";
    semver:module-version "2.0.0";
  }
  revision 2021-02-17 {
    description
      "Added AFI only filters";
    semver:module-version "1.0.0";
  }
  revision 2021-02-10 {
    description
      "Removed redundant fail route index";
  }
  revision 2021-02-04 {
    description
      "Added multi framed route support, metric and tag";
  }
  revision 2021-01-23 {
    description
      "Added new NAL counter type thread_stats";
  }
  revision 2020-12-13 {
    description
      "NAL SVM service final timestamp.";
  }
  revision 2020-12-08 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-15 {
    description
      "Added schema support for cnbng-nal filter oper commands.";
  }
  revision 2020-10-08 {
    description
      "Moved counter and AIPC stats to new bag files.";
  }
  revision 2020-10-02 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  container cnbng-nal {
    config false;
    description
      "cnBNG NAL operational data";
    container nodes {
      description
        "List of cnBNG NAL supported nodes";
      list node {
        key "node-name";
        description
          "cnBNG NAL operational data for a particular
           node";
        container nal-counters-tbl {
          description
            "operational data for NAL counters context dump";
          uses NAL-MAIN-EDM-NAL-COUNTERS;
        }
        container disconnect-uniques {
          description
            "operational data for disconnect history unique
             table";
          list disconnect-unique {
            key "disconnect-error-code";
            description
              "operational data for disconnect history
               unique table (all UP instances)";
            leaf disconnect-error-code {
              type uint32;
              description
                "disconnect history unique error code";
            }
            uses NAL-SUBSCRIBER-DISCONNECT-HISTORY-UNIQUE-DETAIL-DATA;
          }
        }
        container srg-group-summary-table {
          description
            "operational data for NAL SRG group summary";
          container srg-group-summaries {
            description
              "operational data for NAL SRG group summary
               (all UP instances)";
            list srg-group-summary {
              key "srg-group-name";
              description
                "operational data for NAL SRG group summary";
              leaf srg-group-name {
                type xr:Cisco-ios-xr-string;
                description
                  "Srg group name";
              }
              uses NAL-MAIN-EDM-SRG-GROUP-SUMMARY;
            }
          }
        }
        container feature-ids {
          description
            "operational data for NAL subscriber sessions";
          list feature-id {
            key "fadb-path";
            description
              "operational data for NAL subscriber sessions
               FADB (all UP instances)";
            leaf fadb-path {
              type xr:Cisco-ios-xr-string;
              description
                "FADB";
            }
            uses NAL-OPER-FADB-RECORD-DATA;
          }
        }
        container api-stats {
          description
            "operational data for NAL API stats";
          uses NAL-MAIN-EDM-API-STATS;
        }
        container session-detail-filter-cold-state-table {
          description
            "operational data for NAL cold-standby active
             subscriber sessions";
          container session-detail-filter-cold-state-upids {
            description
              "Cold-standby active subscriber filter (all UP
               instances)";
            list session-detail-filter-cold-state-upid {
              key "up-id";
              description
                "Cold-standby active subscriber details (all
                 UP instances)";
              leaf up-id {
                type uint32;
                description
                  "user plane ID";
              }
              uses NAL-SUBSCRIBER-SESSION-DATA;
            }
          }
        }
        container session-detail-internal-filter-upids {
          description
            "operational data based on filter UPID";
          list session-detail-internal-filter-upid {
            key "up-id";
            description
              "Filter based on UPID (all UP instances)";
            leaf up-id {
              type uint32;
              description
                "user plane ID";
            }
            uses NAL-SUBSCRIBER-SESSION-DATA-INTERNAL;
          }
        }
        container services {
          description
            "operational data for NAL subscriber services";
          list service {
            key "service";
            description
              "operational data for NAL subscriber services
               (all UP instances)";
            leaf service {
              type xr:Cisco-ios-xr-string;
              description
                "service name";
            }
            uses NAL-SERVICE-PROFILE-DATA;
          }
        }
        container warm-session-summary-table {
          description
            "operational data for NAL Warm subscriber
             summary";
          container warm-session-summary {
            description
              "operational data for NAL Warm subscriber
               summary";
            uses NAL-WARM-SUBSCRIBER-SUMMARY;
          }
        }
        container disconnect-unique-summaries {
          description
            "operational data for disconnect history unique
             table";
          list disconnect-unique-summary {
            key "disconnect-error-code";
            description
              "operational data for disconnect history
               unique (all UP instances)";
            leaf disconnect-error-code {
              type uint32;
              description
                "disconnect history unique";
            }
            uses NAL-SUBSCRIBER-DISCONNECT-HISTORY-UNIQUE-DATA;
          }
        }
        container summary-filters-vrfs {
          description
            "Operational data for subscriber summary based
             on VRF name";
          list summary-filters-vrf {
            key "vrf-name";
            description
              "Operational data for subscriber summary based
               on VRF name";
            leaf vrf-name {
              type xr:Cisco-ios-xr-string;
              description
                "VRF Name";
            }
            leaf up-id {
              type uint32;
              description
                "User plane ID";
            }
            uses NAL-SUBSCRIBER-SUMMARY;
          }
        }
        container session-detail-internal-filter-states {
          description
            "operational data based on state";
          list session-detail-internal-filter-state {
            key "state";
            description
              "Filter based on state (all UP instances)";
            leaf state {
              type uint32;
              description
                "subscriber state";
            }
            leaf up-id {
              type uint32;
              description
                "user plane ID";
            }
            uses NAL-SUBSCRIBER-SESSION-DATA-INTERNAL;
          }
        }
        container main {
          description
            "cnBNG NAL main";
          container events {
            description
              "operational data for NAL main process boot up
               events";
            uses NAL-MAIN-EDM-EVENTS;
          }
        }
        container disconnect-last-summaries {
          description
            "operational data for disconnect history last
             summary table";
          list disconnect-last-summary {
            key "disconnect-error-code";
            description
              "operational data for disconnect history last
               summary (all UP instances)";
            leaf disconnect-error-code {
              type xr:Cisco-ios-xr-string;
              description
                "disconnect error code";
            }
            uses NAL-SUBSCRIBER-DISCONNECT-HISTORY-LAST-SUMMARY-DATA;
          }
        }
        container spa-l2tp-tunnels {
          description
            "Operational tunnel data based on filter tunnel
             id";
          list spa-l2tp-tunnel {
            key "tunnel-id";
            description
              "Filter based on Tunnel id";
            leaf tunnel-id {
              type uint32 {
                range "1..65535";
              }
              description
                "Tunnel Id";
            }
            uses NAL-MAIN-EDM-SPA-L2TP-TUNNEL-CTX;
          }
        }
        container session-briefs {
          description
            "Brief data for subscriber sessions";
          list session-brief {
            key "up-id";
            description
              " Brief operational data for NAL subscriber
               sessions";
            leaf up-id {
              type uint32;
              description
                "user plane ID";
            }
            uses NAL-SUBS-BRIEF;
          }
        }
        container session-detail-filter-upids {
          description
            "operational data for NAL subscriber sessions";
          list session-detail-filter-upid {
            key "up-id";
            description
              "Subscriber details based on UPID (all UP
               instances)";
            leaf up-id {
              type uint32;
              description
                "user plane ID";
            }
            uses NAL-SUBSCRIBER-SESSION-DATA;
          }
        }
        container nal-chunks-stats-tbl {
          description
            "operational data for NAL chunks statistics
             info";
          uses NAL-MAIN-EDM-CHUNK-STATS;
        }
        container cps-stats {
          description
            "Operational data for NAL CPS(Calls per sec)
             stats";
          list cps-stat {
            key "arrayindex";
            description
              "Operational data for NAL CPS stats for a CPS
               index";
            leaf arrayindex {
              type xr:Cisco-ios-xr-string;
              description
                "cps array index";
            }
            uses NAL-CPS-STATS-ENTRY;
          }
        }
        container srg-group-detail-table {
          description
            "operational data for NAL SRG group info";
          container srg-group-details {
            description
              "operational data for NAL SRG group info (all
               UP instances)";
            list srg-group-detail {
              key "srg-group-name";
              description
                "operational data for NAL SRG group info";
              leaf srg-group-name {
                type xr:Cisco-ios-xr-string;
                description
                  "Srg group name";
              }
              uses NAL-MAIN-EDM-SRG-GROUP-INFO;
            }
          }
        }
        container disconnect-warm-last-summaries {
          description
            "operational data for disconnect history warm
             last summary table";
          list disconnect-warm-last-summary {
            key "disconnect-error-code";
            description
              "operational data for disconnect history warm
               last summary";
            leaf disconnect-error-code {
              type uint32;
              description
                "disconnect error code";
            }
            uses NAL-SPA-WARM-SUBS-DISCONNECT-LAST-SUMMARY-DATA;
          }
        }
        container process-readiness {
          description
            "operational data for NAL main process
             readiness";
          uses NAL-MAIN-EDM-PROCESS-READINESS;
        }
        container cp-server-table {
          description
            "operational data for NAL control-plane
             transport server info";
          container cp-connection-sts-summary {
            description
              "operational data for NAL control-plane
               connection status summary (all UP instances)";
            uses NAL-MAIN-EDM-CP-CONN-STS-SUMMARY;
          }
          container cp-connection-sts-info-up-instance-table {
            description
              "operational data for NAL control-plane
               connection status (all UP instances)";
            container cp-connection-sts-info-up-instance {
              description
                "operational data for NAL control-plane
                 transport server connection status (all UP
                 instances)";
              uses NAL-MAIN-EDM-CP-CONN-STS-INFO-ARRAY;
            }
          }
          container cp-connection-sts-infos {
            description
              "operational data for NAL control-plane
               connection status per UP instance";
            list cp-connection-sts-info {
              key "up-instance-id";
              description
                "operational data for NAL control-plane
                 transport server connection status (single
                 UP instance)";
              leaf up-instance-id {
                type uint32;
                description
                  "UP Instance ID";
              }
              uses NAL-MAIN-EDM-CP-CONN-STS-INFO;
            }
          }
        }
        container summary-table {
          description
            "operational data for NAL subscriber summary";
          container summary-filters {
            description
              "operational data for NAL subscriber summary
               filters";
            uses NAL-SUBSCRIBER-SUMMARY;
          }
        }
        container disconnect-warm-unique-details {
          description
            "operational data for disconnect history warm
             unique detail table";
          list disconnect-warm-unique-detail {
            key "disconnect-error-code";
            description
              "operational data for disconnect history warm
               unique table";
            leaf disconnect-error-code {
              type uint32;
              description
                "disconnect history warm unique error code";
            }
            uses NAL-SPA-WARM-DISCONNECT-UNIQUE-DETAIL-DATA;
          }
        }
        container session-detail-filter-states {
          description
            "operational data for NAL subscriber sessions
             based on state";
          list session-detail-filter-state {
            key "state";
            description
              "Subscriber details based on state (all UP
               instances)";
            leaf state {
              type uint32;
              description
                "subscriber state";
            }
            leaf up-id {
              type uint32;
              description
                "user plane ID";
            }
            uses NAL-SUBSCRIBER-SESSION-DATA;
          }
        }
        container warm-session-cpid-details {
          description
            "operational data for NAL warm subscriber
             sessions";
          list warm-session-cpid-detail {
            key "cp-id";
            description
              "Warm subscriber details based on CPID";
            leaf cp-id {
              type uint64;
              description
                "Control plane ID";
            }
            uses NAL-MAIN-EDM-WARM-SUB-DETAIL-DATA;
          }
        }
        container cp-up-trans-id-mappings {
          description
            "operational data for Subscriber Control Plane,
             User Plane and transaction ID Mapping";
          list cp-up-trans-id-mapping {
            key "user-plane-id";
            description
              "operational data for subscriber Control Plane
               , User Plane and transaction ID map for
               UserPlaneID (all UP instances)";
            leaf user-plane-id {
              type uint32;
              description
                "user plane ID";
            }
            uses NAL-SUBSCRIBER-CP-UP-TRANS-ID;
          }
        }
        container aipc-server-stats {
          description
            "operational data for NAL AIPC Server stats";
          list aipc-server-stat {
            key "aipc-path";
            description
              "operational data for aipc stats ";
            leaf aipc-path {
              type xr:Cisco-ios-xr-string;
              description
                "aipc";
            }
            uses NAL-AIPC-SERVER-STATS-DATA;
          }
        }
        container disconnect-warm-lasts {
          description
            "operational data for warm disconnected
             subscriber sessions";
          list disconnect-warm-last {
            key "disconnect-last-index";
            description
              "operational data for warm disconnect history
               stats ";
            leaf disconnect-last-index {
              type uint32;
              description
                "disconnect history last";
            }
            uses NAL-SPA-WARM-SUBS-DISCONNECT-DATA;
          }
        }
        container disconnectlasts {
          description
            "operational data for Disconnected subscriber
             sessions";
          list disconnectlast {
            key "disconnect-last-index";
            description
              "operational data for disconnect history stats
               (all UP instances)";
            leaf disconnect-last-index {
              type xr:Cisco-ios-xr-string;
              description
                "disconnect history last";
            }
            uses NAL-SUBSCRIBER-DISCONNECT-HISTORY-DATA;
          }
        }
        container dynamic-route-up-instance-table {
          description
            "operational data for dynamic-route tables per
             UP instance";
          container dynamic-route-up-instance-afi-alls {
            description
              "operational data for dynamic-route AFI filter
               (all UP instances)";
            list dynamic-route-up-instance-afi-all {
              key "afi";
              description
                "operational data for all AFI dynamic-routes
                 per UP instance";
              leaf afi {
                type uint32;
                description
                  "AFI type";
              }
              list dynamic-route-up-instance-entry {
                key "route";
                description
                  "operational data for dynamic route-entry
                   per UP instance";
                leaf route {
                  type xr:Cisco-ios-xr-string;
                  description
                    "Dynamic Route";
                }
                leaf vrf {
                  type xr:Cisco-ios-xr-string;
                  description
                    "Dynamic Route vrf";
                }
                uses NAL-MAIN-EDM-OC-ENTRY;
              }
            }
          }
        }
        container vrf-names {
          description
            "operational data for NAL VRF-Table context";
          list vrf-name {
            key "vrf-name";
            description
              "operational data for NAL VRF-Table context";
            leaf vrf-name {
              type xr:Cisco-ios-xr-string;
              description
                "VRF Name";
            }
            uses NAL-MAIN-EDM-VRFTBL-INFO;
          }
        }
        container dynamic-route-up-instance-summary-table {
          description
            "operational data for NAL dynamic-routes
             summary per UP instance";
          container dynamic-route-up-instance-summary {
            description
              "operational data for NAL dynamic-routes
               summary (all UP instances)";
            uses NAL-MAIN-EDM-OC-SUMMARY;
          }
        }
        container process-info-class {
          description
            "Significant operational data for NAL main
             process";
          uses NAL-MAIN-EDM-PROCESS-INFO;
        }
        container dynamic-route-afi-tables {
          description
            "operational data for dynamic-route tables";
          list dynamic-route-afi-table {
            key "route";
            description
              "operational data for dynamic route-entries
               based on AFI type";
            leaf route {
              type xr:Cisco-ios-xr-string;
              description
                "Dynamic Route";
            }
            leaf vrf {
              type xr:Cisco-ios-xr-string;
              description
                "Dynamic Route vrf";
            }
            uses NAL-MAIN-EDM-OC-ENTRY;
          }
        }
        container summary-filters-access-intfs {
          description
            "Operational data for subscriber summary based
             on access interface";
          list summary-filters-access-intf {
            key "access-intf-name";
            description
              "Operational data for subscriber summary based
               on access interface";
            leaf access-intf-name {
              type xr:Cisco-ios-xr-string;
              description
                "Access Interface Name";
            }
            leaf afi-only-filter {
              type uint32;
              description
                "AFI Only Filter";
            }
            leaf up-id {
              type uint32;
              description
                "user plane ID";
            }
            uses NAL-SUBSCRIBER-SUMMARY;
          }
        }
        container disconnect-warm-unique-summaries {
          description
            "operational data for disconnect history warm
             unique table";
          list disconnect-warm-unique-summary {
            key "disconnect-error-code";
            description
              "operational data for disconnect history warm
               unique";
            leaf disconnect-error-code {
              type uint32;
              description
                "disconnect history warm unique";
            }
            uses NAL-SPA-WARM-DISCONNECT-UNIQUE-SUMMARY;
          }
        }
        container access-intf-alls {
          description
            "cnBNG NAL access interface type";
          list access-intf-all {
            key "intf-handle";
            description
              "cnBNG NAL access interface ";
            leaf intf-handle {
              type uint32;
              description
                "Access interface";
            }
            uses NAL-MAIN-EDM-PARENT-INTF-DATA;
          }
        }
        leaf node-name {
          type xr:Node-id;
          description
            "Node name";
        }
      }
    }
  }
}
