module Cisco-IOS-XR-mfwd-fretta-oper {
  namespace "http://cisco.com/ns/yang/Cisco-IOS-XR-mfwd-fretta-oper";
  prefix mfwd-fretta-oper;

  import ietf-inet-types {
    prefix inet;
  }
  import Cisco-IOS-XR-types {
    prefix xr;
  }
  import cisco-semver {
    prefix semver;
  }
  include Cisco-IOS-XR-mfwd-fretta-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mfwd-fretta package operational data.
     
     This module contains definitions
     for the following management objects:
       ipv6-mfwd-fretta: MFWD Fretta IPv6 Platform operational data
       mfwd-fretta: MFWD Fretta Platform operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Mfwd-fretta-route-sub-cmds {
    type enumeration {
      enum "none" {
        value 0;
        description
          "No Sub Command";
      }
      enum "olist" {
        value 1;
        description
          "Route Outgoing Interfaces";
      }
      enum "accept" {
        value 2;
        description
          "Route Accept Interfaces";
      }
      enum "signal" {
        value 3;
        description
          "Route Signals";
      }
    }
    description
      "Mfwd fretta route sub cmds";
  }

  grouping NODE-TABLE {
    description
      "Common node of mfwd-fretta, ipv6-mfwd-fretta";
    container nodes {
      description
        "All Nodes";
      list node {
        key "node-name";
        description
          "Multicast Forwarding Fretta operational data
           for this particular node";
        container databases {
          description
            "MFWD Fretta Databases";
          list database {
            key "database-name";
            description
              "Database Name";
            container route-summary {
              description
                "Route Summary information in MFIB PD";
              uses IPV4-MFWD-FRETTA-ROUTE-SUMM-BAG;
            }
            container route-table-filters {
              description
                "The set of MFWD Fretta Route operations";
              list route-table-filter {
                key "sub-cmd is-shadow is-detail show-internal af-specific-flags";
                description
                  "Container for mandatory operational data
                   filters";
                leaf sub-cmd {
                  type Mfwd-fretta-route-sub-cmds;
                  description
                    "route sub-command";
                }
                leaf is-shadow {
                  type boolean;
                  description
                    "Hardware or Shadow data";
                }
                leaf is-detail {
                  type boolean;
                  description
                    "Detailed information";
                }
                leaf show-internal {
                  type boolean;
                  description
                    "Show hardware internal information";
                }
                leaf af-specific-flags {
                  type boolean;
                  description
                    "Address-Family specific flags";
                }
                list route {
                  description
                    "MFWD Fretta Route Entry Information";
                  leaf source-address {
                    type inet:ip-address-no-zone;
                    description
                      "Source Address";
                  }
                  leaf group-address {
                    type inet:ip-address-no-zone;
                    description
                      "Group Address";
                  }
                  leaf prefix-length {
                    type uint32 {
                      range "0..128";
                    }
                    description
                      "Prefix Length";
                  }
                  uses IPV4-MFWD-FRETTA-ROUTE-BAG;
                }
              }
            }
            container memory-counters {
              description
                "Statistics for memory
                 allocation/deallocation in MFIB PD";
              uses IPV4-MFWD-FRETTA-MGMT-BAG;
            }
            container connections {
              description
                "Connections to other modules from MFIB PD";
              uses IPV4-MFWD-FRETTA-CONNECTION-BAG;
            }
            leaf database-name {
              type xr:Cisco-ios-xr-string {
                length "1..32";
              }
              description
                "Database Name";
            }
          }
        }
        leaf node-name {
          type xr:Node-id;
          description
            "Node name";
        }
      }
    }
  }

  container ipv6-mfwd-fretta {
    config false;
    description
      "MFWD Fretta IPv6 Platform operational data";
    uses NODE-TABLE;
  }
  container mfwd-fretta {
    config false;
    description
      "MFWD Fretta Platform operational data";
    uses NODE-TABLE;
  }
}
