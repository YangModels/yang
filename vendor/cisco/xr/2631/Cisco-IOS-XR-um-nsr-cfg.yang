module Cisco-IOS-XR-um-nsr-cfg {
  yang-version 1.1;
  namespace "http://cisco.com/ns/yang/Cisco-IOS-XR-um-nsr-cfg";
  prefix um-nsr-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     Non-stop Routing (NSR) configuration.
     
     Copyright (c) 2020-2026 by Cisco Systems, Inc., and/or its affiliates.
     All rights reserved.";

  revision 2026-03-05 {
    description
      "Update to align with latest IOS-XR YANG quality guidelines.";
    semver:module-version "2.0.0";
  }
  revision 2020-03-23 {
    description
      "Initial release";
    semver:module-version "1.0.0";
  }

  container nsr {
    description
      "Global NSR configuration";
    container process-failures {
      description
        "Recovery action for process failures on active RP/DRP";
      leaf switchover {
        type empty;
        description
          "Switch over to standby RP/DRP to maintain NSR";
      }
    }
  }
}
