module Cisco-IOS-XR-ipv4-autorp-oper {
  namespace "http://cisco.com/ns/yang/Cisco-IOS-XR-ipv4-autorp-oper";
  prefix ipv4-autorp-oper;

  import ietf-inet-types {
    prefix inet;
  }
  import Cisco-IOS-XR-types {
    prefix xr;
  }
  import cisco-semver {
    prefix semver;
  }
  import Cisco-IOS-XR-ipv4-autorp-datatypes {
    prefix dt1;
  }
  include Cisco-IOS-XR-ipv4-autorp-oper-sub2 {
    revision-date 2025-01-31;
  }
  include Cisco-IOS-XR-ipv4-autorp-oper-sub1 {
    revision-date 2025-01-31;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-autorp package operational data.
     
     This module contains definitions
     for the following management objects:
       auto-rp: AutoRP operational data
     
     Copyright (c) 2013-2025 by Cisco Systems, Inc.
     All rights reserved.";

  revision 2025-01-31 {
    description
      "Removed the candidate-rp list and missed-packets from the model, leaving the instance under the active/standby role nodes";
    semver:module-version "1.2.0";
  }
  revision 2019-08-27 {
    description
      "Providing AutoRP information";
    semver:module-version "1.1.0";
  }
  revision 2019-04-05 {
    description
      "Establish semantic version baseline.";
    semver:module-version "1.0.1";
  }
  revision 2015-11-09 {
    description
      "IOS XR 6.0 revision.";
  }

  grouping MAPPING-AGENT {
    description
      "Common node of active, standby";
    container mapping-agent {
      description
        "AutoRP Mapping Agent Table";
      container traffic {
        description
          "AutoRP Mapping Agent Traffic Counters";
        uses AUTORP-MAP-TRAFFIC-BAG;
      }
      container rp-addresses {
        description
          "AutoRP Mapping Agent Table Entries";
        list rp-address {
          key "rp-address";
          description
            "AutoRP Mapping Agent Entry";
          leaf rp-address {
            type inet:ipv4-address-no-zone;
            description
              "RP Address";
          }
          uses AUTORP-MAP-RP-BAG;
        }
      }
      container missed-packets {
        description
          "AutoRP Mapping Agent Missed Packets Information";
        uses AUTORP-MAP-MISSED-PACKETS-LIST-BAG;
      }
      container summary {
        description
          "AutoRP Mapping Agent Summary Information";
        uses AUTORP-MAP-SUMMARY-BAG;
      }
    }
  }

  grouping CANDIDATE-RP {
    description
      "Common node of active, standby";
    container candidate-rp {
      description
        "AutoRP Candidate RP";
      container traffic {
        description
          "AutoRP Candidate Traffic Counters";
        uses AUTORP-CRP-TRAFFIC-BAG;
      }
      container missed-packets {
        description
          "AutoRP Candidate RP Missed Packets Information";
        uses AUTORP-CRP-MISSED-PACKETS-LIST-BAG;
      }
      container rps {
        description
          "AutoRP Candidate RP Table";
        list rp {
          key "interface-name protocol-mode";
          description
            "AutoRP Candidate RP Entry";
          leaf interface-name {
            type xr:Interface-name;
            description
              "Interface Name";
          }
          leaf protocol-mode {
            type dt1:Auto-rp-protocol-mode;
            description
              "Protocol Mode";
          }
          uses AUTORP-CRP-BAG;
        }
      }
    }
  }

  container auto-rp {
    config false;
    description
      "AutoRP operational data";
    container standby {
      description
        "Standby Process";
      uses CANDIDATE-RP;
      uses MAPPING-AGENT;
    }
    container active {
      description
        "Active Process";
      uses CANDIDATE-RP;
      uses MAPPING-AGENT;
    }
  }
}
