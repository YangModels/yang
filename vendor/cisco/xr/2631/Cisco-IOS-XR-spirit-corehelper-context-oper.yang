module Cisco-IOS-XR-spirit-corehelper-context-oper {
  namespace "http://cisco.com/ns/yang/Cisco-IOS-XR-spirit-corehelper-context-oper";
  prefix spirit-corehelper-context-oper;

  import Cisco-IOS-XR-types {
    prefix xr;
  }
  import cisco-semver {
    prefix semver;
  }
  include Cisco-IOS-XR-spirit-corehelper-context-oper-sub1 {
    revision-date 2020-10-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR spirit-corehelper-context package operational data.
     
     This module contains definitions
     for the following management objects:
       core-helper: Corehelper operational data space
     
     Copyright (c) 2013-2020 by Cisco Systems, Inc.
     All rights reserved.";

  revision 2020-10-01 {
    description
      "Adding show context yang model";
    semver:module-version "1.0.0";
  }
  revision 2019-04-05 {
    description
      "Establish semantic version baseline.";
  }
  revision 2015-11-09 {
    description
      "IOS XR 6.0 revision.";
  }

  container core-helper {
    config false;
    description
      "Corehelper operational data space";
    container node-ids {
      description
        "Show Context";
      list node-id {
        key "node";
        description
          "Show Context Location <location>";
        leaf node {
          type xr:Node-id;
          description
            "Node location";
        }
        list context-id {
          key "context-id";
          description
            "Contexts for a node";
          leaf context-id {
            type uint32;
            description
              "Node context";
          }
          uses COREHELPER-CONTEXT-CONTEXT;
        }
      }
    }
  }
}
