module Cisco-IOS-XR-infra-ltrace-cfg {
  namespace "http://cisco.com/ns/yang/Cisco-IOS-XR-infra-ltrace-cfg";
  prefix infra-ltrace-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-ltrace package configuration.
     
     This YANG module augments the
       Cisco-IOS-XR-config-mda-cfg
     module with configuration data.
     
     Copyright (c) 2013-2025 by Cisco Systems, Inc.
     All rights reserved.";

  revision 2025-09-17 {
    description
      "Added support for ltrace persist dump-enable configuration.";
    semver:module-version "1.1.0";
  }
  revision 2019-04-05 {
    description
      "Establish semantic version baseline.";
    semver:module-version "1.0.0";
  }
  revision 2015-11-09 {
    description
      "IOS XR 6.0 revision.";
  }

  typedef Infra-ltrace-mode {
    type enumeration {
      enum "static" {
        value 1;
        description
          "Set ltrace memory allocation to static mode";
      }
      enum "dynamic" {
        value 2;
        description
          "Set ltrace memory allocation to dynamic mode";
      }
    }
    description
      "Infra ltrace mode";
  }

  typedef Infra-ltrace-scale {
    type enumeration {
      enum "0" {
        value 0;
        description
          "Use platform-defined scale-factor";
      }
      enum "1" {
        value 1;
        description
          "Do not scale down ltrace memory request";
      }
      enum "2" {
        value 2;
        description
          "Scale down ltrace memory request by 2";
      }
      enum "4" {
        value 4;
        description
          "Scale down ltrace memory request by 4";
      }
      enum "8" {
        value 8;
        description
          "Scale down ltrace memory request by 8";
      }
      enum "16" {
        value 16;
        description
          "Scale down ltrace memory request by 16";
      }
    }
    description
      "Infra ltrace scale";
  }

  grouping NODE-CFG {
    description
      "active/preconfigured nodes configuration";
    container ltrace {
      description
        "Ltrace Memory configuration";
      container allocation-params {
        description
          "Select Ltrace mode and scale-factor";
        leaf mode {
          type Infra-ltrace-mode;
          description
            "Select an allocation mode (static:1, dynamic
             :2)";
        }
        leaf scale-factor {
          type Infra-ltrace-scale;
          description
            "Select a scaling down factor";
        }
      }
      container server {
        description
          "Ltrace server configuration";
        leaf dump-enable {
          type empty;
          description
            "Enable dumping to persistent storage";
        }
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
