module Cisco-IOS-XR-sysadmin-vm-mgr {
  namespace "http://www.cisco.com/ns/yang/Cisco-IOS-XR-sysadmin-vm-mgr";
  prefix vmmh;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2012-2020 by Cisco Systems, Inc.
     All rights reserved.";

  revision 2024-11-27 {
    description
      "Added description";
    semver:module-version "1.1.0";
  }
  revision 2019-06-12 {
    description
      "Fixed canonical order error for keyword config";
    semver:module-version "1.0.0";
  }
  revision 2019-04-15 {
    description
      "Establish semantic version baseline.";
  }
  revision 2018-07-13 {
    description
      "Removed unused show fields in show vm";
  }
  revision 2017-04-12 {
    description
      "Changed the namespace and module name";
  }
  revision 2016-05-12 {
    description
      "Initial Version";
  }

  container VM {
    config false;
    description
      "VM Info";
    list all-locations {
      key "location";
      description
        "VM Mgr per location information";
      leaf location {
        type string;
        description
          "VM Mgr location key";
      }
      list all-uiids {
        key "uiid";
        description
          "VM Mgr per unique immutable ID info";
        leaf uiid {
          type string;
          description
            "Unique Immutable ID";
        }
        leaf id {
          type string;
          description
            "ID of the VM";
        }
        leaf status {
          type string;
          description
            "Status of the VM";
        }
        leaf ipaddr {
          type string;
          description
            "CE IP address";
        }
        leaf last_hb_sent {
          type string;
          description
            "Last heartbeat sent";
        }
        leaf last_hb_rec {
          type string;
          description
            "Last heartbeat received";
        }
      }
    }
  }
}
