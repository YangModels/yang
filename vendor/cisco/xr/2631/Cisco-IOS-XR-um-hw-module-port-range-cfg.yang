module Cisco-IOS-XR-um-hw-module-port-range-cfg {
  namespace "http://cisco.com/ns/yang/Cisco-IOS-XR-um-hw-module-port-range-cfg";
  prefix um-hw-module-port-range-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-port-range package configuration.
     
     This YANG module augments the
     modules with configuration data.
     
     Copyright (c) 2020-2025 by Cisco Systems, Inc., and/or its affiliates.
     All rights reserved.";

  revision 2025-09-28 {
    description
      "Added new modes to the mode pattern";
    semver:module-version "2.0.0";
  }
  revision 2020-11-16 {
    description
      "Initial release";
    semver:module-version "1.0.0";
  }

  grouping LOCATION-BODY {
    description
      "Grouping for location";
    container hw-module {
      description
        "Configure h/w module";
      container port-ranges {
        description
          "Configure port range";
        list port-range {
          must "(mode or instances/instance)";
          key "start-port end-port";
          description
            "Configure port range";
          leaf start-port {
            type uint32 {
              range "0..71" {
                description
                  "configure start port";
              }
            }
            description
              "Configure port range";
          }
          leaf end-port {
            type uint32 {
              range "0..71" {
                description
                  "configure end port";
              }
            }
            description
              "configure end port";
          }
          leaf mode {
            type string {
              pattern "40-100|400|2x100|4x10|4x25|4x10-4x25|1x100|3x100|4x100|2x400|8x100";
            }
            description
              "port mode";
          }
          container instances {
            description
              "card instance of MPA's";
            list instance {
              key "instance-id";
              description
                "card instance of MPA's";
              leaf instance-id {
                type uint32 {
                  range "0..5" {
                    description
                      "MPA Instance 1,2,3 etc for MPA's";
                  }
                }
                description
                  "MPA Instance 1,2,3 etc for MPA's";
              }
              leaf mode {
                type string {
                  pattern "40-100|400|2x100|4x10|4x25|4x10-4x25|1x100|3x100|4x100";
                }
                mandatory true;
                description
                  "port mode";
              }
            }
          }
        }
      }
    }
  }

  augment "/location:locations/location:location" {
    description
      "This augment extends active nodes configuration";
    uses LOCATION-BODY;
  }
}
