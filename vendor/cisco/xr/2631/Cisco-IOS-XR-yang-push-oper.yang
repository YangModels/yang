module Cisco-IOS-XR-yang-push-oper {
  namespace "http://cisco.com/ns/yang/Cisco-IOS-XR-yang-push-oper";
  prefix yang-push-oper;

  import Cisco-IOS-XR-types {
    prefix xr;
  }
  import cisco-semver {
    prefix semver;
  }
  include Cisco-IOS-XR-yang-push-oper-sub1 {
    revision-date 2026-03-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR yang-push package operational data.
     
     This module contains definitions
     for the following management objects:
       yang-push: YANG-Push operational data
     
     Copyright (c) 2013-2026 by Cisco Systems, Inc.
     All rights reserved.";

  revision 2026-03-17 {
    description
      "Add receiver DTLS information";
    semver:module-version "1.0.0";
  }
  revision 2026-02-09 {
    description
      "Add CBOR encoding.";
  }
  revision 2025-11-25 {
    description
      "Initial commit";
  }
  revision 2019-04-05 {
    description
      "Establish semantic version baseline.";
  }
  revision 2015-11-09 {
    description
      "IOS XR 6.0 revision.";
  }

  container yang-push {
    config false;
    description
      "YANG-Push operational data";
    container subscriptions {
      description
        "YANG-Push Subscriptions operational data";
      list subscription {
        key "sub-id";
        description
          "Subscription data";
        leaf sub-id {
          type uint32;
          description
            "Subscription ID";
        }
        uses YANG-PUSH-DIAGS-SUBSCRIPTION;
      }
    }
    container receivers {
      description
        "YANG-Push Receivers operational data";
      list receiver {
        key "recv-name";
        description
          "Receiver data";
        leaf recv-name {
          type xr:Cisco-ios-xr-string;
          description
            "Receiver name";
        }
        uses YANG-PUSH-DIAGS-RECEIVER;
      }
    }
  }
}
