submodule Cisco-IOS-XR-ip-rib-lblmgr-oper-sub2 {
  belongs-to Cisco-IOS-XR-ip-rib-lblmgr-oper {
    prefix Cisco-IOS-XR-ip-rib-lblmgr-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-rib-lblmgr package operational data.
     
     Copyright (c) 2013-2026 by Cisco Systems, Inc.
     All rights reserved.";

  revision 2026-07-28 {
    description
      "Added pending label conflicts to label manager operational data
       2026-04-16
         Added label range info to label manager EDM";
    semver:module-version "1.1.0";
  }
  revision 2025-08-20 {
    description
      "Added local labels associated with prefixes";
    semver:module-version "1.0.0";
  }
  revision 2025-07-14 {
    description
      "Removed local-label attributes that are no longer necessary";
  }
  revision 2025-03-20 {
    description
      "Added label producer info to RIB EDM routes";
  }
  revision 2025-01-06 {
    description
      "Optimized route and path schema";
  }
  revision 2024-11-22 {
    description
      "Added option to display MPLS routes with pending delete NHGs";
  }
  revision 2024-10-29 {
    description
      "Added last clear time of rib statistics";
  }
  revision 2024-10-01 {
    description
      "Add potential label routes";
  }
  revision 2024-08-16 {
    description
      "Added label-summary";
  }
  revision 2024-07-11 {
    description
      "Add unviable label routes";
  }
  revision 2024-02-15 {
    description
      "New rib-manager schema";
  }
  revision 2024-02-06 {
    description
      "New label-manager schema";
  }
  revision 2019-04-05 {
    description
      "Establish semantic version baseline.";
  }
  revision 2015-11-09 {
    description
      "IOS XR 6.0 revision.";
  }

  typedef Rib-edm-safi-id {
    type enumeration {
      enum "none" {
        value 0;
        description
          "No sub-address family";
      }
      enum "unicast" {
        value 1;
        description
          "Unicast SAFI";
      }
      enum "multicast" {
        value 2;
        description
          "Multicast SAFI";
      }
    }
    description
      "Rib edm safi id";
  }

  typedef Rib-edm-route {
    type enumeration {
      enum "invalid" {
        value 0;
        description
          "No route type";
      }
      enum "prefix-route" {
        value 1;
        description
          "Prefix Route";
      }
      enum "label-route" {
        value 2;
        description
          "Labelled Route";
      }
      enum "label-prefix-route" {
        value 3;
        description
          "Labelled Prefix Route";
      }
    }
    description
      "Rib edm route";
  }

  typedef Mgmt-lsd-lbl-range {
    type enumeration {
      enum "mgmt-lsd-lbl-range-type-invalid" {
        value 0;
        description
          "Invalid label range";
      }
      enum "mgmt-lsd-lbl-range-type-cbf" {
        value 1;
        description
          "CBF label range";
      }
      enum "mgmt-lsd-lbl-range-type-pfp" {
        value 2;
        description
          "PFP label range";
      }
      enum "mgmt-lsd-lbl-range-type-generic" {
        value 3;
        description
          "Generic label range";
      }
    }
    description
      "Label range type";
  }

  typedef Rib-in6-addr {
    type inet:ipv6-address;
    description
      "Rib in6 addr";
  }

  typedef Rib-in4-addr {
    type inet:ipv4-address;
    description
      "Rib in4 addr";
  }

  typedef Rib-edm-afi-id {
    type enumeration {
      enum "none" {
        value 0;
        description
          "No address family";
      }
      enum "ipv4" {
        value 1;
        description
          "IPv4 AFI";
      }
      enum "ipv6" {
        value 2;
        description
          "IPv6 AFI";
      }
    }
    description
      "Rib edm afi id";
  }

  typedef Lbl-state {
    type enumeration {
      enum "unknown" {
        description
          "Unknown";
      }
      enum "in-use" {
        description
          "In Use";
      }
      enum "stale" {
        description
          "Stale";
      }
    }
    description
      "LBL manager LBL state";
  }

  typedef Mgmt-label-context {
    type enumeration {
      enum "none" {
        value 0;
        description
          "None type";
      }
    }
    description
      "RIB Label Context Types";
  }

  grouping MPLS-LSD-LBL-RANGE-DATA-PFP {
    description
      "PFP label range data";
    leaf client {
      type string {
        length "0..48";
      }
      description
        "Client name";
    }
  }

  grouping MPLS-LSD-LBL-RANGE-DATA-CBF {
    description
      "CBF label range data";
    leaf client {
      type string {
        length "0..48";
      }
      description
        "Client name";
    }
  }

  grouping MPLS-LSD-LBL-RANGE-DATA {
    description
      "MPLS LSD LBL RANGE DATA";
    container cbf-data {
      when "../range-type = 'mgmt-lsd-lbl-range-type-cbf'" {
        description
          "../RangeType = 'MGMT_LSD_LBL_RANGE_TYPE_CBF'";
      }
      description
        "cbf data";
      uses MPLS-LSD-LBL-RANGE-DATA-CBF;
    }
    container pfp-data {
      when "../range-type = 'mgmt-lsd-lbl-range-type-pfp'" {
        description
          "../RangeType = 'MGMT_LSD_LBL_RANGE_TYPE_PFP'";
      }
      description
        "pfp data";
      uses MPLS-LSD-LBL-RANGE-DATA-PFP;
    }
    leaf range-type {
      type Mgmt-lsd-lbl-range;
      description
        "RangeType";
    }
  }

  grouping LBL-RANGE-OWNER {
    description
      "Label range owner";
    leaf client-id {
      type uint32;
      description
        "Client identifier";
    }
    leaf proto-id {
      type uint32;
      description
        "Protocol identifier";
    }
    leaf sub-protocol-id {
      type uint8;
      description
        "Sub protocol ID";
    }
    leaf stale {
      type boolean;
      description
        "Stale owner or not";
    }
    leaf mirrored {
      type boolean;
      description
        "The owner is mirrored from the active RP or not";
    }
  }

  grouping LBL-RANGE-INFO {
    description
      "Reserved label range information";
    container range-data {
      description
        "Type-specific range data";
      uses MPLS-LSD-LBL-RANGE-DATA;
    }
    leaf start {
      type uint32;
      description
        "Start label value";
    }
    leaf end {
      type uint32;
      description
        "End label value";
    }
    list owner {
      description
        "Applications owning the range";
      uses LBL-RANGE-OWNER;
    }
  }

  grouping LBLMGR-SUMMARY {
    description
      "LBL Manager summary";
    leaf label-count {
      type uint32;
      description
        "Number of allocated labels";
    }
    leaf stale-label-count {
      type uint32;
      description
        "Number of Stale labels";
    }
    leaf conflict-count {
      type uint32;
      description
        "Number of pending label conflicts";
    }
  }

  grouping LBL-CONFLICT-INFO {
    description
      "Pending label conflict";
    container associated-prefix {
      description
        "Associated prefix";
      uses RIB-EDM-IP-PFX;
    }
    leaf client-id {
      type uint16;
      description
        "Client identifier";
    }
    leaf proto-id {
      type uint16;
      description
        "Protocol identifier";
    }
    leaf sub-protocol-id {
      type uint8;
      description
        "Sub-protocol identifier";
    }
    leaf table-id {
      type uint32;
      description
        "Table identifier";
    }
  }

  grouping MGMT-LBLMGR-STRING {
    description
      "Generic string";
    leaf string {
      type string;
      description
        "String";
    }
  }

  grouping MGMT-LBLMGR-TIMESTAMP {
    description
      "LBL Manager Generic Timestamp";
    container time-in-nano-seconds {
      description
        "Timestamp in nano seconds";
      uses MGMT-LBLMGR-STRING;
    }
    container age-in-nano-seconds {
      description
        "Age in nano seconds";
      uses MGMT-LBLMGR-STRING;
    }
  }

  grouping RIB-EDM-IP-ADDR {
    description
      "RIB EDM IP ADDR";
    leaf afi {
      type Rib-edm-afi-id;
      description
        "AFI";
    }
    leaf none {
      when "../afi = 'none'" {
        description
          "../AFI = 'None'";
      }
      type uint8;
      description
        "No address family";
    }
    leaf ipv4 {
      when "../afi = 'ipv4'" {
        description
          "../AFI = 'IPv4'";
      }
      type Rib-in4-addr;
      description
        "IPv4 address type";
    }
    leaf ipv6 {
      when "../afi = 'ipv6'" {
        description
          "../AFI = 'IPv6'";
      }
      type Rib-in6-addr;
      description
        "IPv6 address type";
    }
  }

  grouping RIB-EDM-IP-PFX {
    description
      "IPv4/IPv6 IP address and Prefix length";
    container ip-address {
      description
        "IPv4/IPv6 address";
      uses RIB-EDM-IP-ADDR;
    }
    leaf prefix-length {
      type uint8;
      description
        "Prefix length";
    }
  }

  grouping MGMT-RIB-LBL-CTX-NONE {
    description
      "None Label Context";
    leaf label {
      type uint32;
      description
        "Label value";
    }
  }

  grouping MGMT-RIB-LBL-CTX-KEY {
    description
      "MGMT RIB LBL CTX KEY";
    container none {
      when "../label-context-type = 'none'" {
        description
          "../LabelContextType = 'None'";
      }
      description
        "None Context";
      uses MGMT-RIB-LBL-CTX-NONE;
    }
    leaf label-context-type {
      type Mgmt-label-context;
      description
        "LabelContextType";
    }
  }

  grouping RIB-LBL-CTX {
    description
      "Label Context";
    container key {
      description
        "Label Key";
      uses MGMT-RIB-LBL-CTX-KEY;
    }
  }

  grouping LBL-INFO {
    description
      "LBL Manager LBL info";
    container label-context {
      description
        "Label Context";
      uses RIB-LBL-CTX;
    }
    container associated-prefix {
      description
        "Associated prefix";
      uses RIB-EDM-IP-PFX;
    }
    container create-timestamp {
      description
        "Creation timestamp";
      uses MGMT-LBLMGR-TIMESTAMP;
    }
    leaf label {
      type uint32;
      description
        "LBL value";
    }
    leaf state {
      type Lbl-state;
      description
        "State";
    }
    leaf has-forwarding {
      type boolean;
      description
        "Rewrite done or not";
    }
    leaf vrf-name {
      type string;
      description
        "VRF name";
    }
    list conflict {
      description
        "Pending conflicts";
      uses LBL-CONFLICT-INFO;
    }
  }
}
