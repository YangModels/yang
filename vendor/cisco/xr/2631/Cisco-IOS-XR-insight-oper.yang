module Cisco-IOS-XR-insight-oper {
  yang-version 1;
  namespace "http://cisco.com/ns/yang/Cisco-IOS-XR-insight-oper";
  prefix insight-oper;

  import openconfig-yang-types {
    prefix oc-yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module defines operational state data for monitoring and
     observability of the IOS XR Insight component.
     
     Copyright (c) 2025-2026 by Cisco Systems, Inc., and/or its affiliates.
     All rights reserved.";

  revision 2025-10-21 {
    description
      "Initial revision";
  }

  grouping queue-counters {
    description
      "Counters for a generic queue.";
    leaf num-enqueue {
      type oc-yang:counter64;
      description
        "Number of enqueue operations";
    }
    leaf num-dequeue {
      type oc-yang:counter64;
      description
        "Number of dequeue operations. This, coupled with num-enqueue, can be used to determine throughput.";
    }
    leaf queue-hwm {
      type uint64;
      units "elements";
      description
        "Highest observed length of queue. High values indicate backpressure.";
    }
    leaf queue-len {
      type uint64;
      units "elements";
      description
        "Current length of queue. High values indicate backpressure.";
    }
    leaf buffer-size {
      type uint64;
      units "bytes";
      description
        "Memory used by buffered elements. Some queues might be short in element length but high in memory usage.";
    }
  }

  grouping task-counters {
    description
      "Counters that track status of requests.";
    leaf incoming-requests {
      type oc-yang:counter64;
      description
        "Number of requests that are pending processing.";
    }
    leaf completed-requests {
      type oc-yang:counter64;
      description
        "Number of requests that have successfully completed processing.";
    }
    leaf error-count {
      type oc-yang:counter64;
      description
        "Number of total errors that have occurred.";
    }
  }

  grouping producer-state {
    description
      "Producer state that tracks various publish metrics.";
    leaf last-update-time {
      type uint64;
      units "nanoseconds";
      description
        "Time of last update (since Unix epoch)";
    }
    leaf db-append {
      type oc-yang:counter64;
      description
        "Number of writes to database.";
    }
    leaf generic-publish-called {
      type oc-yang:counter64;
      description
        "Number of times generic publish was called.";
    }
  }

  grouping producer-content {
    description
      "Producer Information";
    leaf name {
      type string;
      description
        "Producer name";
    }
    container state {
      config false;
      description
        "Producer state";
      uses producer-state;
    }
  }

  grouping producer-exec-queue-state {
    description
      "Producer exec queue state that tracks various publish metrics.";
    uses queue-counters;
  }

  grouping producer-exec-queue-content {
    description
      "Per-feature exec queue used to buffer messages before processing.";
    leaf name {
      type string;
      description
        "Exec queue identifier in the format producer:feature (e.g. npu_drvr:ASIC_CTR).";
    }
    container state {
      config false;
      description
        "Producer exec queue state";
      uses producer-exec-queue-state;
    }
  }

  grouping edm-proxy-content {
    description
      "EDM Proxy content";
    leaf name {
      type string;
      description
        "EDM Proxy name";
    }
    container state {
      config false;
      description
        "EDM Proxy state";
      leaf last-update-time {
        type uint64;
        units "nanoseconds";
        description
          "Time of last update (since Unix epoch)";
      }
      leaf get-value-input-count {
        type oc-yang:counter64;
        description
          "Number of get-value callback entries";
      }
      leaf get-value-output-count {
        type oc-yang:counter64;
        description
          "Number of get-value callback exits";
      }
      leaf get-value-byte-count {
        type oc-yang:counter64;
        units "bytes";
        description
          "Number of bytes processed by get-value callback";
      }
      leaf get-list-input-count {
        type oc-yang:counter64;
        description
          "Number of get-list callback entries";
      }
      leaf get-list-output-count {
        type oc-yang:counter64;
        description
          "Number of get-list callback exits";
      }
      leaf get-list-byte-count {
        type oc-yang:counter64;
        units "bytes";
        description
          "Number of bytes processed by get-list callback";
      }
      leaf get-datalist-input-count {
        type oc-yang:counter64;
        description
          "Number of get-datalist callback entries";
      }
      leaf get-datalist-output-count {
        type oc-yang:counter64;
        description
          "Number of get-datalist callback exits";
      }
      leaf get-datalist-byte-count {
        type oc-yang:counter64;
        units "bytes";
        description
          "Number of bytes processed by get-datalist callback";
      }
      leaf get-finddata-input-count {
        type oc-yang:counter64;
        description
          "Number of get-finddata callback entries";
      }
      leaf get-finddata-output-count {
        type oc-yang:counter64;
        description
          "Number of get-finddata callback exits";
      }
      leaf get-finddata-byte-count {
        type oc-yang:counter64;
        units "bytes";
        description
          "Number of bytes processed by get-finddata callback";
      }
    }
  }

  grouping consumer-state {
    description
      "Consumer state tracks various counters like number of pending and completed operations as well as bytes processed.";
    leaf last-update-time {
      type uint64;
      units "nanoseconds";
      description
        "Time of last update (since Unix epoch)";
    }
    leaf pending-get {
      type uint64;
      description
        "Number of pending DB Gets that need to be processed. High values indicate backpressure";
    }
    leaf pending-pop-update {
      type uint64;
      description
        "Number of pending notification queue pops for the update channel";
    }
    leaf pending-pop-delete {
      type uint64;
      description
        "Number of pending notification queue pops for the delete channel";
    }
    leaf send-count {
      type oc-yang:counter64;
      description
        "Number of send callbacks invoked";
    }
    leaf send-bytes {
      type oc-yang:counter64;
      units "bytes";
      description
        "Number of bytes being sent via send callback";
    }
    leaf notification-key-bytes {
      type oc-yang:counter64;
      units "bytes";
      description
        "Number of bytes being processed from notification queue. This coupled with send-bytes can be used to observe size of payload compared to size of key.";
    }
    leaf pending-scan-get {
      type oc-yang:counter64;
      description
        "Number of pending DB Gets attributable to scan operations. High values indicate backpressure. The difference between pending-get and pending-scan-get can be used to observe the number of pending DB Gets attributable to on-change and sampling Gets.";
    }
  }

  grouping consumer-content {
    description
      "Consumer Information";
    leaf name {
      type string;
      description
        "Consumer name";
    }
    container state {
      config false;
      description
        "Consumer state";
      uses consumer-state;
    }
  }

  grouping notification-queue-state {
    description
      "Notification queue state tracks the generic queue metrics for both update and delete notification queues.";
    leaf last-update-time {
      type uint64;
      units "nanoseconds";
      description
        "Time of last update (since Unix epoch)";
    }
    uses queue-counters;
  }

  grouping notification-queue-content {
    description
      "Notification queue Information";
    leaf name {
      type string;
      description
        "Notification queue name";
    }
    container state {
      config false;
      description
        "Notification queue state";
      uses notification-queue-state;
    }
  }

  grouping client-buffer-state {
    description
      "Client buffer state tracks generic queue metrics when payloads are buffered before being consumed.";
    leaf last-update-time {
      type uint64;
      units "nanoseconds";
      description
        "Time of last update (since Unix epoch)";
    }
    leaf buffer-length {
      type uint64;
      units "bytes";
      description
        "Total length of buffer in bytes.";
    }
    leaf buffer-length-hwm {
      type uint64;
      units "bytes";
      description
        "High water mark of buffer in bytes.";
    }
  }

  grouping client-buffer-content {
    description
      "Client buffer Information";
    leaf name {
      type string;
      description
        "Client buffer name";
    }
    container state {
      config false;
      description
        "Client buffer state";
      uses client-buffer-state;
    }
  }

  grouping message-queue-state {
    description
      "Counters for a subscription message queue.";
    uses queue-counters;
  }

  grouping broker-subscription-state {
    description
      "Subscription state and message queue counters";
    leaf last-update-time {
      type uint64;
      units "nanoseconds";
      description
        "Time of the last update (since Unix epoch)";
    }
    leaf timeout {
      type uint64;
      units "nanoseconds";
      description
        "Send timeout";
    }
    leaf sent {
      type oc-yang:counter64;
      description
        "Messages sent to this subscriber";
    }
    container message-channel {
      description
        "Message channel counters for this subscription";
      uses message-queue-state;
    }
  }

  grouping broker-subscription-content {
    description
      "Per-subscriber state and metrics";
    leaf subscription-id {
      type string;
      description
        "Subscriber ID";
    }
    container state {
      config false;
      description
        "Subscription state";
      uses broker-subscription-state;
    }
  }

  grouping pubsub-channel-state {
    description
      "Counters for a pub/sub channel.";
    uses queue-counters;
  }

  grouping broker-state {
    description
      "Notification broker counters.";
    leaf num-pub-sub-patterns {
      type uint64;
      description
        "Active number of pubsub patterns in the broker";
    }
    leaf num-subscriptions {
      type uint64;
      description
        "Active number of subscriptions in the broker";
    }
    leaf matcher-size {
      type uint64;
      description
        "Size of matcher's trie node array";
    }
    leaf unmatched-messages {
      type oc-yang:counter64;
      description
        "Number of unmatched messages (no subscriber wanted this message). Higher values suggest that more time is being spent optimizing glob patterns.";
    }
    leaf last-update-time {
      type uint64;
      units "nanoseconds";
      description
        "Time of the last update (since Unix epoch)";
    }
    container pubsub-channel {
      description
        "Pub/sub channel counters from Redis";
      uses pubsub-channel-state;
    }
  }

  grouping broker-content {
    description
      "Notification broker content tracks counters for the broker.";
    container state {
      config false;
      description
        "Notification broker counters";
      uses broker-state;
    }
  }

  grouping module-state {
    description
      "Database module state will track counters for state of tasks and errors";
    leaf last-update-time {
      type uint64;
      units "nanoseconds";
      description
        "Time of last update (since Unix epoch)";
    }
    uses task-counters;
  }

  grouping module-content {
    description
      "Database module content";
    leaf name {
      type string;
      description
        "Module name";
    }
    container state {
      config false;
      description
        "Module state";
      uses module-state;
    }
  }

  grouping pipeline-state {
    description
      "Pipeline state will track counters for state of tasks and errors";
    leaf last-update-time {
      type uint64;
      units "nanoseconds";
      description
        "Time of last update (since Unix epoch)";
    }
    uses task-counters;
  }

  grouping pipeline-content {
    description
      "Pipeline content";
    leaf name {
      type string;
      description
        "Pipeline name";
    }
    container state {
      config false;
      description
        "Pipeline state";
      uses pipeline-state;
    }
  }

  container nodes {
    config false;
    description
      "Top-level container for nodes";
    list node {
      key "name";
      description
        "List of nodes";
      leaf name {
        type string;
        description
          "Node name";
      }
      container clients {
        description
          "Data sources and sinks";
        list producer {
          key "name";
          description
            "Library that XR processes use to publish telemetry data into database";
          uses producer-content;
        }
        list producer-exec-queue {
          key "name";
          description
            "Per-feature exec queues used by producers to buffer messages before processing. Keyed by producer:feature.";
          uses producer-exec-queue-content;
        }
        list consumer {
          key "name";
          description
            "Library that XR processes use to fetch telemetry data from database";
          uses consumer-content;
        }
        list edm-proxy {
          key "name";
          description
            "External Data Manager proxy for data access within Insight component";
          uses edm-proxy-content;
        }
      }
      container components {
        description
          "Infrastructure services";
        container database {
          description
            "Database-related services";
          container server {
            description
              "Database server hosting notification queues and client buffers";
            list notification-queue {
              key "name";
              description
                "A queue that stores notification messages indicating that data is ready to be fetched from the database.";
              uses notification-queue-content;
            }
            list client-buffer {
              key "name";
              description
                "A queue that is used to buffer payloads from the database before the client is ready to consume the data.";
              uses client-buffer-content;
            }
          }
          container broker {
            description
              "A broker that manages and optimizes pub/sub between data processors and the database.";
            uses broker-content;
          }
          list broker-subscription {
            key "subscription-id";
            description
              "Per-subscriber state and metrics";
            uses broker-subscription-content;
          }
          list module {
            key "name";
            description
              "Database module. One such example is the Stats Module which performs statistics collection and aggregation.";
            uses module-content;
          }
        }
      }
      container transformations {
        description
          "Data processing and transformations";
        list pipeline {
          key "name";
          description
            "Data processing pipeline.
             
             Examples include:
             - NHG flattening: next-hop group flattening operations
             - Conditional NHG flattening: conditional next-hop group processing.";
          uses pipeline-content;
        }
      }
    }
  }
}
