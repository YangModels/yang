module Cisco-IOS-XR-pmengine-cfg {
  namespace "http://cisco.com/ns/yang/Cisco-IOS-XR-pmengine-cfg";
  prefix pmengine-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pmengine package configuration.
     
     This YANG module augments the
       Cisco-IOS-XR-ifmgr-cfg
     module with configuration data.
     
     Copyright (c) 2013-2025 by Cisco Systems, Inc.
     All rights reserved.";

  revision 2025-06-02 {
    description
      "Added support for RAMAN-6 and RAMAN-7 parameters in Optics layer.";
    semver:module-version "4.0.0";
  }
  revision 2021-07-09 {
    description
      "Support added for cem layer. Containers second30cem, minute15cem and hour24cem added.
       2021-04-26
           Support added for E1 controller.
       2021-02-24
           Support added for fc layer. Containers second30fc, minute15fc and hour24fc added.";
    semver:module-version "3.1.0";
  }
  revision 2020-04-17 {
    description
      "Added Instantaneous Q Margin in fec layer.
       2020-04-07
            Threshold and report config support provided for OTU PRBS layer parameters.";
    semver:module-version "3.0.0";
  }
  revision 2019-10-31 {
    description
      "Added mandatory nodes.";
    semver:module-version "2.0.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef Secyif-report {
    type enumeration {
      enum "report-if-inpkts-untagged" {
        value 134217728;
        description
          "PM SECYIF if InPktsUntagged report";
      }
      enum "report-if-inpkts-not-ag" {
        value 134217729;
        description
          "PM SECYIF if InPktsNoTag report";
      }
      enum "report-if-inpktsbadtag" {
        value 134217730;
        description
          "PM SECYIF if InPktsBadTag report";
      }
      enum "report-if-inpkts-unknown-sci" {
        value 134217731;
        description
          "PM SECYIF if InPktsUnknownSCI report";
      }
      enum "report-if-inpktsnosci" {
        value 134217732;
        description
          "PM SECYIF if InPktsNoSCI report";
      }
      enum "report-if-inpkts-overrun" {
        value 134217733;
        description
          "PM SECYIF if InPktsOverrun report";
      }
      enum "report-if-inoctets-validate-d" {
        value 134217734;
        description
          "PM SECYIF if InOctetsValidated report";
      }
      enum "report-if-inoctetsdecrypted" {
        value 134217735;
        description
          "PM SECYIF if InOctetsDecrypted report";
      }
      enum "report-if-outpkts-untagged" {
        value 134217736;
        description
          "PM SECYIF if OutPktsUntagged report";
      }
      enum "report-if-outpkts-too-long" {
        value 134217737;
        description
          "PM SECYIF if OutPktsTooLong report";
      }
      enum "report-if-outoctetsprotected" {
        value 134217738;
        description
          "PM SECYIF if OutOctetsProtected report";
      }
      enum "report-if-outoctetsencrypted" {
        value 134217739;
        description
          "PM SECYIF if OutOctetsEncrypted report";
      }
    }
    description
      "Secyif report";
  }

  typedef Gfp-report {
    type enumeration {
      enum "report-rx-bit-err" {
        value 6291456;
        description
          "PM GFP rx bit err report";
      }
      enum "report-rx-inv-typ" {
        value 6291457;
        description
          "PM GFP rx inv type report";
      }
      enum "report-rx-crc" {
        value 6291458;
        description
          "PM GFP rx crc report";
      }
      enum "report-rx-lfd" {
        value 6291459;
        description
          "PM GFP rx lfd report";
      }
      enum "report-rx-csf" {
        value 6291460;
        description
          "PM GFP rx csf report";
      }
    }
    description
      "Gfp report";
  }

  typedef Pcs-threshold {
    type enumeration {
      enum "thresh-bip" {
        value 100663296;
        description
          "PM PCS Bip thresh";
      }
      enum "thresh-frm-err" {
        value 100663297;
        description
          "PM PCS frm-err thresh";
      }
      enum "thresh-bad-sh" {
        value 100663298;
        description
          "PM PCS bad-sh thresh";
      }
      enum "thresh-es" {
        value 100663299;
        description
          "PM PCS es thresh";
      }
      enum "thresh-ses" {
        value 100663300;
        description
          "PM PCS ses thresh";
      }
      enum "thresh-uas" {
        value 100663301;
        description
          "PM PCS uas thresh";
      }
      enum "thresh-es-fe" {
        value 100663302;
        description
          "PM PCS es-fe thresh";
      }
      enum "thresh-ses-fe" {
        value 100663303;
        description
          "PM PCS ses-fe thresh";
      }
      enum "thresh-uas-fe" {
        value 100663304;
        description
          "PM PCS uas-fe thresh";
      }
    }
    description
      "Pcs threshold";
  }

  typedef Ho-vc-threshold {
    type enumeration {
      enum "thresh-eb" {
        value 33554432;
        description
          "PM EB threshold";
      }
      enum "thresh-es" {
        value 33554433;
        description
          "PM ES threshold";
      }
      enum "thresh-esr" {
        value 33554434;
        description
          "PM ESR threshold";
      }
      enum "thresh-ses" {
        value 33554435;
        description
          "PM SES threshold";
      }
      enum "thresh-sesr" {
        value 33554436;
        description
          "PM SESR threshold";
      }
      enum "thresh-bbe" {
        value 33554437;
        description
          "PM BBE threshold";
      }
      enum "thresh-bber" {
        value 33554438;
        description
          "PM BBER threshold";
      }
      enum "thresh-uass" {
        value 33554439;
        description
          "PM UASS threshold";
      }
    }
    description
      "Ho vc threshold";
  }

  typedef Ether-threshold {
    type enumeration {
      enum "thresh-rx-pkt" {
        value 8388608;
        description
          "PM Ether rx pkt threshold";
      }
      enum "thresh-rx-util" {
        value 8388609;
        description
          "PM Ether rx util threshold";
      }
      enum "thresh-tx-util" {
        value 8388610;
        description
          "PM Ether tx util threshold";
      }
      enum "thresh-stat-pkt" {
        value 8388611;
        description
          "PM ether stat pkt threshold";
      }
      enum "thresh-octet-stat" {
        value 8388612;
        description
          "PM Ether octet stat threshold";
      }
      enum "thresh-over-size-pkt" {
        value 8388613;
        description
          "PM Ether oversize pkt threshold";
      }
      enum "thresh-fcs-err" {
        value 8388614;
        description
          "PMEther fcs error threshold";
      }
      enum "thresh-long-frame-s" {
        value 8388615;
        description
          "PM Ether long frames threshold";
      }
      enum "thresh-jabber-stats" {
        value 8388616;
        description
          "PM Ether jabber stats threshold";
      }
      enum "thresh-64-octet" {
        value 8388617;
        description
          "PM Ether 64 octet threshold";
      }
      enum "thresh-65-127-octet" {
        value 8388618;
        description
          "PM Ether 65 to 127 octet threshold";
      }
      enum "thresh-128-255-octet" {
        value 8388619;
        description
          "PM Ether 128 to 255 octet threshold";
      }
      enum "thresh-256-511-octet" {
        value 8388620;
        description
          "PM Ether 256 to 511 octet threshold";
      }
      enum "thresh-512-1023-octet" {
        value 8388621;
        description
          "PM Ether 512 to 1023 octet threshold";
      }
      enum "thresh-1024-1518-octet" {
        value 8388622;
        description
          "PM Ether 1024 to 1518 threshold";
      }
      enum "thresh-in-ucast" {
        value 8388623;
        description
          "PM Ether rx ucast threshold";
      }
      enum "thresh-in-mcast" {
        value 8388624;
        description
          "PM Ether rx mcast threshold";
      }
      enum "thresh-in-bcast" {
        value 8388625;
        description
          "PM Ether rx bcast threshold";
      }
      enum "thresh-out-ucast" {
        value 8388626;
        description
          "PM Ether tx ucast threshold";
      }
      enum "thresh-out-mcast" {
        value 8388627;
        description
          "PM Ether tx mcast threshold";
      }
      enum "thresh-out-bcast" {
        value 8388628;
        description
          "PM Ether tx bcast threshold";
      }
      enum "thresh-tx-pkt" {
        value 8388629;
        description
          "PM Ether tx pkt threshold";
      }
      enum "thresh-ifin-error-s" {
        value 8388630;
        description
          "PM ether ifIn errors threshold";
      }
      enum "thresh-ifin-octets" {
        value 8388631;
        description
          "PM ether ifInOctets threshold";
      }
      enum "thresh-ether-stat-multicast-pkt" {
        value 8388632;
        description
          "PM ether stat multicast pkt threshold";
      }
      enum "thresh-ether-stat-broadcast-pkt" {
        value 8388633;
        description
          "PM ether stat broadcast pkt threshold";
      }
      enum "thresh-ether-stat-under-size-d-pkt" {
        value 8388634;
        description
          "PM ether stat undersized pkt threshold";
      }
      enum "thresh-out-octet" {
        value 8388635;
        description
          "PM ether out octets threshold";
      }
      enum "thresh-in-pause-frame" {
        value 8388636;
        description
          "PM in pause frame threshold";
      }
      enum "thresh-in-go-od-bytes" {
        value 8388637;
        description
          "PM in good bytes threshold";
      }
      enum "thresh-in-802-1q-frame-s" {
        value 8388638;
        description
          "PM in 802_1 Q threshold";
      }
      enum "thresh-in-pkts-1519-max-octets" {
        value 8388639;
        description
          "PM in pkts 1519 max octets threshold";
      }
      enum "thresh-in-go-od-pkts" {
        value 8388640;
        description
          "PM in good pkts threshold";
      }
      enum "thresh-in-drop-overrun" {
        value 8388641;
        description
          "PM in drop overrun threshold";
      }
      enum "thresh-in-drop-abort" {
        value 8388642;
        description
          "PM in drop abort threshold";
      }
      enum "thresh-in-drop-invalid-vlan" {
        value 8388643;
        description
          "PM in drop invalid vlan threshold";
      }
      enum "thresh-in-drop-invalid-dmac" {
        value 8388644;
        description
          "PM in drop invalid DMAC threshold";
      }
      enum "thresh-in-drop-invalid-encap" {
        value 8388645;
        description
          "PM in drop invalid encap threshold";
      }
      enum "thresh-in-drop-other" {
        value 8388646;
        description
          "PM in drop other threshold";
      }
      enum "thresh-in-mib-giant" {
        value 8388647;
        description
          "PM in MIB giant threshold";
      }
      enum "thresh-in-mib-jabber" {
        value 8388648;
        description
          "PM in MIB jabber threshold";
      }
      enum "thresh-in-mib-crc" {
        value 8388649;
        description
          "PM in MIB CRC threshold";
      }
      enum "thresh-in-error-collision-s" {
        value 8388650;
        description
          "PM in error collisions threshold";
      }
      enum "thresh-in-error-symbol" {
        value 8388651;
        description
          "PM in error symbol threshold";
      }
      enum "thresh-out-go-od-bytes" {
        value 8388652;
        description
          "PM out good bytes threshold";
      }
      enum "thresh-out-802-1q-frame-s" {
        value 8388653;
        description
          "PM out 802_1 Q threshold";
      }
      enum "thresh-out-pause-frame-s" {
        value 8388654;
        description
          "PM out pause frame threshold";
      }
      enum "thresh-out-pkts-1519-max-octets" {
        value 8388655;
        description
          "PM out pkts 1519 max octets threshold";
      }
      enum "thresh-out-go-od-pkts" {
        value 8388656;
        description
          "PM out good pkts threshold";
      }
      enum "thresh-out-drop-under-run" {
        value 8388657;
        description
          "PM out drop underrun threshold";
      }
      enum "thresh-out-drop-abort" {
        value 8388658;
        description
          "PM out drop abort threshold";
      }
      enum "thresh-out-drop-other" {
        value 8388659;
        description
          "PM out drop other threshold";
      }
      enum "thresh-out-error-other" {
        value 8388660;
        description
          "PM out error other threshold";
      }
      enum "thresh-in-error-giant" {
        value 8388661;
        description
          "PM in error giant threshold";
      }
      enum "thresh-in-error-runt" {
        value 8388662;
        description
          "PM in error runt threshold";
      }
      enum "thresh-in-error-jabbers" {
        value 8388663;
        description
          "PM in error jabber threshold";
      }
      enum "thresh-in-error-fragments" {
        value 8388664;
        description
          "PM in error fragments threshold";
      }
      enum "thresh-in-error-other" {
        value 8388665;
        description
          "PM in error other threshold";
      }
      enum "thresh-in-pkt-64-octet" {
        value 8388666;
        description
          "PM in pkt 64 octet threshold";
      }
      enum "thresh-in-pkts-65-127octets" {
        value 8388667;
        description
          "PM in pkts 65_127 octets threshold";
      }
      enum "thresh-in-pkts-128-255-octets" {
        value 8388668;
        description
          "PM in pkts 128_255 octets threshold";
      }
      enum "thresh-in-pkts-256-511-octets" {
        value 8388669;
        description
          "PM in pkts 256_511 octets threshold";
      }
      enum "thresh-in-pkts-512-1023-octets" {
        value 8388670;
        description
          "PM in pkts 512_1023 octets threshold";
      }
      enum "thresh-in-pkts-1024-1518-octets" {
        value 8388671;
        description
          "PM in pkts 1024_1058 octets threshold";
      }
      enum "thresh-out-pkt-64-octet" {
        value 8388672;
        description
          "PM out pkt 64 octet threshold";
      }
      enum "thresh-out-pkts-65-127octets" {
        value 8388673;
        description
          "PM out pkts 65_127 octets threshold";
      }
      enum "thresh-out-pkts-128-255-octets" {
        value 8388674;
        description
          "PM out pkts 128_255 octets threshold";
      }
      enum "thresh-out-pkts-256-511-octets" {
        value 8388675;
        description
          "PM out pkts 256_511 octets threshold";
      }
      enum "thresh-out-pkts-512-1023-octets" {
        value 8388676;
        description
          "PM out pkts 512_1023 octets threshold";
      }
      enum "thresh-out-pkts-1024-1518-octets" {
        value 8388677;
        description
          "PM out pkts 1024_1058 octets threshold";
      }
      enum "thresh-tx-under-size-d-pkt" {
        value 8388678;
        description
          "PM tx undersized pkt threshold";
      }
      enum "thresh-tx-over-size-d-pkt" {
        value 8388679;
        description
          "PM tx oversized pkt threshold";
      }
      enum "thresh-tx-fragments" {
        value 8388680;
        description
          "PM tx fragments threshold";
      }
      enum "thresh-tx-jabber" {
        value 8388681;
        description
          "PM tx jabber threshold";
      }
      enum "thresh-tx-bad-fcs" {
        value 8388682;
        description
          "PM tx bad fcs threshold";
      }
    }
    description
      "Ether threshold";
  }

  typedef Path-threshold {
    type enumeration {
      enum "thresh-cv" {
        value 5242880;
        description
          "PM CV threshold";
      }
      enum "thresh-es" {
        value 5242881;
        description
          "PM ES threshold";
      }
      enum "thresh-ses" {
        value 5242882;
        description
          "PM SES threshold";
      }
      enum "thresh-uas" {
        value 5242883;
        description
          "PM UAS threshold";
      }
    }
    description
      "Path threshold";
  }

  typedef Fc-report {
    type enumeration {
      enum "report-ifin-octets" {
        value 20971520;
        description
          "PM FC ifIn-Octets report";
      }
      enum "report-rx-pkts" {
        value 20971521;
        description
          "PM FC rx-pkt report";
      }
      enum "report-ifin-error-s" {
        value 20971522;
        description
          "PM FC ifIn-Errors report";
      }
      enum "report-rx-bad-fcs" {
        value 20971523;
        description
          "PM FC rx-bad-fcs report";
      }
      enum "report-ifout-octets" {
        value 20971524;
        description
          "PM FC ifOut-Octets report";
      }
      enum "report-tx-pkts" {
        value 20971525;
        description
          "PM FC tx-pkt report";
      }
      enum "report-tx-bad-fcs" {
        value 20971526;
        description
          "PM FC tx-bad-fcs report";
      }
      enum "report-rx-frame-s-too-long" {
        value 20971527;
        description
          "PM FC rx-frames-too-long report";
      }
      enum "report-rx-frame-s-trunc" {
        value 20971528;
        description
          "PM FC rx-frames-trunc report";
      }
      enum "report-tx-frame-s-too-long" {
        value 20971529;
        description
          "PM FC tx-frames-too-long report";
      }
      enum "report-tx-frame-s-trunc" {
        value 20971530;
        description
          "PM FC tx-frames-trunc report";
      }
    }
    description
      "Fc report";
  }

  typedef Sts-threshold {
    type enumeration {
      enum "thresh-cv" {
        value 4194304;
        description
          "PM CV threshold";
      }
      enum "thresh-es" {
        value 4194305;
        description
          "PM ES threshold";
      }
      enum "thresh-ses" {
        value 4194306;
        description
          "PM SES threshold";
      }
      enum "thresh-uas" {
        value 4194307;
        description
          "PM UAS threshold";
      }
    }
    description
      "Sts threshold";
  }

  typedef Secytx-report {
    type enumeration {
      enum "report-tx-outpktsprotected" {
        value 150994944;
        description
          "PM SECYTX tx OutPktsProtected report";
      }
      enum "report-tx-outpktsencrypted" {
        value 150994945;
        description
          "PM SECYTX tx OutPktsEncrypted report";
      }
      enum "report-tx-outoctetsprotected" {
        value 150994946;
        description
          "PM SECYTX tx OutOctetsProtected report";
      }
      enum "report-tx-outoctetsencrypted" {
        value 150994947;
        description
          "PM SECYTX tx OutOctetsEncrypted report";
      }
      enum "report-tx-outpkts-too-long" {
        value 150994948;
        description
          "PM SECYTX tx OutPktsTooLong report";
      }
    }
    description
      "Secytx report";
  }

  typedef Prbs-threshold {
    type enumeration {
      enum "thresh-ebc" {
        value 17825792;
        description
          "PM Prbs ebc threshold";
      }
      enum "thresh-found-count" {
        value 17825793;
        description
          "PM Prbs found count threshold";
      }
      enum "thresh-lost-count" {
        value 17825794;
        description
          "PM Prbs lost count threshold";
      }
    }
    description
      "Prbs threshold";
  }

  typedef Cem-report {
    type enumeration {
      enum "report-missing-pkts" {
        value 24117248;
        description
          "PM CEM missing-pkts report";
      }
      enum "report-pkts-re-order" {
        value 24117249;
        description
          "PM CEM pkts-reorder report";
      }
      enum "report-jtr-bfr-under" {
        value 24117250;
        description
          "PM CEM jtr-bfr-underrun report";
      }
      enum "report-mis-order-drop" {
        value 24117251;
        description
          "PM CEM mis-order-drop report";
      }
      enum "report-malformed-pkt" {
        value 24117252;
        description
          "PM CEM malformed-pkts report";
      }
      enum "report-es" {
        value 24117253;
        description
          "PM CEM ES report";
      }
      enum "report-ses" {
        value 24117254;
        description
          "PM CEM SES report";
      }
      enum "report-uas" {
        value 24117255;
        description
          "PM CEM UAS report";
      }
      enum "report-fc" {
        value 24117256;
        description
          "PM CEM FC report";
      }
      enum "report-input-errs" {
        value 24117257;
        description
          "PM CEM input-errs report";
      }
      enum "report-output-errs" {
        value 24117258;
        description
          "PM CEM output-errs report";
      }
      enum "report-jtr-bfr-over" {
        value 24117259;
        description
          "PM CEM jtr-bfr-overruns report";
      }
      enum "report-tx-lbits" {
        value 24117260;
        description
          "PM CEM tx-lbits report";
      }
      enum "report-tx-rbits" {
        value 24117261;
        description
          "PM CEM tx-rbits report";
      }
      enum "report-rx-lbits" {
        value 24117262;
        description
          "PM CEM rx-lbits report";
      }
      enum "report-rx-rbits" {
        value 24117263;
        description
          "PM CEM rx-rbits report";
      }
      enum "report-in-pkts" {
        value 24117264;
        description
          "PM CEM ingress-pkts report";
      }
      enum "report-eg-pkts" {
        value 24117265;
        description
          "PM CEM egress-pkts report";
      }
      enum "report-in-pkts-drop" {
        value 24117266;
        description
          "PM CEM ingress-pkts-dropped report";
      }
      enum "report-eg-pkts-drop" {
        value 24117267;
        description
          "PM CEM egress-pkts-dropped report";
      }
    }
    description
      "Cem report";
  }

  typedef Ocn-report {
    type enumeration {
      enum "report-sefss" {
        value 3145728;
        description
          "PM SEFSS threshold";
      }
      enum "report-cvs" {
        value 3145729;
        description
          "PM CVS threshold";
      }
      enum "report-ess" {
        value 3145730;
        description
          "PM ESS threshold";
      }
      enum "report-sess" {
        value 3145731;
        description
          "PM SESS threshold";
      }
      enum "report-cvl-ne" {
        value 3145734;
        description
          "PM CVL-NE threshold";
      }
      enum "report-esl-ne" {
        value 3145735;
        description
          "PM ESL-NE threshold";
      }
      enum "report-sesl-ne" {
        value 3145736;
        description
          "PM SESL-NE threshold";
      }
      enum "report-uasl-ne" {
        value 3145738;
        description
          "PM UASL-NE threshold";
      }
      enum "report-fcl-ne" {
        value 3145739;
        description
          "PM FCL-NE threshold";
      }
      enum "report-fcl-fe" {
        value 3145751;
        description
          "PM FCL_FE threshold";
      }
      enum "report-cvl-fe" {
        value 3145752;
        description
          "PM CVL-FE threshold";
      }
      enum "report-esl-fe" {
        value 3145753;
        description
          "PM ESL_FE threshold";
      }
      enum "report-sesl-fe" {
        value 3145754;
        description
          "PM SESL_FE threshold";
      }
      enum "report-uasl-fe" {
        value 3145756;
        description
          "PM UASL_FEthreshold";
      }
    }
    description
      "Ocn report";
  }

  typedef Ho-vc-report {
    type enumeration {
      enum "report-eb" {
        value 33554432;
        description
          "PM EB report";
      }
      enum "report-es" {
        value 33554433;
        description
          "PM ES report";
      }
      enum "report-esr" {
        value 33554434;
        description
          "PM ESR report";
      }
      enum "report-ses" {
        value 33554435;
        description
          "PM SES report";
      }
      enum "report-sesr" {
        value 33554436;
        description
          "PM SESR report";
      }
      enum "report-bbe" {
        value 33554437;
        description
          "PM BBE report";
      }
      enum "report-bber" {
        value 33554438;
        description
          "PM BBER report";
      }
      enum "report-uass" {
        value 33554439;
        description
          "PM UASS report";
      }
    }
    description
      "Ho vc report";
  }

  typedef Otnsec-report {
    type enumeration {
      enum "report-in-block-s" {
        value 327680;
        description
          "PM OTNSEC Inblocks report";
      }
      enum "report-in-block-senc" {
        value 327681;
        description
          "PM OTNSEC InblocksEnc report";
      }
      enum "report-in-block-sunencrypted" {
        value 327682;
        description
          "PM OTNSEC InblocksUnEncrypted report";
      }
      enum "report-in-block-sprotected" {
        value 327683;
        description
          "PM OTNSEC InblocksProtected report";
      }
      enum "report-in-block-sunprotected" {
        value 327684;
        description
          "PM OTNSEC InblocksUnProtected report";
      }
      enum "report-in-block-ssequence-error-s" {
        value 327685;
        description
          "PM OTNSEC InblocksSequenceErrors report";
      }
      enum "report-in-block-sreplay-error-s" {
        value 327686;
        description
          "PM OTNSEC InblocksReplayErrors report";
      }
      enum "report-in-block-sauth-error-s" {
        value 327687;
        description
          "PM OTNSEC InblocksAuthErrors report";
      }
      enum "report-in-block-s-zero-ed" {
        value 327688;
        description
          "PM OTNSEC InblocksZeroed report";
      }
      enum "report-out-block-s" {
        value 327689;
        description
          "PM OTNSEC Outblocks report";
      }
      enum "report-out-block-senc" {
        value 327690;
        description
          "PM OTNSEC OutblocksEnc report";
      }
      enum "report-out-block-sunencrypted" {
        value 327691;
        description
          "PM OTNSEC OUTBLOCKSUNENCRYPTED report";
      }
      enum "report-out-block-ssequence-error-s" {
        value 327692;
        description
          "PM OTNSEC OutblocksSequenceErrors report";
      }
      enum "report-out-block-s-zero-ed" {
        value 327693;
        description
          "PM OTNSEC OutblocksZeroed report";
      }
      enum "report-out-block-sprotected" {
        value 327694;
        description
          "PM OTNSEC OutblocksProtected report";
      }
      enum "report-out-block-sunprotected" {
        value 327695;
        description
          "PM OTNSEC OutblocksUnProtected report";
      }
    }
    description
      "Otnsec report";
  }

  typedef Otn-threshold {
    type enumeration {
      enum "thresh-es-sm-ne" {
        value 262144;
        description
          "PM Otn es sm ne threshold";
      }
      enum "thresh-ses-sm-ne" {
        value 262145;
        description
          "PM Otn ses sm ne threshold";
      }
      enum "thresh-uas-sm-ne" {
        value 262146;
        description
          "PM Otn uas sm ne threshold";
      }
      enum "thresh-bbe-sm-ne" {
        value 262147;
        description
          "PM Otn bbe sm ne threshold";
      }
      enum "thresh-fc-sm-ne" {
        value 262148;
        description
          "PM Otn fc sm ne threshold";
      }
      enum "thresh-esr-sm-ne" {
        value 262149;
        description
          "PM Otn esr sm ne threshold";
      }
      enum "thresh-sesr-sm-ne" {
        value 262150;
        description
          "PM Otn sesr sm ne threshold";
      }
      enum "thresh-bber-sm-ne" {
        value 262151;
        description
          "PM Otn bber sm ne threshold";
      }
      enum "thresh-es-pm-ne" {
        value 524288;
        description
          "PM Otn es pm ne threshold";
      }
      enum "thresh-ses-pm-ne" {
        value 524289;
        description
          "PM Otn ses pm ne threshold";
      }
      enum "thresh-uas-pm-ne" {
        value 524290;
        description
          "PM Otn uas pm ne threshold";
      }
      enum "thresh-bbe-pm-ne" {
        value 524291;
        description
          "PM Otn bbe pm ne threshold";
      }
      enum "thresh-fc-pm-ne" {
        value 524292;
        description
          "PM Otn fc pm ne threshold";
      }
      enum "thresh-esr-pm-ne" {
        value 524293;
        description
          "PM Otn esr pm ne threshold";
      }
      enum "thresh-sesr-pm-ne" {
        value 524294;
        description
          "PM Otn sesr pm ne threshold";
      }
      enum "thresh-bber-pm-ne" {
        value 524295;
        description
          "PM Otn bber pm ne threshold";
      }
      enum "thresh-es-sm-fe" {
        value 1048584;
        description
          "PM Otn es sm fe threshold";
      }
      enum "thresh-ses-sm-fe" {
        value 1048585;
        description
          "PM Otn ses sm fe threshold";
      }
      enum "thresh-uas-sm-fe" {
        value 1048586;
        description
          "PM Otn uas sm fe threshold";
      }
      enum "thresh-bbe-sm-fe" {
        value 1048587;
        description
          "PM Otn bbe sm fe threshold";
      }
      enum "thresh-fc-sm-fe" {
        value 1048588;
        description
          "PM Otn fc sm fe threshold";
      }
      enum "thresh-esr-sm-fe" {
        value 1048589;
        description
          "PM Otn esr sm fe threshold";
      }
      enum "thresh-sesr-sm-fe" {
        value 1048590;
        description
          "PM Otn sesr sm fe threshold";
      }
      enum "thresh-bber-sm-fe" {
        value 1048591;
        description
          "PM Otn bber sm fe threshold";
      }
      enum "thresh-es-pm-fe" {
        value 2097160;
        description
          "PM Otn es pm fe threshold";
      }
      enum "thresh-ses-pm-fe" {
        value 2097161;
        description
          "PM Otn ses pm fe threshold";
      }
      enum "thresh-uas-pm-fe" {
        value 2097162;
        description
          "PM Otn uas pm fe threshold";
      }
      enum "thresh-bbe-pm-fe" {
        value 2097163;
        description
          "PM Otn bbe pm fe threshold";
      }
      enum "thresh-fc-pm-fe" {
        value 2097164;
        description
          "PM Otn fc pm fe threshold";
      }
      enum "thresh-esr-pm-fe" {
        value 2097165;
        description
          "PM Otn esr pm fe threshold";
      }
      enum "thresh-sesr-pm-fe" {
        value 2097166;
        description
          "PM Otn sesr pm fe threshold";
      }
      enum "thresh-bber-pm-fe" {
        value 2097167;
        description
          "PM Otn bber pm fe threshold";
      }
    }
    description
      "Otn threshold";
  }

  typedef E1-report {
    type enumeration {
      enum "report-lcv" {
        value 18874368;
        description
          "PM E1 lcv report";
      }
      enum "report-pcv" {
        value 18874369;
        description
          "PM E1 pcv report";
      }
      enum "report-sels" {
        value 18874370;
        description
          "PM E1 sels report";
      }
      enum "report-les" {
        value 18874371;
        description
          "PM E1 les report";
      }
      enum "report-aiss-sef" {
        value 18874372;
        description
          "PM E1 aiss-sef report";
      }
      enum "report-fcp" {
        value 18874373;
        description
          "PM E1 fcp report";
      }
      enum "report-es" {
        value 18874374;
        description
          "PM E1 es report";
      }
      enum "report-ses" {
        value 18874375;
        description
          "PM E1 ses report";
      }
      enum "report-uas" {
        value 18874376;
        description
          "PM E1 uas report";
      }
      enum "report-es-fe" {
        value 18874377;
        description
          "PM E1 es-fe report";
      }
      enum "report-ses-fe" {
        value 18874378;
        description
          "PM E1 ses-fe report";
      }
      enum "report-uas-fe" {
        value 18874379;
        description
          "PM E1 uas-fe report";
      }
    }
    description
      "E1 report";
  }

  typedef Optics-threshold {
    type enumeration {
      enum "thresh-opt-min" {
        value 65596;
        description
          "PM Optics opt min threshold in dbm or uW";
      }
      enum "thresh-opr-min" {
        value 65597;
        description
          "PM Optics opr min threshold in dbm or uW";
      }
      enum "thresh-lbc-min" {
        value 65598;
        description
          "PM Optics lbc min threshold";
      }
      enum "thresh-lbc-pc-min" {
        value 65599;
        description
          "PM Optics lbcpc min threshold";
      }
      enum "thresh-cd-min" {
        value 65603;
        description
          "PM Optics cd min threshold";
      }
      enum "thresh-dgd-min" {
        value 65604;
        description
          "PM Optics dgd min threshold";
      }
      enum "thresh-pmd-min" {
        value 65605;
        description
          "PM Optics sopmd min threshold";
      }
      enum "thresh-osnr-min" {
        value 65606;
        description
          "PM Optics osnr min threshold";
      }
      enum "thresh-pdl-min" {
        value 65607;
        description
          "PM Optics pdl min threshold";
      }
      enum "thresh-pcr-min" {
        value 65608;
        description
          "PM Optics pcr min threshold";
      }
      enum "thresh-pn-min" {
        value 65609;
        description
          "PM Optics pn min threshold";
      }
      enum "thresh-rx-sig-pow-min" {
        value 65610;
        description
          "PM Optics rx sig pow min threshold";
      }
      enum "thresh-low-sig-freq-off-min" {
        value 65611;
        description
          "PM Optics low sig freq off min threshold";
      }
      enum "thresh-ampli-gain-min" {
        value 65612;
        description
          "PM Optics ampli gain min threshold";
      }
      enum "thresh-ampli-gain-tilt-min" {
        value 65613;
        description
          "PM Optics ampli gain tilt min threshold";
      }
      enum "thresh-snr-min" {
        value 65614;
        description
          "PM Optics snr min threshold";
      }
      enum "thresh-snr-ax-min" {
        value 65615;
        description
          "PM Optics snr ax min threshold";
      }
      enum "thresh-snr-bx-min" {
        value 65616;
        description
          "PM Optics snr bx min threshold";
      }
      enum "thresh-snr-ay-min" {
        value 65617;
        description
          "PM Optics snr ay min threshold";
      }
      enum "thresh-snr-by-min" {
        value 65618;
        description
          "PM Optics snr by min threshold";
      }
      enum "thresh-sop-s1-min" {
        value 65619;
        description
          "PM Optics sop s1 min threshold";
      }
      enum "thresh-sop-s2-min" {
        value 65620;
        description
          "PM Optics sop s2 min threshold";
      }
      enum "thresh-sop-s3-min" {
        value 65621;
        description
          "PM Optics sop s3 min threshold";
      }
      enum "thresh-opt-cl-min" {
        value 65622;
        description
          "PM Optics opt-cl min threshold in dbm or uW";
      }
      enum "thresh-opr-cl-min" {
        value 65623;
        description
          "PM Optics opr-cl min threshold in dbm or uW";
      }
      enum "thresh-opt-s-min" {
        value 65624;
        description
          "PM Optics opt-s min threshold in dbm or uW";
      }
      enum "thresh-opr-s-min" {
        value 65625;
        description
          "PM Optics opr-s min threshold in dbm or uW";
      }
      enum "thresh-opbr-min" {
        value 65626;
        description
          "PM Optics opbr min threshold in dbm or uW";
      }
      enum "thresh-opbrr-min" {
        value 65627;
        description
          "PM Optics opbrr min threshold in db";
      }
      enum "thresh-eagn-min" {
        value 65628;
        description
          "PM Optics eagn min threshold in dbm";
      }
      enum "thresh-eatl-min" {
        value 65629;
        description
          "PM Optics eatl min threshold in dbm";
      }
      enum "thresh-iagn-min" {
        value 65630;
        description
          "PM Optics iagn min threshold in dbm";
      }
      enum "thresh-iatl-min" {
        value 65631;
        description
          "PM Optics iatl min threshold in dbm";
      }
      enum "thresh-raman-tot-min" {
        value 65632;
        description
          "PM Optics raman-tot min threshold in mW";
      }
      enum "thresh-raman-1-min" {
        value 65633;
        description
          "PM Optics raman-1 min threshold in mW";
      }
      enum "thresh-raman-2-min" {
        value 65634;
        description
          "PM Optics raman-2 min threshold in mW";
      }
      enum "thresh-raman-3-min" {
        value 65635;
        description
          "PM Optics raman-3 min threshold in mW";
      }
      enum "thresh-raman-4-min" {
        value 65636;
        description
          "PM Optics raman-4 min threshold in mW";
      }
      enum "thresh-raman-5-min" {
        value 65637;
        description
          "PM Optics raman-5 min threshold in mW";
      }
      enum "thresh-snr-x-min" {
        value 65638;
        description
          "PM Optics snr ax min threshold";
      }
      enum "thresh-snr-y-min" {
        value 65639;
        description
          "PM Optics snr ax min threshold";
      }
      enum "thresh-raman-br-min" {
        value 65640;
        description
          "PM Optics raman-br min threshold in dbm";
      }
      enum "thresh-raman-brr-min" {
        value 65641;
        description
          "PM Optics raman-brr min threshold in db";
      }
      enum "thresh-tot-span-loss-rx-min" {
        value 65642;
        description
          "PM Optics span loss Rx min threshold in db";
      }
      enum "thresh-tot-span-loss-tx-min" {
        value 65643;
        description
          "PM Optics span loss Tx min threshold in db";
      }
      enum "thresh-tot-span-loss-rx-cl-min" {
        value 65644;
        description
          "PM Optics span loss Rx (C+L) band min threshold
           in db";
      }
      enum "thresh-tot-span-loss-tx-cl-min" {
        value 65645;
        description
          "PM Optics span loss Tx (C+L) band min threshold
           in db";
      }
      enum "thresh-opt-max" {
        value 65656;
        description
          "PM Optics opt max threshold in dbm or uW";
      }
      enum "thresh-opr-max" {
        value 65657;
        description
          "PM Optics opr max threshold in dbm or uW";
      }
      enum "thresh-lbc-max" {
        value 65658;
        description
          "PM Optics lbc max threshold";
      }
      enum "thresh-lbc-pc-max" {
        value 65659;
        description
          "PM Optics lbcpc max threshold";
      }
      enum "thresh-cd-max" {
        value 65663;
        description
          "PM Optics cd max threshold";
      }
      enum "thresh-dgd-max" {
        value 65664;
        description
          "PM Optics dgd max threshold";
      }
      enum "thresh-pmd-max" {
        value 65665;
        description
          "PM Optics sopmd max threshold";
      }
      enum "thresh-osnr-max" {
        value 65666;
        description
          "PM Optics osnr max threshold";
      }
      enum "thresh-pdl-max" {
        value 65667;
        description
          "PM Optics pdl max threshold";
      }
      enum "thresh-pcr-max" {
        value 65668;
        description
          "PM Optics pcr max threshold";
      }
      enum "thresh-pn-max" {
        value 65669;
        description
          "PM Optics pn max threshold";
      }
      enum "thresh-rx-sig-pow-max" {
        value 65670;
        description
          "PM Optics rx sig pow max threshold";
      }
      enum "thresh-low-sig-freq-off-max" {
        value 65671;
        description
          "PM Optics low sig freq off max threshold";
      }
      enum "thresh-ampli-gain-max" {
        value 65672;
        description
          "PM Optics ampli gain max threshold";
      }
      enum "thresh-ampli-gain-tilt-max" {
        value 65673;
        description
          "PM Optics ampli gain tilt max threshold";
      }
      enum "thresh-snr-max" {
        value 65674;
        description
          "PM Optics snr max threshold";
      }
      enum "thresh-snr-ax-max" {
        value 65675;
        description
          "PM Optics snr ax max threshold";
      }
      enum "thresh-snr-bx-max" {
        value 65676;
        description
          "PM Optics snr bx max threshold";
      }
      enum "thresh-snr-ay-max" {
        value 65677;
        description
          "PM Optics snr ay max threshold";
      }
      enum "thresh-snr-by-max" {
        value 65678;
        description
          "PM Optics snr by max threshold";
      }
      enum "thresh-sop-s1-max" {
        value 65679;
        description
          "PM Optics sop s1 max threshold";
      }
      enum "thresh-sop-s2-max" {
        value 65680;
        description
          "PM Optics sop s2 max threshold";
      }
      enum "thresh-sop-s3-max" {
        value 65681;
        description
          "PM Optics sop s3 max threshold";
      }
      enum "thresh-opt-cl-max" {
        value 65682;
        description
          "PM Optics opt-cl  max threshold in dbm or uW";
      }
      enum "thresh-opr-cl-max" {
        value 65683;
        description
          "PM Optics opr-cl  max threshold in dbm or uW";
      }
      enum "thresh-opt-s-max" {
        value 65684;
        description
          "PM Optics opt-s  max threshold in dbm or uW";
      }
      enum "thresh-opr-s-max" {
        value 65685;
        description
          "PM Optics opr-s  max threshold in dbm or uW";
      }
      enum "thresh-opbr-max" {
        value 65686;
        description
          "PM Optics opbr  max threshold in dbm or uW";
      }
      enum "thresh-opbrr-max" {
        value 65687;
        description
          "PM Optics opbrr  max threshold in db";
      }
      enum "thresh-eagn-max" {
        value 65688;
        description
          "PM Optics eagn  max threshold in dbm";
      }
      enum "thresh-eatl-max" {
        value 65689;
        description
          "PM Optics eatl max threshold in dbm";
      }
      enum "thresh-iagn-max" {
        value 65690;
        description
          "PM Optics iagn  max threshold in dbm";
      }
      enum "thresh-iatl-max" {
        value 65691;
        description
          "PM Optics iatl max threshold in dbm";
      }
      enum "thresh-raman-tot-max" {
        value 65692;
        description
          "PM Optics raman-tot max threshold in mW";
      }
      enum "thresh-raman-1-max" {
        value 65693;
        description
          "PM Optics raman-1 max threshold in mW";
      }
      enum "thresh-raman-2-max" {
        value 65694;
        description
          "PM Optics raman-2 max threshold in mW";
      }
      enum "thresh-raman-3-max" {
        value 65695;
        description
          "PM Optics raman-3 max threshold in mW";
      }
      enum "thresh-raman-4-max" {
        value 65696;
        description
          "PM Optics raman-4 max threshold in mW";
      }
      enum "thresh-raman-5-max" {
        value 65697;
        description
          "PM Optics raman-5 max threshold in mW";
      }
      enum "thresh-snr-x-max" {
        value 65698;
        description
          "PM Optics snr ax max threshold";
      }
      enum "thresh-snr-y-max" {
        value 65699;
        description
          "PM Optics snr ax max threshold";
      }
      enum "thresh-raman-br-max" {
        value 65700;
        description
          "PM Optics raman-br  max threshold in dbm";
      }
      enum "thresh-raman-brr-max" {
        value 65701;
        description
          "PM Optics raman-brr  max threshold in db";
      }
      enum "thresh-tot-span-loss-rx-max" {
        value 65702;
        description
          "PM Optics span loss Rx max threshold in db";
      }
      enum "thresh-tot-span-loss-tx-max" {
        value 65703;
        description
          "PM Optics span loss Tx max threshold in db";
      }
      enum "thresh-tot-span-loss-rx-cl-max" {
        value 65704;
        description
          "PM Optics span loss Rx (C+L) band max threshold
           in db";
      }
      enum "thresh-tot-span-loss-tx-cl-max" {
        value 65705;
        description
          "PM Optics span loss Tx (C+L) band max threshold
           in db";
      }
      enum "thresh-raman-6-max" {
        value 65838;
        description
          "PM Optics raman-6 max threshold in mW";
      }
      enum "thresh-raman-7-max" {
        value 65839;
        description
          "PM Optics raman-7 max threshold in mW";
      }
      enum "thresh-raman-6-min" {
        value 65844;
        description
          "PM Optics raman-6 min threshold in mW";
      }
      enum "thresh-raman-7-min" {
        value 65845;
        description
          "PM Optics raman-7 min threshold in mW";
      }
    }
    description
      "Optics threshold";
  }

  typedef Ocn-threshold {
    type enumeration {
      enum "thresh-sefss" {
        value 3145728;
        description
          "PM SEFSS threshold";
      }
      enum "thresh-cvs" {
        value 3145729;
        description
          "PM CVS threshold";
      }
      enum "thresh-ess" {
        value 3145730;
        description
          "PM ESS threshold";
      }
      enum "thresh-sess" {
        value 3145731;
        description
          "PM SESS threshold";
      }
      enum "thresh-cvl-ne" {
        value 3145734;
        description
          "PM CVL-NE threshold";
      }
      enum "thresh-esl-ne" {
        value 3145735;
        description
          "PM ESL-NE threshold";
      }
      enum "thresh-sesl-ne" {
        value 3145736;
        description
          "PM SESL-NE threshold";
      }
      enum "thresh-uasl-ne" {
        value 3145738;
        description
          "PM UASL-NE threshold";
      }
      enum "thresh-fcl-ne" {
        value 3145739;
        description
          "PM FCL-NE threshold";
      }
      enum "thresh-fcl-fe" {
        value 3145751;
        description
          "PM FCL_FE threshold";
      }
      enum "thresh-cvl-fe" {
        value 3145752;
        description
          "PM CVL-FE threshold";
      }
      enum "thresh-esl-fe" {
        value 3145753;
        description
          "PM ESL_FE threshold";
      }
      enum "thresh-sesl-fe" {
        value 3145754;
        description
          "PM SESL_FE threshold";
      }
      enum "thresh-uasl-fe" {
        value 3145756;
        description
          "PM UASL_FEthreshold";
      }
    }
    description
      "Ocn threshold";
  }

  typedef E1-threshold {
    type enumeration {
      enum "thresh-lcv" {
        value 18874368;
        description
          "PM E1 lcv thresh";
      }
      enum "thresh-pcv" {
        value 18874369;
        description
          "PM E1 pcv thresh";
      }
      enum "thresh-sels" {
        value 18874370;
        description
          "PM E1 sels thresh";
      }
      enum "thresh-les" {
        value 18874371;
        description
          "PM E1 les thresh";
      }
      enum "thresh-aiss-sef" {
        value 18874372;
        description
          "PM E1 aiss-sef thresh";
      }
      enum "thresh-fcp" {
        value 18874373;
        description
          "PM E1 fcp thresh";
      }
      enum "thresh-es" {
        value 18874374;
        description
          "PM E1 es thresh";
      }
      enum "thresh-ses" {
        value 18874375;
        description
          "PM E1 ses thresh";
      }
      enum "thresh-uas" {
        value 18874376;
        description
          "PM E1 uas thresh";
      }
      enum "thresh-es-fe" {
        value 18874377;
        description
          "PM E1 es-fe thresh";
      }
      enum "thresh-ses-fe" {
        value 18874378;
        description
          "PM E1 ses-fe thresh";
      }
      enum "thresh-uas-fe" {
        value 18874379;
        description
          "PM E1 uas-fe thresh";
      }
    }
    description
      "E1 threshold";
  }

  typedef Otnsec-threshold {
    type enumeration {
      enum "thresh-in-block-s" {
        value 327680;
        description
          "PM OTNSEC Inblocks thresh";
      }
      enum "thresh-in-block-senc" {
        value 327681;
        description
          "PM OTNSEC InblocksEnc thresh";
      }
      enum "thresh-in-block-sunencrypted" {
        value 327682;
        description
          "PM OTNSEC InblocksUnEncrypted thresh";
      }
      enum "thresh-in-block-sprotected" {
        value 327683;
        description
          "PM OTNSEC InblocksProtected thresh";
      }
      enum "thresh-in-block-sunprotected" {
        value 327684;
        description
          "PM OTNSEC InblocksUnProtected thresh";
      }
      enum "thresh-in-block-ssequence-error-s" {
        value 327685;
        description
          "PM OTNSEC InblocksSequenceErrors thresh";
      }
      enum "thresh-in-block-sreplay-error-s" {
        value 327686;
        description
          "PM OTNSEC InblocksReplayErrors thresh";
      }
      enum "thresh-in-block-sauth-error-s" {
        value 327687;
        description
          "PM OTNSEC InblocksAuthErrors thresh";
      }
      enum "thresh-in-block-s-zero-ed" {
        value 327688;
        description
          "PM OTNSEC InblocksZeroed thresh";
      }
      enum "thresh-out-block-s" {
        value 327689;
        description
          "PM OTNSEC Outblocks thresh";
      }
      enum "thresh-out-block-senc" {
        value 327690;
        description
          "PM OTNSEC OutblocksEnc thresh";
      }
      enum "thresh-out-block-sunencrypted" {
        value 327691;
        description
          "PM OTNSEC OUTBLOCKSUNENCRYPTED thresh";
      }
      enum "thresh-out-block-ssequence-error-s" {
        value 327692;
        description
          "PM OTNSEC OutblocksSequenceErrors thresh";
      }
      enum "thresh-out-block-s-zero-ed" {
        value 327693;
        description
          "PM OTNSEC OutblocksZeroed thresh";
      }
      enum "thresh-out-block-sprotected" {
        value 327694;
        description
          "PM OTNSEC OutblocksProtected thresh";
      }
      enum "thresh-out-block-sunprotected" {
        value 327695;
        description
          "PM OTNSEC OutblocksUnProtected thresh";
      }
    }
    description
      "Otnsec threshold";
  }

  typedef Optics-report {
    type enumeration {
      enum "report-opt-min" {
        value 65596;
        description
          "PM Optics opt min report";
      }
      enum "report-opr-min" {
        value 65597;
        description
          "PM Optics opr min report";
      }
      enum "report-lbc-min" {
        value 65598;
        description
          "PM Optics lbc min report";
      }
      enum "report-lbc-pc-min" {
        value 65599;
        description
          "PM Optics lbcpc min report";
      }
      enum "report-cd-min" {
        value 65603;
        description
          "PM Optics cd min report";
      }
      enum "report-dgd-min" {
        value 65604;
        description
          "PM Optics dgd min report";
      }
      enum "report-pmd-min" {
        value 65605;
        description
          "PM Optics sopmd min report";
      }
      enum "report-osnr-min" {
        value 65606;
        description
          "PM Optics osnr min report";
      }
      enum "report-pdl-min" {
        value 65607;
        description
          "PM Optics pdl min report";
      }
      enum "report-pcr-min" {
        value 65608;
        description
          "PM Optics pcr min report";
      }
      enum "report-pn-min" {
        value 65609;
        description
          "PM Optics pn min report";
      }
      enum "report-rx-sig-pow-min" {
        value 65610;
        description
          "PM Optics rx sig pow min report";
      }
      enum "report-low-sig-freq-off-min" {
        value 65611;
        description
          "PM Optics low sig freq off min report";
      }
      enum "report-ampli-gain-min" {
        value 65612;
        description
          "PM Optics ampli gain min report";
      }
      enum "report-ampli-gain-tilt-min" {
        value 65613;
        description
          "PM Optics ampli gain tilt min report";
      }
      enum "report-snr-min" {
        value 65614;
        description
          "PM Optics snr min report";
      }
      enum "report-snr-ax-min" {
        value 65615;
        description
          "PM Optics snr ax min report";
      }
      enum "report-snr-bx-min" {
        value 65616;
        description
          "PM Optics snr bx min report";
      }
      enum "report-snr-ay-min" {
        value 65617;
        description
          "PM Optics snr ay min report";
      }
      enum "report-snr-by-min" {
        value 65618;
        description
          "PM Optics snr by min report";
      }
      enum "report-sop-s1-min" {
        value 65619;
        description
          "PM Optics sop s1 min report";
      }
      enum "report-sop-s2-min" {
        value 65620;
        description
          "PM Optics sop s2 min report";
      }
      enum "report-sop-s3-min" {
        value 65621;
        description
          "PM Optics sop s3 min report";
      }
      enum "report-opt-cl-min" {
        value 65622;
        description
          "PM Optics opt-cl min report";
      }
      enum "report-opr-cl-min" {
        value 65623;
        description
          "PM Optics opr-cl min report";
      }
      enum "report-opt-s-min" {
        value 65624;
        description
          "PM Optics opt-s min report";
      }
      enum "report-opr-s-min" {
        value 65625;
        description
          "PM Optics opr-s min report";
      }
      enum "report-opbr-min" {
        value 65626;
        description
          "PM Optics opbr min report";
      }
      enum "report-opbrr-min" {
        value 65627;
        description
          "PM Optics opbrr min report";
      }
      enum "report-eagn-min" {
        value 65628;
        description
          "PM Optics eagn min report";
      }
      enum "report-eatl-min" {
        value 65629;
        description
          "PM Optics eatl min report";
      }
      enum "report-iagn-min" {
        value 65630;
        description
          "PM Optics iagn min report";
      }
      enum "report-iatl-min" {
        value 65631;
        description
          "PM Optics iatl min report";
      }
      enum "report-raman-tot-min" {
        value 65632;
        description
          "PM Optics raman_tot min report";
      }
      enum "report-raman-1-min" {
        value 65633;
        description
          "PM Optics raman_1 min report";
      }
      enum "report-raman-2-min" {
        value 65634;
        description
          "PM Optics raman_2 min report";
      }
      enum "report-raman-3-min" {
        value 65635;
        description
          "PM Optics raman_3 min report";
      }
      enum "report-raman-4-min" {
        value 65636;
        description
          "PM Optics raman_4 min report";
      }
      enum "report-raman-5-min" {
        value 65637;
        description
          "PM Optics raman_5 min report";
      }
      enum "report-snr-x-min" {
        value 65638;
        description
          "PM Optics snr ax min report";
      }
      enum "report-snr-y-min" {
        value 65639;
        description
          "PM Optics snr ax min report";
      }
      enum "report-raman-br-min" {
        value 65640;
        description
          "PM Optics raman-br min report";
      }
      enum "report-raman-brr-min" {
        value 65641;
        description
          "PM Optics raman-brr min report";
      }
      enum "report-tot-span-loss-rx-min" {
        value 65642;
        description
          "PM Optics total span loss Rx min report";
      }
      enum "report-tot-span-loss-tx-min" {
        value 65643;
        description
          "PM Optics total span loss Tx min report";
      }
      enum "report-tot-span-loss-rx-cl-min" {
        value 65644;
        description
          "PM Optics total span loss Rx (C+L) band min
           report";
      }
      enum "report-tot-span-loss-tx-cl-min" {
        value 65645;
        description
          "PM Optics total span loss Tx (C+L) band min
           report";
      }
      enum "report-sig-span-loss-rx-min" {
        value 65646;
        description
          "PM Optics signal span loss Rx min report";
      }
      enum "report-sig-span-loss-tx-min" {
        value 65647;
        description
          "PM Optics signal span loss Tx min report";
      }
      enum "report-opt-max" {
        value 65656;
        description
          "PM Optics opt max report";
      }
      enum "report-opr-max" {
        value 65657;
        description
          "PM Optics opr max report";
      }
      enum "report-lbc-max" {
        value 65658;
        description
          "PM Optics lbc max report";
      }
      enum "report-lbc-pc-max" {
        value 65659;
        description
          "PM Optics lbcpc max report";
      }
      enum "report-cd-max" {
        value 65663;
        description
          "PM Optics cd max report";
      }
      enum "report-dgd-max" {
        value 65664;
        description
          "PM Optics dgd max report";
      }
      enum "report-pmd-max" {
        value 65665;
        description
          "PM Optics sopmd max report";
      }
      enum "report-osnr-max" {
        value 65666;
        description
          "PM Optics osnr max report";
      }
      enum "report-pdl-max" {
        value 65667;
        description
          "PM Optics pdl max report";
      }
      enum "report-pcr-max" {
        value 65668;
        description
          "PM Optics pcr max report";
      }
      enum "report-pn-max" {
        value 65669;
        description
          "PM Optics pn max report";
      }
      enum "report-rx-sig-pow-max" {
        value 65670;
        description
          "PM Optics rx sig pow max report";
      }
      enum "report-low-sig-freq-off-max" {
        value 65671;
        description
          "PM Optics low sig freq off max report";
      }
      enum "report-ampli-gain-max" {
        value 65672;
        description
          "PM Optics ampli gain max report";
      }
      enum "report-ampli-gain-tilt-max" {
        value 65673;
        description
          "PM Optics ampli gain tilt max report";
      }
      enum "report-snr-max" {
        value 65674;
        description
          "PM Optics snr max report";
      }
      enum "report-snr-ax-max" {
        value 65675;
        description
          "PM Optics snr ax max report";
      }
      enum "report-snr-bx-max" {
        value 65676;
        description
          "PM Optics snr bx max report";
      }
      enum "report-snr-ay-max" {
        value 65677;
        description
          "PM Optics snr ay max report";
      }
      enum "report-snr-by-max" {
        value 65678;
        description
          "PM Optics snr by max report";
      }
      enum "report-sop-s1-max" {
        value 65679;
        description
          "PM Optics sop s1 max report";
      }
      enum "report-sop-s2-max" {
        value 65680;
        description
          "PM Optics sop s2 max report";
      }
      enum "report-sop-s3-max" {
        value 65681;
        description
          "PM Optics sop s3 max report";
      }
      enum "report-opt-cl-max" {
        value 65682;
        description
          "PM Optics opt-cl max report";
      }
      enum "report-opr-cl-max" {
        value 65683;
        description
          "PM Optics opr-cl max report";
      }
      enum "report-opt-s-max" {
        value 65684;
        description
          "PM Optics opt-s max report";
      }
      enum "report-opr-s-max" {
        value 65685;
        description
          "PM Optics opr-s max report";
      }
      enum "report-opbr-max" {
        value 65686;
        description
          "PM Optics opbr max report";
      }
      enum "report-opbrr-max" {
        value 65687;
        description
          "PM Optics opbrr max report";
      }
      enum "report-eagn-max" {
        value 65688;
        description
          "PM Optics eagn max report";
      }
      enum "report-eatl-max" {
        value 65689;
        description
          "PM Optics eatl max report";
      }
      enum "report-iagn-max" {
        value 65690;
        description
          "PM Optics iagn max report";
      }
      enum "report-iatl-max" {
        value 65691;
        description
          "PM Optics iatl max report";
      }
      enum "report-raman-tot-max" {
        value 65692;
        description
          "PM Optics raman-tot max report";
      }
      enum "report-raman-1-max" {
        value 65693;
        description
          "PM Optics raman-1 max report";
      }
      enum "report-raman-2-max" {
        value 65694;
        description
          "PM Optics raman-2 max report";
      }
      enum "report-raman-3-max" {
        value 65695;
        description
          "PM Optics raman-3 max report";
      }
      enum "report-raman-4-max" {
        value 65696;
        description
          "PM Optics raman-1 max report";
      }
      enum "report-raman-5-max" {
        value 65697;
        description
          "PM Optics raman-5 max report";
      }
      enum "report-snr-x-max" {
        value 65698;
        description
          "PM Optics snr ax max report";
      }
      enum "report-snr-y-max" {
        value 65699;
        description
          "PM Optics snr ax max report";
      }
      enum "report-raman-br-max" {
        value 65700;
        description
          "PM Optics raman-br max report";
      }
      enum "report-raman-brr-max" {
        value 65701;
        description
          "PM Optics raman-brr max report";
      }
      enum "report-tot-span-loss-rx-max" {
        value 65702;
        description
          "PM Optics total span loss Rx max report";
      }
      enum "report-tot-span-loss-tx-max" {
        value 65703;
        description
          "PM Optics total span loss Tx max report";
      }
      enum "report-tot-span-loss-rx-cl-max" {
        value 65704;
        description
          "PM Optics total span loss Rx (C+L) band max
           report";
      }
      enum "report-tot-span-loss-tx-cl-max" {
        value 65705;
        description
          "PM Optics total span loss Tx (C+L) band  max
           report";
      }
      enum "report-sig-span-loss-rx-max" {
        value 65706;
        description
          "PM Optics signal span loss Rx max report";
      }
      enum "report-sig-span-loss-tx-max" {
        value 65707;
        description
          "PM Optics signal span loss Tx max report";
      }
      enum "report-raman-6-max" {
        value 65838;
        description
          "PM Optics raman-5 max report";
      }
      enum "report-raman-7-max" {
        value 65839;
        description
          "PM Optics raman-7 max report";
      }
      enum "report-raman-6-min" {
        value 65844;
        description
          "PM Optics raman_6 min report";
      }
      enum "report-raman-7-min" {
        value 65845;
        description
          "PM Optics raman_7 min report";
      }
    }
    description
      "Optics report";
  }

  typedef Ether-report {
    type enumeration {
      enum "report-rx-pkt" {
        value 524288;
        description
          "PM Ether rx pkt report";
      }
      enum "report-rx-util" {
        value 524289;
        description
          "PM Ether rx util report";
      }
      enum "report-tx-util" {
        value 524290;
        description
          "PM Ether tx util report";
      }
      enum "report-stat-pkt" {
        value 524291;
        description
          "PM ether stat pkt threshold";
      }
      enum "report-octet-stat" {
        value 524292;
        description
          "PM Ether octet stat report";
      }
      enum "report-over-size-pkt" {
        value 524293;
        description
          "PM Ether oversize pkt report";
      }
      enum "report-fcs-err" {
        value 524294;
        description
          "PM Ether fcs error report";
      }
      enum "report-long-frame-s" {
        value 524295;
        description
          "PM Ether long frames report";
      }
      enum "report-jabber-stats" {
        value 524296;
        description
          "PM Ether jabber stats report";
      }
      enum "report-64-octet" {
        value 524297;
        description
          "PM Ether 64 octet report";
      }
      enum "report-65-127-octet" {
        value 524298;
        description
          "PM Ether 65 to 127 octet report";
      }
      enum "report-128-255-octet" {
        value 524299;
        description
          "PM Ether 128 to 255 octet report";
      }
      enum "report-256-511-octet" {
        value 524300;
        description
          "PM Ether 256 to 511 octet report";
      }
      enum "report-512-1023-octet" {
        value 524301;
        description
          "PM Ether 512 to 1023 octet report";
      }
      enum "report-1024-1518-octet" {
        value 524302;
        description
          "PM Ether 1024 to 1518 report";
      }
      enum "report-in-ucast" {
        value 524303;
        description
          "PM Ether rx ucast report";
      }
      enum "report-in-mcast" {
        value 524304;
        description
          "PM Ether rx mcast report";
      }
      enum "report-in-bcast" {
        value 524305;
        description
          "PM Ether rx bcast report";
      }
      enum "report-out-ucast" {
        value 524306;
        description
          "PM Ether tx ucast report";
      }
      enum "report-out-mcast" {
        value 524307;
        description
          "PM Ether tx mcast report";
      }
      enum "report-out-bcast" {
        value 524308;
        description
          "PM Ether tx bcast report";
      }
      enum "report-tx-pkt" {
        value 524309;
        description
          "PM Ether tx pkt threshold";
      }
      enum "report-ifin-error-s" {
        value 524310;
        description
          "PM ether ifIn errors threshold";
      }
      enum "report-ifin-octets" {
        value 524311;
        description
          "PM ether ifInOctets threshold";
      }
      enum "report-ether-stat-multicast-pkt" {
        value 524312;
        description
          "PM ether stat multicast pkt threshold";
      }
      enum "report-ether-stat-broadcast-pkt" {
        value 524313;
        description
          "PM ether stat broadcast pkt threshold";
      }
      enum "report-ether-stat-under-size-d-pkt" {
        value 524314;
        description
          "PM ether stat undersized pkt threshold";
      }
      enum "report-out-octet" {
        value 524315;
        description
          "PM ether out octets threshold";
      }
      enum "report-in-pause-frame" {
        value 524316;
        description
          "PM ether in pause frame report";
      }
      enum "report-in-go-od-bytes" {
        value 524317;
        description
          "PM in good bytes report";
      }
      enum "report-in-802-1q-frame-s" {
        value 524318;
        description
          "PM in 802_1 Q report";
      }
      enum "report-in-pkts-1519-max-octets" {
        value 524319;
        description
          "PM in pkts 1519 max octets report";
      }
      enum "report-in-go-od-pkts" {
        value 524320;
        description
          "PM in good pkts report";
      }
      enum "report-in-drop-overrun" {
        value 524321;
        description
          "PM in drop overrun report";
      }
      enum "report-in-drop-abort" {
        value 524322;
        description
          "PM in drop abort report";
      }
      enum "report-in-drop-invalid-vlan" {
        value 524323;
        description
          "PM in drop invalid vlan report";
      }
      enum "report-in-drop-invalid-dmac" {
        value 524324;
        description
          "PM in drop invalid DMAC report";
      }
      enum "report-in-drop-invalid-encap" {
        value 524325;
        description
          "PM in drop invalid encap report";
      }
      enum "report-in-drop-other" {
        value 524326;
        description
          "PM in drop other report";
      }
      enum "report-in-mib-giant" {
        value 524327;
        description
          "PM in MIB giant report";
      }
      enum "report-in-mib-jabber" {
        value 524328;
        description
          "PM in MIB jabber report";
      }
      enum "report-in-mib-crc" {
        value 524329;
        description
          "PM in MIB CRC report";
      }
      enum "report-in-error-collision-s" {
        value 524330;
        description
          "PM in error collisions report";
      }
      enum "report-in-error-symbol" {
        value 524331;
        description
          "PM in error symbol report";
      }
      enum "report-out-go-od-bytes" {
        value 524332;
        description
          "PM out good bytes report";
      }
      enum "report-out-802-1q-frame-s" {
        value 524333;
        description
          "PM out 802_1 Q report";
      }
      enum "report-out-pause-frame-s" {
        value 524334;
        description
          "PM out pause frame report";
      }
      enum "report-out-pkts-1519-max-octets" {
        value 524335;
        description
          "PM out pkts 1519 max octets report";
      }
      enum "report-out-go-od-pkts" {
        value 524336;
        description
          "PM out good pkts report";
      }
      enum "report-out-drop-under-run" {
        value 524337;
        description
          "PM out drop underrun report";
      }
      enum "report-out-drop-abort" {
        value 524338;
        description
          "PM out drop abort report";
      }
      enum "report-out-drop-other" {
        value 524339;
        description
          "PM out drop other report";
      }
      enum "report-out-error-other" {
        value 524340;
        description
          "PM out error other report";
      }
      enum "report-in-error-giant" {
        value 524341;
        description
          "PM in error giant report";
      }
      enum "report-in-error-runt" {
        value 524342;
        description
          "PM in error runt report";
      }
      enum "report-in-error-jabbers" {
        value 524343;
        description
          "PM in error jabber report";
      }
      enum "report-in-error-fragments" {
        value 524344;
        description
          "PM in error fragments report";
      }
      enum "report-in-error-other" {
        value 524345;
        description
          "PM in error other report";
      }
      enum "report-in-pkt-64-octet" {
        value 524346;
        description
          "PM in pkt 64 octet report";
      }
      enum "report-in-pkts-65-127octets" {
        value 524347;
        description
          "PM in pkts 65_127 octets report";
      }
      enum "report-in-pkts-128-255-octets" {
        value 524348;
        description
          "PM in pkts 128_255 octets report";
      }
      enum "report-in-pkts-256-511-octets" {
        value 524349;
        description
          "PM in pkts 256_511 octets report";
      }
      enum "report-in-pkts-512-1023-octets" {
        value 524350;
        description
          "PM in pkts 512_1023 octets report";
      }
      enum "report-in-pkts-1024-1518-octets" {
        value 524351;
        description
          "PM in pkts 1024_1058 octets report";
      }
      enum "report-out-pkt-64-octet" {
        value 524352;
        description
          "PM out pkt 64 octet report";
      }
      enum "report-out-pkts-65-127octets" {
        value 524353;
        description
          "PM out pkts 65_127 octets report";
      }
      enum "report-out-pkts-128-255-octets" {
        value 524354;
        description
          "PM out pkts 128_255 octets report";
      }
      enum "report-out-pkts-256-511-octets" {
        value 524355;
        description
          "PM out pkts 256_511 octets report";
      }
      enum "report-out-pkts-512-1023-octets" {
        value 524356;
        description
          "PM out pkts 512_1023 octets report";
      }
      enum "report-out-pkts-1024-1518-octets" {
        value 524357;
        description
          "PM out pkts 1024_1058 octets report";
      }
      enum "report-tx-under-size-d-pkt" {
        value 524358;
        description
          "PM tx undersized pkt report";
      }
      enum "report-tx-over-size-d-pkt" {
        value 524359;
        description
          "PM tx oversized pkt report";
      }
      enum "report-tx-fragments" {
        value 524360;
        description
          "PM tx fragments report";
      }
      enum "report-tx-jabber" {
        value 524361;
        description
          "PM tx jabber report";
      }
      enum "report-tx-bad-fcs" {
        value 524362;
        description
          "PM tx bad fcs report";
      }
    }
    description
      "Ether report";
  }

  typedef Otn-tcm-report {
    type enumeration {
      enum "report-es-tcm-fe" {
        value 16777224;
        description
          "PM Otn es TCM fe report";
      }
      enum "report-ses-tcm-fe" {
        value 16777225;
        description
          "PM Otn ses TCM fe report";
      }
      enum "report-uas-tcm-fe" {
        value 16777226;
        description
          "PM Otn uas TCM fe report";
      }
      enum "report-bbe-tcm-fe" {
        value 16777227;
        description
          "PM Otn bbe TCM fe report";
      }
      enum "report-fc-tcm-fe" {
        value 16777228;
        description
          "PM Otn fc TCM fe report";
      }
      enum "report-esr-tcm-fe" {
        value 16777229;
        description
          "PM Otn esr TCM fe report";
      }
      enum "report-sesr-tcm-fe" {
        value 16777230;
        description
          "PM Otn sesr TCM fe report";
      }
      enum "report-bber-tcm-fe" {
        value 16777231;
        description
          "PM Otn bber TCM fe report";
      }
      enum "report-es-tcm-ne" {
        value 33554432;
        description
          "PM Otn es TCM ne report";
      }
      enum "report-ses-tcm-ne" {
        value 33554433;
        description
          "PM Otn ses TCM ne report";
      }
      enum "report-uas-tcm-ne" {
        value 33554434;
        description
          "PM Otn uas TCM ne report";
      }
      enum "report-bbe-tcm-ne" {
        value 33554435;
        description
          "PM Otn bbe TCM ne report";
      }
      enum "report-fc-tcm-ne" {
        value 33554436;
        description
          "PM Otn fc TCM ne report";
      }
      enum "report-esr-tcm-ne" {
        value 33554437;
        description
          "PM Otn esr TCM ne report";
      }
      enum "report-sesr-tcm-ne" {
        value 33554438;
        description
          "PM Otn sesr TCM ne report";
      }
      enum "report-bber-tcm-ne" {
        value 33554439;
        description
          "PM Otn bber TCM ne report";
      }
    }
    description
      "Otn tcm report";
  }

  typedef Fec-threshold {
    type enumeration {
      enum "thresh-ec-bits" {
        value 131072;
        description
          "PM Fec ec bits threshold";
      }
      enum "thresh-uc-words" {
        value 131076;
        description
          "PM Fec uc words threshold";
      }
      enum "thresh-ec-words" {
        value 131077;
        description
          "PM Fec ec words threshold";
      }
      enum "thresh-pre-fec-ber-max" {
        value 131085;
        description
          "PM Fec pre-fe-ber max threshold";
      }
      enum "thresh-post-fec-ber-max" {
        value 131086;
        description
          "PM Fec post-fec-ber max threshold";
      }
      enum "thresh-q-max" {
        value 131087;
        description
          "PM Fec Q max threshold";
      }
      enum "thresh-q-margin-max" {
        value 131088;
        description
          "PM Fec uc words max threshold";
      }
      enum "thresh-q-margin-inst-max" {
        value 131089;
        description
          "PM Fec Q margin instantaneuos max threshold";
      }
      enum "thresh-ber-lane-max" {
        value 131090;
        description
          "PM Fec ber-lane max threshold";
      }
      enum "thresh-ferc-lane-max" {
        value 131091;
        description
          "PM Fec ferc-lane max threshold";
      }
      enum "thresh-pre-fec-ber-min" {
        value 131092;
        description
          "PM Fec pre-fe-ber min threshold";
      }
      enum "thresh-post-fec-ber-min" {
        value 131093;
        description
          "PM Fec post-fec-ber min threshold";
      }
      enum "thresh-q-min" {
        value 131094;
        description
          "PM Fec Q min threshold";
      }
      enum "thresh-q-margin-min" {
        value 131095;
        description
          "PM Fec uc words min threshold";
      }
      enum "thresh-q-margin-inst-min" {
        value 131096;
        description
          "PM Fec Q margin instantaneuos min threshold";
      }
      enum "thresh-ber-lane-min" {
        value 131097;
        description
          "PM Fec ber-lane min threshold";
      }
      enum "thresh-ferc-lane-min" {
        value 131098;
        description
          "PM Fec ferc-lane min threshold";
      }
    }
    description
      "Fec threshold";
  }

  typedef Secyif-threshold {
    type enumeration {
      enum "thresh-if-inpkts-untagged" {
        value 150994944;
        description
          "PM SECYIF if InPktsUntagged thresh";
      }
      enum "thresh-if-inpkts-not-ag" {
        value 150994945;
        description
          "PM SECYIF if InPktsNoTag thresh";
      }
      enum "thresh-if-inpktsbadtag" {
        value 150994946;
        description
          "PM SECYIF if InPktsBadTag thresh";
      }
      enum "thresh-if-inpktsunkownsci" {
        value 150994947;
        description
          "PM SECYIF if InPktsUnknownSCI thresh";
      }
      enum "thresh-if-inpktsnosci" {
        value 150994948;
        description
          "PM SECYIF if InPktsNoSCI thresh";
      }
      enum "thresh-if-inpkts-overrun" {
        value 150994949;
        description
          "PM SECYIF if InPktsOverrun thresh";
      }
      enum "thresh-if-inoctets-validate-d" {
        value 150994950;
        description
          "PM SECYIF if InOctetsValidated thresh";
      }
      enum "thresh-if-inoctetsdecrypted" {
        value 150994951;
        description
          "PM SECYIF if InOctetsDecrypted thresh";
      }
      enum "thresh-if-outpkts-untagged" {
        value 150994952;
        description
          "PM SECYIF if OutPktsUntagged thresh";
      }
      enum "thresh-if-thresh-outpkts-too-long" {
        value 150994953;
        description
          "PM SECYIF if OutPktsTooLong thresh";
      }
      enum "thresh-if-outoctetsprotected" {
        value 150994954;
        description
          "PM SECYIF if OutOctetsProtected thresh";
      }
      enum "thresh-if-outoctetsencrypted" {
        value 150994955;
        description
          "PM SECYIF if OutOctetsEncrypted thresh";
      }
    }
    description
      "Secyif threshold";
  }

  typedef Sts-report {
    type enumeration {
      enum "report-cv" {
        value 4194304;
        description
          "PM CV threshold";
      }
      enum "report-es" {
        value 4194305;
        description
          "PM ES threshold";
      }
      enum "report-ses" {
        value 4194306;
        description
          "PM SES threshold";
      }
      enum "report-uas" {
        value 4194307;
        description
          "PM UAS threshold";
      }
    }
    description
      "Sts report";
  }

  typedef Fc-threshold {
    type enumeration {
      enum "thresh-ifin-octets" {
        value 20971520;
        description
          "PM FC ifIn-Octets threshold";
      }
      enum "thresh-rx-pkts" {
        value 20971521;
        description
          "PM FC rx-pkt threshold";
      }
      enum "thresh-ifin-error-s" {
        value 20971522;
        description
          "PM FC ifIn-Errors threshold";
      }
      enum "thresh-rx-bad-fcs" {
        value 20971523;
        description
          "PM FC rx-bad-fcs threshold";
      }
      enum "thresh-ifout-octets" {
        value 20971524;
        description
          "PM FC ifOut-Octets threshold";
      }
      enum "thresh-tx-pkts" {
        value 20971525;
        description
          "PM FC tx-pkt threshold";
      }
      enum "thresh-tx-bad-fcs" {
        value 20971526;
        description
          "PM FC tx-bad-fcs threshold";
      }
      enum "thresh-rx-frame-s-too-long" {
        value 20971527;
        description
          "PM FC rx-frames-too-long threshold";
      }
      enum "thresh-rx-frame-s-trunc" {
        value 20971528;
        description
          "PM FC rx-frames-trunc threshold";
      }
      enum "thresh-tx-frame-s-too-long" {
        value 20971529;
        description
          "PM FC tx-frames-too-long threshold";
      }
      enum "thresh-tx-frame-s-trunc" {
        value 20971530;
        description
          "PM FC tx-frames-trunc threshold";
      }
    }
    description
      "Fc threshold";
  }

  typedef Stm-threshold {
    type enumeration {
      enum "thresh-ebs" {
        value 16777217;
        description
          "PM EBS threshold";
      }
      enum "thresh-ess" {
        value 16777218;
        description
          "PM ESS threshold";
      }
      enum "thresh-esrs" {
        value 16777219;
        description
          "PM ESRS threshold";
      }
      enum "thresh-sess" {
        value 16777220;
        description
          "PM SES threshold";
      }
      enum "thresh-sesrs" {
        value 16777221;
        description
          "PM SESR threshold";
      }
      enum "thresh-bbes" {
        value 16777222;
        description
          "PM BBES threshold";
      }
      enum "thresh-bbesr" {
        value 16777223;
        description
          "PM BBESR threshold";
      }
      enum "thresh-uass" {
        value 16777224;
        description
          "PM UASS threshold";
      }
      enum "thresh-ebl-ne" {
        value 16777225;
        description
          "PM EBLNE threshold";
      }
      enum "thresh-esl-ne" {
        value 16777226;
        description
          "PM ESLNE threshold";
      }
      enum "thresh-eslr-ne" {
        value 16777227;
        description
          "PM ESLRNE threshold";
      }
      enum "thresh-sesl-ne" {
        value 16777228;
        description
          "PM SESL threshold";
      }
      enum "thresh-sesrl-ne" {
        value 16777229;
        description
          "PM SESRL threshold";
      }
      enum "thresh-bbel-ne" {
        value 16777230;
        description
          "PM BBERLNE threshold";
      }
      enum "thresh-bberl-ne" {
        value 16777231;
        description
          "PM BBERLNE threshold";
      }
      enum "thresh-uasl-ne" {
        value 16777232;
        description
          "PM UASNE threshold";
      }
      enum "thresh-ebl-fe" {
        value 16777245;
        description
          "PM EBFE threshold";
      }
      enum "thresh-esl-fe" {
        value 16777246;
        description
          "PM ESFE threshold";
      }
      enum "thresh-esrl-fe" {
        value 16777247;
        description
          "PM EBFE threshold";
      }
      enum "thresh-sesl-fe" {
        value 16777248;
        description
          "PM SESFE threshold";
      }
      enum "thresh-sesrl-fe" {
        value 16777249;
        description
          "PM SESRLFE threshold";
      }
      enum "thresh-bbel-fe" {
        value 16777250;
        description
          "PM BBEL threshold";
      }
      enum "thresh-bberl-fe" {
        value 16777251;
        description
          "PM BBELFE threshold";
      }
      enum "thresh-uasl-fe" {
        value 16777252;
        description
          "PM UASLFE threshold";
      }
    }
    description
      "Stm threshold";
  }

  typedef Otn-tcm-threshold {
    type enumeration {
      enum "thresh-es-tcm-fe" {
        value 16777224;
        description
          "PM Otn es TCM fe threshold";
      }
      enum "thresh-ses-tcm-fe" {
        value 16777225;
        description
          "PM Otn ses TCM fe threshold";
      }
      enum "thresh-uas-tcm-fe" {
        value 16777226;
        description
          "PM Otn uas TCM fe threshold";
      }
      enum "thresh-bbe-tcm-fe" {
        value 16777227;
        description
          "PM Otn bbe TCM fe threshold";
      }
      enum "thresh-fc-tcm-fe" {
        value 16777228;
        description
          "PM Otn fc TCM fe threshold";
      }
      enum "thresh-esr-tcm-fe" {
        value 16777229;
        description
          "PM Otn esr TCM fe threshold";
      }
      enum "thresh-sesr-tcm-fe" {
        value 16777230;
        description
          "PM Otn sesr TCM fe threshold";
      }
      enum "thresh-bber-tcm-fe" {
        value 16777231;
        description
          "PM Otn bber TCM fe threshold";
      }
      enum "thresh-es-tcm-ne" {
        value 33554432;
        description
          "PM Otn es TCM ne threshold";
      }
      enum "thresh-ses-tcm-ne" {
        value 33554433;
        description
          "PM Otn ses TCM ne threshold";
      }
      enum "thresh-uas-tcm-ne" {
        value 33554434;
        description
          "PM Otn uas TCM ne threshold";
      }
      enum "thresh-bbe-tcm-ne" {
        value 33554435;
        description
          "PM Otn bbe TCM ne threshold";
      }
      enum "thresh-fc-tcm-ne" {
        value 33554436;
        description
          "PM Otn fc TCM ne threshold";
      }
      enum "thresh-esr-tcm-ne" {
        value 33554437;
        description
          "PM Otn esr TCM ne threshold";
      }
      enum "thresh-sesr-tcm-ne" {
        value 33554438;
        description
          "PM Otn sesr TCM ne threshold";
      }
      enum "thresh-bber-tcm-ne" {
        value 33554439;
        description
          "PM Otn bber TCM ne threshold";
      }
    }
    description
      "Otn tcm threshold";
  }

  typedef Report {
    type enumeration {
      enum "false" {
        value 0;
        description
          "Performance Monitoring Disabled";
      }
      enum "true" {
        value 1;
        description
          "Performance Monitoring Enabled";
      }
    }
    description
      "Report";
  }

  typedef Prbs-report {
    type enumeration {
      enum "report-ebc" {
        value 17825792;
        description
          "PM Prbs ebc bits report";
      }
      enum "report-found-count" {
        value 17825793;
        description
          "PM Prbs found count report";
      }
      enum "report-lost-count" {
        value 17825794;
        description
          "PM Prbs lost count report";
      }
    }
    description
      "Prbs report";
  }

  typedef Otn-report {
    type enumeration {
      enum "report-es-sm-ne" {
        value 262144;
        description
          "PM Otn es sm ne report";
      }
      enum "report-ses-sm-ne" {
        value 262145;
        description
          "PM Otn ses sm ne report";
      }
      enum "report-uas-sm-ne" {
        value 262146;
        description
          "PM Otn uas sm ne report";
      }
      enum "report-bbe-sm-ne" {
        value 262147;
        description
          "PM Otn bbe sm ne report";
      }
      enum "report-fc-sm-ne" {
        value 262148;
        description
          "PM Otn fc sm ne report";
      }
      enum "report-esr-sm-ne" {
        value 262149;
        description
          "PM Otn esr sm ne report";
      }
      enum "report-sesr-sm-ne" {
        value 262150;
        description
          "PM Otn sesr sm ne report";
      }
      enum "report-bber-sm-ne" {
        value 262151;
        description
          "PM Otn bber sm ne report";
      }
      enum "report-es-pm-ne" {
        value 524288;
        description
          "PM Otn es pm ne report";
      }
      enum "report-ses-pm-ne" {
        value 524289;
        description
          "PM Otn ses pm ne report";
      }
      enum "report-uas-pm-ne" {
        value 524290;
        description
          "PM Otn uas pm ne report";
      }
      enum "report-bbe-pm-ne" {
        value 524291;
        description
          "PM Otn bbe pm ne report";
      }
      enum "report-fc-pm-ne" {
        value 524292;
        description
          "PM Otn fc pm ne report";
      }
      enum "report-esr-pm-ne" {
        value 524293;
        description
          "PM Otn esr pm ne report";
      }
      enum "report-sesr-pm-ne" {
        value 524294;
        description
          "PM Otn sesr pm ne report";
      }
      enum "report-bber-pm-ne" {
        value 524295;
        description
          "PM Otn bber pm ne report";
      }
      enum "report-es-sm-fe" {
        value 1048584;
        description
          "PM Otn es sm fe report";
      }
      enum "report-ses-sm-fe" {
        value 1048585;
        description
          "PM Otn ses sm fe report";
      }
      enum "report-uas-sm-fe" {
        value 1048586;
        description
          "PM Otn uas sm fe report";
      }
      enum "report-bbe-sm-fe" {
        value 1048587;
        description
          "PM Otn bbe sm fe report";
      }
      enum "report-fc-sm-fe" {
        value 1048588;
        description
          "PM Otn fc sm fe report";
      }
      enum "report-esr-sm-fe" {
        value 1048589;
        description
          "PM Otn esr sm fe report";
      }
      enum "report-sesr-sm-fe" {
        value 1048590;
        description
          "PM Otn sesr sm fe report";
      }
      enum "report-bber-sm-fe" {
        value 1048591;
        description
          "PM Otn bber sm fe report";
      }
      enum "report-es-pm-fe" {
        value 2097160;
        description
          "PM Otn es pm fe report";
      }
      enum "report-ses-pm-fe" {
        value 2097161;
        description
          "PM Otn ses pm fe report";
      }
      enum "report-uas-pm-fe" {
        value 2097162;
        description
          "PM Otn uas pm fe report";
      }
      enum "report-bbe-pm-fe" {
        value 2097163;
        description
          "PM Otn bbe pm fe report";
      }
      enum "report-fc-pm-fe" {
        value 2097164;
        description
          "PM Otn fc pm fe report";
      }
      enum "report-esr-pm-fe" {
        value 2097165;
        description
          "PM Otn esr pm fe report";
      }
      enum "report-sesr-pm-fe" {
        value 2097166;
        description
          "PM Otn sesr pm fe report";
      }
      enum "report-bber-pm-fe" {
        value 2097167;
        description
          "PM Otn bber pm fe report";
      }
    }
    description
      "Otn report";
  }

  typedef Secytx-threshold {
    type enumeration {
      enum "thresh-tx-outpktsprotected" {
        value 134217728;
        description
          "PM SECYTX tx OutPktsProtected thresh";
      }
      enum "thresh-tx-outpktsencrypted" {
        value 134217729;
        description
          "PM SECYTX tx OutPktsEncrypted thresh";
      }
      enum "thresh-tx-outoctetsprotected" {
        value 134217730;
        description
          "PM SECYTX tx OutOctetsProtected thresh";
      }
      enum "thresh-tx-outoctetsencrypted" {
        value 134217731;
        description
          "PM SECYTX tx OutOctetsEncrypted thresh";
      }
      enum "thresh-tx-outpkts-too-long" {
        value 134217732;
        description
          "PM SECYTX tx OutPktsTooLong thresh";
      }
    }
    description
      "Secytx threshold";
  }

  typedef Pcs-report {
    type enumeration {
      enum "report-bip" {
        value 100663296;
        description
          "PM PCS Bip report";
      }
      enum "report-frm-err" {
        value 100663297;
        description
          "PM PCS frm-err report";
      }
      enum "report-bad-sh" {
        value 100663298;
        description
          "PM PCS bad-sh report";
      }
      enum "report-es" {
        value 100663299;
        description
          "PM PCS es report";
      }
      enum "report-ses" {
        value 100663300;
        description
          "PM PCS ses report";
      }
      enum "report-uas" {
        value 100663301;
        description
          "PM PCS uas report";
      }
      enum "report-es-fe" {
        value 100663302;
        description
          "PM PCS es-fe report";
      }
      enum "report-ses-fe" {
        value 100663303;
        description
          "PM PCS ses-fe_report";
      }
      enum "report-uas-fe" {
        value 100663304;
        description
          "PM PCS uas-fe report";
      }
    }
    description
      "Pcs report";
  }

  typedef Cem-threshold {
    type enumeration {
      enum "thresh-missing-pkts" {
        value 24117248;
        description
          "PM CEM missing-pkts threshold";
      }
      enum "thresh-pkts-re-order" {
        value 24117249;
        description
          "PM CEM pkts-reorder threshold";
      }
      enum "thresh-jtr-bfr-under" {
        value 24117250;
        description
          "PM CEM jtr-bfr-underrun threshold";
      }
      enum "thresh-mis-order-drop" {
        value 24117251;
        description
          "PM CEM mis-order-drop threshold";
      }
      enum "thresh-malformed-pkt" {
        value 24117252;
        description
          "PM CEM malformed-pkts threshold";
      }
      enum "thresh-es" {
        value 24117253;
        description
          "PM CEM ES threshold";
      }
      enum "thresh-ses" {
        value 24117254;
        description
          "PM CEM SES threshold";
      }
      enum "thresh-uas" {
        value 24117255;
        description
          "PM CEM UAS threshold";
      }
      enum "thresh-fc" {
        value 24117256;
        description
          "PM CEM FC threshold";
      }
      enum "thresh-input-errs" {
        value 24117257;
        description
          "PM CEM input-errs threshold";
      }
      enum "thresh-output-errs" {
        value 24117258;
        description
          "PM CEM output-errs threshold";
      }
      enum "thresh-jtr-bfr-over" {
        value 24117259;
        description
          "PM CEM jtr-bfr-overruns threshold";
      }
      enum "thresh-tx-lbits" {
        value 24117260;
        description
          "PM CEM tx-lbits threshold";
      }
      enum "thresh-tx-rbits" {
        value 24117261;
        description
          "PM CEM tx-rbits threshold";
      }
      enum "thresh-rx-lbits" {
        value 24117262;
        description
          "PM CEM rx-lbits threshold";
      }
      enum "thresh-rx-rbits" {
        value 24117263;
        description
          "PM CEM rx-rbits threshold";
      }
      enum "thresh-in-pkts" {
        value 24117264;
        description
          "PM CEM ingress-pkts threshold";
      }
      enum "thresh-eg-pkts" {
        value 24117265;
        description
          "PM CEM egress-pkts threshold";
      }
      enum "thresh-in-pkts-drop" {
        value 24117266;
        description
          "PM CEM ingress-pkts-dropped threshold";
      }
      enum "thresh-eg-pkts-drop" {
        value 24117267;
        description
          "PM CEM egress-pkts-dropped threshold";
      }
    }
    description
      "Cem threshold";
  }

  typedef Fec-report {
    type enumeration {
      enum "report-ec-bits" {
        value 131072;
        description
          "PM Fec ec bits report";
      }
      enum "report-uc-words" {
        value 131076;
        description
          "PM Fec uc words report";
      }
      enum "report-ec-words" {
        value 131077;
        description
          "PM Fec ec words report";
      }
      enum "report-pre-fec-ber-max" {
        value 131085;
        description
          "PM Fec pre fec ber max report";
      }
      enum "report-post-fec-ber-max" {
        value 131086;
        description
          "PM Fec post fec ber max report";
      }
      enum "report-q-max" {
        value 131087;
        description
          "PM Fec Q max report";
      }
      enum "report-q-margin-max" {
        value 131088;
        description
          "PM Fec Q_margin max report";
      }
      enum "report-q-margin-inst-max" {
        value 131089;
        description
          "PM Fec Q_margin_inst max report";
      }
      enum "report-ber-lane-max" {
        value 131090;
        description
          "PM Fec ber lane max report";
      }
      enum "report-ferc-lane-max" {
        value 131091;
        description
          "PM Fec ferc lane max report";
      }
      enum "report-pre-fec-ber-min" {
        value 131092;
        description
          "PM Fec pre fec ber min report";
      }
      enum "report-post-fec-ber-min" {
        value 131093;
        description
          "PM Fec post fec ber min report";
      }
      enum "report-q-min" {
        value 131094;
        description
          "PM Fec Q min report";
      }
      enum "report-q-margin-min" {
        value 131095;
        description
          "PM Fec Q_margin min report";
      }
      enum "report-q-margin-inst-min" {
        value 131096;
        description
          "PM Fec Q_margin_inst min report";
      }
      enum "report-ber-lane-min" {
        value 131097;
        description
          "PM Fec ber lane min report";
      }
      enum "report-ferc-lane-min" {
        value 131098;
        description
          "PM Fec ferc lane min report";
      }
    }
    description
      "Fec report";
  }

  typedef Path-report {
    type enumeration {
      enum "report-cv" {
        value 5242880;
        description
          "PM CV threshold";
      }
      enum "report-es" {
        value 5242881;
        description
          "PM ES threshold";
      }
      enum "report-ses" {
        value 5242882;
        description
          "PM SES threshold";
      }
      enum "report-uas" {
        value 5242883;
        description
          "PM UAS threshold";
      }
    }
    description
      "Path report";
  }

  typedef Secyrx-report {
    type enumeration {
      enum "report-rx-inpktsun-check-ed" {
        value 117440512;
        description
          "PM SECYRX rx InPktsUnchecked report";
      }
      enum "report-rx-inpkts-delayed" {
        value 117440513;
        description
          "PM SECYRX rx InPktsDelayed report";
      }
      enum "report-rx-inpktslate" {
        value 117440514;
        description
          "PM SECYRX rx InPktsLate report";
      }
      enum "report-rx-inpktsok" {
        value 117440515;
        description
          "PM SECYRX rx InPktsOK report";
      }
      enum "report-rx-inpkts-invalid" {
        value 117440516;
        description
          "PM SECYRX rx InPktsInvalid report";
      }
      enum "report-rx-inpkts-not-valid" {
        value 117440517;
        description
          "PM SECYRX rx InPktsNotValid report";
      }
      enum "report-rx-inpkts-not-usingsa" {
        value 117440518;
        description
          "PM SECYRX rx InPktsNotUsingSA sa report";
      }
      enum "report-rx-inpktsunusedsa" {
        value 117440519;
        description
          "PM SECYRX rx InPktsUnusedSA report";
      }
      enum "report-rx-inpkts-untagged-hit" {
        value 117440520;
        description
          "PM SECYRX rx InPktsUntaggedHit report";
      }
      enum "report-rx-inoctets-validate-d" {
        value 117440521;
        description
          "PM SECYRX rx InOctetsValidated report";
      }
      enum "report-rx-inoctetsdecrypted" {
        value 117440522;
        description
          "PM SECYRX rx InOctetsDecrypted report";
      }
    }
    description
      "Secyrx report";
  }

  typedef Secyrx-threshold {
    type enumeration {
      enum "thresh-rx-inpktsun-check-ed" {
        value 117440512;
        description
          "PM SECYRX rx InPktsUnchecked thresh";
      }
      enum "thresh-rx-inpkts-delayed" {
        value 117440513;
        description
          "PM SECYRX rx InPktsDelayed thresh";
      }
      enum "thresh-rx-inpktslate" {
        value 117440514;
        description
          "PM SECYRX rx InPktsLate thresh";
      }
      enum "thresh-rx-inpktsok" {
        value 117440515;
        description
          "PM SECYRX rx InPktsOK thresh";
      }
      enum "thresh-rx-inpkts-invalid" {
        value 117440516;
        description
          "PM SECYRX rx InPktsInvalid thresh";
      }
      enum "thresh-rx-inpkts-not-valid" {
        value 117440517;
        description
          "PM SECYRX rx InPktsNotValid thresh";
      }
      enum "thresh-rx-inpkts-not-usingsa" {
        value 117440518;
        description
          "PM SECYRX rx InPktsNotUsingSA thresh";
      }
      enum "thresh-rx-inpktsunusedsa" {
        value 117440519;
        description
          "PM SECYRX rx InPktsUnusedSA thresh";
      }
      enum "thresh-rx-inpkts-untagged-hit" {
        value 117440520;
        description
          "PM SECYRX rx InPktsUntaggedHit thresh";
      }
      enum "thresh-rx-inoctets-validate-d" {
        value 117440521;
        description
          "PM SECYRX rx InOctetsValidated thresh";
      }
      enum "thresh-rx-inoctetsdecrypted" {
        value 117440522;
        description
          "PM SECYRX rx InOctetsDecrypted thresh";
      }
    }
    description
      "Secyrx threshold";
  }

  typedef Gfp-threshold {
    type enumeration {
      enum "thresh-rx-bit-err" {
        value 67108864;
        description
          "PM GFP rx bit err threshold";
      }
      enum "thresh-rx-inv-typ" {
        value 67108865;
        description
          "PM GFP rx inv type threshold";
      }
      enum "thresh-rx-crc" {
        value 67108866;
        description
          "PM GFP rx crc threshold";
      }
      enum "thresh-rx-lfd" {
        value 67108867;
        description
          "PM GFP rx lfd threshold";
      }
      enum "thresh-rx-csf" {
        value 67108868;
        description
          "PM GFP rx csf threshold";
      }
    }
    description
      "Gfp threshold";
  }

  typedef Stm-report {
    type enumeration {
      enum "report-ebs" {
        value 16777217;
        description
          "PM EBS REPORT";
      }
      enum "report-ess" {
        value 16777218;
        description
          "PM ESS REPORT";
      }
      enum "report-esrs" {
        value 16777219;
        description
          "PM ESRS REPORT";
      }
      enum "report-sess" {
        value 16777220;
        description
          "PM SES REPORT";
      }
      enum "report-sesrs" {
        value 16777221;
        description
          "PM SESR REPORT";
      }
      enum "report-bbes" {
        value 16777222;
        description
          "PM BBES REPORT";
      }
      enum "report-bbesr" {
        value 16777223;
        description
          "PM BBESR REPORT";
      }
      enum "report-uass" {
        value 16777224;
        description
          "PM UASS REPORT";
      }
      enum "report-ebl-ne" {
        value 16777225;
        description
          "PM EBLNE REPORT";
      }
      enum "report-esl-ne" {
        value 16777226;
        description
          "PM ESLNE REPORT";
      }
      enum "report-eslr-ne" {
        value 16777227;
        description
          "PM ESLRNE REPORT";
      }
      enum "report-sesl-ne" {
        value 16777228;
        description
          "PM SESL REPORT";
      }
      enum "report-sesrl-ne" {
        value 16777229;
        description
          "PM SESRL REPORT";
      }
      enum "report-bbel-ne" {
        value 16777230;
        description
          "PM BBELNE REPORT";
      }
      enum "report-bberl-ne" {
        value 16777231;
        description
          "PM BBERLNE REPORT";
      }
      enum "report-uasl-ne" {
        value 16777232;
        description
          "PM UASNE REPORT";
      }
      enum "report-ebl-fe" {
        value 16777245;
        description
          "PM EBFE REPORT";
      }
      enum "report-esl-fe" {
        value 16777246;
        description
          "PM ESFE REPORT";
      }
      enum "report-esrl-fe" {
        value 16777247;
        description
          "PM EBFE REPORT";
      }
      enum "report-sesl-fe" {
        value 16777248;
        description
          "PM SESFE REPORT";
      }
      enum "report-sesrl-fe" {
        value 16777249;
        description
          "PM SESRLFE REPORT";
      }
      enum "report-bbel-fe" {
        value 16777250;
        description
          "PM BBELFE REPORT";
      }
      enum "report-bberl-fe" {
        value 16777251;
        description
          "PM ESFE REPORT";
      }
      enum "report-uasl-fe" {
        value 16777252;
        description
          "PM UASLFE REPORT";
      }
    }
    description
      "Stm report";
  }

  augment "/a1:interface-configurations/a1:interface-configuration" {
    description
      "This augment extends the configuration data of
       'Cisco-IOS-XR-ifmgr-cfg'";
    container performance-management {
      description
        "Configure pm parameters";
      container stm-hour24 {
        description
          "set STM threshold";
        container stm-hour24-stm {
          description
            "Configure stm performance monitoring";
          container stm-hour24-stm-reports {
            description
              "set stm TCA reporting status";
            list stm-hour24-stm-report {
              key "stm-report";
              description
                "none";
              leaf stm-report {
                type Stm-report;
                description
                  "Stm Report Type";
              }
              leaf enable {
                type Report;
                mandatory true;
                description
                  "Stm Report";
              }
            }
          }
          container stm-hour24-stm-thresholds {
            description
              "Configure threshold on stm parameters";
            list stm-hour24-stm-threshold {
              key "stm-threshold";
              description
                "none";
              leaf stm-threshold {
                type Stm-threshold;
                description
                  "Stm Threshold Type";
              }
              leaf stm-threshold-value {
                type uint32;
                mandatory true;
                description
                  "Stm Thresh Value";
              }
            }
          }
        }
      }
      container second30-gfp {
        description
          "set opr min threshold";
        container second30-gfp {
          description
            "Configure gfp performance monitoring";
          container second30-gfp-thresholds {
            description
              "Configure threshold on gfp parameters";
            list second30-gfp-threshold {
              key "gfp-threshold";
              description
                "none";
              leaf gfp-threshold {
                type Gfp-threshold;
                description
                  "Gfp Threshold Type";
              }
              leaf gfp-threshold-value {
                type uint32;
                mandatory true;
                description
                  "Gfp Threshold Value";
              }
            }
          }
          container second30-gfp-reports {
            description
              "set gfp TCA reporting status";
            list second30-gfp-report {
              key "gfp-report";
              description
                "none";
              leaf gfp-report {
                type Gfp-report;
                description
                  "Gfp Report Type";
              }
            }
          }
        }
      }
      container minute15-gfp {
        description
          "set opr min threshold";
        container minute15-gfp {
          description
            "Configure gfp performance monitoring";
          container minute15-gfp-reports {
            description
              "set gfp TCA reporting status";
            list minute15-gfp-report {
              key "gfp-report";
              description
                "none";
              leaf gfp-report {
                type Gfp-report;
                description
                  "Gfp Report Type";
              }
            }
          }
          container minute15-gfp-thresholds {
            description
              "Configure threshold on gfp parameters";
            list minute15-gfp-threshold {
              key "gfp-threshold";
              description
                "none";
              leaf gfp-threshold {
                type Gfp-threshold;
                description
                  "Gfp Threshold Type";
              }
              leaf gfp-threshold-value {
                type uint32;
                mandatory true;
                description
                  "Gfp Threshold Value";
              }
            }
          }
        }
      }
      container second30-path {
        description
          "set opr min threshold";
        container second30otn-path {
          description
            "configure otn g709 performance monitoring";
          container sec30-otn-path-threshes {
            description
              "Configure threshold on otn parameters";
            list sec30-otn-path-thresh {
              key "otn-threshold";
              description
                "none";
              leaf otn-threshold {
                type Otn-threshold;
                description
                  "Otn Threshold Type";
              }
              leaf otn-threshold-value {
                type uint32;
                mandatory true;
                description
                  "Otn Threshold Value";
              }
            }
          }
          container second30otn-path-reports {
            description
              "set otn TCA reporting status";
            list second30otn-path-report {
              key "otn-report";
              description
                "none";
              leaf otn-report {
                type Otn-report;
                description
                  "Otn Report Type";
              }
              leaf enable {
                type Report;
                mandatory true;
                description
                  "Otn Report";
              }
            }
          }
        }
      }
      container sonet-minute15 {
        description
          "set Sonet threshold";
        container sonet-minute15-path {
          description
            "Configure Path performance monitoring";
          container sonet-minute15-path-reports {
            description
              "set Path TCA reporting status";
            list sonet-minute15-path-report {
              key "path-report";
              description
                "none";
              leaf path-report {
                type Path-report;
                description
                  "Path Report Type";
              }
            }
          }
          container sonet-minute15-path-thresholds {
            description
              "Configure threshold on Path parameters";
            list sonet-minute15-path-threshold {
              key "path-threshold";
              description
                "none";
              leaf path-threshold {
                type Path-threshold;
                description
                  "Path Threshold Type";
              }
              leaf path-threshold-value {
                type uint32;
                mandatory true;
                description
                  "Path Threshold Value";
              }
            }
          }
        }
        container sonet-minute15-ocn {
          description
            "Configure ocn performance monitoring";
          container sonet-minute15-ocn-reports {
            description
              "set ocn TCA reporting status";
            list sonet-minute15-ocn-report {
              key "ocn-report";
              description
                "none";
              leaf ocn-report {
                type Ocn-report;
                description
                  "Ocn Report Type";
              }
            }
          }
          container sonet-minute15-ocn-thresholds {
            description
              "Configure threshold on ocn parameters";
            list sonet-minute15-ocn-threshold {
              key "ocn-threshold";
              description
                "none";
              leaf ocn-threshold {
                type Ocn-threshold;
                description
                  "Ocn Threshold Type";
              }
              leaf ocn-threshold-value {
                type uint32;
                mandatory true;
                description
                  "Ocn Threshold Value";
              }
            }
          }
        }
      }
      container hour24-gfp {
        description
          "Configure pm parameters of gfp 24 hour interval";
        container hour24-gfp {
          description
            "Configure gfp performance monitoring";
          container hour24-gfp-reports {
            description
              "set gfp TCA reporting status";
            list hour24-gfp-report {
              key "gfp-report";
              description
                "none";
              leaf gfp-report {
                type Gfp-report;
                description
                  "Gfp Report Type";
              }
            }
          }
          container hour24-gfp-thresholds {
            description
              "Configure threshold on gfp parameters";
            list hour24-gfp-threshold {
              key "gfp-threshold";
              description
                "none";
              leaf gfp-threshold {
                type Gfp-threshold;
                description
                  "Gfp Threshold Type";
              }
              leaf gfp-threshold-value {
                type uint32;
                mandatory true;
                description
                  "Gfp Thresh Value";
              }
            }
          }
        }
      }
      container second30otn-tcms {
        description
          "set opr min threshold";
        list second30otn-tcm {
          key "tcm-number";
          description
            "configure otn g709 tcm's performance
             monitoring";
          container sec30-otn-tcm-threshes {
            description
              "Configure threshold on otn parameters";
            list sec30-otn-tcm-thresh {
              key "otn-threshold";
              description
                "none";
              leaf otn-threshold {
                type Otn-tcm-threshold;
                description
                  "Otn Threshold Type";
              }
              leaf otn-threshold-value {
                type uint32;
                mandatory true;
                description
                  "Otn Threshold Value";
              }
            }
          }
          container second30otn-tcm-reports {
            description
              "set otn TCA reporting status";
            list second30otn-tcm-report {
              key "otn-report";
              description
                "none";
              leaf otn-report {
                type Otn-tcm-report;
                description
                  "Otn Report Type";
              }
              leaf enable {
                type Report;
                mandatory true;
                description
                  "Otn Report";
              }
            }
          }
          leaf tcm-number {
            type uint32;
            description
              "TCM number";
          }
        }
      }
      container ethernet-hour24 {
        description
          "Configure pm parameters of 24 hour interval";
        container hour24-ether {
          description
            "Configure ether performance monitoring";
          container hour24-ether-thresholds {
            description
              "Configure threshold on ether parameters";
            list hour24-ether-threshold {
              key "ether-threshold";
              description
                "none";
              leaf ether-threshold {
                type Ether-threshold;
                description
                  "Ether Threshold Type";
              }
              leaf ether-threshold-value {
                type uint32;
                mandatory true;
                description
                  "Ether Thresh Value";
              }
            }
          }
          container hour24-ether-reports {
            description
              "set ether TCA reporting status";
            list hour24-ether-report {
              key "ether-report";
              description
                "none";
              leaf ether-report {
                type Ether-report;
                description
                  "Ether Report Type";
              }
            }
          }
        }
      }
      container minute15otn-tcms {
        description
          "set opr min threshold";
        list minute15otn-tcm {
          key "tcm-number";
          description
            "configure otn g709 tcm's performance
             monitoring";
          container min15-otn-tcm-threshes {
            description
              "Configure threshold on otn parameters";
            list min15-otn-tcm-thresh {
              key "otn-threshold";
              description
                "none";
              leaf otn-threshold {
                type Otn-tcm-threshold;
                description
                  "Otn Threshold Type";
              }
              leaf otn-threshold-value {
                type uint32;
                mandatory true;
                description
                  "Otn Threshold Value";
              }
            }
          }
          container minute15otn-tcm-reports {
            description
              "set otn TCA reporting status";
            list minute15otn-tcm-report {
              key "otn-report";
              description
                "none";
              leaf otn-report {
                type Otn-tcm-report;
                description
                  "Otn Report Type";
              }
              leaf enable {
                type Report;
                mandatory true;
                description
                  "Otn Report";
              }
            }
          }
          leaf tcm-number {
            type uint32;
            description
              "TCM number";
          }
        }
      }
      container oc-hour24 {
        description
          "set Oc threshold";
        container oc-hour24-ocn {
          description
            "Configure ocn performance monitoring";
          container oc-hour24-ocn-reports {
            description
              "set ocn TCA reporting status";
            list oc-hour24-ocn-report {
              key "ocn-report";
              description
                "none";
              leaf ocn-report {
                type Ocn-report;
                description
                  "Ocn Report Type";
              }
              leaf enable {
                type Report;
                mandatory true;
                description
                  "Ocn Report";
              }
            }
          }
          container oc-hour24-ocn-thresholds {
            description
              "Configure threshold on ocn parameters";
            list oc-hour24-ocn-threshold {
              key "ocn-threshold";
              description
                "none";
              leaf ocn-threshold {
                type Ocn-threshold;
                description
                  "Ocn Threshold Type";
              }
              leaf ocn-threshold-value {
                type uint32;
                mandatory true;
                description
                  "Ocn Thresh Value";
              }
            }
          }
        }
      }
      container ethernet-minute15 {
        description
          "set opr min threshold";
        container minute15-ether {
          description
            "Configure ether performance monitoring";
          container minute15-ether-thresholds {
            description
              "Configure threshold on ether parameters";
            list minute15-ether-threshold {
              key "ether-threshold";
              description
                "none";
              leaf ether-threshold {
                type Ether-threshold;
                description
                  "Ether Threshold Type";
              }
              leaf ether-threshold-value {
                type uint32;
                mandatory true;
                description
                  "Ether Threshold Value";
              }
            }
          }
          container minute15-ether-reports {
            description
              "set ether TCA reporting status";
            list minute15-ether-report {
              key "ether-report";
              description
                "none";
              leaf ether-report {
                type Ether-report;
                description
                  "Ether Report Type";
              }
            }
          }
        }
      }
      container ho-vc-hour24 {
        description
          "set HO_VC threshold";
        container ho-vc-hour24ho-vc {
          description
            "Configure ho_vc performance monitoring";
          container ho-vc-hour24ho-vc-reports {
            description
              "set ho_vc TCA reporting status";
            list ho-vc-hour24ho-vc-report {
              key "ho-vc-report";
              description
                "none";
              leaf ho-vc-report {
                type Ho-vc-report;
                description
                  "ho_vc Report Type";
              }
              leaf enable {
                type Report;
                mandatory true;
                description
                  "ho_vc Report";
              }
            }
          }
          container ho-vc-hour24ho-vc-thresholds {
            description
              "Configure threshold on ho_vc parameters";
            list ho-vc-hour24ho-vc-threshold {
              key "ho-vc-threshold";
              description
                "none";
              leaf ho-vc-threshold {
                type Ho-vc-threshold;
                description
                  "ho_vc Threshold Type";
              }
              leaf ho-vc-threshold-value {
                type uint32;
                mandatory true;
                description
                  "ho_vc Thresh Value";
              }
            }
          }
        }
      }
      container second30 {
        description
          "Configure optics performance monitoring for 30
           sec";
        container second30cem {
          description
            "Configure cem performance monitoring";
          container second30cem-reports {
            description
              "set cem TCA reporting status";
            list second30cem-report {
              key "cem-report";
              description
                "none";
              leaf cem-report {
                type Cem-report;
                description
                  "CEM Report Type";
              }
            }
          }
          container second30cem-thresholds {
            description
              "Configure threshold on cem parameters";
            list second30cem-threshold {
              key "cem-threshold";
              description
                "none";
              leaf cem-threshold {
                type Cem-threshold;
                description
                  "CEM Threshold Type";
              }
              leaf cem-threshold-value {
                type uint32;
                mandatory true;
                description
                  "CEM Threshold Value";
              }
            }
          }
        }
        container second30otnsec {
          description
            "Configure otnsec performance monitoring";
          container second30otnsec-reports {
            description
              "set otnsec TCA reporting status";
            list second30otnsec-report {
              key "otnsec-report";
              description
                "none";
              leaf otnsec-report {
                type Otnsec-report;
                description
                  "OTNSEC pm Report Type";
              }
              leaf enable {
                type Report;
                mandatory true;
                description
                  "OTNSEC pm Report";
              }
            }
          }
          container second30otnsec-thresholds {
            description
              "Configure otnsec threshold";
            list second30otnsec-threshold {
              key "otnsec-threshold";
              description
                "none";
              leaf otnsec-threshold {
                type Otnsec-threshold;
                description
                  "OTNSEC Threshold Type";
              }
              leaf otnsec-threshold-value {
                type string {
                  length "1..20";
                }
                mandatory true;
                description
                  "OTNSEC Threshold Value";
              }
            }
          }
        }
        container second30pcs {
          description
            "Configure pcs performance monitoring";
          container second30pcs-thresholds {
            description
              "Configure pcs threshold";
            list second30pcs-threshold {
              key "pcs-threshold";
              description
                "none";
              leaf pcs-threshold {
                type Pcs-threshold;
                description
                  "Pcs Threshold Type";
              }
              leaf pcs-threshold-value {
                type string {
                  length "1..20";
                }
                mandatory true;
                description
                  "Pcs Threshold Value";
              }
            }
          }
          container second30pcs-reports {
            description
              "set pcs TCA reporting status";
            list second30pcs-report {
              key "pcs-report";
              description
                "none";
              leaf pcs-report {
                type Pcs-report;
                description
                  "Pcs Report Type";
              }
              leaf enable {
                type Report;
                mandatory true;
                description
                  "PCS Report";
              }
            }
          }
        }
        container second30fec {
          description
            "Configure fec g709 performance monitoring";
          container second30fec-thresholds {
            description
              "Configure fec threshold";
            list second30fec-threshold {
              key "fec-threshold";
              description
                "none";
              leaf fec-threshold {
                type Fec-threshold;
                description
                  "Fec Threshold Type";
              }
              leaf fec-threshold-value {
                type string {
                  length "1..20";
                }
                mandatory true;
                description
                  "Fec Threshold Value";
              }
            }
          }
          container second30fec-reports {
            description
              "set fec TCA reporting status";
            list second30fec-report {
              key "fec-report";
              description
                "none";
              leaf fec-report {
                type Fec-report;
                description
                  "Fec Report Type";
              }
              leaf enable {
                type Report;
                mandatory true;
                description
                  "Fec Report";
              }
            }
          }
        }
        container second30-optics {
          description
            "Configure optics performance monitoring";
          container second30-optics-reports {
            description
              "set optics TCA reporting status";
            list second30-optics-report {
              key "optics-report";
              description
                "none";
              leaf optics-report {
                type Optics-report;
                description
                  "Optics Report Type";
              }
            }
          }
          container second30-optics-thresholds {
            description
              "Configure threshold on optics parameters";
            list second30-optics-threshold {
              key "optics-threshold";
              description
                "none";
              leaf optics-threshold {
                type Optics-threshold;
                description
                  "Optics Threshold Type";
              }
              leaf optics-threshold-value {
                type int32;
                description
                  "Optics Thresh Value";
              }
              leaf dbm {
                type uint32;
                mandatory true;
                description
                  "Used only for Opt and Opr,To Enter
                   Threshold in dbm use 1";
              }
            }
          }
        }
        container second30secyif {
          description
            "Configure secy-if performance monitoring";
          container second30secyif-thresholds {
            description
              "Configure threshold on secyif parameters";
            list second30secyif-threshold {
              key "secyif-threshold";
              description
                "none";
              leaf secyif-threshold {
                type Secyif-threshold;
                description
                  "Secyif Threshold Type";
              }
              leaf secyif-threshold-value {
                type uint32;
                mandatory true;
                description
                  "Secyif Threshold Value";
              }
            }
          }
          container second30secyif-reports {
            description
              "set secyif TCA reporting status";
            list second30secyif-report {
              key "secyif-report";
              description
                "none";
              leaf secyif-report {
                type Secyif-report;
                description
                  "Secyif Report Type";
              }
              leaf enable {
                type Report;
                mandatory true;
                description
                  "Enabled Secyif Report";
              }
            }
          }
        }
        container second30secyrx {
          description
            "Configure secy-rx performance monitoring";
          container second30secyrx-thresholds {
            description
              "Configure threshold on secyrx parameters";
            list second30secyrx-threshold {
              key "secyrx-threshold";
              description
                "none";
              leaf secyrx-threshold {
                type Secyrx-threshold;
                description
                  "Secyrx Threshold Type";
              }
              leaf secyrx-threshold-value {
                type uint32;
                mandatory true;
                description
                  "Secyrx Threshold Value";
              }
            }
          }
          container second30secyrx-reports {
            description
              "set secyrx TCA reporting status";
            list second30secyrx-report {
              key "secyrx-report";
              description
                "none";
              leaf secyrx-report {
                type Secyrx-report;
                description
                  "Secyrx Report Type";
              }
              leaf enable {
                type Report;
                mandatory true;
                description
                  "Enabled Secyrx Report";
              }
            }
          }
        }
        container second30prbs {
          description
            "Configure prbs performance monitoring data";
          container second30prbs-thresholds {
            description
              "Configure prbs threshold";
            list second30prbs-threshold {
              key "prbs-threshold";
              description
                "none";
              leaf prbs-threshold {
                type Prbs-threshold;
                description
                  "Prbs Threshold Type";
              }
              leaf prbs-threshold-value {
                type string {
                  length "1..20";
                }
                mandatory true;
                description
                  "Prbs Threshold Value";
              }
            }
          }
          container second30prbs-reports {
            description
              "set prbs TCA reporting status";
            list second30prbs-report {
              key "prbs-report";
              description
                "none";
              leaf prbs-report {
                type Prbs-report;
                description
                  "Prbs Report Type";
              }
              leaf enable {
                type Report;
                mandatory true;
                description
                  "Prbs Report";
              }
            }
          }
        }
        container second30otn {
          description
            "configure otn g709 performance monitoring";
          container second30-otn-threshes {
            description
              "Configure threshold on otn parameters";
            list second30-otn-thresh {
              key "otn-threshold";
              description
                "none";
              leaf otn-threshold {
                type Otn-threshold;
                description
                  "Otn Threshold Type";
              }
              leaf otn-threshold-value {
                type uint32;
                mandatory true;
                description
                  "Otn Threshold Value";
              }
            }
          }
          container second30otn-reports {
            description
              "set otn TCA reporting status";
            list second30otn-report {
              key "otn-report";
              description
                "none";
              leaf otn-report {
                type Otn-report;
                description
                  "Otn Report Type";
              }
              leaf enable {
                type Report;
                mandatory true;
                description
                  "Otn Report";
              }
            }
          }
        }
        container second30secytx {
          description
            "Configure secy-tx performance monitoring";
          container second30secytx-thresholds {
            description
              "Configure threshold on secytx parameters";
            list second30secytx-threshold {
              key "secytx-threshold";
              description
                "none";
              leaf secytx-threshold {
                type Secytx-threshold;
                description
                  "Secytx Threshold Type";
              }
              leaf secytx-threshold-value {
                type uint32;
                mandatory true;
                description
                  "Secytx Threshold Value";
              }
            }
          }
          container second30secytx-reports {
            description
              "set secytx TCA reporting status";
            list second30secytx-report {
              key "secytx-report";
              description
                "none";
              leaf secytx-report {
                type Secytx-report;
                description
                  "Secytx Report Type";
              }
              leaf enable {
                type Report;
                mandatory true;
                description
                  "Enabled Secytx Report";
              }
            }
          }
        }
        container second30fc {
          description
            "Configure fc performance monitoring";
          container second30fc-thresholds {
            description
              "Configure threshold on fc parameters";
            list second30fc-threshold {
              key "fc-threshold";
              description
                "none";
              leaf fc-threshold {
                type Fc-threshold;
                description
                  "Fc Threshold Type";
              }
              leaf fc-threshold-value {
                type uint32;
                mandatory true;
                description
                  "Fc Threshold Value";
              }
            }
          }
          container second30fc-reports {
            description
              "set fc TCA reporting status";
            list second30fc-report {
              key "fc-report";
              description
                "none";
              leaf fc-report {
                type Fc-report;
                description
                  "Fc Report Type";
              }
            }
          }
        }
      }
      container hour24otn-tcms {
        description
          "Configure pm parameters of tcm's 24 hour
           interval";
        list hour24otn-tcm {
          key "tcm-number";
          description
            "configure otn g709 tcm's performance
             monitoring";
          container hour24otn-tcm-thresholds {
            description
              "Configure threshold on otn parameters";
            list hour24otn-tcm-threshold {
              key "otn-threshold";
              description
                "none";
              leaf otn-threshold {
                type Otn-tcm-threshold;
                description
                  "Otn Threshold Type";
              }
              leaf otn-threshold-value {
                type uint32;
                mandatory true;
                description
                  "Otn Threshold Value";
              }
            }
          }
          container hour24otn-tcm-reports {
            description
              "set otn TCA reporting status";
            list hour24otn-tcm-report {
              key "otn-report";
              description
                "none";
              leaf otn-report {
                type Otn-tcm-report;
                description
                  "Otn Report Type";
              }
              leaf enable {
                type Report;
                mandatory true;
                description
                  "Otn Report";
              }
            }
          }
          leaf tcm-number {
            type uint32;
            description
              "TCM number";
          }
        }
      }
      container sts-minute15 {
        description
          "set STS threshold";
        container sts-minute15-path {
          description
            "Configure Path performance monitoring";
          container sts-minute15-path-reports {
            description
              "set Path TCA reporting status";
            list sts-minute15-path-report {
              key "path-report";
              description
                "none";
              leaf path-report {
                type Sts-report;
                description
                  "Path Report Type";
              }
              leaf enable {
                type Report;
                mandatory true;
                description
                  "Path Report";
              }
            }
          }
          container sts-minute15-path-thresholds {
            description
              "Configure threshold on Path parameters";
            list sts-minute15-path-threshold {
              key "path-threshold";
              description
                "none";
              leaf path-threshold {
                type Sts-threshold;
                description
                  "Path Threshold Type";
              }
              leaf path-threshold-value {
                type uint32;
                mandatory true;
                description
                  "Path Threshold Value";
              }
            }
          }
        }
      }
      container hour24 {
        description
          "Configure pm parameters of 24 hour interval";
        container hour24otn {
          description
            "configure otn g709 performance monitoring";
          container hour24otn-thresholds {
            description
              "Configure threshold on otn parameters";
            list hour24otn-threshold {
              key "otn-threshold";
              description
                "none";
              leaf otn-threshold {
                type Otn-threshold;
                description
                  "Otn Threshold Type";
              }
              leaf otn-threshold-value {
                type uint32;
                mandatory true;
                description
                  "Otn Threshold Value";
              }
            }
          }
          container hour24otn-reports {
            description
              "set otn TCA reporting status";
            list hour24otn-report {
              key "otn-report";
              description
                "none";
              leaf otn-report {
                type Otn-report;
                description
                  "Otn Report Type";
              }
              leaf enable {
                type Report;
                mandatory true;
                description
                  "Otn Report";
              }
            }
          }
        }
        container hour24fc {
          description
            "Configure fc performance monitoring";
          container hour24fc-reports {
            description
              "set fc TCA reporting status";
            list hour24fc-report {
              key "fc-report";
              description
                "none";
              leaf fc-report {
                type Fc-report;
                description
                  "Fc Report Type";
              }
            }
          }
          container hour24fc-thresholds {
            description
              "Configure threshold on fc parameters";
            list hour24fc-threshold {
              key "fc-threshold";
              description
                "none";
              leaf fc-threshold {
                type Fc-threshold;
                description
                  "Fc Threshold Type";
              }
              leaf fc-threshold-value {
                type uint32;
                mandatory true;
                description
                  "Fc Thresh Value";
              }
            }
          }
        }
        container hour24cem {
          description
            "Configure cem performance monitoring";
          container hour24cem-reports {
            description
              "set cem TCA reporting status";
            list hour24cem-report {
              key "cem-report";
              description
                "none";
              leaf cem-report {
                type Cem-report;
                description
                  "CEM Report Type";
              }
            }
          }
          container hour24cem-thresholds {
            description
              "Configure threshold on cem parameters";
            list hour24cem-threshold {
              key "cem-threshold";
              description
                "none";
              leaf cem-threshold {
                type Cem-threshold;
                description
                  "CEM Threshold Type";
              }
              leaf cem-threshold-value {
                type uint32;
                mandatory true;
                description
                  "CEM Thresh Value";
              }
            }
          }
        }
        container hour24-optics {
          description
            "Configure optics performance monitoring";
          container hour24-optics-thresholds {
            description
              "Configure threshold on optics parameters";
            list hour24-optics-threshold {
              key "optics-threshold";
              description
                "none";
              leaf optics-threshold {
                type Optics-threshold;
                description
                  "Optics Threshold Type";
              }
              leaf optics-threshold-value {
                type int32;
                description
                  "Optics Thresh Value";
              }
              leaf dbm {
                type uint32;
                mandatory true;
                description
                  "Used only for Opt and Opr,To Enter
                   Threshold in dbm use 1";
              }
            }
          }
          container hour24-optics-reports {
            description
              "set optics TCA reporting status";
            list hour24-optics-report {
              key "optics-report";
              description
                "none";
              leaf optics-report {
                type Optics-report;
                description
                  "Optics Report Type";
              }
            }
          }
        }
        container hour24pcs {
          description
            "Configure pcs performance monitoring";
          container hour24pcs-thresholds {
            description
              "Configure pcs threshold";
            list hour24pcs-threshold {
              key "pcs-threshold";
              description
                "none";
              leaf pcs-threshold {
                type Pcs-threshold;
                description
                  "Pcs Threshold Type";
              }
              leaf pcs-threshold-value {
                type string {
                  length "1..20";
                }
                mandatory true;
                description
                  "Pcs Threshold Value";
              }
            }
          }
          container hour24pcs-reports {
            description
              "set pcs TCA reporting status";
            list hour24pcs-report {
              key "pcs-report";
              description
                "none";
              leaf pcs-report {
                type Pcs-report;
                description
                  "Pcs Report Type";
              }
              leaf enable {
                type Report;
                mandatory true;
                description
                  "PCS Report";
              }
            }
          }
        }
        container hour24fec {
          description
            "Configure fec g709 performance monitoring";
          container hour24fec-thresholds {
            description
              "Configure fec threshold";
            list hour24fec-threshold {
              key "fec-threshold";
              description
                "none";
              leaf fec-threshold {
                type Fec-threshold;
                description
                  "Fec Threshold Type";
              }
              leaf fec-threshold-value {
                type string {
                  length "1..20";
                }
                mandatory true;
                description
                  "Fec threshold value";
              }
            }
          }
          container hour24fec-reports {
            description
              "set fec TCA reporting status";
            list hour24fec-report {
              key "fec-report";
              description
                "none";
              leaf fec-report {
                type Fec-report;
                description
                  "Fec Report type";
              }
              leaf enable {
                type Report;
                mandatory true;
                description
                  "Fec Report";
              }
            }
          }
        }
        container hour24secyif {
          description
            "Configure secy-if performance monitoring";
          container hour24secyif-reports {
            description
              "set secyif TCA reporting status";
            list hour24secyif-report {
              key "secyif-report";
              description
                "none";
              leaf secyif-report {
                type Secyif-report;
                description
                  "Secyif Report type";
              }
              leaf enable {
                type Report;
                mandatory true;
                description
                  "Secyif Report";
              }
            }
          }
          container hour24secyif-thresholds {
            description
              "Configure secyif threshold";
            list hour24secyif-threshold {
              key "secyif-threshold";
              description
                "none";
              leaf secyif-threshold {
                type Secyif-threshold;
                description
                  "Secyif Threshold Type";
              }
              leaf secyif-threshold-value {
                type uint32;
                mandatory true;
                description
                  "Secyif threshold value";
              }
            }
          }
        }
        container hour24e1 {
          description
            "Configure e1 performance monitoring";
          container hour24e1-thresholds {
            description
              "Configure e1 threshold";
            list hour24e1-threshold {
              key "e1-threshold";
              description
                "none";
              leaf e1-threshold {
                type E1-threshold;
                description
                  "E1 Threshold Type";
              }
              leaf e1-threshold-value {
                type uint32;
                mandatory true;
                description
                  "E1 Threshold Value";
              }
            }
          }
          container hour24e1-reports {
            description
              "set e1 TCA reporting status";
            list hour24e1-report {
              key "e1-report";
              description
                "none";
              leaf e1-report {
                type E1-report;
                description
                  "E1 Report Type";
              }
              leaf enable {
                type Report;
                mandatory true;
                description
                  "E1 Report";
              }
            }
          }
        }
        container hour24secyrx {
          description
            "Configure secy-rx performance monitoring";
          container hour24secyrx-reports {
            description
              "set secyrx TCA reporting status";
            list hour24secyrx-report {
              key "secyrx-report";
              description
                "none";
              leaf secyrx-report {
                type Secyrx-report;
                description
                  "Secyrx Report type";
              }
              leaf enable {
                type Report;
                mandatory true;
                description
                  "Secyrx Report";
              }
            }
          }
          container hour24secyrx-thresholds {
            description
              "Configure secyrx threshold";
            list hour24secyrx-threshold {
              key "secyrx-threshold";
              description
                "none";
              leaf secyrx-threshold {
                type Secyrx-threshold;
                description
                  "Secyrx Threshold Type";
              }
              leaf secyrx-threshold-value {
                type uint32;
                mandatory true;
                description
                  "Secyrx threshold value";
              }
            }
          }
        }
        container hour24secytx {
          description
            "Configure secy-tx performance monitoring";
          container hour24secytx-thresholds {
            description
              "Configure secytx threshold";
            list hour24secytx-threshold {
              key "secytx-threshold";
              description
                "none";
              leaf secytx-threshold {
                type Secytx-threshold;
                description
                  "Secytx Threshold Type";
              }
              leaf secytx-threshold-value {
                type uint32;
                mandatory true;
                description
                  "Secytx threshold value";
              }
            }
          }
          container hour24secytx-reports {
            description
              "set secytx TCA reporting status";
            list hour24secytx-report {
              key "secytx-report";
              description
                "none";
              leaf secytx-report {
                type Secytx-report;
                description
                  "Secytx Report type";
              }
              leaf enable {
                type Report;
                mandatory true;
                description
                  "Secytx Report";
              }
            }
          }
        }
        container hour24prbs {
          description
            "Configure prbs performance monitoring data";
          container hour24prbs-thresholds {
            description
              "Configure prbs threshold";
            list hour24prbs-threshold {
              key "prbs-threshold";
              description
                "none";
              leaf prbs-threshold {
                type Prbs-threshold;
                description
                  "Prbs Threshold Type";
              }
              leaf prbs-threshold-value {
                type string {
                  length "1..20";
                }
                mandatory true;
                description
                  "PRBS threshold value";
              }
            }
          }
          container hour24prbs-reports {
            description
              "set prbs TCA reporting status";
            list hour24prbs-report {
              key "prbs-report";
              description
                "none";
              leaf prbs-report {
                type Prbs-report;
                description
                  "Prbs Report type";
              }
              leaf enable {
                type Report;
                mandatory true;
                description
                  "Prbs Report";
              }
            }
          }
        }
        container hour24otnsec {
          description
            "Configure otnsec performance monitoring";
          container hour24otnsec-reports {
            description
              "set otnsec TCA reporting status";
            list hour24otnsec-report {
              key "otnsec-report";
              description
                "none";
              leaf otnsec-report {
                type Otnsec-report;
                description
                  "OTNSEC Report Type";
              }
              leaf enable {
                type Report;
                mandatory true;
                description
                  "OTNSEC Report";
              }
            }
          }
          container hour24otnsec-thresholds {
            description
              "Configure otnsec threshold";
            list hour24otnsec-threshold {
              key "otnsec-threshold";
              description
                "none";
              leaf otnsec-threshold {
                type Otnsec-threshold;
                description
                  "OTNSEC Threshold Type";
              }
              leaf otnsec-threshold-value {
                type string {
                  length "1..20";
                }
                mandatory true;
                description
                  "OTNSEC Threshold Value";
              }
            }
          }
        }
      }
      container ho-vc-minute15 {
        description
          "set HO_VC threshold";
        container ho-vc-minute15ho-vc {
          description
            "Configure ho_vc performance monitoring";
          container ho-vc-minute15ho-vc-reports {
            description
              "set ho_vc TCA reporting status";
            list ho-vc-minute15ho-vc-report {
              key "ho-vc-report";
              description
                "none";
              leaf ho-vc-report {
                type Ho-vc-report;
                description
                  "ho_vc Report Type";
              }
              leaf enable {
                type Report;
                mandatory true;
                description
                  "ho_vc Report";
              }
            }
          }
          container ho-vc-minute15ho-vc-thresholds {
            description
              "Configure threshold on ho_vc parameters";
            list ho-vc-minute15ho-vc-threshold {
              key "ho-vc-threshold";
              description
                "none";
              leaf ho-vc-threshold {
                type Ho-vc-threshold;
                description
                  "ho_vc Threshold Type";
              }
              leaf ho-vc-threshold-value {
                type uint32;
                mandatory true;
                description
                  "ho_vc Threshold Value";
              }
            }
          }
        }
      }
      container sts-hour24 {
        description
          "set STS threshold";
        container sts-hour24-path {
          description
            "Configure Path performance monitoring";
          container sts-hour24-path-thresholds {
            description
              "Configure threshold on Path parameters";
            list sts-hour24-path-threshold {
              key "path-threshold";
              description
                "none";
              leaf path-threshold {
                type Sts-threshold;
                description
                  "Path Threshold Type";
              }
              leaf path-threshold-value {
                type uint32;
                mandatory true;
                description
                  "Path Thresh Value";
              }
            }
          }
          container sts-hour24-path-reports {
            description
              "set Path TCA reporting status";
            list sts-hour24-path-report {
              key "path-report";
              description
                "none";
              leaf path-report {
                type Sts-report;
                description
                  "Path Report Type";
              }
              leaf enable {
                type Report;
                mandatory true;
                description
                  "Path Report";
              }
            }
          }
        }
      }
      container stm-minute15 {
        description
          "set STM threshold";
        container stm-minute15-stm {
          description
            "Configure stm performance monitoring";
          container stm-minute15-stm-reports {
            description
              "set stm TCA reporting status";
            list stm-minute15-stm-report {
              key "stm-report";
              description
                "none";
              leaf stm-report {
                type Stm-report;
                description
                  "Stm Report Type";
              }
              leaf enable {
                type Report;
                mandatory true;
                description
                  "Stm Report";
              }
            }
          }
          container stm-minute15-stm-thresholds {
            description
              "Configure threshold on stm parameters";
            list stm-minute15-stm-threshold {
              key "stm-threshold";
              description
                "none";
              leaf stm-threshold {
                type Stm-threshold;
                description
                  "Stm Threshold Type";
              }
              leaf stm-threshold-value {
                type uint32;
                mandatory true;
                description
                  "Stm Threshold Value";
              }
            }
          }
        }
      }
      container sonet-hour24 {
        description
          "set Sonet threshold";
        container sonet-hour24-path {
          description
            "Configure Path performance monitoring";
          container sonet-hour24-path-thresholds {
            description
              "Configure threshold on Path parameters";
            list sonet-hour24-path-threshold {
              key "path-threshold";
              description
                "none";
              leaf path-threshold {
                type Path-threshold;
                description
                  "Path Threshold Type";
              }
              leaf path-threshold-value {
                type uint32;
                mandatory true;
                description
                  "Path Thresh Value";
              }
            }
          }
          container sonet-hour24-path-reports {
            description
              "set Path TCA reporting status";
            list sonet-hour24-path-report {
              key "path-report";
              description
                "none";
              leaf path-report {
                type Path-report;
                description
                  "Path Report Type";
              }
            }
          }
        }
        container sonet-hour24-ocn {
          description
            "Configure ocn performance monitoring";
          container sonet-hour24-ocn-thresholds {
            description
              "Configure threshold on ocn parameters";
            list sonet-hour24-ocn-threshold {
              key "ocn-threshold";
              description
                "none";
              leaf ocn-threshold {
                type Ocn-threshold;
                description
                  "Ocn Threshold Type";
              }
              leaf ocn-threshold-value {
                type uint32;
                mandatory true;
                description
                  "Ocn Thresh Value";
              }
            }
          }
          container sonet-hour24-ocn-reports {
            description
              "set ocn TCA reporting status";
            list sonet-hour24-ocn-report {
              key "ocn-report";
              description
                "none";
              leaf ocn-report {
                type Ocn-report;
                description
                  "Ocn Report Type";
              }
            }
          }
        }
      }
      container minute15-path {
        description
          "set opr min threshold";
        container minute15otn-path {
          description
            "configure otn g709 performance monitoring";
          container minute15otn-path-reports {
            description
              "set otn TCA reporting status";
            list minute15otn-path-report {
              key "otn-report";
              description
                "none";
              leaf otn-report {
                type Otn-report;
                description
                  "Otn Report Type";
              }
              leaf enable {
                type Report;
                mandatory true;
                description
                  "Otn Report";
              }
            }
          }
          container min15-otn-path-threshes {
            description
              "Configure threshold on otn parameters";
            list min15-otn-path-thresh {
              key "otn-threshold";
              description
                "none";
              leaf otn-threshold {
                type Otn-threshold;
                description
                  "Otn Threshold Type";
              }
              leaf otn-threshold-value {
                type uint32;
                mandatory true;
                description
                  "Otn Threshold Value";
              }
            }
          }
        }
      }
      container oc-minute15 {
        description
          "set OC threshold";
        container oc-minute15-ocn {
          description
            "Configure ocn performance monitoring";
          container oc-minute15-ocn-reports {
            description
              "set ocn TCA reporting status";
            list oc-minute15-ocn-report {
              key "ocn-report";
              description
                "none";
              leaf ocn-report {
                type Ocn-report;
                description
                  "Ocn Report Type";
              }
              leaf enable {
                type Report;
                mandatory true;
                description
                  "Ocn Report";
              }
            }
          }
          container oc-minute15-ocn-thresholds {
            description
              "Configure threshold on ocn parameters";
            list oc-minute15-ocn-threshold {
              key "ocn-threshold";
              description
                "none";
              leaf ocn-threshold {
                type Ocn-threshold;
                description
                  "Ocn Threshold Type";
              }
              leaf ocn-threshold-value {
                type uint32;
                mandatory true;
                description
                  "Ocn Threshold Value";
              }
            }
          }
        }
      }
      container ethernet-second30 {
        description
          "Configure ethernet performance monitoring for
           30 sec";
        container second30-ether {
          description
            "Configure ether performance monitoring";
          container second30-ether-thresholds {
            description
              "Configure threshold on ether parameters";
            list second30-ether-threshold {
              key "ether-threshold";
              description
                "none";
              leaf ether-threshold {
                type Ether-threshold;
                description
                  "Ether Threshold Type";
              }
              leaf ether-threshold-value {
                type uint32;
                mandatory true;
                description
                  "Ether Threshold Value";
              }
            }
          }
          container second30-ether-reports {
            description
              "set ether TCA reporting status";
            list second30-ether-report {
              key "ether-report";
              description
                "none";
              leaf ether-report {
                type Ether-report;
                description
                  "Ether Report Type";
              }
            }
          }
        }
      }
      container hour24-path {
        description
          "Configure pm parameters of pathmonitor 24 hour
           interval";
        container hour24otn-path {
          description
            "configure otn g709 performance monitoring";
          container hour24otn-path-reports {
            description
              "set otn TCA reporting status";
            list hour24otn-path-report {
              key "otn-report";
              description
                "none";
              leaf otn-report {
                type Otn-report;
                description
                  "Otn Report Type";
              }
              leaf enable {
                type Report;
                mandatory true;
                description
                  "Otn Report";
              }
            }
          }
          container hour24otn-path-thresholds {
            description
              "Configure threshold on otn parameters";
            list hour24otn-path-threshold {
              key "otn-threshold";
              description
                "none";
              leaf otn-threshold {
                type Otn-threshold;
                description
                  "Otn Threshold Type";
              }
              leaf otn-threshold-value {
                type uint32;
                mandatory true;
                description
                  "Otn Threshold Value";
              }
            }
          }
        }
      }
      container minute15 {
        description
          "set opr min threshold";
        container minute15cem {
          description
            "Configure cem performance monitoring";
          container minute15cem-reports {
            description
              "set cem TCA reporting status";
            list minute15cem-report {
              key "cem-report";
              description
                "none";
              leaf cem-report {
                type Cem-report;
                description
                  "CEM Report Type";
              }
            }
          }
          container minute15cem-thresholds {
            description
              "Configure threshold on cem parameters";
            list minute15cem-threshold {
              key "cem-threshold";
              description
                "none";
              leaf cem-threshold {
                type Cem-threshold;
                description
                  "CEM Threshold Type";
              }
              leaf cem-threshold-value {
                type uint32;
                mandatory true;
                description
                  "CEM Threshold Value";
              }
            }
          }
        }
        container minute15e1 {
          description
            "Configure e1 performance monitoring";
          container minute15e1-thresholds {
            description
              "Configure e1 threshold";
            list minute15e1-threshold {
              key "e1-threshold";
              description
                "none";
              leaf e1-threshold {
                type E1-threshold;
                description
                  "E1 Threshold Type";
              }
              leaf e1-threshold-value {
                type uint32;
                mandatory true;
                description
                  "E1 Threshold Value";
              }
            }
          }
          container minute15e1-reports {
            description
              "set e1 TCA reporting status";
            list minute15e1-report {
              key "e1-report";
              description
                "none";
              leaf e1-report {
                type E1-report;
                description
                  "E1 Report Type";
              }
              leaf enable {
                type Report;
                mandatory true;
                description
                  "E1 Report";
              }
            }
          }
        }
        container minute15-optics {
          description
            "Configure optics performance monitoring";
          container minute15-optics-thresholds {
            description
              "Configure threshold on optics parameters";
            list minute15-optics-threshold {
              key "optics-threshold";
              description
                "none";
              leaf optics-threshold {
                type Optics-threshold;
                description
                  "Optics Threshold Type";
              }
              leaf optics-threshold-value {
                type int32;
                description
                  "Optics Threshold Value";
              }
              leaf dbm {
                type uint32;
                mandatory true;
                description
                  "Used only for Opt and Opr,To Enter
                   Threshold in dbm use 1";
              }
            }
          }
          container minute15-optics-reports {
            description
              "set optics TCA reporting status";
            list minute15-optics-report {
              key "optics-report";
              description
                "none";
              leaf optics-report {
                type Optics-report;
                description
                  "Optics Report Type";
              }
            }
          }
        }
        container minute15secyif {
          description
            "Configure secy-if performance monitoring";
          container minute15secyif-reports {
            description
              "set secyif TCA reporting status";
            list minute15secyif-report {
              key "secyif-report";
              description
                "none";
              leaf secyif-report {
                type Secyif-report;
                description
                  "Secyif Report Type";
              }
              leaf enable {
                type Report;
                mandatory true;
                description
                  "Enabled Secyif Report";
              }
            }
          }
          container minute15secyif-thresholds {
            description
              "Configure threshold on secyif parameters";
            list minute15secyif-threshold {
              key "secyif-threshold";
              description
                "none";
              leaf secyif-threshold {
                type Secyif-threshold;
                description
                  "Secyif Threshold Type";
              }
              leaf secyif-threshold-value {
                type uint32;
                mandatory true;
                description
                  "Secyif Threshold Value";
              }
            }
          }
        }
        container minute15secyrx {
          description
            "Configure secy-rx performance monitoring";
          container minute15secyrx-reports {
            description
              "set secyrx TCA reporting status";
            list minute15secyrx-report {
              key "secyrx-report";
              description
                "none";
              leaf secyrx-report {
                type Secyrx-report;
                description
                  "Secyrx Report Type";
              }
              leaf enable {
                type Report;
                mandatory true;
                description
                  "Enabled Secyrx Report";
              }
            }
          }
          container minute15secyrx-thresholds {
            description
              "Configure threshold on secyrx parameters";
            list minute15secyrx-threshold {
              key "secyrx-threshold";
              description
                "none";
              leaf secyrx-threshold {
                type Secyrx-threshold;
                description
                  "Secyrx Threshold Type";
              }
              leaf secyrx-threshold-value {
                type uint32;
                mandatory true;
                description
                  "Secyrx Threshold Value";
              }
            }
          }
        }
        container minute15pcs {
          description
            "Configure pcs performance monitoring";
          container minute15pcs-reports {
            description
              "set pcs TCA reporting status";
            list minute15pcs-report {
              key "pcs-report";
              description
                "none";
              leaf pcs-report {
                type Pcs-report;
                description
                  "Pcs Report Type";
              }
              leaf enable {
                type Report;
                mandatory true;
                description
                  "PCS Report";
              }
            }
          }
          container minute15pcs-thresholds {
            description
              "Configure pcs threshold";
            list minute15pcs-threshold {
              key "pcs-threshold";
              description
                "none";
              leaf pcs-threshold {
                type Pcs-threshold;
                description
                  "Pcs Threshold Type";
              }
              leaf pcs-threshold-value {
                type string {
                  length "1..20";
                }
                mandatory true;
                description
                  "Pcs Threshold Value";
              }
            }
          }
        }
        container minute15fec {
          description
            "Configure fec g709 performance monitoring";
          container minute15fec-thresholds {
            description
              "Configure fec threshold";
            list minute15fec-threshold {
              key "fec-threshold";
              description
                "none";
              leaf fec-threshold {
                type Fec-threshold;
                description
                  "Fec Threshold Type";
              }
              leaf fec-threshold-value {
                type string {
                  length "1..20";
                }
                mandatory true;
                description
                  "Fec Threshold Value";
              }
            }
          }
          container minute15fec-reports {
            description
              "set fec TCA reporting status";
            list minute15fec-report {
              key "fec-report";
              description
                "none";
              leaf fec-report {
                type Fec-report;
                description
                  "Fec Report Type";
              }
              leaf enable {
                type Report;
                mandatory true;
                description
                  "Fec Report";
              }
            }
          }
        }
        container minute15secytx {
          description
            "Configure secy-tx performance monitoring";
          container minute15secytx-reports {
            description
              "set secytx TCA reporting status";
            list minute15secytx-report {
              key "secytx-report";
              description
                "none";
              leaf secytx-report {
                type Secytx-report;
                description
                  "Secytx Report Type";
              }
              leaf enable {
                type Report;
                mandatory true;
                description
                  "Enabled Secytx Report";
              }
            }
          }
          container minute15secytx-thresholds {
            description
              "Configure threshold on secytx parameters";
            list minute15secytx-threshold {
              key "secytx-threshold";
              description
                "none";
              leaf secytx-threshold {
                type Secytx-threshold;
                description
                  "Secytx Threshold Type";
              }
              leaf secytx-threshold-value {
                type uint32;
                mandatory true;
                description
                  "Secytx Threshold Value";
              }
            }
          }
        }
        container minute15fc {
          description
            "Configure fc performance monitoring";
          container minute15fc-reports {
            description
              "set fc TCA reporting status";
            list minute15fc-report {
              key "fc-report";
              description
                "none";
              leaf fc-report {
                type Fc-report;
                description
                  "Fc Report Type";
              }
            }
          }
          container minute15fc-thresholds {
            description
              "Configure threshold on fc parameters";
            list minute15fc-threshold {
              key "fc-threshold";
              description
                "none";
              leaf fc-threshold {
                type Fc-threshold;
                description
                  "Fc Threshold Type";
              }
              leaf fc-threshold-value {
                type uint32;
                mandatory true;
                description
                  "Fc Threshold Value";
              }
            }
          }
        }
        container minute15otnsec {
          description
            "Configure otnsec performance monitoring";
          container minute15otnsec-thresholds {
            description
              "Configure otnsec threshold";
            list minute15otnsec-threshold {
              key "otnsec-threshold";
              description
                "none";
              leaf otnsec-threshold {
                type Otnsec-threshold;
                description
                  "OTNSEC Threshold Type";
              }
              leaf otnsec-threshold-value {
                type string {
                  length "1..20";
                }
                mandatory true;
                description
                  "OTNSEC Threshold Value";
              }
            }
          }
          container minute15otnsec-reports {
            description
              "set otnsec TCA reporting status";
            list minute15otnsec-report {
              key "otnsec-report";
              description
                "none";
              leaf otnsec-report {
                type Otnsec-report;
                description
                  "OTNSEC Report Type";
              }
              leaf enable {
                type Report;
                mandatory true;
                description
                  "OTNSEC Report";
              }
            }
          }
        }
        container minute15prbs {
          description
            "Configure prbs performance monitoring data";
          container minute15prbs-reports {
            description
              "set prbs TCA reporting status";
            list minute15prbs-report {
              key "prbs-report";
              description
                "none";
              leaf prbs-report {
                type Prbs-report;
                description
                  "Prbs Report Type";
              }
              leaf enable {
                type Report;
                mandatory true;
                description
                  "Prbs Report";
              }
            }
          }
          container minute15prbs-thresholds {
            description
              "Configure prbs threshold";
            list minute15prbs-threshold {
              key "prbs-threshold";
              description
                "none";
              leaf prbs-threshold {
                type Prbs-threshold;
                description
                  "Prbs Threshold Type";
              }
              leaf prbs-threshold-value {
                type string {
                  length "1..20";
                }
                mandatory true;
                description
                  "Prbs Threshold Value";
              }
            }
          }
        }
        container minute15otn {
          description
            "configure otn g709 performance monitoring";
          container min15-otn-threshes {
            description
              "Configure threshold on otn parameters";
            list min15-otn-thresh {
              key "otn-threshold";
              description
                "none";
              leaf otn-threshold {
                type Otn-threshold;
                description
                  "Otn Threshold Type";
              }
              leaf otn-threshold-value {
                type uint32;
                mandatory true;
                description
                  "Otn Threshold Value";
              }
            }
          }
          container minute15otn-reports {
            description
              "set otn TCA reporting status";
            list minute15otn-report {
              key "otn-report";
              description
                "none";
              leaf otn-report {
                type Otn-report;
                description
                  "Otn Report Type";
              }
              leaf enable {
                type Report;
                mandatory true;
                description
                  "Otn Report";
              }
            }
          }
        }
      }
    }
  }
}
