module Cisco-IOS-XR-optics-server-configurability-profiles-oper {
  namespace "http://cisco.com/ns/yang/Cisco-IOS-XR-optics-server-configurability-profiles-oper";
  prefix optics-server-configurability-profiles-oper;

  import cisco-semver {
    prefix semver;
  }
  include Cisco-IOS-XR-optics-server-configurability-profiles-oper-sub1 {
    revision-date 2025-03-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-server-configurability-profiles package operational data.
     
     This module contains definitions
     for the following management objects:
       configurability-oper: Configurability profile data
     
     Copyright (c) 2013-2025 by Cisco Systems, Inc.
     All rights reserved.";

  revision 2025-03-27 {
    description
      "Schema added.";
    semver:module-version "1.0.0";
  }
  revision 2019-04-05 {
    description
      "Establish semantic version baseline.";
  }
  revision 2015-11-09 {
    description
      "IOS XR 6.0 revision.";
  }

  container configurability-oper {
    config false;
    description
      "Configurability profile data";
    container configurability {
      description
        "Configurability profile data";
      uses OPTICS-CONFIGURABILITY-SHOW;
    }
  }
}
