module Cisco-IOS-XR-man-ems-oper {
  namespace "http://cisco.com/ns/yang/Cisco-IOS-XR-man-ems-oper";
  prefix man-ems-oper;

  import Cisco-IOS-XR-types {
    prefix xr;
  }
  import cisco-semver {
    prefix semver;
  }
  include Cisco-IOS-XR-man-ems-oper-sub2 {
    revision-date 2026-07-08;
  }
  include Cisco-IOS-XR-man-ems-oper-sub1 {
    revision-date 2026-07-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR man-ems package operational data.
     
     This module contains definitions
     for the following management objects:
       grpc: grpc commands
     
     Copyright (c) 2013-2026 by Cisco Systems, Inc.
     All rights reserved.";

  revision 2026-07-08 {
    description
      "Added pre-authentication connection gating counters to gRPC server state";
    semver:module-version "2.1.0";
  }
  revision 2025-04-28 {
    description
      "Removed status container under grpc.
       2024-08-28
          Added yang support for show grpc services
       2024-07-16
          Added support to view tls versions
       2024-03-03
          Added SRTE session list
       2023-12-18
          Added 'key' statement to list node 'destination'.
       2023-11-28
          Added support to view max-concurrent-streams.
       2023-09-01
          Added support to view certificate used by gRPC server for TLS authentication.
       2023-07-27
          Added gNMI, P4RT, and gRIBI service ports to grpc state.
       2023-06-01
          Added support for certificate common name.
       2023-04-26
          Added support for EMSd-Go soft memory limit.
       2023-04-21
          Added server name, keepalive time, timeout, enforcement to grpc state
       2023-03-22
          Added nodes server-keepalive-timeout and server-keepalive-time.
       2023-02-05
          Added gRPC tunnel virtual IP and listen address.
       2022-12-07
          Added support for gRPC listen addresses
       2022-07-20
          Added support for gRPC TLS version 1.0 flag
       2022-04-26
          Added support for gRPC server name
       2021-10-22
          Added certificate bundle statistics
       2021-10-20
          Added counters for load bundle
       2021-09-13
          Added status string to reflect unavailable port state.";
    semver:module-version "2.0.0";
  }
  revision 2021-06-10 {
    description
      "Added gRPC tunnel.";
    semver:module-version "1.2.0";
  }
  revision 2021-03-22 {
    description
      "Added keep alive commands.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  container grpc {
    config false;
    description
      "grpc commands";
    container certificate {
      description
        "Grpc server certificate";
      uses CERTIFICATE;
    }
    container servers {
      description
        "gRPC Servers";
      list server {
        key "name";
        description
          "gRPC Server Information";
        leaf name {
          type xr:Cisco-ios-xr-string;
          description
            "Server Name";
        }
        uses GRPC-SERVER-INFO-B;
      }
    }
    container streams {
      description
        "gRPC streams table";
      list stream {
        key "stream-id";
        description
          "gRPC stream information";
        leaf stream-id {
          type xr:Cisco-ios-xr-string;
          description
            "Stream ID";
        }
        uses GRPC-STREAM;
      }
    }
    container srte {
      description
        "segment-routing traffic-eng";
      container sessions {
        description
          "srte service sessions";
        list session {
          key "service address port";
          description
            "srte service session";
          leaf service {
            type xr:Cisco-ios-xr-string {
              length "1..128";
            }
            description
              "Service Name";
          }
          leaf address {
            type xr:Cisco-ios-xr-string {
              length "1..128";
            }
            description
              "IPv4 address in dotted-quad notation, or IPv6
               address in full, mixed, shortened, and
               shortened-mixed notation.";
          }
          leaf port {
            type xr:Cisco-ios-xr-port-number;
            description
              "Destination port";
          }
          uses GRPC-SRTE-SERVICE-SESSIONS;
        }
      }
    }
    container state {
      description
        "Grpc State";
      uses GRPC-STATE;
    }
    container connections {
      description
        "gRPC connections table";
      list connection {
        key "connection-id";
        description
          "gRPC connection information";
        leaf connection-id {
          type xr:Cisco-ios-xr-string;
          description
            "Connection ID";
        }
        uses GRPC-CONNECTIONS-INFO-B;
      }
    }
    container services {
      description
        "Grpc Services Table";
      list service {
        key "name";
        description
          "Grpc Service";
        leaf name {
          type xr:Cisco-ios-xr-string;
          description
            "Service Name";
        }
        uses GRPC-VERSIONS-INFO-B;
      }
    }
    container tunnel {
      description
        "Grpc tunnels";
      container destinations {
        description
          "Grpc tunnel destinations";
        list destination {
          key "address port";
          description
            "Grpc tunnel sessions";
          leaf address {
            type xr:Cisco-ios-xr-string {
              length "1..128";
            }
            description
              "IPv4 address in dotted-quad notation, or IPv6
               address in full, mixed, shortened, and
               shortened-mixed notation.";
          }
          leaf port {
            type xr:Cisco-ios-xr-port-number;
            description
              "Destination port";
          }
          uses GRPC-TUNNEL-SESSIONS;
        }
      }
    }
    container statistics {
      description
        "Grpc Statistics";
      uses GRPC-STATISTICS-INFO-B;
    }
  }
}
