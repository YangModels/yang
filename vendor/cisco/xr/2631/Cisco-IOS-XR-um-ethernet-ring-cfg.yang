module Cisco-IOS-XR-um-ethernet-ring-cfg {
  namespace "http://cisco.com/ns/yang/Cisco-IOS-XR-um-ethernet-ring-cfg";
  prefix um-ethernet-ring-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-ring package configuration.
     
     This YANG module augments the
     modules with configuration data.
     
     Copyright (c) 2020-2025 by Cisco Systems, Inc., and/or its affiliates.
     All rights reserved.";

  revision 2020-12-18 {
    description
      "Initial release";
    semver:module-version "1.0.0";
  }

  container ring {
    description
      "Ethernet Ring Protection";
    container g8032 {
      description
        "G.8032 Ethernet Ring Protection";
      container profiles {
        description
          "G.8032 ring profile configuration";
        list profile {
          key "profile-name";
          description
            "G.8032 ring profile configuration";
          leaf profile-name {
            type xr:Cisco-ios-xr-string {
              length "1..32" {
                description
                  "ERP profile name string";
              }
            }
            description
              "G.8032 ring profile configuration";
          }
          container timer {
            description
              "G.8032 timer";
            leaf wtr {
              type uint32 {
                range "1..12" {
                  description
                    "minutes";
                }
              }
              description
                "Wait-to-Restore timer";
            }
            leaf hold-off {
              type uint32 {
                range "0..10" {
                  description
                    "seconds";
                }
              }
              description
                "Hold off timer";
            }
            leaf guard {
              type uint32 {
                range "10..2000" {
                  description
                    "milliseconds";
                }
              }
              description
                "Guard timer";
            }
          }
          container non-revertive {
            presence "Indicates a non-revertive node is configured.";
            description
              "Non-revertive ring instance";
          }
        }
      }
    }
  }
}
