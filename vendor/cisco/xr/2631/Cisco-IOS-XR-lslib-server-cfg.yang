module Cisco-IOS-XR-lslib-server-cfg {
  namespace "http://cisco.com/ns/yang/Cisco-IOS-XR-lslib-server-cfg";
  prefix lslib-server-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lslib-server package configuration.
     
     This module contains definitions
     for the following management objects:
       lslib-server: Configure LSLIB Server
     
     Copyright (c) 2013-2024 by Cisco Systems, Inc.
     All rights reserved.";

  revision 2024-10-28 {
    description
      "Initial Config yang";
    semver:module-version "1.0.0";
  }
  revision 2019-04-05 {
    description
      "Establish semantic version baseline.";
  }
  revision 2015-11-09 {
    description
      "IOS XR 6.0 revision.";
  }

  container lslib-server {
    description
      "Configure LSLIB Server";
    leaf enable {
      type empty;
      description
        "Enable LSLIB Server configuration. Deletion of
         this object also causes deletion of all
         associated objects under LslibServer.";
    }
  }
}
