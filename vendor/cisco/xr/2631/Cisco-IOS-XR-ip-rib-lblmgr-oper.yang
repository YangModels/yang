module Cisco-IOS-XR-ip-rib-lblmgr-oper {
  namespace "http://cisco.com/ns/yang/Cisco-IOS-XR-ip-rib-lblmgr-oper";
  prefix ip-rib-lblmgr-oper;

  import Cisco-IOS-XR-types {
    prefix xr;
  }
  import cisco-semver {
    prefix semver;
  }
  include Cisco-IOS-XR-ip-rib-lblmgr-oper-sub2 {
    revision-date 2026-07-28;
  }
  include Cisco-IOS-XR-ip-rib-lblmgr-oper-sub1 {
    revision-date 2026-07-28;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-rib-lblmgr package operational data.
     
     This module contains definitions
     for the following management objects:
       rib-manager: RIB Manager operational data
     
     Copyright (c) 2013-2026 by Cisco Systems, Inc.
     All rights reserved.";

  revision 2026-07-28 {
    description
      "Added pending label conflicts to label manager operational data
       2026-04-16
         Added label range info to label manager EDM";
    semver:module-version "1.1.0";
  }
  revision 2025-08-20 {
    description
      "Added local labels associated with prefixes";
    semver:module-version "1.0.0";
  }
  revision 2025-07-14 {
    description
      "Removed local-label attributes that are no longer necessary";
  }
  revision 2025-03-20 {
    description
      "Added label producer info to RIB EDM routes";
  }
  revision 2025-01-06 {
    description
      "Optimized route and path schema";
  }
  revision 2024-11-22 {
    description
      "Added option to display MPLS routes with pending delete NHGs";
  }
  revision 2024-10-29 {
    description
      "Added last clear time of rib statistics";
  }
  revision 2024-10-01 {
    description
      "Add potential label routes";
  }
  revision 2024-08-16 {
    description
      "Added label-summary";
  }
  revision 2024-07-11 {
    description
      "Add unviable label routes";
  }
  revision 2024-02-15 {
    description
      "New rib-manager schema";
  }
  revision 2024-02-06 {
    description
      "New label-manager schema";
  }
  revision 2019-04-05 {
    description
      "Establish semantic version baseline.";
  }
  revision 2015-11-09 {
    description
      "IOS XR 6.0 revision.";
  }

  typedef Lbl-mgr-af-name {
    type string {
      pattern "(IPv4)|(IPv6)";
    }
    description
      "IPv4: Comment: v4 string for <afi_name>, IPv6:
       Comment: v6 string for <afi_name>";
  }

  grouping MPLS {
    description
      "Common node of active, standby, node";
    container mpls {
      description
        "MPLS Routing Information";
      container labels {
        description
          "Label table";
        list label {
          key "label-key";
          description
            "Data for label";
          leaf label-key {
            type uint32 {
              range "0..1048575";
            }
            description
              "Label value";
          }
          uses LBL-INFO;
        }
      }
      container label-summary {
        description
          "Label Summary";
        uses LBLMGR-SUMMARY;
      }
      container label-ranges {
        description
          "Label range table";
        list label-range {
          description
            "Data for label range";
          leaf start-label {
            type uint32 {
              range "0..1048575";
            }
            description
              "Start label value";
          }
          leaf end-label {
            type uint32 {
              range "0..1048575";
            }
            description
              "End label value";
          }
          leaf index {
            type uint32;
            description
              "Label range index";
          }
          uses LBL-RANGE-INFO;
        }
      }
      container vrfs {
        description
          "VRF table";
        list vrf {
          key "vrf-name";
          description
            "Specific VRF";
          container afs {
            description
              "Address Family (AF) table";
            list af {
              key "af-name";
              description
                "Specific AF information";
              leaf af-name {
                type Lbl-mgr-af-name;
                description
                  "Name of the AF";
              }
              uses FORWARDING-TABLE;
              uses UNVIABLE-TABLE;
              uses PENDING-NHG-TABLE;
              uses POTENTIAL-TABLE;
            }
          }
          leaf vrf-name {
            type string;
            description
              "Name of the VRF";
          }
        }
      }
      uses FORWARDING-TABLE;
      uses UNVIABLE-TABLE;
      uses PENDING-NHG-TABLE;
      uses POTENTIAL-TABLE;
    }
  }

  grouping UNVIABLE-TABLE {
    description
      "Common node of mpls, af";
    container unviables {
      description
        "Unviable label forwarding entry table";
      list unviable {
        key "label-key";
        description
          "Unviable forwarding information for a specific
           label";
        leaf label-key {
          type uint32 {
            range "0..1048575";
          }
          description
            "Label value";
        }
        uses RIB-EDM-ROUTE;
      }
    }
  }

  grouping POTENTIAL-TABLE {
    description
      "Common node of mpls, af";
    container potentials {
      description
        "Potential label forwarding entry table";
      list potential {
        key "label-key";
        description
          "Potential forwarding information for a specific
           label";
        leaf label-key {
          type uint32 {
            range "0..1048575";
          }
          description
            "Label value";
        }
        uses RIB-EDM-ROUTE;
      }
    }
  }

  grouping FORWARDING-TABLE {
    description
      "Common node of mpls, af";
    container forwardings {
      description
        "Label forwarding table";
      list forwarding {
        key "label-key";
        description
          "Forwarding information of a specific label ";
        leaf label-key {
          type uint32 {
            range "0..1048575";
          }
          description
            "Label value";
        }
        uses RIB-EDM-ROUTE;
      }
    }
  }

  grouping PENDING-NHG-TABLE {
    description
      "Common node of mpls, af";
    container pending-nhgs {
      description
        "Forwarding entries with pending NHGs table";
      list pending-nhg {
        key "label-key";
        description
          "Potential NHG information for a specific label";
        leaf label-key {
          type uint32 {
            range "0..1048575";
          }
          description
            "Label value";
        }
        uses RIB-EDM-ROUTE;
      }
    }
  }

  container rib-manager {
    config false;
    description
      "RIB Manager operational data";
    container nodes {
      description
        "Location for RIB Manager operational data";
      list node {
        key "node-name";
        description
          "The RIB Manager operational data for a
           particular node";
        leaf node-name {
          type xr:Node-id;
          description
            "The identifier for the node";
        }
        uses MPLS;
      }
    }
    container global {
      description
        "Global RIB Manager operational data";
      container active {
        description
          "Active RIB Manager operational data";
        uses MPLS;
      }
      container standby {
        description
          "Standby RIB Manager operational data";
        uses MPLS;
      }
    }
  }
}
