module Cisco-IOS-XR-sysadmin-ncs1001-envmon-ui {
  namespace "http://www.cisco.com/ns/yang/Cisco-IOS-XR-sysadmin-ncs1001-envmon-ui";
  prefix envmon;

  import Cisco-IOS-XR-sysadmin-show-trace {
    prefix show_trace;
  }
  import tailf-xsd-types {
    prefix xs;
  }
  import Cisco-IOS-XR-sysadmin-types {
    prefix calvados;
  }
  import Cisco-IOS-XR-sysadmin-ncs1001-envmon-types {
    prefix envmon-types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module holds chassis, cards Enviroment data.
     
     Copyright (c) 2012-2020 by Cisco Systems, Inc.
     All rights reserved.";

  revision 2025-02-06 {
    description
      "Added description and units in required fluid";
    semver:module-version "2.1.0";
  }
  revision 2019-04-15 {
    description
      "Establish semantic version baseline.";
    semver:module-version "2.0.0";
  }
  revision 2018-04-09 {
    description
      "Required changes for ConfD 6.4.5";
  }
  revision 2018-02-06 {
    description
      "Adding CLI input validation for LC priority shutdown feature";
  }
  revision 2018-01-25 {
    description
      "Initial revision of LC priority shutdown feature";
  }
  revision 2017-11-27 {
    description
      "Add graceful shutdown disable CLI.";
  }
  revision 2017-07-31 {
    description
      "Changing the namespace to follow Cisco guidelines on naming convention";
  }
  revision 2017-04-10 {
    description
      "Adding the source leaf to altitude value,
          this is to distinguish the source of the altitude value ";
  }
  revision 2017-03-31 {
    description
      "Renamed module and namespace";
  }
  revision 2017-03-30 {
    description
      "commenting the sensor_attributes callpoints for the oper sensors,
          using only the location based callpoints for sensor_attributes ";
  }
  revision 2016-10-12 {
    description
      "unhide commands and configs. moved to advanced-grp";
  }
  revision 2011-11-24 {
    description
      "Initial revision of show environment commands";
  }

  grouping temp-data {
    description
      "Grouping for environmental operational temperature data";
    container temperatures {
      config false;
      description
        "Environmental operational temperature data";
      list location {
        key "location";
        description
          "Location";
        leaf location {
          type string;
          description
            "Location Name";
        }
        list sensor_attributes {
          key "sensor";
          description
            "Temperature sensor attributes";
          leaf loc_header {
            type boolean;
            default "false";
            description
              "Flag to customize the header in the display template";
          }
          leaf print_header {
            type boolean;
            default "false";
            description
              "Flag to customize the header in the display template";
          }
          leaf location {
            type string;
            description
              "Location Name";
          }
          leaf sensor {
            type string;
            description
              "Sensor Name";
          }
          leaf sensor_id {
            type string;
            description
              "Sensor id (unique for location)";
          }
          leaf alarm {
            type string;
            description
              "Alarm Name";
          }
          leaf temperature_value {
            type string;
            units "degreeC";
            description
              "Temperature sensor value in degree Celsius";
          }
          leaf value {
            type int32;
            units "degreeC";
            description
              "Temperature value in degree Celsius";
          }
          leaf critical_lo {
            type int32;
            units "degreeC";
            description
              "Critical low threshold value, interpret -32768 value as N/A";
          }
          leaf major_lo {
            type int32;
            units "degreeC";
            description
              "Major low threshold value, interpret -32768 value as N/A";
          }
          leaf minor_lo {
            type int32;
            units "degreeC";
            description
              "Minor low threshold value, interpret -32768 value as N/A";
          }
          leaf minor_hi {
            type int32;
            units "degreeC";
            description
              "Minor high threshold value, interpret 32768 value as N/A";
          }
          leaf major_hi {
            type int32;
            units "degreeC";
            description
              "Major high threshold value, interpret 32768 value as N/A";
          }
          leaf critical_hi {
            type int32;
            units "degreeC";
            description
              "Critical high threshold value, interpret 32768 value as N/A";
          }
        }
      }
    }
  }

  grouping all-temp-data {
    description
      "All environmental temperature data";
    list temperatures {
      key "loc_iden";
      config false;
      description
        "Environmental parameter temperature data";
      leaf loc_iden {
        type string;
        description
          "Temperature sensor location";
      }
      leaf print_header {
        type boolean;
        default "false";
        description
          "Flag to customize the temperature table in the display template";
      }
      list sensor_attributes {
        key "sensor";
        leaf sensor {
          type string;
          description
            "Temperature sensor name";
        }
        leaf sensor_id {
          type string;
          description
            "Temperature sensor id (unique for location)";
        }
        leaf alarm {
          type string;
          description
            "Alarm name";
        }
        leaf temperature_value {
          type string;
          units "degreeC";
          description
            "Temperature sensor value in degree Celsius";
        }
        leaf value {
          type int32;
          units "degreeC";
          description
            "Temperature value in degree Celsius";
        }
        leaf critical_lo {
          type int32;
          units "degreeC";
          description
            "Critical low threshold value, interpret -32768 value as N/A";
        }
        leaf major_lo {
          type int32;
          units "degreeC";
          description
            "Major low threshold value, interpret -32768 value as N/A";
        }
        leaf minor_lo {
          type int32;
          units "degreeC";
          description
            "Minor low threshold value, interpret -32768 value as N/A";
        }
        leaf minor_hi {
          type int32;
          units "degreeC";
          description
            "Minor high threshold value, interpret 32768 value as N/A";
        }
        leaf major_hi {
          type int32;
          units "degreeC";
          description
            "Major high threshold value, interpret 32768 value as N/A";
        }
        leaf critical_hi {
          type int32;
          units "degreeC";
          description
            "Critical high threshold value, interpret 32768 value as N/A";
        }
      }
    }
  }

  grouping volt-data {
    description
      "Environmental operational voltages data";
    container voltages {
      config false;
      description
        "Environmental parameter voltages";
      list location {
        key "location";
        description
          "Locations of the voltage sensors";
        leaf location {
          type string;
          description
            "Voltage sensor location";
        }
        list sensor_attributes {
          key "sensor";
          description
            "Voltage sensor attributes";
          leaf loc_header {
            type boolean;
            default "false";
            description
              "Flag to customize the display of the voltage sensor";
          }
          leaf print_header {
            type boolean;
            default "false";
            description
              "Flag to customize the display of the voltage sensor";
          }
          leaf location {
            type string;
            description
              "Location Name";
          }
          leaf sensor {
            type string;
            description
              "Voltage sensor name";
          }
          leaf sensor_id {
            type string;
            description
              "Voltage sensor id (unique for location)";
          }
          leaf alarm {
            type string;
            description
              "Alarm Name";
          }
          leaf value {
            type string;
            units "millivolts";
            description
              "Voltage sensor value in millivolts";
          }
          leaf temperature_value {
            type int32;
            units "degreeC";
            description
              "Temperature value in degree Celsius";
          }
          leaf critical_lo {
            type int32;
            units "millivolts";
            description
              "Critical low threshold value, interpret -32768 value as N/A";
          }
          leaf major_lo {
            type int32;
            units "millivolts";
            description
              "Major low threshold value, interpret -32768 value as N/A";
          }
          leaf minor_lo {
            type int32;
            units "millivolts";
            description
              "Minor low threshold value, interpret -32768 value as N/A";
          }
          leaf minor_hi {
            type int32;
            units "millivolts";
            description
              "Minor high threshold value, interpret 32768 value as N/A";
          }
          leaf major_hi {
            type int32;
            units "millivolts";
            description
              "Major high threshold value, interpret 32768 value as N/A";
          }
          leaf critical_hi {
            type int32;
            units "millivolts";
            description
              "Critical high threshold value, interpret 32768 value as N/A";
          }
        }
      }
    }
  }

  grouping all-volt-data {
    description
      "All environmental voltages data";
    list voltages {
      key "loc_iden";
      config false;
      description
        "Environmental parameter voltage";
      leaf loc_iden {
        type string;
        description
          "Voltage sensor locations";
      }
      leaf print_header {
        type boolean;
        default "false";
        description
          "Flag to customize the display template";
      }
      list sensor_attributes {
        key "sensor";
        description
          "Voltage sensor attributes";
        leaf sensor {
          type string;
          description
            "Voltage sensor name";
        }
        leaf sensor_id {
          type string;
          description
            "Voltage sensor id (unique for location)";
        }
        leaf alarm {
          type string;
          description
            "Alarm Name";
        }
        leaf value {
          type string;
          units "millivolts";
          description
            "Voltage sensor value in millivolts";
        }
        leaf temperature_value {
          type int32;
          units "degreeC";
          description
            "Temperature value in degree Celsius";
        }
        leaf critical_lo {
          type int32;
          units "millivolts";
          description
            "Critical low threshold value, interpret -32768 value as N/A";
        }
        leaf major_lo {
          type int32;
          units "millivolts";
          description
            "Major low threshold value, interpret -32768 value as N/A";
        }
        leaf minor_lo {
          type int32;
          units "millivolts";
          description
            "Minor low threshold value, interpret -32768 value as N/A";
        }
        leaf minor_hi {
          type int32;
          units "millivolts";
          description
            "Minor high threshold value, interpret 32768 value as N/A";
        }
        leaf major_hi {
          type int32;
          units "millivolts";
          description
            "Major high threshold value, interpret 32768 value as N/A";
        }
        leaf critical_hi {
          type int32;
          units "millivolts";
          description
            "Critical high threshold value, interpret 32768 value as N/A";
        }
      }
    }
  }

  grouping current-data {
    description
      "Environmental operational current sensor data";
    container current {
      config false;
      description
        "Environmental parameter current";
      list location {
        key "location";
        description
          "Sensor location";
        leaf location {
          type string;
          description
            "Sensor location";
        }
        list sensor_attributes {
          key "sensor";
          description
            "Current sensor attributes";
          leaf loc_header {
            type boolean;
            default "false";
            description
              "Flag to customize the display template";
          }
          leaf print_header {
            type boolean;
            default "false";
            description
              "Flag to customize the display template";
          }
          leaf location {
            type string;
            description
              "Current sensor location name";
          }
          leaf sensor {
            type string;
            description
              "Current sensor name";
          }
          leaf sensor_id {
            type string;
            description
              "Current sensor id (unique for location)";
          }
          leaf alarm {
            type string;
            description
              "Alarm Name";
          }
          leaf value {
            type string;
            units "milliamps";
            description
              "Current sensor value in milliamps";
          }
          leaf temperature_value {
            type int32;
            units "degreeC";
            description
              "Temperature value in degree Celsius";
          }
        }
      }
    }
  }

  grouping all-current-data {
    description
      "All environmental current sensor data";
    list current {
      key "loc_iden";
      config false;
      description
        "Environmental parameter current";
      leaf loc_iden {
        type string;
        description
          "Current sensor location";
      }
      leaf print_header {
        type boolean;
        default "false";
        description
          "Flag to customize the display template";
      }
      list sensor_attributes {
        key "sensor";
        description
          "Current sensor attributes";
        leaf sensor {
          type string;
          description
            "Current sensor name";
        }
        leaf sensor_id {
          type string;
          description
            "Current sensor id (unique for location)";
        }
        leaf value {
          type string;
          units "milliamps";
          description
            "Current sensor value in milliamps";
        }
      }
    }
  }

  grouping fan-data {
    description
      "Environmental operational fan data";
    container fan {
      config false;
      description
        "Environmental parameter fan";
      list location {
        key "location";
        description
          "Location Number";
        leaf location {
          type string;
          description
            "Fan location";
        }
        leaf print_header {
          type boolean;
          default "false";
          description
            "Flag to customize the display template for fan header";
        }
        leaf loc_header {
          type uint32;
          description
            "A flag that enables or disables customization of the CLI show-template.";
        }
        list fan_attributes {
          key "logical_slot";
          description
            "Fan Attributes";
          leaf print_fan_header {
            type string;
            description
              "Flag to customize the display template for fan header";
          }
          leaf location {
            type string;
            description
              "Fan location name";
          }
          leaf logical_slot {
            type string;
            description
              "Fan logical slot";
          }
          leaf fru_PID {
            type string;
            description
              "Fru PID";
          }
          leaf fans_speed {
            type string;
            units "rpm";
            description
              "Fan Speed in rpm";
          }
          leaf fan_header {
            type uint32;
            description
              "Flag to customize the display template for fan header";
          }
          leaf speed_space {
            type uint32;
            description
              "Fan speed space";
          }
        }
      }
    }
  }

  grouping all-fan-data {
    description
      "Grouping for all fan data, containing information about chassis fans";
    list fan {
      key "loc_iden";
      config false;
      description
        "All environmental fan data";
      leaf loc_iden {
        type string;
        description
          "Fan location";
      }
      list fan_attributes {
        key "logical_slot";
        description
          "Fan Attributes";
        leaf print_fan_header {
          type string;
          description
            "Flag to customize the display template for the fan header";
        }
        leaf location {
          type string;
          description
            "Fan location name";
        }
        leaf logical_slot {
          type string;
          description
            "Fan logical slot";
        }
        leaf fru_PID {
          type string;
          description
            "Fru PID";
        }
        leaf fans_speed {
          type string;
          units "rpm";
          description
            "Fan Speed in rpm";
        }
        leaf fan_header {
          type uint32;
          description
            "Flag to customize the display template for the fan header";
        }
        leaf speed_space {
          type uint32;
          description
            "Fan speed space";
        }
      }
    }
  }

  grouping power-data {
    description
      "Environmental operational power data";
    container power {
      config false;
      description
        "Environmental operational power data";
      list location {
        key "location";
        description
          "Power Location";
        leaf location {
          type string;
          description
            "Power Location";
        }
        list pem_attributes {
          key "pem";
          description
            "Power module attributes";
          leaf pem {
            type string;
            description
              "Power module name";
          }
          leaf pem_id {
            type string;
            description
              "Power module id";
          }
          leaf card_type {
            type string;
            description
              "Power card type";
          }
          leaf ps_type {
            type string;
            description
              "Power supply type";
          }
          leaf shelf_num {
            type uint16;
            description
              "Power shelf number";
          }
          leaf supply_type {
            type string;
            description
              "Power supply type";
          }
          leaf input_voltage {
            type string;
            units "volts";
            description
              "Input voltage in volts";
          }
          leaf input_current {
            type string;
            units "amps";
            description
              "Input current in Amps";
          }
          leaf output_voltage {
            type xs:double;
            units "volts";
            description
              "Output voltage in volts";
          }
          leaf output_current {
            type xs:double;
            units "amps";
            description
              "Output current in Amps";
          }
          leaf status {
            type string;
            description
              "Power status";
          }
          leaf input_power_to_ps {
            type uint32;
            units "watts";
            description
              "Input power to power supply in Watts";
          }
          leaf input_current_to_ps {
            type string;
            units "amps";
            description
              "Input current to power supply in Amps";
          }
          leaf output_power_from_ps {
            type uint32;
            units "watts";
            description
              "Output power from power supply in Watts";
          }
          leaf output_current_from_ps {
            type xs:double;
            units "amps";
            description
              "Output current from power supply in Amps";
          }
          leaf power_allocated {
            type uint32;
            units "watts";
            description
              "Allocated Power in Watts";
          }
          leaf power_consumed {
            type string;
            units "watts";
            description
              "Power consumed in Watts";
          }
          leaf power_status {
            type string;
            description
              "Power status";
          }
          leaf confgd_power_redundancy_mode {
            type string;
            description
              "Configured power redundancy mode";
          }
          leaf usable_power_capacity {
            type uint32;
            description
              "Usable Power Capacity in Watts";
          }
          leaf protection_power_capacity {
            type uint32;
            description
              "Protection Power Capacity";
          }
          leaf power_resrv_and_alloc {
            type uint32;
            description
              "Power Reservation and Allocation";
          }
          leaf system_power_used {
            type uint32;
            description
              "Used System Power";
          }
          leaf system_power_input {
            type uint32;
            description
              "Sysyem Power Input";
          }
          leaf power_level {
            type uint16;
            description
              "Power level";
          }
          leaf output_header {
            type uint16;
            description
              "Power output header";
          }
          leaf output_footer {
            type uint16;
            description
              "Power output footer";
          }
          leaf ps_sum_footer {
            type uint16;
            description
              "Power power supply sum footer";
          }
        }
      }
    }
  }

  grouping all-power-data {
    description
      "All environmental power data";
    list power {
      key "loc_iden";
      config false;
      description
        "Environmental parameter power";
      leaf loc_iden {
        type string;
        description
          "Power location";
      }
      list pem_attributes {
        key "pem";
        description
          "Power entery module Attributes";
        leaf pem {
          type string;
          description
            "Power entity module Name";
        }
        leaf pem_id {
          type string;
          description
            "Power entity module ID";
        }
        leaf card_type {
          type string;
          description
            "Power card type";
        }
        leaf ps_type {
          type string;
          description
            "Power power supply type";
        }
        leaf shelf_num {
          type uint16;
          description
            "Power shelf number";
        }
        leaf supply_type {
          type string;
          description
            "Power supply type";
        }
        leaf input_voltage {
          type string;
          units "volts";
          description
            "Input voltage in volts";
        }
        leaf input_current {
          type string;
          units "amps";
          description
            "Input current in Amps";
        }
        leaf output_voltage {
          type xs:double;
          units "volts";
          description
            "Output voltage in volts";
        }
        leaf output_current {
          type xs:double;
          units "amps";
          description
            "Output current in Amps";
        }
        leaf status {
          type string;
          description
            "Power status";
        }
        leaf input_power_to_ps {
          type uint32;
          units "watts";
          description
            "Input power to power supply in Watts";
        }
        leaf input_current_to_ps {
          type string;
          units "amps";
          description
            "Input current to power supply in Amps";
        }
        leaf output_power_from_ps {
          type uint32;
          units "watts";
          description
            "Output power from power supply in Watts";
        }
        leaf output_current_from_ps {
          type xs:double;
          units "amps";
          description
            "Output current from power supply in Amps";
        }
        leaf power_allocated {
          type uint32;
          units "watts";
          description
            "Allocated Power in Watts";
        }
        leaf power_consumed {
          type string;
          units "watts";
          description
            "Power consumed in Watts";
        }
        leaf power_status {
          type string;
          description
            "Power status";
        }
        leaf confgd_power_redundancy_mode {
          type string;
          description
            "Configured power redundancy mode";
        }
        leaf usable_power_capacity {
          type uint32;
          description
            "Usable Power Capacity in Watts";
        }
        leaf protection_power_capacity {
          type uint32;
          description
            "Protection Power Capacity";
        }
        leaf power_resrv_and_alloc {
          type uint32;
          description
            "Reserved and Allocated Power";
        }
        leaf system_power_used {
          type uint32;
          description
            "Used System Power";
        }
        leaf system_power_input {
          type uint32;
          description
            "Input System Power";
        }
        leaf power_level {
          type uint16;
          description
            "Power level";
        }
        leaf output_header {
          type uint16;
          description
            "Flag to customize the header of the power module display";
        }
        leaf output_footer {
          type uint16;
          description
            "Flag to customize the footer of the power module display";
        }
        leaf ps_sum_footer {
          type uint16;
          description
            "Flag to customize the footer of the power supply summary display";
        }
      }
    }
  }

  grouping altitude-data {
    description
      "Operational environmental altitude data";
    container altitude {
      config false;
      description
        "Environmental parameter altitude";
      list location {
        key "location";
        description
          "Sensor location";
        leaf location {
          type string;
          description
            "Location Name";
        }
        list alt_attributes {
          key "sensor";
          description
            "Name of Altitude Sensor Attributes";
          leaf sensor {
            type string;
            description
              "Sensor name";
          }
          leaf rack {
            type uint32;
            description
              "Rack value";
          }
          leaf sensor_value {
            type string;
            description
              "Value of Sensor";
          }
          leaf source {
            type string;
            description
              "Source name";
          }
          leaf print_header {
            type boolean;
            default "false";
            description
              "Flag to customize the altitude table header display";
          }
        }
      }
    }
  }

  grouping all-altitude-data {
    description
      "All environmental altitude data";
    list altitude {
      key "loc_iden";
      config false;
      description
        "Environmental parameter altitude";
      leaf loc_iden {
        type string;
        description
          "Sensor location";
      }
      list alt_attributes {
        key "sensor";
        description
          "Altitude attributes";
        leaf print_header {
          type boolean;
          default "false";
          description
            "Flag to customize the altitude attributes header display";
        }
        leaf sensor {
          type string;
          description
            "Sensor Name";
        }
        leaf rack {
          type uint32;
          description
            "Rack value";
        }
        leaf sensor_value {
          type string;
          description
            "Sensor value";
        }
        leaf source {
          type string;
          description
            "Source name";
        }
      }
    }
  }

  grouping rack-location {
    description
      "Rack location";
    leaf all {
      type empty;
      description
        "All racks";
    }
    list location {
      key "rackId";
      description
        "Location name";
      leaf rackId {
        type calvados:rack-id;
        description
          "Rack id";
      }
    }
  }

  grouping router-group {
    description
      "Environmnetal config router group";
    container router {
      description
        "Environmnetal config router";
      container altitude {
        description
          "Environmnetal config altitude";
        container all {
          description
            "Configured altitude value in meters, negative value not allowed";
          leaf num_meters {
            type uint32 {
              range "1..4000";
            }
            units "meters";
          }
        }
        container rack_loc {
          list location {
            key "rackId";
            description
              "Environmnetal config rack location";
            leaf rackId {
              type calvados:rack-id;
              description
                "Rack ID";
            }
            leaf num_meters {
              type uint32 {
                range "1..4000";
              }
              units "meters";
              description
                "configured rack altitude value in Meters";
            }
          }
        }
      }
    }
  }

  grouping air-filter-group {
    description
      "Environmnetal config air filter";
    container air-filter {
      description
        "Environmnetal configuration air filter";
      container replaced {
        description
          "Air Filter replaced date";
        container all {
          description
            "All environmnetal configuration air filter";
          leaf date {
            type xs:date;
            description
              "Date";
          }
        }
        container rack_loc {
          description
            "Rack Location";
          list location {
            key "rackId";
            description
              "Location";
            leaf rackId {
              type calvados:rack-id;
              description
                "Environmental air filter rack id";
            }
            leaf date {
              type xs:date;
              description
                "Air filter replaced rack location date";
            }
          }
        }
      }
    }
  }

  grouping fan-ctrl-group {
    description
      "Environmental config fan control group";
    container fan-ctrl {
      description
        "Environmental config fan control";
      container disable {
        description
          "Environmental config fan control disable";
        container rack_loc {
          description
            "Environmental config fan control rack location";
          uses rack-location;
        }
      }
    }
  }

  grouping temp-monitor-group {
    description
      "Environmental config temperature monitor";
    container temperature {
      description
        "Temperature monitoring";
      container disable {
        description
          "Environmental monitoring disable";
        container rack_loc {
          description
            "Environmental monitoring rack location";
          uses rack-location;
        }
      }
    }
  }

  grouping env-monitor-group {
    description
      "Environmental monitoring group";
    container monitoring {
      description
        "Environment monitoring";
      container disable {
        description
          "Environmental monitoring disable";
        container rack_loc {
          description
            "Environmental monitoring rack location";
          uses rack-location;
        }
      }
    }
  }

  grouping power-mgmt-group {
    description
      "Environmental power management config";
    container action {
      description
        "Power management action";
      container disable {
        description
          "Power management action disable";
        container rack_loc {
          description
            "Power management rack location";
          uses rack-location;
        }
      }
    }
    container single-feed-mode {
      description
        "Action for suppressing alarms for missing feed";
      container enable {
        description
          "Suppression of alarms State";
        container rack_loc {
          description
            "Single feed mode rack location";
          uses rack-location;
        }
      }
    }
    container extended-temp {
      description
        "Action for setting power budget for extended temp mode";
      container enable {
        description
          "Enable extended temperature";
        container rack_loc {
          description
            "Enable extended temperature rack location";
          uses rack-location;
        }
      }
    }
    container redundancy-num-pms {
      description
        "Power management redundancy of power modules Attributes";
      container all {
        description
          "All redundancy number power modules name";
        leaf num_pm {
          type envmon-types:num_pm;
          description
            "Redundancy number power modules";
        }
      }
      container rack_loc {
        description
          "Rack Location";
        list location {
          key "rackId";
          description
            "Location Name";
          leaf rackId {
            type calvados:rack-id;
            description
              "Rack ID";
          }
          leaf num_pm {
            type envmon-types:num_pm;
            description
              "Power module Number";
          }
        }
      }
    }
  }

  grouping cmd_types {
    description
      "Operational environmental data";
    container oper {
      config false;
      description
        "Environment operational (show) data";
      uses temp-data;
      uses volt-data;
      uses current-data;
      uses fan-data;
      uses power-data;
      uses altitude-data;
    }
    container all {
      config false;
      description
        "All environment monitor parameters";
      list location {
        key "location";
        description
          "Environment location";
        leaf location {
          type string;
          description
            "Location";
        }
        uses all-temp-data;
        uses all-volt-data;
        uses all-current-data;
        uses all-fan-data;
        uses all-power-data;
        uses all-altitude-data;
      }
    }
    container config {
      description
        "environment configurational data";
      uses router-group;
      uses air-filter-group;
      uses fan-ctrl-group;
      uses temp-monitor-group;
      uses env-monitor-group;
      uses envmon-types:fan-speed-group;
      uses envmon-types:fan-ctrl-optics-group;
      uses envmon-types:vin-uv-shut-group;
    }
  }

  container environment {
    description
      "Environmental Monitoring ui data space";
    uses cmd_types;
    uses show_trace:traceable;
  }
  container power-mgmt {
    description
      "Manage Chassis Power Trays and PEMs";
    container config {
      description
        "Power Trays and PEMs configurational data";
      uses power-mgmt-group;
    }
  }
}
