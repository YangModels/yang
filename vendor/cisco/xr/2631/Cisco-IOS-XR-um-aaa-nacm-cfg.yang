module Cisco-IOS-XR-um-aaa-nacm-cfg {
  namespace "http://cisco.com/ns/yang/Cisco-IOS-XR-um-aaa-nacm-cfg";
  prefix um-aaa-nacm-cfg;

  import Cisco-IOS-XR-types {
    prefix xr;
  }
  import Cisco-IOS-XR-um-aaa-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-nacm package configuration.
     
     This YANG module augments the
     modules with configuration data.
     
     Copyright (c) 2021-2026 by Cisco Systems, Inc., and/or its affiliates.
     All rights reserved.";

  revision 2026-05-28 {
    description
      "Deprecated bypass-get-config and bypass-get-oper nodes";
    semver:module-version "2.1.0";
  }
  revision 2022-08-05 {
    description
      "Added container enable-external-policies
       2022-07-11
          Added missing description statement to nodes
       2022-06-27
          Removed must expression under group node
       2021-11-02
          Added bypass-get-config and bypass-get-oper nodes";
    semver:module-version "2.0.0";
  }
  revision 2021-02-11 {
    description
      "Initial release";
    semver:module-version "1.0.0";
  }

  augment "/a1:aaa" {
    description
      "This augment extends aaa nodes configuration";
    container nacm {
      description
        "NACM configuration";
      container read-default {
        description
          "Read default flag";
        container permit {
          must "not(../deny)";
          presence "Indicates a permit node is configured.";
          description
            "Permit read operation by default.";
        }
        container deny {
          must "not(../permit)";
          presence "Indicates a deny node is configured.";
          description
            "Deny read operation by default.";
        }
      }
      container write-default {
        description
          "Write default flag";
        container permit {
          must "not(../deny)";
          presence "Indicates a permit node is configured.";
          description
            "Permit write operation by default.";
        }
        container deny {
          must "not(../permit)";
          presence "Indicates a deny node is configured.";
          description
            "Deny write operation by default.";
        }
      }
      container exec-default {
        description
          "Exec default flag";
        container permit {
          must "not(../deny)";
          presence "Indicates a permit node is configured.";
          description
            "Permit exec operation by default.";
        }
        container deny {
          must "not(../permit)";
          presence "Indicates a deny node is configured.";
          description
            "Deny exec operation by default.";
        }
      }
      container enable-external-policies {
        presence "Indicates a enable-external-policies node is configured.";
        description
          "Enable external policies flag.";
      }
      container enable-external-groups {
        description
          "Enable external groups flag";
        container true {
          must "not(../false)";
          presence "Indicates a true node is configured.";
          description
            "Enable external groups by default.";
        }
        container false {
          must "not(../true)";
          presence "Indicates a false node is configured.";
          description
            "Disable external groups by default.";
        }
      }
      container bypass-get-config {
        status deprecated;
        description
          "Bypass get-config response authorization. This configuration is deprecated and will be removed in 27.1.1 and later releases.";
        container enabled {
          must "not(../disabled)";
          presence "Indicates a enabled node is configured.";
          description
            "Enable bypass of get-config response authorization. This configuration is deprecated and will be removed in 27.1.1 and later releases.";
        }
        container disabled {
          must "not(../enabled)";
          presence "Indicates a disabled node is configured.";
          description
            "Disable bypass of get-config response authorization. This configuration is deprecated and will be removed in 27.1.1 and later releases.";
        }
      }
      container bypass-get-oper {
        status deprecated;
        description
          "Bypass get response authorization. This configuration is deprecated and will be removed in 27.1.1 and later releases.";
        container enabled {
          must "not(../disabled)";
          presence "Indicates a enabled node is configured.";
          description
            "Enable bypass of get response authorization. This configuration is deprecated and will be removed in 27.1.1 and later releases.";
        }
        container disabled {
          must "not(../enabled)";
          presence "Indicates a disabled node is configured.";
          description
            "Disable bypass of get response authorization. This configuration is deprecated and will be removed in 27.1.1 and later releases.";
        }
      }
      container groups {
        description
          "Specify groups in nacm";
        list group {
          key "group-name";
          description
            "Specify groups in nacm";
          leaf group-name {
            type xr:Cisco-ios-xr-string {
              length "1..800" {
                description
                  "Name of nacm group";
              }
            }
            description
              "Specify groups in nacm";
          }
          container usernames {
            presence "Indicates a usernames node is configured.";
            description
              "Usernames list to add under nacm group";
            leaf-list username {
              type xr:Cisco-ios-xr-string {
                length "1..800" {
                  description
                    "Username to add under nacm group";
                }
              }
              max-elements "16";
              description
                "Username to add under nacm group";
            }
          }
        }
      }
      container rule-lists {
        description
          "Specify rule-list in nacm";
        list rule-list {
          key "index name";
          description
            "Specify rule-list in nacm";
          leaf index {
            type xr:Cisco-ios-xr-string {
              length "1..800" {
                description
                  "Index of nacm rule-list";
              }
            }
            description
              "Specify rule-list in nacm";
          }
          leaf name {
            type xr:Cisco-ios-xr-string {
              length "1..800" {
                description
                  "Name of nacm rule-list";
              }
            }
            description
              "Name of nacm rule-list";
          }
          container groupnames {
            description
              "Specify groups under rule-list";
            leaf-list groupname {
              type xr:Cisco-ios-xr-string {
                length "1..800" {
                  description
                    "Groupname to add under nacm rule-list";
                }
              }
              max-elements "16";
              description
                "Groupname to add under nacm rule-list";
            }
          }
          container rules {
            description
              "Specify rules in nacm rule-list";
            list rule {
              key "index name";
              description
                "Specify rules in nacm rule-list";
              leaf index {
                type xr:Cisco-ios-xr-string {
                  length "1..800" {
                    description
                      "Index of nacm rule in rule-list";
                  }
                }
                description
                  "Specify rules in nacm rule-list";
              }
              leaf name {
                type xr:Cisco-ios-xr-string {
                  length "1..800" {
                    description
                      "Name of nacm rule in rule-list";
                  }
                }
                description
                  "Name of nacm rule in rule-list";
              }
              container action {
                description
                  "Action for rule";
                container permit {
                  must "not(../deny)";
                  presence "Indicates a permit node is configured.";
                  description
                    "Action value for rule";
                }
                container deny {
                  must "not(../permit)";
                  presence "Indicates a deny node is configured.";
                  description
                    "Action value for rule";
                }
              }
              leaf module-name {
                type string {
                  length "1..800" {
                    description
                      "Module-name value for rule";
                  }
                }
                description
                  "Module-name for rule";
              }
              container rule-type {
                description
                  "Rule-type values for rule";
                leaf rpc {
                  type string {
                    length "1..800" {
                      description
                        "rpc value for rule";
                    }
                  }
                  must "not(../data-node)";
                  description
                    "Rule-type rpc";
                }
                leaf data-node {
                  type string {
                    length "1..800" {
                      description
                        "Rule-type value for rule";
                    }
                  }
                  must "not(../rpc)";
                  description
                    "rule-type data-node";
                }
              }
              container access-operations {
                presence "Indicates a access-operations node is configured.";
                description
                  "Access-operations for rule";
                leaf create {
                  type uint32 {
                    range "0..1" {
                      description
                        "Create bit for rule";
                    }
                  }
                  mandatory true;
                  description
                    "Create bit for rule";
                }
                leaf read {
                  type uint32 {
                    range "0..1" {
                      description
                        "Read bit for rule";
                    }
                  }
                  mandatory true;
                  description
                    "Read bit for rule";
                }
                leaf update {
                  type uint32 {
                    range "0..1" {
                      description
                        "Update bit for rule";
                    }
                  }
                  mandatory true;
                  description
                    "Update bit for rule";
                }
                leaf delete {
                  type uint32 {
                    range "0..1" {
                      description
                        "Delete bit for rule";
                    }
                  }
                  mandatory true;
                  description
                    "Delete bit for rule";
                }
                leaf exec {
                  type uint32 {
                    range "0..1" {
                      description
                        "Exec bit for rule";
                    }
                  }
                  mandatory true;
                  description
                    "Exec bit for rule";
                }
                leaf all {
                  type uint32 {
                    range "0..1" {
                      description
                        "All bit for rule";
                    }
                  }
                  mandatory true;
                  description
                    "All bits for rule";
                }
              }
              leaf comment {
                type string {
                  length "1..800" {
                    description
                      "Comment value for rule";
                  }
                }
                description
                  "Comment for rule";
              }
            }
          }
        }
      }
    }
  }
}
