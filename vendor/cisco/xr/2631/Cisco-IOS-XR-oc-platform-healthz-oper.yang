module Cisco-IOS-XR-oc-platform-healthz-oper {
  namespace "http://cisco.com/ns/yang/Cisco-IOS-XR-oc-platform-healthz-oper";
  prefix oc-platform-healthz-oper;

  import cisco-semver {
    prefix semver;
  }
  include Cisco-IOS-XR-oc-platform-healthz-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR oc-platform-healthz package operational data.
     
     This module contains definitions
     for the following management objects:
       oc-platform-healthz: This module defines a data model for
         representing a system component inventory, which can include
         hardware or software elements arranged in an arbitrary
         structure
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container oc-platform-healthz {
    config false;
    description
      "This module defines a data model for representing
       a system component inventory, which can include
       hardware or software elements arranged in an
       arbitrary structure";
    container components {
      description
        "List of components, keyed by component name";
      list component {
        key "name";
        description
          "List of components, keyed by component name";
        container subcomponents {
          description
            "List of subcomponent references";
          list subcomponent {
            key "name";
            description
              "List of subcomponent references";
            leaf name {
              type string;
              description
                "Reference to the name list key";
            }
            uses OVERLAY-OC-PLATFORM-HEALTHZ-SUBCOMPONENT;
          }
        }
        container state {
          description
            "Operational state data for each component";
          uses OVERLAY-OC-PLATFORM-HEALTHZ-STATE;
        }
        container healthz {
          description
            "The health of the component";
          uses OVERLAY-OC-PLATFORM-HEALTHZ-HEALTHZ;
        }
        leaf name {
          type string;
          description
            "References the component name";
        }
      }
    }
  }
}
