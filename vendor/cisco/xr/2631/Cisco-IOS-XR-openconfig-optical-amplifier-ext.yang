module Cisco-IOS-XR-openconfig-optical-amplifier-ext {
  namespace "http://cisco.com/ns/yang/Cisco-IOS-XR-openconfig-optical-amplifier-ext";
  prefix oc-opt-amp-ext;

  import openconfig-optical-amplifier {
    prefix oc-opt-amp;
  }
  import openconfig-yang-types {
    prefix oc-yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical amplifier model
     and contains the definition of extended parameters for Optical
     Amplifiers  deployed as part of a transport line system.
     
     Copyright (c) 2024-2025 by Cisco Systems, Inc.
     All rights reserved.";

  revision 2026-02-05 {
    description
      "Added correction span loss leaf and renamed span loss correction leaves";
    reference "26.2.1";
  }
  revision 2026-01-08 {
    description
      "Added support for ampli apc regulation parameters";
    reference "26.2.1";
  }
  revision 2024-08-23 {
    description
      "Extension of optical amplifier model";
    reference "25.1.1";
  }

  grouping min-max-configurational-operational-stats-precision2-dB {
    description
      "Common grouping for recording dB values with 2 decimal
       precision. Values include the minimum, maximum, configurational
       and operational statistics.";
    leaf min {
      type decimal64 {
        fraction-digits 2;
      }
      units "dB";
      description
        "The minimum value of the parameter (dB).";
    }
    leaf max {
      type decimal64 {
        fraction-digits 2;
      }
      units "dB";
      description
        "The maximum value of the parameter (dB).";
    }
    leaf configurational {
      type decimal64 {
        fraction-digits 2;
      }
      units "dB";
      description
        "The configurational value of the parameter (dB).";
    }
    leaf operational {
      type decimal64 {
        fraction-digits 2;
      }
      units "dB";
      description
        "The operational value of the parameter (dB).";
    }
  }

  grouping min-max-configurational-operational-stats-precision2-dBm {
    description
      "Common grouping for recording dBm values with 2 decimal
       precision. Values include the minimum, maximum, configurational
       and operational statistics in dB units.";
    leaf min {
      type decimal64 {
        fraction-digits 2;
      }
      units "dBm";
      description
        "The minimum value of the parameter (dBm).";
    }
    leaf max {
      type decimal64 {
        fraction-digits 2;
      }
      units "dBm";
      description
        "The maximum value of the parameter (dBm).";
    }
    leaf configurational {
      type decimal64 {
        fraction-digits 2;
      }
      units "dBm";
      description
        "The configurational value of the parameter (dBm).";
    }
    leaf operational {
      type decimal64 {
        fraction-digits 2;
      }
      units "dBm";
      description
        "The operational value of the parameter (dBm).";
    }
  }

  grouping ampli-apc-regulation-config {
    description
      "Configuration data for OSC Regulation Management";
    leaf span-pause {
      type boolean;
      description
        "OSC regulation span pause configuration";
    }
  }

  grouping ampli-apc-regulation-state {
    description
      "Operational data for ampli-apc Regulation Management";
    leaf block-reasons {
      type string;
      description
        "Free-form reason string explaining why regulation is currently blocked or paused (empty if not blocked).";
    }
    leaf internal-state {
      type string;
      description
        "Current operational mode that triggered ampli-apc regulation.";
    }
    leaf gain-range {
      type string;
      description
        "Gain range status";
    }
    leaf last-correction-span-loss {
      type decimal64 {
        fraction-digits 2;
      }
      units "dB";
      description
        "Most recent measured correction span loss (dB).";
    }
    leaf last-correction-span-loss-timestamp {
      type oc-yang:date-and-time;
      description
        "Timestamp of the last applied OSC regulation correction.";
    }
    leaf last-span-loss-input {
      type decimal64 {
        fraction-digits 2;
      }
      units "dB";
      description
        "Most recent measured span loss at the input (dB).";
    }
    leaf last-span-loss-input-timestamp {
      type oc-yang:date-and-time;
      description
        "Timestamp of the most recent measured span loss at the input.";
    }
    leaf span-loss-input-correction-threshold {
      type decimal64 {
        fraction-digits 2;
      }
      units "dB";
      description
        "Most recent measured span loss at the input (dB).";
    }
    container egress-ampli-input-power {
      description
        "Egress Ampli Input power - minimum, maximum, configurational, operational
         in units of dBm";
      uses min-max-configurational-operational-stats-precision2-dBm;
    }
    container egress-ampli-output-power {
      description
        "Egress Ampli Output power - minimum, maximum, configurational, operational
         in units of dBm";
      uses min-max-configurational-operational-stats-precision2-dBm;
    }
    container egress-ampli-gain {
      description
        "Egress Ampli Gain - minimum, maximum, configurational, operational
         in units of dB";
      uses min-max-configurational-operational-stats-precision2-dB;
    }
    container tx-voa-attenuation {
      description
        "Tx Voa Attenuation - minimum, maximum, configurational, operational
         in units of dB";
      uses min-max-configurational-operational-stats-precision2-dB;
    }
    container tx-signal-power {
      description
        "Tx Signal Power - minimum, maximum, configurational, operational
         in units of dB";
      uses min-max-configurational-operational-stats-precision2-dBm;
    }
  }

  grouping oc-opt-amp-extended {
    description
      "This augment extends the configuration & operational
       data for optical amplifier model";
    container cisco {
      description
        "Enclosing container for the parameters for callisto LC ";
      container ampli-apc-regulation {
        description
          "Enclosing container for OSC Regulation Management parameters.";
        container config {
          description
            "Extended OSC Regulation Configuration parameters";
          uses ampli-apc-regulation-config;
        }
        container state {
          config false;
          description
            "Extended OSC Regulation Operational parameters";
          uses ampli-apc-regulation-config;
          uses ampli-apc-regulation-state;
        }
      }
    }
  }

  augment "/oc-opt-amp:optical-amplifier/oc-opt-amp:amplifiers/oc-opt-amp:amplifier" {
    description
      "This augment extends the openconfig-optical-amplifier model";
    uses oc-opt-amp-extended;
  }
}
