module Cisco-IOS-XR-tamsvcs-oper {
  namespace "http://cisco.com/ns/yang/Cisco-IOS-XR-tamsvcs-oper";
  prefix tamsvcs-oper;

  import Cisco-IOS-XR-types {
    prefix xr;
  }
  import cisco-semver {
    prefix semver;
  }
  include Cisco-IOS-XR-tamsvcs-oper-sub1 {
    revision-date 2025-10-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tamsvcs package operational data.
     
     This module contains definitions
     for the following management objects:
       tam: TAM services operational data
     
     Copyright (c) 2013-2025 by Cisco Systems, Inc.
     All rights reserved.";

  revision 2025-10-25 {
    description
      "Added new ECC256 SUDI/AIK certificate type";
    semver:module-version "1.3.0";
  }
  revision 2021-06-25 {
    description
      "3rd Party Key Package support in XR";
    semver:module-version "1.2.0";
  }
  revision 2020-11-15 {
    description
      "Show device info and sudi certs support for tam";
    semver:module-version "1.1.0";
  }
  revision 2019-04-05 {
    description
      "Establish semantic version baseline.";
    semver:module-version "1.0.1";
  }
  revision 2015-11-09 {
    description
      "IOS XR 6.0 revision.";
  }

  container tam {
    config false;
    description
      "TAM services operational data";
    container nodes {
      description
        "Per Node Tam Services operation data";
      list node {
        key "node";
        description
          "Node Location for TAM services operational data";
        container ha-sudi-certs {
          description
            "TAM services HA Sudi Certificates";
          uses TAMSVCS-HA-SUDI-CERTS;
        }
        container public-keys-allowed {
          description
            "TAM Public Keys Allowed List";
          uses TAMSVCS-PUBKEYS-ALLOWED;
        }
        container all {
          description
            "TAM services all information";
          uses TAMSVCS-INFO-ALL;
        }
        container storage {
          description
            "TAM storage information";
          uses TAMSVCS-STORAGE;
        }
        container public-keys-revoked {
          description
            "TAM Public Keys Revoked List";
          uses TAMSVCS-PUBKEYS-REVOKED;
        }
        container device-info {
          description
            "TAM services device information";
          uses TAMSVCS-DEVICE-INFO;
        }
        container ecc256p-sudi-certs {
          description
            "TAM services ECCp256 HA Sudi Certificates";
          uses TAMSVCS-HA-SUDI-CERTS;
        }
        container sudi-certs {
          description
            "TAM services Sudi Certificates";
          uses TAMSVCS-SUDI-CERTS;
        }
        leaf node {
          type xr:Node-id;
          description
            "Node location";
        }
      }
    }
  }
}
