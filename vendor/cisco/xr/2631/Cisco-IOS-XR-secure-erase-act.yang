module Cisco-IOS-XR-secure-erase-act {
  namespace "http://cisco.com/ns/yang/Cisco-IOS-XR-secure-erase-act";
  prefix secure-erase-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2024 by Cisco Systems, Inc.
     All rights reserved.";

  revision 2024-08-19 {
    description
      "IOS XR 25.1.1 revision.";
    semver:module-version "1.0.0";
  }

  rpc secure-erase {
    description
      "Action to start secure erase on a location";
    input {
      leaf location {
        type string;
        mandatory true;
        description
          "Location string to start reset";
      }
    }
    xr:xr-task "cisco-support";
    xr:cli-command "secure-erase location <location>";
  }
}
