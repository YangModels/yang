module Cisco-IOS-XR-tunnel-nve-oper {
  namespace "http://cisco.com/ns/yang/Cisco-IOS-XR-tunnel-nve-oper";
  prefix tunnel-nve-oper;

  import Cisco-IOS-XR-types {
    prefix xr;
  }
  import cisco-semver {
    prefix semver;
  }
  include Cisco-IOS-XR-tunnel-nve-oper-sub1 {
    revision-date 2026-03-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-nve package operational data.
     
     This module contains definitions
     for the following management objects:
       nve: NVE operational data
     
     Copyright (c) 2013-2026 by Cisco Systems, Inc.
     All rights reserved.";

  revision 2026-03-12 {
    description
      "Added ip-afi-preference field to nve_show_nve_intf_bd
       2026-02-19
         Added previous table ID field to vrf-info
       2026-01-29
         Added capabilities: max-ipv4-prefixes-in-obj-grp and max-ipv6-prefixes-in-obj-grp";
    semver:module-version "1.2.0";
  }
  revision 2025-01-22 {
    description
      "Added support for viewing guev1 udp ports if feature supported
       2025-01-22
          Added a new capability in nve platform capability (global guev1)
       2024-01-31
          Added a new capability in nve platform capability (udp src start)
       2023-11-01
          Added a new capability in nve platform capability
       2023-08-01
          Added a new capabilities in nve platform capability
       2023-04-13
          Added a new capability in nve platform capability
       2022-10-08
          Added support for viewing platform capability details.
       2022-09-08
          global: Added vxlan-interfaceless-l3vni-bringup indication.
       2022-09-08
          global: Added system mac information.
       2022-02-25
          Added member-vni table with extended keys to complement vni
       2022-02-08
          Added support for 'show nve vrf'
       2022-01-28
          Added nve-interface IPv6 support";
    semver:module-version "1.1.0";
  }
  revision 2019-04-05 {
    description
      "Establish semantic version baseline.";
    semver:module-version "1.0.1";
  }
  revision 2015-11-09 {
    description
      "IOS XR 6.0 revision.";
  }

  container nve {
    config false;
    description
      "NVE operational data";
    container vnis {
      status deprecated;
      description
        "Table for VNIs";
      list vni {
        key "vni";
        status deprecated;
        description
          "The attributes for a particular VNI";
        leaf vni {
          type xr:Cisco-ios-xr-string;
          description
            "VNI ID";
        }
        uses NVE-SHOW-VNI-BD;
      }
    }
    container vrfs {
      description
        "Table for VRFs";
      list vrf {
        key "vrf";
        description
          "The attributes for a particular VRF";
        leaf vrf {
          type xr:Cisco-ios-xr-string;
          description
            "VRF name";
        }
        uses NVE-SHOW-VRF;
      }
    }
    container capabilities {
      description
        "NVE Platform Capability information";
      uses NVE-PDCAP;
    }
    container global {
      description
        "NVE Global information";
      uses NVE-GLOBAL;
    }
    container member-vnis {
      description
        "Table for VNIs";
      list member-vni {
        description
          "The attributes for a particular VNI";
        leaf vni {
          type uint32;
          description
            "VNI ID";
        }
        leaf nve-id {
          type xr:Cisco-ios-xr-string;
          description
            "NVE ID";
        }
        uses NVE-SHOW-VNI-BD;
      }
    }
    container interfaces {
      description
        "Table for NVE interface attributes";
      list interface {
        key "interface-name";
        description
          "The attributes for a particular interface";
        leaf interface-name {
          type xr:Interface-name;
          description
            "Interface Name";
        }
        uses NVE-SHOW-NVE-INTF-BD;
      }
    }
  }
}
