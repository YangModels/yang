module Cisco-IOS-XR-sks-server-oper {
  namespace "http://cisco.com/ns/yang/Cisco-IOS-XR-sks-server-oper";
  prefix sks-server-oper;

  import Cisco-IOS-XR-types {
    prefix xr;
  }
  import cisco-semver {
    prefix semver;
  }
  include Cisco-IOS-XR-sks-server-oper-sub1 {
    revision-date 2025-04-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sks-server package operational data.
     
     This module contains definitions
     for the following management objects:
       sks: Secure Key Server(SKS) data
     
     Copyright (c) 2013-2025 by Cisco Systems, Inc.
     All rights reserved.";

  revision 2025-04-08 {
    description
      "Updated size of peer identifier";
    semver:module-version "2.0.0";
  }
  revision 2021-08-11 {
    description
      "Added string bound check.";
    semver:module-version "1.0.0";
  }
  revision 2020-10-14 {
    description
      "Initial yang support for sks oper.";
  }
  revision 2019-04-05 {
    description
      "Establish semantic version baseline.";
  }
  revision 2015-11-09 {
    description
      "IOS XR 6.0 revision.";
  }

  container sks {
    config false;
    description
      "Secure Key Server(SKS) data";
    container profile-stats {
      description
        "Secure Key Server(SKS) Profile statistics info";
      list profile-stat {
        key "profile-name";
        description
          "Secure Key Server(SKS) Stats bag";
        leaf profile-name {
          type xr:Cisco-ios-xr-string {
            length "1..127";
          }
          description
            "Enter Profile name";
        }
        uses SKS-PROFILE-STATS;
      }
    }
    container profiles {
      description
        "Secure Key Server(SKS) Profile info";
      list profile {
        key "profile-name";
        description
          "Secure Key Server(SKS) Peer bag";
        leaf profile-name {
          type xr:Cisco-ios-xr-string {
            length "1..127";
          }
          description
            "Enter Profile name";
        }
        uses SKS-PROFILE-INFO;
      }
    }
    container self-mc-pubkeys {
      description
        "Secure Key Server(SKS) self pubkey data";
      list self-mc-pubkey {
        key "label";
        description
          "Secure Key Server(SKS) self mceliece pubkey
           details";
        leaf label {
          type xr:Cisco-ios-xr-string {
            length "1..23";
          }
          description
            "Enter Pubkey label";
        }
        uses SKS-MCELIECE-PUBKEY-INFO;
      }
    }
    container peers {
      description
        "Secure Key Server(SKS) Peer info";
      list peer {
        key "peer-name";
        description
          "Secure Key Server(SKS) Peer bag";
        leaf peer-name {
          type xr:Cisco-ios-xr-string {
            length "1..18";
          }
          description
            "Enter Peer name";
        }
        uses SKS-PEER-INFO;
      }
    }
    container peer-mc-pubkeys {
      description
        "Secure Key Server(SKS) peer pubkey data";
      list peer-mc-pubkey {
        key "label";
        description
          "Secure Key Server(SKS) peer mceliece pubkey
           details";
        leaf label {
          type xr:Cisco-ios-xr-string {
            length "1..23";
          }
          description
            "Enter Pubkey label";
        }
        uses SKS-MCELIECE-PUBKEY-INFO;
      }
    }
  }
}
