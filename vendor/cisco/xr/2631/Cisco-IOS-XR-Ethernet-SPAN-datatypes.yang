module Cisco-IOS-XR-Ethernet-SPAN-datatypes {
  namespace "http://cisco.com/ns/yang/Cisco-IOS-XR-Ethernet-SPAN-datatypes";
  prefix ethernet-span-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2026 by Cisco Systems, Inc.
     All rights reserved.";

  revision 2026-05-29 {
    description
      "Restrict session name characters";
    semver:module-version "2.0.0";
  }
  revision 2021-10-06 {
    description
      "Added support for global mirror intervals";
    semver:module-version "1.1.0";
  }
  revision 2019-04-05 {
    description
      "Establish semantic version baseline.";
    semver:module-version "1.0.0";
  }
  revision 2015-11-09 {
    description
      "IOS XR 6.0 revision.";
  }

  typedef Span-session-name {
    type string {
      length "1..79";
      pattern "[A-Za-z0-9_.-]+";
    }
    description
      "Span session name";
  }

  typedef Span-session-class {
    type enumeration {
      enum "ethernet" {
        value 0;
        description
          "Mirror Ethernet packets";
      }
      enum "ipv4" {
        value 1;
        description
          "Mirror IPv4 packets";
      }
      enum "ipv6" {
        value 2;
        description
          "Mirror IPv6 packets";
      }
      enum "mpls-ipv4" {
        value 3;
        description
          "Mirror MPLS-encapsulated IPv4 packets";
      }
      enum "mpls-ipv6" {
        value 4;
        description
          "Mirror MPLS-encapsulated IPv6 packets";
      }
    }
    description
      "Span session class";
  }

  typedef Span-acl-name {
    type string {
      length "1..129";
    }
    description
      "Span acl name";
  }

  typedef Span-session-id {
    type uint32;
    description
      "Span session id";
  }

  typedef Span-mirror-interval {
    type enumeration {
      enum "512" {
        value 1;
        description
          "Mirror 1 in every 512 packets";
      }
      enum "1k" {
        value 2;
        description
          "Mirror 1 in every 1024 packets";
      }
      enum "2k" {
        value 3;
        description
          "Mirror 1 in every 2048 packets";
      }
      enum "4k" {
        value 4;
        description
          "Mirror 1 in every 4096 packets";
      }
      enum "8k" {
        value 5;
        description
          "Mirror 1 in every 8192 packets";
      }
      enum "16k" {
        value 6;
        description
          "Mirror 1 in every 16384 packets";
      }
      enum "2" {
        value 7;
        description
          "Mirror 1 in every 2 packets";
      }
      enum "4" {
        value 8;
        description
          "Mirror 1 in every 4 packets";
      }
      enum "8" {
        value 9;
        description
          "Mirror 1 in every 8 packets";
      }
      enum "16" {
        value 10;
        description
          "Mirror 1 in every 16 packets";
      }
      enum "32" {
        value 11;
        description
          "Mirror 1 in every 32 packets";
      }
      enum "64" {
        value 12;
        description
          "Mirror 1 in every 64 packets";
      }
      enum "128" {
        value 13;
        description
          "Mirror 1 in every 128 packets";
      }
      enum "256" {
        value 14;
        description
          "Mirror 1 in every 256 packets";
      }
    }
    description
      "Span mirror interval";
  }

  typedef Span-session-class-old {
    type enumeration {
      enum "true" {
        value 0;
        description
          "Mirror Ethernet packets";
      }
    }
    description
      "Span session class old";
  }
}
