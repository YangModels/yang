//*************  DO-NOT EDIT  **************
//*********** Auto-generated file ********** 

 module cisco-xr-openconfig-platform-deviations {

  prefix  "oc-platformdevs";

  namespace "http://cisco.com/ns/yang/cisco-xr-openconfig-platform-deviations";

  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-platform.yang@2022-07-11 

     on Cisco IOS-XR devices.

     Copyright (c) 2017-2025 by Cisco Systems, Inc., and/or its affiliates.
     All rights reserved.";

  revision "2026-06-09" {
    description
      "Added deviations for integrated-circuit resource state leaves";
  }
  revision "2026-01-28" {
    description
      "Added deviations for last-poweroff-reason
      and last-poweroff-time, removed model-name deviation";
  }
  revision "2025-12-11" {
    description
      "Added deviation for name leaf to fix broken leafref";
  }
  revision "2024-01-23" {
    description
      "Removed the deviations for Res Utilization state";
  }
  revision "2023-08-30" {
    description
      "Initial revision applicable to IOS-XR 6.4.1";
  }

  deviation /oc-platform:components/oc-platform:component/oc-platform:state/oc-platform:base-mac-address {
    deviate not-supported;
  }

  deviation /oc-platform:components/oc-platform:component/oc-platform:properties/oc-platform:property {
    deviate not-supported;
  }

  deviation /oc-platform:components/oc-platform:component/oc-platform:state/oc-platform:last-poweroff-reason {
    deviate not-supported;
  }

  deviation /oc-platform:components/oc-platform:component/oc-platform:state/oc-platform:last-poweroff-time {
    deviate not-supported;
  }

  deviation /oc-platform:components/oc-platform:component/oc-platform:integrated-circuit/oc-platform:utilization/oc-platform:resources/oc-platform:resource/oc-platform:config {
    deviate not-supported;
  }

  deviation /oc-platform:components/oc-platform:component/oc-platform:integrated-circuit/oc-platform:utilization/oc-platform:resources/oc-platform:resource/oc-platform:name {
    deviate replace {
      type string;
    }
  }

  deviation /oc-platform:components/oc-platform:component/oc-platform:integrated-circuit/oc-platform:utilization/oc-platform:resources/oc-platform:resource/oc-platform:state/oc-platform:name {
    deviate not-supported;
  }

  deviation /oc-platform:components/oc-platform:component/oc-platform:integrated-circuit/oc-platform:utilization/oc-platform:resources/oc-platform:resource/oc-platform:state/oc-platform:used-threshold-upper {
    deviate not-supported;
  }

  deviation /oc-platform:components/oc-platform:component/oc-platform:integrated-circuit/oc-platform:utilization/oc-platform:resources/oc-platform:resource/oc-platform:state/oc-platform:used-threshold-upper-clear {
    deviate not-supported;
  }

  deviation /oc-platform:components/oc-platform:component/oc-platform:integrated-circuit/oc-platform:utilization/oc-platform:resources/oc-platform:resource/oc-platform:state/oc-platform:used-threshold-upper-exceeded {
    deviate not-supported;
  }
}
//total deviations:10
