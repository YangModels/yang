module Cisco-IOS-XR-snmp-agent-secure-cfg {
  namespace "http://cisco.com/ns/yang/Cisco-IOS-XR-snmp-agent-secure-cfg";
  prefix snmp-agent-secure-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-agent-secure package configuration.
     
     This module contains definitions
     for the following management objects:
       snmp: The hierarchy point for secure SNMP configurations
     
     Copyright (c) 2013-2026 by Cisco Systems, Inc.
     All rights reserved.";

  revision 2026-04-22 {
    description
      "Updated sysdb path path snmp securev3 vrf host";
    semver:module-version "1.0.0";
  }
  revision 2026-04-15 {
    description
      "Renamed class names and removed duplicate class";
  }
  revision 2026-03-14 {
    description
      "Initial secure-v3 configuration support.";
  }
  revision 2019-04-05 {
    description
      "Establish semantic version baseline.";
  }
  revision 2015-11-09 {
    description
      "IOS XR 6.0 revision.";
  }

  typedef Snmp-owner-access {
    type enumeration {
      enum "sdr-owner" {
        value 0;
        description
          "Secure Domain Router Owner permissions";
      }
      enum "system-owner" {
        value 1;
        description
          "System owner permissions";
      }
    }
    description
      "Snmp owner access";
  }

  typedef Snmpacl {
    type enumeration {
      enum "ipv4" {
        value 1;
        description
          "Ipv4 Access-list";
      }
      enum "ipv6" {
        value 2;
        description
          "Ipv6 Access-list";
      }
    }
    description
      "Snmpacl";
  }

  typedef Snmp-security-model {
    type enumeration {
      enum "privacy" {
        value 2;
        description
          "Authentication and privacy password required
           for access";
      }
    }
    description
      "Snmp security model";
  }

  typedef User-hash-algorithm {
    type enumeration {
      enum "sha224" {
        value 3;
        description
          "HMAC SHA-224 algorithm";
      }
      enum "sha256" {
        value 4;
        description
          "HMAC SHA-256 algorithm";
      }
      enum "sha384" {
        value 5;
        description
          "HMAC SHA-384 algorithm";
      }
      enum "sha512" {
        value 6;
        description
          "HMAC SHA-512 algorithm";
      }
    }
    description
      "User hash algorithm";
  }

  typedef User-priv-algorithm {
    type enumeration {
      enum "aes128" {
        value 3;
        description
          "aes128 algorithm";
      }
      enum "aes192" {
        value 4;
        description
          "aes192 algorithm";
      }
      enum "aes256" {
        value 5;
        description
          "aes256 algorithm";
      }
    }
    description
      "User priv algorithm";
  }

  typedef Group-snmp-version {
    type enumeration {
      enum "v3" {
        value 2;
        description
          "SNMP version 3";
      }
    }
    description
      "Group snmp version";
  }

  typedef User-snmp-version {
    type enumeration {
      enum "v3" {
        value 3;
        description
          "SNMP version 3";
      }
    }
    description
      "User snmp version";
  }

  container snmp {
    description
      "The hierarchy point for secure SNMP
       configurations";
    container secure {
      description
        "Secure SNMP configuration";
      container groups {
        description
          "Secure SNMP group configuration";
        list group {
          key "name";
          description
            "Name of the secure group";
          leaf name {
            type xr:Cisco-ios-xr-string {
              length "1..128";
            }
            description
              "Name of the group";
          }
          leaf snmp-version {
            type Group-snmp-version;
            mandatory true;
            description
              "snmp version";
          }
          leaf security-model {
            type Snmp-security-model;
            mandatory true;
            description
              "security model like priv applicable for
               secure-v3";
          }
          leaf notify-view {
            type string;
            description
              "notify view name";
          }
          leaf read-view {
            type string;
            description
              "read view name";
          }
          leaf write-view {
            type string;
            description
              "write view name";
          }
          leaf v4acl-type {
            type Snmpacl;
            description
              "Access-list type";
          }
          leaf v4-access-list {
            type string;
            description
              "Ipv4 Access-list name";
          }
          leaf v6acl-type {
            type Snmpacl;
            description
              "Access-list type";
          }
          leaf v6-access-list {
            type string;
            description
              "Ipv6 Access-list name";
          }
          leaf context-name {
            type string;
            description
              "Context name";
          }
        }
      }
      container trap-hosts {
        description
          "Specify hosts to receive fully secure SNMP
           notifications";
        list trap-host {
          key "ip-address";
          description
            "Specify hosts to receive fully secure SNMP
             notifications";
          container inform-host {
            description
              "Container class for defining notification
               type for a secure inform host";
            container inform-user-communities {
              description
                "Container class for defining plain secure
                 communities for an inform host";
              list inform-user-community {
                key "community-name";
                description
                  "Plain secure community name associated with
                   an inform host";
                leaf community-name {
                  type xr:Cisco-ios-xr-string {
                    length "1..128";
                  }
                  description
                    "SNMPv3 user";
                }
                leaf port {
                  type xr:Cisco-ios-xr-port-number;
                  description
                    "UDP port number";
                }
                leaf version {
                  type string;
                  mandatory true;
                  description
                    "SNMP Version to be used secure-v3";
                }
                leaf security-level {
                  type Snmp-security-model;
                  mandatory true;
                  description
                    "Security level to be used auth/priv";
                }
                leaf basic-trap-types {
                  type uint32;
                  mandatory true;
                  description
                    "Basic trap type bitmap";
                }
                leaf advanced-trap-types1 {
                  type uint32;
                  mandatory true;
                  description
                    "Advanced trap type bitmap 1";
                }
                leaf advanced-trap-types2 {
                  type uint32;
                  mandatory true;
                  description
                    "Advanced trap type bitmap 2";
                }
                leaf dying-gasp {
                  type boolean;
                  description
                    "Enable dying gasp trap for this host";
                }
              }
            }
            container inform-type6-encrypted-user-communities {
              description
                "Container class for defining secure type6
                 communities for an inform host";
              list inform-type6-encrypted-user-community {
                key "community-name";
                description
                  "Secure type6 community name associated with
                   an inform host";
                leaf community-name {
                  type xr:Cisco-ios-xr-string;
                  description
                    "SNMPv3 user";
                }
                leaf port {
                  type xr:Cisco-ios-xr-port-number;
                  description
                    "UDP port number";
                }
                leaf version {
                  type string;
                  mandatory true;
                  description
                    "SNMP Version to be used secure-v3";
                }
                leaf security-level {
                  type Snmp-security-model;
                  mandatory true;
                  description
                    "Security level to be used auth/priv";
                }
                leaf basic-trap-types {
                  type uint32;
                  mandatory true;
                  description
                    "Basic trap type bitmap";
                }
                leaf advanced-trap-types1 {
                  type uint32;
                  mandatory true;
                  description
                    "Advanced trap type bitmap 1";
                }
                leaf advanced-trap-types2 {
                  type uint32;
                  mandatory true;
                  description
                    "Advanced trap type bitmap 2";
                }
                leaf dying-gasp {
                  type boolean;
                  description
                    "Enable dying gasp trap for this host";
                }
              }
            }
          }
          container type6-encrypted-user-communities {
            description
              "Container class for defining secure type6
               communities for a trap host";
            list type6-encrypted-user-community {
              key "community-name";
              description
                "Secure type6 community name associated with
                 a trap host";
              leaf community-name {
                type xr:Cisco-ios-xr-string;
                description
                  "SNMPv3 user";
              }
              leaf port {
                type xr:Cisco-ios-xr-port-number;
                description
                  "UDP port number";
              }
              leaf version {
                type string;
                mandatory true;
                description
                  "SNMP Version to be used secure-v3";
              }
              leaf security-level {
                type Snmp-security-model;
                mandatory true;
                description
                  "Security level to be used auth/priv";
              }
              leaf basic-trap-types {
                type uint32;
                mandatory true;
                description
                  "Basic trap type bitmap";
              }
              leaf advanced-trap-types1 {
                type uint32;
                mandatory true;
                description
                  "Advanced trap type bitmap 1";
              }
              leaf advanced-trap-types2 {
                type uint32;
                mandatory true;
                description
                  "Advanced trap type bitmap 2";
              }
              leaf dying-gasp {
                type boolean;
                description
                  "Enable dying gasp trap for this host";
              }
            }
          }
          container default-user-communities {
            description
              "Container class for defining plain secure
               communities for a trap host";
            list default-user-community {
              key "community-name";
              description
                "Plain secure community name associated with
                 a trap host";
              leaf community-name {
                type xr:Cisco-ios-xr-string {
                  length "1..128";
                }
                description
                  "SNMPv3 user";
              }
              leaf port {
                type xr:Cisco-ios-xr-port-number;
                description
                  "UDP port number";
              }
              leaf version {
                type string;
                mandatory true;
                description
                  "SNMP Version to be used secure-v3";
              }
              leaf security-level {
                type Snmp-security-model;
                mandatory true;
                description
                  "Security level to be used auth/priv";
              }
              leaf basic-trap-types {
                type uint32;
                mandatory true;
                description
                  "Basic trap type bitmap";
              }
              leaf advanced-trap-types1 {
                type uint32;
                mandatory true;
                description
                  "Advanced trap type bitmap 1";
              }
              leaf advanced-trap-types2 {
                type uint32;
                mandatory true;
                description
                  "Advanced trap type bitmap 2";
              }
              leaf dying-gasp {
                type boolean;
                description
                  "Enable dying gasp trap for this host";
              }
            }
          }
          leaf ip-address {
            type inet:ip-address-no-zone;
            description
              "IP address of SNMP notification host";
          }
        }
      }
      container users {
        description
          "Define a fully secure user who can access the
           SNMP engine";
        list user {
          key "user-name";
          description
            "Name of the fully secure SNMPv3 user";
          leaf user-name {
            type string;
            description
              "Name of the user";
          }
          leaf group-name {
            type string;
            mandatory true;
            description
              "Group to which the user belongs";
          }
          leaf version {
            type User-snmp-version;
            mandatory true;
            description
              "SNMP version to be used. secure-v3";
          }
          leaf authentication-password-configured {
            type empty;
            mandatory true;
            description
              "Flag to indicate that authentication password
               is configured";
          }
          leaf algorithm {
            type User-hash-algorithm;
            description
              "The algorithm used sha-224 or above";
          }
          leaf authentication-password {
            type xr:Proprietary-password;
            description
              "The authentication password";
          }
          leaf privacy-password-configured {
            type empty;
            mandatory true;
            description
              "Flag to indicate that the privacy password is
               configured";
          }
          leaf priv-algorithm {
            type User-priv-algorithm;
            description
              "The algorithm used aes128 or aes192 or aes256";
          }
          leaf privacy-password {
            type xr:Proprietary-password;
            description
              "The privacy password";
          }
          leaf v4acl-type {
            type Snmpacl;
            description
              "Access-list type";
          }
          leaf v4-access-list {
            type string;
            description
              "Ipv4 Access-list name";
          }
          leaf v6acl-type {
            type Snmpacl;
            description
              "Access-list type";
          }
          leaf v6-access-list {
            type string;
            description
              "Ipv6 Access-list name";
          }
          leaf owner {
            type Snmp-owner-access;
            description
              "The system access either SDROwner or
               SystemOwner";
          }
          leaf remote-address {
            type inet:ip-address-no-zone;
            description
              "IP address of remote SNMP entity";
          }
          leaf port {
            type xr:Cisco-ios-xr-port-number;
            description
              "UDP port number";
          }
          leaf user-auth-type {
            type uint32;
            mandatory true;
            description
              "User Authentication Type";
          }
          leaf user-priv-auth-type {
            type uint32;
            mandatory true;
            description
              "User Priv Authentication Type";
          }
        }
      }
    }
  }
}
