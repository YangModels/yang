module Cisco-IOS-XR-controller-ots-oper {
  namespace "http://cisco.com/ns/yang/Cisco-IOS-XR-controller-ots-oper";
  prefix controller-ots-oper;

  import Cisco-IOS-XR-types {
    prefix xr;
  }
  import cisco-semver {
    prefix semver;
  }
  include Cisco-IOS-XR-controller-ots-oper-sub1 {
    revision-date 2026-07-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ots package operational data.
     
     This module contains definitions
     for the following management objects:
       ots-oper: Ots operational data
     
     Copyright (c) 2013-2026 by Cisco Systems, Inc.
     All rights reserved.";

  revision 2026-07-15 {
    description
      "Updated OTDR long scan region description from 150 km to 160 km
       2026-06-16
         Added RX Low Threshold Current
       2026-05-25
         Updated PSM selected-switching-criteria from Channel power to Signal power
       2026-03-31
         Updated PSM switching-type enum values
       2026-03-04
         Added support for PSM oper params
       2025-12-02
         Added new field power_state in ots_raman_tx_power to support raman pump state";
    semver:module-version "1.1.0";
  }
  revision 2025-11-18 {
    description
      "Updated description for tx_power and rx_power";
    semver:module-version "1.0.0";
  }
  revision 2025-09-25 {
    description
      "Change ampli gain fields from uint32 to int32";
  }
  revision 2025-06-05 {
    description
      "Added raman-6-low-pwr, raman-7-low-pwr, raman-6-high-pwr and raman-7-high-pwr";
  }
  revision 2025-05-29 {
    description
      "Added Raman Auto Laser Shut Parameter for Ots Controller";
  }
  revision 2025-04-09 {
    description
      "Added ingress-ampli-tx-psd and egress-ampli-rx-psd & removed ingress-ampli-tx-power and egress-ampli-rx-power";
  }
  revision 2024-10-15 {
    description
      "Added last link flap field";
  }
  revision 2024-10-01 {
    description
      "Added ingress-ampli-laser-off and egress-ampli-laser-off";
  }
  revision 2024-09-12 {
    description
      "Added otdr-info-baseline-rx,otdr-info-baseline-tx,otdr-multiregion-baseline-info-rx, otdr-multiregion-baseline-info-tx in ots-edm-info container";
  }
  revision 2024-08-26 {
    description
      "Added new param baseline to support OTDR Baseline info";
  }
  revision 2023-12-07 {
    description
      "Added new enum definition for C+L band type";
  }
  revision 2023-06-23 {
    description
      "Added new enum definition Excess-Attenuation and optical-return-loss leaf for OTDR";
  }
  revision 2023-04-27 {
    description
      "Parameter raman-br-ratio, egress-ampli-br-power, egress-ampli-br-ratio are added in ots_edm_info container";
  }
  revision 2023-02-06 {
    description
      "Amplifier Control Mode introduced in OTS-EDM-INFO group";
  }
  revision 2023-01-18 {
    description
      "Leaves egress-ampli-working-mode-config, ingress-ampli-working-mode-config, egress-ampli-working-mode, ingress-ampli-working-mode and ingress-ampli-power-config added. Leaf egress-ampli-power renamed to egress-ampli-power-config.";
  }
  revision 2022-12-16 {
    description
      "OTS-TRANSCEIVER-DATA group, leaf form-factor, leaf temperature, leaf voltage are introduced in OTS-EDM-INFO group";
  }
  revision 2022-11-17 {
    description
      "description leaf added in container optics-lane";
  }
  revision 2022-10-17 {
    description
      "Egress Amplifier Power, OTS egress amplifier power added";
  }
  revision 2022-08-30 {
    description
      "Egress Amplifier BR Ratio, OTS Port Type and Raman BR Ratio are added in ots-info container";
  }
  revision 2022-06-13 {
    description
      "channel-attenuation-info container separated out from ots info container";
  }
  revision 2022-04-25 {
    description
      "Units added for channel frequency in ots bag.";
  }
  revision 2022-04-18 {
    description
      "ots_och_alarm_info is converted to a pointer";
  }
  revision 2022-03-25 {
    description
      "Units changed for location and accuracy leaf nodes in otdr-info-rx and otdr-info-tx containers.";
  }
  revision 2022-03-15 {
    description
      "Units added for some leaf nodes in spectrum-info, channel-attenuation-info, raman-tx-power and ots_info containers.";
  }
  revision 2022-03-07 {
    description
      "Removed Low-Tx-PWR information for ots controller";
  }
  revision 2022-02-22 {
    description
      "Name of the enum led_state is changed to LedState";
  }
  revision 2022-01-13 {
    description
      "raman-tx-power range extended in ots controller";
  }
  revision 2021-12-23 {
    description
      "Parameters egress_ampli_br, egress_ampli_br_high_th_cfgd, egress_ampli_br_cfgd, raman_br, raman_br_cfgd and raman_br_high_th_cfgd are removed from ots_ui bag";
  }
  revision 2021-12-10 {
    description
      "led_state parameter added for OTS controller";
  }
  revision 2021-12-08 {
    description
      "Added alarms and counters for OTS, OTS-OCH, OSC, DFB, OMS, OCH controllers.";
  }
  revision 2021-12-01 {
    description
      "Parameters br_power and raman_br_power are added in ots_edm_info container";
  }
  revision 2021-11-19 {
    description
      "led_state container and parameters controller_state, led_state are added for OCH and OMS controllers";
  }
  revision 2021-11-13 {
    description
      "Config container added for Raman TX power in OTS controller";
  }
  revision 2021-10-25 {
    description
      "Parameters lower_frequency, upper_frequency, rx_psd and tx_psd are removed and data type of rx_power and tx_power is changed to int16_t in ots_edm_spectrum_power_info_v1 bag and first_slice_frequency added in ots_edm_spectrum_info_v1 bag";
  }
  revision 2021-09-16 {
    description
      "parameter chan_atten_first_slice_freq added in the ots_edm_chan_atten_info bag";
  }
  revision 2021-09-01 {
    description
      "Changed otdr_event_type enum definition";
  }
  revision 2021-08-23 {
    description
      "Added OTS OTDR oper support";
  }
  revision 2021-06-14 {
    description
      "Added support for Channel Slice Attenuation Info and Spectrum Info";
  }
  revision 2021-03-28 {
    description
      "egress-ampli-br, egress-ampli-br-high-th-cfgd, egress-ampli-br-cfgd are added in ots-info container";
  }
  revision 2021-02-17 {
    description
      "Raman Safety Params added";
  }
  revision 2021-02-08 {
    description
      "Ingress/Egress Safety Params added";
  }
  revision 2020-11-10 {
    description
      "Photodiode State Params Added for Ots Controller";
  }
  revision 2020-09-02 {
    description
      "Raman Transmit Params Added for Ots Controller";
  }
  revision 2020-08-21 {
    description
      "New Oper Model Added for Ots Controller";
  }
  revision 2019-04-05 {
    description
      "Establish semantic version baseline.";
  }
  revision 2015-11-09 {
    description
      "IOS XR 6.0 revision.";
  }

  container ots-oper {
    config false;
    description
      "Ots operational data";
    container ots-ports {
      description
        "All Ots Port operational data";
      list ots-port {
        key "name";
        description
          "Ots operational data";
        container ots-channel-attenuation-info {
          description
            "Ots Channel Slice Attenuation Operational data";
          uses OTS-EDM-CHAN-ATTEN-INFO;
        }
        container ots-info {
          description
            "Ots operational data";
          uses OTS-EDM-INFO;
        }
        container ots-psm-status-info {
          description
            "Ots PSM Status Operational data";
          uses OTS-EDM-PSM-STATUS-INFO;
        }
        container ots-spectrum-info {
          description
            "Ots Spectrum Operational data";
          uses OTS-EDM-SPECTRUM-BAG-INFO;
        }
        leaf name {
          type xr:Interface-name;
          description
            "Port name";
        }
      }
    }
  }
}
