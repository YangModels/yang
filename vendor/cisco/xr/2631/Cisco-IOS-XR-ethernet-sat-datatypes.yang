module Cisco-IOS-XR-ethernet-sat-datatypes {
  namespace "http://cisco.com/ns/yang/Cisco-IOS-XR-ethernet-sat-datatypes";
  prefix ethernet-sat-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2022 by Cisco Systems, Inc.
     All rights reserved.";

  revision 2022-12-13 {
    description
      "Add support for configuring the ethertype used in SAT packets";
    semver:module-version "1.1.0";
  }
  revision 2019-04-05 {
    description
      "Establish semantic version baseline.";
    semver:module-version "1.0.0";
  }
  revision 2015-11-09 {
    description
      "IOS XR 6.0 revision.";
  }

  typedef Sat-direction {
    type enumeration {
      enum "external" {
        value 1;
        description
          "External direction";
      }
      enum "internal" {
        value 2;
        description
          "Internal direction";
      }
    }
    description
      "Sat direction";
  }

  typedef Sat-inf-rate-units {
    type enumeration {
      enum "kbps" {
        value 1;
        description
          "Kb/s";
      }
      enum "mbps" {
        value 2;
        description
          "Mb/s";
      }
      enum "gbps" {
        value 3;
        description
          "Gb/s";
      }
    }
    description
      "Sat inf rate units";
  }

  typedef Measurement-option {
    type enumeration {
      enum "combined" {
        value 1;
        description
          "Combined";
      }
    }
    description
      "Measurement option";
  }

  typedef Sat-cbs-unites {
    type enumeration {
      enum "kb" {
        value 1;
        description
          "KB";
      }
      enum "mb" {
        value 2;
        description
          "MB";
      }
      enum "gb" {
        value 3;
        description
          "GB";
      }
    }
    description
      "Sat cbs unites";
  }

  typedef Sat-mode {
    type enumeration {
      enum "two-way" {
        value 2;
        description
          "Two way";
      }
    }
    description
      "Sat mode";
  }

  typedef Sat-l2cp-ether {
    type enumeration {
      enum "msrp" {
        value 1;
        description
          "MSRP";
      }
      enum "stp" {
        value 2;
        description
          "STP";
      }
      enum "pfc" {
        value 3;
        description
          "PFC";
      }
      enum "lacp" {
        value 4;
        description
          "LACP";
      }
      enum "link-oam" {
        value 5;
        description
          "Link OAM";
      }
      enum "esmc" {
        value 6;
        description
          "ESMC";
      }
      enum "pnac" {
        value 7;
        description
          "PNAC";
      }
      enum "lldp" {
        value 8;
        description
          "LLDP";
      }
      enum "e-lmi" {
        value 9;
        description
          "E LMI";
      }
      enum "mvrp" {
        value 10;
        description
          "MVRP";
      }
      enum "mmrp" {
        value 11;
        description
          "MMRP";
      }
      enum "ptp" {
        value 12;
        description
          "PTP";
      }
      enum "mirp" {
        value 13;
        description
          "MIRP";
      }
      enum "vdp" {
        value 14;
        description
          "VDP";
      }
      enum "pe-csp" {
        value 15;
        description
          "PE CSP";
      }
    }
    description
      "Sat l2cp ether";
  }

  typedef Packet-format {
    type enumeration {
      enum "lbm" {
        value 1;
        description
          "LBMs";
      }
    }
    description
      "Packet format";
  }

  typedef Sat-duration-units {
    type enumeration {
      enum "minutes" {
        value 1;
        description
          "Duration in minutes";
      }
      enum "hours" {
        value 2;
        description
          "Duration in hours";
      }
    }
    description
      "Sat duration units";
  }

  typedef Sat-permit {
    type enumeration {
      enum "internal-only" {
        value 1;
        description
          "Only internal permitted";
      }
      enum "external-only" {
        value 2;
        description
          "Only external permitted";
      }
      enum "all-permitted" {
        value 3;
        description
          "Internal and external permitted";
      }
    }
    description
      "Sat permit";
  }
}
