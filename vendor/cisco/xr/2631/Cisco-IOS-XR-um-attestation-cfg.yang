module Cisco-IOS-XR-um-attestation-cfg {
  yang-version 1.1;
  namespace "http://cisco.com/ns/yang/Cisco-IOS-XR-um-attestation-cfg";
  prefix um-attestation-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     Attestation Agent configuration.
     
     Copyright (c) 2020-2026 by Cisco Systems, Inc., and/or its affiliates.
     All rights reserved.";

  revision 2026-03-25 {
    description
      "Update to align with latest IOS-XR YANG quality guidelines.";
    semver:module-version "2.0.0";
  }
  revision 2020-09-10 {
    description
      "Initial release";
    semver:module-version "1.0.0";
  }

  container attestation {
    description
      "Attestation Agent configuration";
    container runtime-integrity {
      description
        "IMA related configuration";
      container cache {
        description
          "IMA cache related configuration";
        container job {
          description
            "Cache CRON job related configuration";
          leaf interval {
            type uint16 {
              range "5..1440";
            }
            units "minutes";
            must "(. >= 60 and . mod 60 = 0) or (. < 60 and 60 mod . = 0)" {
              error-message "Interval must be a multiple or factor of 60";
            }
            description
              "Time interval for the CRON job";
          }
          leaf disable {
            type empty;
            description
              "Disable the IMA Cache CRON job";
          }
        }
      }
    }
  }
}
