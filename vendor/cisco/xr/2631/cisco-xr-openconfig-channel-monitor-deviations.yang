//*************  DO-NOT EDIT  **************
//*********** Auto-generated file ********** 

module cisco-xr-openconfig-channel-monitor-deviations {

    prefix  "oc-chan-monitordevs";

    namespace "http://cisco.com/ns/yang/cisco-xr-openconfig-channel-monitor-deviations";

    import openconfig-channel-monitor { prefix oc-chan-monitor; }

    organization "Cisco Systems, Inc.";

    contact
        "Cisco Systems, Inc.
        Customer Service

        Postal: 170 West Tasman Drive
        San Jose, CA 95134

        Tel: +1 800 553-NETS

        E-mail: cs-yang@cisco.com";

    description
        "This module contains a set of deviations for 

        openconfig-channel-monitor.yang@2019-10-24

        on Cisco IOS-XR devices.

        Copyright (c) 2017, 2024 by Cisco Systems, Inc.
        All rights reserved.";

    revision "2024-11-20" {
        description
        "Initial revision applicable to IOS-XR 6.4.1";
    }

  deviation /oc-chan-monitor:channel-monitors/oc-chan-monitor:channel-monitor/oc-chan-monitor:config/oc-chan-monitor:name {
    deviate not-supported;
  }
  deviation /oc-chan-monitor:channel-monitors/oc-chan-monitor:channel-monitor/oc-chan-monitor:config/oc-chan-monitor:monitor-port {
    deviate not-supported;
  }
  deviation /oc-chan-monitor:channel-monitors/oc-chan-monitor:channel-monitor/oc-chan-monitor:channels/oc-chan-monitor:channel/oc-chan-monitor:state/oc-chan-monitor:target-power {
    deviate not-supported;
  }

}
//total deviations:3
