submodule Cisco-IOS-XR-linux-os-heap-summary-oper-sub1 {
  belongs-to Cisco-IOS-XR-linux-os-heap-summary-oper {
    prefix Cisco-IOS-XR-linux-os-heap-summary-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR linux-os-heap-summary package operational data.
     
     Copyright (c) 2013-2026 by Cisco Systems, Inc.
     All rights reserved.";

  revision 2026-03-11 {
    description
      "Adding chunk-mmap leaf in heap summary output.";
    semver:module-version "2.1.0";
  }
  revision 2021-04-16 {
    description
      "Structuring the yang response of show memory heap summary all.";
    semver:module-version "2.0.0";
  }
  revision 2019-04-05 {
    description
      "Establish semantic version baseline.";
    semver:module-version "1.0.1";
  }
  revision 2015-11-09 {
    description
      "IOS XR 6.0 revision.";
  }

  grouping SHOW-MEM-HEAP-SUM-YANG {
    description
      "Heap memory summary info for each process";
    leaf heap-size {
      type uint64;
      description
        "Heap Size";
    }
    leaf alloc-mem {
      type uint64;
      description
        "Allocated Memory";
    }
    leaf free-mem {
      type uint64;
      description
        "Free Memory";
    }
    leaf over-head {
      type uint64;
      description
        "Over Head";
    }
    leaf allocs {
      type uint64;
      description
        "Allocs";
    }
    leaf frees {
      type uint64;
      description
        "Frees";
    }
    leaf chunkmmap {
      type uint64;
      description
        "Chunk Mmap";
    }
  }
}
