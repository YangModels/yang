module Cisco-IOS-XR-drivers-media-eth-oper {
  namespace "http://cisco.com/ns/yang/Cisco-IOS-XR-drivers-media-eth-oper";
  prefix drivers-media-eth-oper;

  import Cisco-IOS-XR-types {
    prefix xr;
  }
  import cisco-semver {
    prefix semver;
  }
  include Cisco-IOS-XR-drivers-media-eth-oper-sub1 {
    revision-date 2021-12-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-media-eth package operational data.
     
     This module contains definitions
     for the following management objects:
       ethernet-interface: Ethernet operational data
     
     Copyright (c) 2013-2021 by Cisco Systems, Inc.
     All rights reserved.";

  revision 2021-12-14 {
    description
      "Start timestamp and validity support added for ethernet ports.
       2021-11-24
         Updated media type string
       2021-10-05
         Insert Idle support added for ethernet controllers.
       2021-09-30
         Added new Ethernet media type definition.";
    semver:module-version "3.0.0";
  }
  revision 2021-09-29 {
    description
      "Removed list rx_drop_data_frames_per_tc and added leaf total_rx_drop_data_frames.
       2021-08-24
          Support added for last data time for generic stats.
       2021-08-16
          Added new Ethernet media type definition.
       2021-07-19
          Removed leaf total_rx_drop_data_frames and added list rx_drop_data_frames_per_tc to maintain backward compatibility.
       2021-07-01
          Support added for hardware timestamp for generic stats.";
    semver:module-version "2.1.0";
  }
  revision 2021-02-12 {
    description
      "Added support for PFC per TC Rx drop Data Frames.
       2020-11-04
           Added support for SER alarms.
       2020-09-08
           Added new ethernet speed values.";
    semver:module-version "2.0.0";
  }
  revision 2020-02-19 {
    description
      "Description updated.
       2019-11-27
         Adding operational value for power m-factor.
       2019-08-15
         Adding PFC watchdog support.";
    semver:module-version "1.2.0";
  }
  revision 2019-05-21 {
    description
      "Added new leaf for frame preemption configuration.";
    semver:module-version "1.1.0";
  }
  revision 2019-04-05 {
    description
      "Establish semantic version baseline.";
    semver:module-version "1.0.0";
  }
  revision 2017-05-01 {
    description
      "Fixing backward compatibility error in module.";
  }
  revision 2017-04-04 {
    description
      "Added new fields to phy data.";
  }
  revision 2015-01-07 {
    description
      "IOS XR 5.3.1 revision.";
  }

  container ethernet-interface {
    config false;
    description
      "Ethernet operational data";
    container statistics {
      description
        "Ethernet controller statistics table";
      list statistic {
        key "interface-name";
        description
          "Ethernet statistics information";
        leaf interface-name {
          type xr:Interface-name;
          description
            "The name of the interface";
        }
        uses ETHERNET-L2-CONTROLLER-STATS;
      }
    }
    container interfaces {
      description
        "Ethernet controller info table";
      list interface {
        key "interface-name";
        description
          "Ethernet controller information";
        leaf interface-name {
          type xr:Interface-name;
          description
            "The name of the interface";
        }
        uses ETHERNET-CONTROLLER-DRIVER-BAG-V2-TYPE;
      }
    }
    container berts {
      description
        "Ethernet controller BERT table";
      list bert {
        key "interface-name";
        description
          "Ethernet BERT information";
        leaf interface-name {
          type xr:Interface-name;
          description
            "The name of the interface";
        }
        uses ETH-SHOWCTRL-BERT;
      }
    }
  }
}
