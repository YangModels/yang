submodule Cisco-IOS-XR-event-manager-policy-map-oper-sub1 {
  belongs-to Cisco-IOS-XR-event-manager-policy-map-oper {
    prefix Cisco-IOS-XR-event-manager-policy-map-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR event-manager-policy-map package operational data.
     
     Copyright (c) 2013-2022 by Cisco Systems, Inc.
     All rights reserved.";

  revision 2022-01-11 {
    description
      "IOS XR 7.7.1 revision.";
    semver:module-version "1.0.0";
  }
  revision 2019-04-05 {
    description
      "Establish semantic version baseline.";
  }
  revision 2015-11-09 {
    description
      "IOS XR 6.0 revision.";
  }

  grouping EEM-EVENT-MAPPING-INFO {
    description
      "Policy-Event map detail info";
    leaf event-name {
      type string;
      description
        "Event Name";
    }
    leaf event-status {
      type string {
        length "0..15";
      }
      description
        "Event Status";
    }
    leaf corr-status {
      type boolean;
      description
        "Event Correlation Status";
    }
    leaf reset-time {
      type uint32;
      description
        "Event Reset time";
    }
  }

  grouping EEM-POLICY-DETAIL-BAG {
    description
      "Policy detail info";
    leaf policy-name-xr {
      type string;
      description
        "Policy Name";
    }
    leaf policy-status {
      type string;
      description
        "Policy Status";
    }
    leaf policy-occurrence {
      type string;
      description
        "Policy Occurs";
    }
    leaf policy-period {
      type string;
      description
        "Policy Period";
    }
    leaf policy-triggered-count {
      type uint32;
      description
        "Trigger Count";
    }
    leaf event-count {
      type uint32;
      description
        "Event Count";
    }
    leaf action-count {
      type uint32;
      description
        "Action Count";
    }
    leaf multi-event-policy {
      type boolean;
      description
        "Multi-event Policy";
    }
    leaf current-correlation-state {
      type boolean;
      description
        "Current Correlation state";
    }
    leaf multi-event-string {
      type string;
      description
        "Multi Event String";
    }
    list policy-event-map {
      description
        "Policy-Event Mapping";
      uses EEM-EVENT-MAPPING-INFO;
    }
    list policy-action-map {
      description
        "Policy-Action Mapping";
      uses EEM-ACTION-MAPPING-INFO;
    }
  }

  grouping EEM-EVENT-TELEMETRY-DETAIL-BAG {
    description
      "Event Telemetry detail info";
    leaf sensor-path {
      type string;
      description
        "Sensor Path";
    }
    leaf sample-interval {
      type uint64;
      description
        "Sample Interval";
    }
  }

  grouping EEM-EVENT-TRACK-DETAIL-BAG {
    description
      "Event Timer detail info";
    leaf track-name {
      type string;
      description
        "Track Name";
    }
    leaf track-state {
      type string;
      description
        "Track State";
    }
  }

  grouping EEM-EVENT-TIMER-WD-DETAIL-BAG {
    description
      "Event Timer watchdog detail info";
    leaf timer-value {
      type uint64;
      description
        "Timer Value";
    }
  }

  grouping EEM-EVENT-TIMER-CRON-DETAIL-BAG {
    description
      "Event Timer cron detail info";
    leaf cron-entry {
      type string;
      description
        "Cron Entry";
    }
  }

  grouping EEM-EVENT-TIMER-DETAIL-BAG {
    description
      "Event Timer detail info";
    container cron-info {
      description
        "cron info";
      uses EEM-EVENT-TIMER-CRON-DETAIL-BAG;
    }
    container wd-info {
      description
        "wd info";
      uses EEM-EVENT-TIMER-WD-DETAIL-BAG;
    }
    leaf timer-type {
      type string;
      description
        "Timer Type";
    }
  }

  grouping EEM-EVENT-SYSLOG-DETAIL-BAG {
    description
      "Event Syslog detail info";
    leaf pattern {
      type string;
      description
        "Event Syslog Pattern";
    }
    leaf severity {
      type string;
      description
        "Event Severity info";
    }
  }

  grouping EEM-EVENT-DETAIL-BAG {
    description
      "Event policy detail info";
    container event-syslog-info {
      description
        "Event Syslog Info";
      uses EEM-EVENT-SYSLOG-DETAIL-BAG;
    }
    container event-timer-info {
      description
        "Event Timer Info";
      uses EEM-EVENT-TIMER-DETAIL-BAG;
    }
    container event-track-info {
      description
        "Event Track Info";
      uses EEM-EVENT-TRACK-DETAIL-BAG;
    }
    container event-telemetry-info {
      description
        "Event Telemetry Info";
      uses EEM-EVENT-TELEMETRY-DETAIL-BAG;
    }
    leaf event-name-xr {
      type string;
      description
        "Event Name";
    }
    leaf event-status {
      type string;
      description
        "Event Status";
    }
    leaf event-type {
      type string;
      description
        "Event type";
    }
    leaf eventesid {
      type uint32;
      description
        "Event Spec ID";
    }
    leaf event-occurrence {
      type string;
      description
        "Event Occurrence";
    }
    leaf event-period {
      type string;
      description
        "Event Period";
    }
    leaf rate-limit {
      type uint32;
      description
        "Rate limit";
    }
    leaf event-triggered-count {
      type uint32;
      description
        "Event Trigger Count";
    }
    leaf event-policy-reg-count {
      type uint32;
      description
        "Event Policy Registration Count";
    }
    list event-policy-map {
      description
        "Event Policy Mapping";
      uses EEM-POLICY-MAPPING-INFO;
    }
  }

  grouping EEM-POLICY-MAPPING-INFO {
    description
      "Event policy mapping info";
    leaf policy-name {
      type string;
      description
        "Policy Name";
    }
  }

  grouping EEM-ACTION-DETAIL-BAG {
    description
      "Action policy detail info";
    leaf action-name-xr {
      type string;
      description
        "Action Name";
    }
    leaf script-name {
      type string;
      description
        "Script Name";
    }
    leaf action-type {
      type string;
      description
        "Action Type";
    }
    leaf triggered-count {
      type uint32;
      description
        "Triggered Count";
    }
    leaf policy-count {
      type uint32;
      description
        "Policy Count";
    }
    leaf max-run {
      type uint32;
      description
        "Max Run";
    }
    leaf checksum-enabled {
      type string {
        length "0..15";
      }
      description
        "Checksum enabled";
    }
    leaf last-run-status {
      type string;
      description
        "Script last run status";
    }
    leaf user-name {
      type string;
      description
        "User Name";
    }
    leaf checksum-string {
      type string;
      description
        "Checksum String";
    }
    list action-policy-map {
      description
        "Action Policy Mapping";
      uses EEM-POLICY-MAPPING-INFO;
    }
  }

  grouping EEM-ACTION-MAPPING-INFO {
    description
      "Policy-Action map detail info";
    leaf action-name {
      type string;
      description
        "Action Name";
    }
    leaf checksum-enabled {
      type string {
        length "0..15";
      }
      description
        "Checksum Enabled";
    }
  }

  grouping EEM-SCRIPT-BAG {
    description
      "Script action mapping";
    leaf script-name-xr {
      type string;
      description
        "Script Name";
    }
    list policy-action-map {
      description
        "Script-Action Mapping";
      uses EEM-ACTION-MAPPING-INFO;
    }
  }
}
