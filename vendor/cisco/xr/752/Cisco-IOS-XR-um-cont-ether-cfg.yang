module Cisco-IOS-XR-um-cont-ether-cfg {
  namespace "http://cisco.com/ns/yang/Cisco-IOS-XR-um-cont-ether-cfg";
  prefix um-cont-ether-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-ether package configuration.
     
     This YANG module augments the
     modules with configuration data.
     
     Copyright (c) 2021 by Cisco Systems, Inc.
     All rights reserved.";

  revision 2021-05-07 {
    description
      "Initial release";
    semver:module-version "1.0.0";
  }

  grouping CONT-BODY {
    container flow-control {
      description
        "Ethernet controller flow control";
      container ingress {
        presence "Indicates a ingress node is configured.";
        description
          "Set the flow control parameter to ingress";
      }
    }
    container perf-mon {
      description
        "Performance Monitoring";
      container disable {
        presence "Indicates a disable node is configured.";
        description
          "Disable performance monitoring";
      }
    }
    leaf loopback {
      type enumeration {
        enum "external" {
          value 0;
          description
            "Enable external loopback (requires loopback connector)";
        }
        enum "internal" {
          value 1;
          description
            "Enable internal loopback";
        }
        enum "line" {
          value 2;
          description
            "Enable line loopback";
        }
      }
      description
        "Set the loopback mode on a controller";
    }
    container laser-squelch {
      presence "Indicates a laser-squelch node is configured.";
      description
        "Enable Ethernet controller laser-squelch";
    }
    leaf fec {
      type enumeration {
        enum "none" {
          value 0;
          description
            "Disable any FEC enabled on the interface";
        }
        enum "standard" {
          value 1;
          description
            "Set the standard (Reed-Solomon) FEC";
        }
      }
      description
        "Set the Forward Error Correction mode on a controller";
    }
    container holdoff-time {
      description
        "Holdoff time configuration";
      leaf trunk-fault {
        type uint32 {
          range "0..3000" {
            description
              "Time in ms";
          }
        }
        description
          "Holdoff time trunk fault configuration";
      }
    }
    container extended-loopback {
      description
        "Extended loopback (diagnostics)";
      container levels {
        description
          "Level at which to loopback";
        list level {
          key "level-id";
          description
            "Level at which to loopback";
          leaf level-id {
            type uint32 {
              range "1..3" {
                description
                  "";
              }
            }
            description
              "Level at which to loopback";
          }
        }
      }
    }
  }

  augment "/a1:interfaces/a1:controller" {
    uses CONT-BODY;
  }
  augment "/a1:interfaces/a1:controller-preconfigure" {
    uses CONT-BODY;
  }
}
