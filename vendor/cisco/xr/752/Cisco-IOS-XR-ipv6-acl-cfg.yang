module Cisco-IOS-XR-ipv6-acl-cfg {
  namespace "http://cisco.com/ns/yang/Cisco-IOS-XR-ipv6-acl-cfg";
  prefix ipv6-acl-cfg;

  import ietf-inet-types {
    prefix inet;
  }
  import Cisco-IOS-XR-types {
    prefix xr;
  }
  import cisco-semver {
    prefix semver;
  }
  import Cisco-IOS-XR-common-acl-datatypes {
    prefix dt1;
  }
  import Cisco-IOS-XR-ipv6-acl-datatypes {
    prefix dt2;
  }
  include Cisco-IOS-XR-ipv6-ace-cfg {
    revision-date 2021-09-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-acl package configuration.
     
     This module contains definitions
     for the following management objects:
       ipv6-acl-and-prefix-list: IPv6 ACL configuration data
     
     Copyright (c) 2013-2021 by Cisco Systems, Inc.
     All rights reserved.";

  revision 2021-09-20 {
    description
      "7.6.1 revision. Adding icmp-on for ace in the schema";
    semver:module-version "1.3.0";
  }
  revision 2021-06-20 {
    description
      "7.5.1 revision. Adding icmp-off in the schema
       2021-03-23
          7.5.1 revision. Changing bag version due to fragment-type addition.
       2021-03-17
          7.3.15 revision. Adding rsvp and vrrp keywords for protocols under access-list config CLI.";
    semver:module-version "1.3.0";
  }
  revision 2020-12-04 {
    description
      "7.4.1 revision. Fixing Remark Length
       2020-11-23
           7.3.2 revision. changing the bag version";
    semver:module-version "1.2.0";
  }
  revision 2019-10-22 {
    description
      "7.0.1 revision. Fixing ICMP TYPE CODE datatype from Enum to RangeEnum";
    semver:module-version "1.1.1";
  }
  revision 2019-04-05 {
    description
      "Establish semantic version baseline.";
    semver:module-version "1.0.0";
  }
  revision 2018-04-03 {
    description
      "6.5.1 revision. Correct enum value for Next-hop-type.";
  }
  revision 2018-03-23 {
    description
      "6.5.1 revision. Removing none-next-type.";
  }
  revision 2018-03-13 {
    description
      "6.5.1 revision. Using YANG bit types for tcp flags.";
  }
  revision 2018-01-03 {
    description
      "6.4.1 revision. Fixed a few typos in the description.";
  }
  revision 2015-11-09 {
    description
      "IOS XR 6.0 revision.";
  }

  container ipv6-acl-and-prefix-list {
    description
      "IPv6 ACL configuration data";
    container prefixes {
      description
        "Table of prefix lists";
      list prefix {
        key "name";
        description
          "Name of a prefix list";
        container prefix-list-entries {
          description
            "Sequence of entries forming a prefix list";
          list prefix-list-entry {
            key "sequence-number";
            description
              "A prefix list entry; either a description
               (remark) or a prefix to match against";
            leaf sequence-number {
              type dt1:Acl-sequence-number-range;
              description
                "Sequence number of prefix list";
            }
            leaf grant {
              type dt2:Ipv6-acl-grant-enum;
              description
                "Whether to forward or drop packets matching
                 the prefix list";
            }
            leaf ipv6-address-as-string {
              type string;
              description
                "The IPv6 address if entered  with the
                 ZoneMutually exclusive with Prefix and
                 PrefixMask";
            }
            leaf zone {
              type string;
              description
                "IPv6 Zone if entered  with the
                 IPV6AddressMutually exclusive with Prefix
                 and PrefixMask";
            }
            leaf prefix {
              type inet:ipv6-address-no-zone;
              description
                "IPv6 address prefix to match";
            }
            leaf prefix-mask {
              type xr:Ipv6-prefix-length;
              description
                "MaskLength of IPv6 address prefix";
            }
            leaf match-exact-length {
              type dt2:Ipv6-prefix-match-exact-length;
              description
                "Set to perform an exact prefix length match.
                 Item is mutually exclusive with minimum and
                 maximum length match items";
            }
            leaf exact-prefix-length {
              type xr:Ipv6-prefix-length;
              description
                "If exact prefix length matching specified,
                 set the length of prefix to be matched";
            }
            leaf match-max-length {
              type dt2:Ipv6-prefix-match-max-length;
              description
                "Set to perform a maximum length prefix match
                 .  Item is mutually exclusive with exact
                 length match item";
            }
            leaf max-prefix-length {
              type xr:Ipv6-prefix-length;
              description
                "If maximum length prefix matching specified,
                 set the maximum length of prefix to be
                 matched";
            }
            leaf match-min-length {
              type dt2:Ipv6-prefix-match-min-length;
              description
                "Set to perform a minimum length prefix match
                 .  Item is mutually exclusive with exact
                 length match item";
            }
            leaf min-prefix-length {
              type xr:Ipv6-prefix-length;
              description
                "If minimum length prefix matching specified,
                 set the minimum length of prefix to be
                 matched";
            }
            leaf remark {
              type dt2:Ipv6-acl-prefix-remark-name;
              description
                "Comments or a description for the prefix
                 list.  Item is mutually exclusive with all
                 others in the object";
            }
          }
        }
        leaf name {
          type dt2:Ipv6-acl-prefix-list-name;
          description
            "Name of a prefix list";
        }
      }
    }
    container log-update {
      description
        "Control access lists log updates";
      leaf threshold {
        type dt2:Ipv6-acl-log-threshold-range;
        description
          "Log update threshold (number of hits)";
      }
      leaf rate {
        type dt2:Ipv6-acl-log-rate-range;
        description
          "Log update rate (log messages per second)";
      }
    }
    container accesses {
      description
        "Table of access lists";
      list access {
        key "name";
        description
          "An ACL";
        container access-list-entries {
          description
            "ACL entry table; contains list of access list
             entries";
          list access-list-entry {
            key "sequence-number";
            description
              "An ACL entry; either a description (remark)
               or anAccess List Entry to match against";
            leaf sequence-number {
              type dt2:Ipv6-acl-sequence-number-range;
              description
                "Sequence number of access list entry";
            }
            uses IPV6-ACE;
          }
        }
        leaf name {
          type dt2:Ipv6-acl-prefix-list-name;
          description
            "Name of the access list";
        }
      }
    }
    leaf icmp-off {
      type empty;
      description
        "This is set to disable the icmpoff messages";
    }
  }
}
