submodule Cisco-IOS-XR-ofa-npu-stats-oper-sub1 {
  belongs-to Cisco-IOS-XR-ofa-npu-stats-oper {
    prefix Cisco-IOS-XR-ofa-npu-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-stats package operational data.
     
     Copyright (c) 2013-2021 by Cisco Systems, Inc.
     All rights reserved.";

  revision 2021-02-05 {
    description
      "Added src-interface show cmd changes";
    semver:module-version "3.0.0";
  }
  revision 2020-10-09 {
    description
      "Added task-id";
    semver:module-version "2.0.0";
  }
  revision 2020-06-25 {
    description
      "Updated task-name";
    semver:module-version "1.2.0";
  }
  revision 2019-12-14 {
    description
      "Updated date for npu stats model";
    semver:module-version "1.1.0";
  }
  revision 2019-04-05 {
    description
      "Establish semantic version baseline.";
    semver:module-version "1.0.0";
  }
  revision 2015-11-09 {
    description
      "IOS XR 6.0 revision.";
  }

  grouping DPA-TRAP-STATS {
    description
      "DPA TRAP STATS";
    leaf trap-strength {
      type uint32;
      description
        "Trap Strength of the trap";
    }
    leaf priority {
      type uint32;
      description
        "Priority of the trap";
    }
    leaf trap-id-xr {
      type uint32;
      description
        "Id of the trap";
    }
    leaf gport {
      type uint32;
      description
        "Gport of the trap";
    }
    leaf fec-id {
      type uint32;
      description
        "Fec id of the trap";
    }
    leaf policer-id {
      type uint32;
      description
        "Id of the policer on the trap";
    }
    leaf stats-id {
      type uint32;
      description
        "Stats Id of the trap";
    }
    leaf encap-id {
      type uint32;
      description
        "Encap Id of the trap";
    }
    leaf mc-group {
      type uint32;
      description
        "McGroup of the trap";
    }
    leaf trap-string {
      type string;
      description
        "Name String of the trap";
    }
    leaf id {
      type uint32;
      description
        "Id for internal use";
    }
    leaf offset {
      type uint64;
      description
        "Offset for internal use";
    }
    leaf npu-id {
      type uint64;
      description
        "NpuId on which trap is enabled";
    }
    leaf trap-action {
      type string;
      description
        "Action taken on the Trap";
    }
    leaf punt-vo-q {
      type uint32;
      description
        "Punt VoQ for the punted trap packet";
    }
    leaf punt-vlan {
      type uint16;
      description
        "Punt VLAN used for the trap";
    }
    leaf punt-tc {
      type uint8;
      description
        "Traffic class on the Punt VoQ";
    }
    leaf cfg-rate {
      type uint32;
      description
        "User configured rate in pps";
    }
    leaf cir-hw-rate {
      type uint32;
      description
        "Programmed HW Cir in pps";
    }
    leaf rate-units {
      type string;
      description
        "Policer level at NPU or IFG";
    }
    leaf avg-pkt-size {
      type uint32;
      units "bit/s";
      description
        "Avg packet size used for the trap with bps meter";
    }
    leaf packet-dropped {
      type uint64;
      description
        "Number of packets dropped after hitting the trap";
    }
    leaf packet-accepted {
      type uint64;
      description
        "Number of packets accepted after hitting the
         trap";
    }
  }

  grouping DPA-VOQ-INGRESS-PACKET-STATISTICS {
    description
      "DPA VOQ INGRESS PACKET STATISTICS";
    leaf received-bytes {
      type uint64;
      units "byte";
      description
        "Bytes Received on the port";
    }
    leaf received-packets {
      type uint64;
      description
        "Packets Received on the port";
    }
    leaf dropped-bytes {
      type uint64;
      units "byte";
      description
        "Bytes Dropped on the port";
    }
    leaf dropped-packets {
      type uint64;
      description
        "Packets Dropeed on the port";
    }
    leaf yellow-received-bytes {
      type uint64;
      units "byte";
      description
        "YBytes Received on the port";
    }
    leaf yellow-received-packets {
      type uint64;
      description
        "YPackets Received on the port";
    }
    leaf yellow-dropped-bytes {
      type uint64;
      units "byte";
      description
        "YBytes Dropped on the port";
    }
    leaf yellow-dropped-packets {
      type uint64;
      description
        "YPackets Dropeed on the port";
    }
    leaf red-received-bytes {
      type uint64;
      units "byte";
      description
        "RBytes Received on the port";
    }
    leaf red-received-packets {
      type uint64;
      description
        "RPackets Received on the port";
    }
    leaf red-dropped-bytes {
      type uint64;
      units "byte";
      description
        "RBytes Dropped on the port";
    }
    leaf red-dropped-packets {
      type uint64;
      description
        "RPackets Dropeed on the port";
    }
  }

  grouping DPA-SRC-INTF-PORT-INFO {
    description
      "DPA SRC INTF PORT INFO";
    leaf npu-num {
      type uint8;
      description
        "NPU of port";
    }
    leaf slice {
      type uint8;
      description
        "NPU slice of port";
    }
    leaf port-num {
      type uint8;
      description
        "Port Number of port";
    }
    leaf if-handle {
      type uint32;
      description
        "IfHandle of port";
    }
    leaf sys-port {
      type uint32;
      description
        "System port of port";
    }
    leaf pp-port {
      type uint32;
      description
        "PP Port number of port";
    }
    leaf port-speed {
      type uint32;
      description
        "Port speed of port";
    }
    leaf connector-id {
      type uint32;
      description
        "Connector id of port";
    }
    leaf is-local-port {
      type boolean;
      description
        "Flag to indicate if port is local to the node";
    }
  }

  grouping DPA-VOQ-INTF-PORT {
    description
      "DPA VOQ INTF PORT";
    container src-intf {
      description
        "src intf info";
      uses DPA-SRC-INTF-PORT-INFO;
    }
    leaf in-use {
      type boolean;
      description
        "Flag to indicate if port is in use";
    }
    leaf rack-num {
      type uint8;
      description
        "Rack of port";
    }
    leaf slot-num {
      type uint8;
      description
        "Slot of port";
    }
    leaf npu-num {
      type uint8;
      description
        "NPU of port";
    }
    leaf slice {
      type uint8;
      description
        "NPU slice of port";
    }
    leaf port-num {
      type uint8;
      description
        "Port Number of port";
    }
    leaf if-handle {
      type uint32;
      description
        "IfHandle of port";
    }
    leaf sys-port {
      type uint32;
      description
        "System port of port";
    }
    leaf pp-port {
      type uint32;
      description
        "PP Port number of port";
    }
    leaf port-speed {
      type uint32;
      description
        "Port speed of port";
    }
    leaf voq-base {
      type uint32;
      description
        "Voq Base number of port";
    }
    leaf connector-id {
      type uint32;
      description
        "Connector id of port";
    }
    leaf is-local-port {
      type boolean;
      description
        "Flag to indicate if port is local to the node";
    }
    leaf counter-grp-size {
      type uint8;
      description
        "Number of VoQ sharing counter";
    }
    leaf voq-mode {
      type uint8;
      description
        "4 or 8 VoQ Mode";
    }
    leaf internal-intf {
      type boolean;
      description
        "Internal interfaces";
    }
    leaf all-src-display {
      type boolean;
      description
        "display ALL in fair-voq mode when used without
         src-intf";
    }
    leaf fair-voq-mode {
      type uint8;
      description
        "Fair-4 or Fair-8 Fair VoQ Mode";
    }
    list voq-stat {
      max-elements "8";
      description
        "Keeps a record of the received and dropped
         packets and bytes on the port";
      uses DPA-VOQ-INGRESS-PACKET-STATISTICS;
    }
  }

  grouping NPU-EDM-DEVICE-STATS-ASIC-BRIEF-FIELD-INFO {
    description
      "NPU statistics field information";
    leaf is-overflow {
      type boolean;
      description
        "Flag to indicate overflow";
    }
    leaf field-name {
      type string {
        length "0..81";
      }
      description
        "Field name";
    }
    leaf field-value {
      type uint64;
      description
        "Field value";
    }
  }

  grouping NPU-EDM-DEVICE-STATS-ASIC-BRIEF-FIELDS {
    description
      "NPU statistics fields";
    leaf block-name {
      type string {
        length "0..41";
      }
      description
        "Block name";
    }
    leaf num-fields {
      type uint8;
      description
        "Number of fields";
    }
    list field-info {
      description
        "Field information";
      uses NPU-EDM-DEVICE-STATS-ASIC-BRIEF-FIELD-INFO;
    }
  }

  grouping NPU-EDM-DEVICE-STATS-ASIC-BRIEF-INFO {
    description
      "NPU Brief statistics information";
    leaf num-blocks {
      type uint8;
      description
        "Number of blocks";
    }
    list block-info {
      description
        "Block information";
      uses NPU-EDM-DEVICE-STATS-ASIC-BRIEF-FIELDS;
    }
  }

  grouping FIA-EDM-STATS-BRIEF-INFO {
    description
      "ASIC statistics information";
    container npu-statistics {
      description
        "NPU Statistics";
      uses NPU-EDM-DEVICE-STATS-ASIC-BRIEF-INFO;
    }
    leaf valid {
      type boolean;
      description
        "Flag to indicate if data is valid";
    }
    leaf rack-number {
      type uint32;
      description
        "Rack number";
    }
    leaf slot-number {
      type uint32;
      description
        "Slot number";
    }
    leaf asic-instance {
      type uint32;
      description
        "ASIC instance";
    }
    leaf chip-version {
      type uint16;
      description
        "Chip version";
    }
    leaf counters-update-timestamp {
      type uint64;
      description
        "Counters update timestamp in msec";
    }
  }

  grouping FIA-EDM-DEVICE-STATS-FIELD-INFO {
    description
      "Detailed ASIC statistics field information";
    leaf field-name {
      type string;
      description
        "Field name";
    }
    leaf field-value {
      type uint64;
      description
        "Field value";
    }
    leaf is-overflow {
      type boolean;
      description
        "Flag to indicate overflow";
    }
  }

  grouping FIA-EDM-DEVICE-STATS-BLK-INFO {
    description
      "Detailed ASIC statistics block information";
    leaf block-name {
      type string;
      description
        "Block name";
    }
    leaf num-fields {
      type uint32;
      description
        "Number of fields";
    }
    list field-info {
      description
        "Field information";
      uses FIA-EDM-DEVICE-STATS-FIELD-INFO;
    }
  }

  grouping FIA-EDM-DEVICE-STATS-ASIC-INFO {
    description
      "Detailed ASIC statistics information";
    leaf num-blocks {
      type uint32;
      description
        "Number of blocks";
    }
    list block-info {
      description
        "Block information";
      uses FIA-EDM-DEVICE-STATS-BLK-INFO;
    }
  }

  grouping FIA-EDM-STATS-INFO {
    description
      "Detailed ASIC statistics";
    container statistics {
      description
        "Statistics";
      uses FIA-EDM-DEVICE-STATS-ASIC-INFO;
    }
    leaf valid {
      type boolean;
      description
        "Flag to indicate if data is valid";
    }
    leaf rack-number {
      type uint32;
      description
        "Rack number";
    }
    leaf slot-number {
      type uint32;
      description
        "Slot number";
    }
    leaf asic-instance {
      type uint32;
      description
        "ASIC instance";
    }
    leaf chip-version {
      type uint16;
      description
        "Chip version";
    }
    leaf counters-update-timestamp {
      type uint64;
      description
        "Counters update timestamp in msec";
    }
  }
}
