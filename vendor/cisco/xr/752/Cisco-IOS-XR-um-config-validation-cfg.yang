module Cisco-IOS-XR-um-config-validation-cfg {
  namespace "http://cisco.com/ns/yang/Cisco-IOS-XR-um-config-validation-cfg";
  prefix um-config-validation-cfg;

  import Cisco-IOS-XR-types {
    prefix xr;
  }
  import Cisco-IOS-XR-um-script-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-validation package configuration.
     
     This YANG module augments the
     modules with configuration data.
     
     Copyright (c) 2021 by Cisco Systems, Inc.
     All rights reserved.";

  revision 2021-06-30 {
    description
      "Initial release";
    semver:module-version "1.0.0";
  }

  augment "/a1:script" {
    container configs {
      description
        "Activate a config script";
      list config {
        must "checksum/sha256";
        key "config-name";
        description
          "Activate a config script";
        leaf config-name {
          type string {
            length "1..800" {
              description
                "Specify the filename of the config script (must end in .py)";
            }
            pattern ".+[.]{1}py";
          }
          description
            "Activate a config script";
        }
        container checksum {
          description
            "Specify a checksum for the script";
          leaf sha256 {
            type xr:Cisco-ios-xr-string {
              length "1..800" {
                description
                  "The SHA256 hash (64 hex characters)";
              }
              pattern "[A-Za-z0-9]{64}";
            }
            description
              "Specify an SHA256 checksum";
          }
        }
        leaf priority {
          type uint32 {
            range "0..4294967295" {
              description
                "The priority value (default 500)";
            }
          }
          description
            "Specify priority of the script (default 500)";
        }
      }
    }
  }
  container configuration {
    description
      "Configuration related settings";
    container validation {
      description
        "Options for configuration validation";
      container scripts {
        presence "Indicates a scripts node is configured.";
        description
          "Enable configuration validation via config scripts";
      }
    }
  }
}
