module Cisco-IOS-XR-um-ptp-log-servo-cfg {
  namespace "http://cisco.com/ns/yang/Cisco-IOS-XR-um-ptp-log-servo-cfg";
  prefix um-ptp-log-servo-cfg;

  import Cisco-IOS-XR-um-ptp-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ptp-log-servo package configuration.
     
     This YANG module augments the
     modules with configuration data.
     
     Copyright (c) 2020 by Cisco Systems, Inc.
     All rights reserved.";

  revision 2020-10-08 {
    description
      "Initial release";
    semver:module-version "1.0.0";
  }

  augment "/a1:ptp/a1:log" {
    container servo {
      description
        "Servo logging options";
      container events {
        presence "Indicates a events node is configured.";
        description
          "Log servo events";
      }
    }
  }
}
