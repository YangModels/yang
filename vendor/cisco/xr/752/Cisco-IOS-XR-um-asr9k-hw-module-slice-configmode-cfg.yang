module Cisco-IOS-XR-um-asr9k-hw-module-slice-configmode-cfg {
  namespace "http://cisco.com/ns/yang/Cisco-IOS-XR-um-asr9k-hw-module-slice-configmode-cfg";
  prefix um-asr9k-hw-module-slice-configmode-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-slice-configmode package configuration.
     
     This YANG module augments the
     modules with configuration data.
     
     Copyright (c) 2022 by Cisco Systems, Inc.
     All rights reserved.";

  revision 2022-02-03 {
    description
      "Initial release";
    semver:module-version "1.0.0";
  }

  grouping LOCATION-BODY {
    container location {
      description
        "Configure line card location";
      container slices {
        description
          "Slice configuration";
        list slice {
          key "slice-id";
          description
            "Slice configuration";
          leaf slice-id {
            type uint32 {
              range "0..9" {
                description
                  "slice number";
              }
            }
            description
              "Slice configuration";
          }
          leaf config-mode {
            type xr:Cisco-ios-xr-string {
              length "1..800" {
                description
                  "Input a string with 4 speeds separated by , Valid speeds are <1x100GE>,<1x40GE>,<4x25GE>,<10x10GE> and <5x1GE_5x10GE>.  Ex:1x100GE,4x25GE,10x10GE,10x10GE ";
              }
              pattern "[a-zA-Z0-9,_ ]+";
            }
            description
              "Configure interface type combination for all four groups of LC, Valid speeds are <4x25GE>,<1x100GE>,<1x40GE>,<10x10GE> and <5x1GE_5x10GE>";
          }
        }
      }
    }
  }

  augment "/location:locations/location:location" {
    uses LOCATION-BODY;
  }
  augment "/location:locations/location:preconfigured-location" {
    uses LOCATION-BODY;
  }
}
