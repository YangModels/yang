submodule Cisco-IOS-XR-npu-fsdb-stats-oper-sub1 {
  belongs-to Cisco-IOS-XR-npu-fsdb-stats-oper {
    prefix Cisco-IOS-XR-npu-fsdb-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR npu-fsdb-stats package operational data.
     
     Copyright (c) 2013-2022 by Cisco Systems, Inc.
     All rights reserved.";

  revision 2022-03-03 {
    description
      "Updated the yang model for link FSM entry";
    semver:module-version "3.0.0";
  }
  revision 2021-05-14 {
    description
      "Updated the type of fabric operational mode in the yang model";
    semver:module-version "2.0.0";
  }
  revision 2020-10-10 {
    description
      "Yang Schema for npu driver link info";
    semver:module-version "1.0.0";
  }
  revision 2019-04-05 {
    description
      "Establish semantic version baseline.";
  }
  revision 2015-11-09 {
    description
      "IOS XR 6.0 revision.";
  }

  typedef Asic-init-method {
    type enumeration {
      enum "asic-init-method-unset" {
        value -1;
        description
          "asic init method unset";
      }
      enum "asic-init-method-no-reset" {
        value 0;
        description
          "asic init method no reset";
      }
      enum "asic-init-method-pon-reset" {
        value 1;
        description
          "asic init method pon reset";
      }
      enum "asic-init-method-pon-reset-on-intr" {
        value 2;
        description
          "asic init method pon reset on intr";
      }
      enum "asic-init-method-hard-reset" {
        value 3;
        description
          "asic init method hard reset";
      }
      enum "asic-init-method-warmboot" {
        value 4;
        description
          "asic init method warmboot";
      }
      enum "asic-init-method-issu-wb" {
        value 5;
        description
          "asic init method issu wb";
      }
      enum "asic-init-method-pci-shutdown" {
        value 6;
        description
          "asic init method pci shutdown";
      }
      enum "asic-init-method-quiesce" {
        value 7;
        description
          "asic init method quiesce";
      }
      enum "asic-init-method-issu-started" {
        value 8;
        description
          "asic init method issu started";
      }
      enum "asic-init-method-issu-rollback" {
        value 9;
        description
          "asic init method issu rollback";
      }
      enum "asic-init-method-issu-abort" {
        value 10;
        description
          "asic init method issu abort";
      }
      enum "asic-init-method-slice-cleanup" {
        value 11;
        description
          "asic init method slice cleanup";
      }
      enum "asic-init-method-lc-remove" {
        value 12;
        description
          "asic init method lc remove";
      }
      enum "asic-init-method-node-down" {
        value 13;
        description
          "asic init method node down";
      }
      enum "asic-init-method-intr" {
        value 14;
        description
          "asic init method intr";
      }
      enum "asic-init-method-board-reload" {
        value 15;
        description
          "asic init method board reload";
      }
      enum "asic-init-method-max" {
        value 16;
        description
          "asic init method max";
      }
    }
    description
      "Asic init method";
  }

  typedef Asic-access-state {
    type enumeration {
      enum "asic-state-unset" {
        value -1;
        description
          "asic state unset";
      }
      enum "asic-state-none" {
        value 0;
        description
          "asic state none";
      }
      enum "asic-state-device-off-line" {
        value 1;
        description
          "asic state device off line";
      }
      enum "asic-state-device-created" {
        value 2;
        description
          "asic state device created";
      }
      enum "asic-state-device-online" {
        value 3;
        description
          "asic state device online";
      }
      enum "asic-state-warmboot" {
        value 4;
        description
          "asic state warmboot";
      }
      enum "asic-state-de-init-start" {
        value 5;
        description
          "asic state de init start";
      }
      enum "asic-state-intr-de-init" {
        value 6;
        description
          "asic state intr de init";
      }
      enum "asic-state-npu-detach" {
        value 7;
        description
          "asic state npu detach";
      }
      enum "asic-state-soc-de-init" {
        value 8;
        description
          "asic state soc de init";
      }
      enum "asic-state-de-init-done" {
        value 9;
        description
          "asic state de init done";
      }
      enum "asic-state-soc-init" {
        value 10;
        description
          "asic state soc init";
      }
      enum "asic-state-npu-init" {
        value 11;
        description
          "asic state npu init";
      }
      enum "asic-state-intr-init" {
        value 12;
        description
          "asic state intr init";
      }
      enum "asic-state-soc-init-start" {
        value 13;
        description
          "asic state soc init start";
      }
      enum "asic-state-npu-init-start" {
        value 14;
        description
          "asic state npu init start";
      }
      enum "asic-state-intr-init-start" {
        value 15;
        description
          "asic state intr init start";
      }
      enum "asic-state-hard-reset" {
        value 16;
        description
          "asic state hard reset";
      }
      enum "asic-state-normal" {
        value 17;
        description
          "asic state normal";
      }
      enum "asic-state-exception" {
        value 18;
        description
          "asic state exception";
      }
      enum "asic-state-hp-attached" {
        value 19;
        description
          "asic state hp attached";
      }
      enum "asic-state-quiesce" {
        value 20;
        description
          "asic state quiesce";
      }
      enum "asic-state-issu-started" {
        value 21;
        description
          "asic state issu started";
      }
      enum "asic-state-issu-started-nn" {
        value 22;
        description
          "asic state issu started nn";
      }
      enum "asic-state-issu-abort" {
        value 23;
        description
          "asic state issu abort";
      }
      enum "asic-state-max" {
        value 24;
        description
          "asic state max";
      }
    }
    description
      "Asic access state";
  }

  typedef Asic-oper-state {
    type enumeration {
      enum "asic-oper-unset" {
        value -1;
        description
          "asic oper unset";
      }
      enum "asic-oper-unknown" {
        value 0;
        description
          "asic oper unknown";
      }
      enum "asic-oper-up" {
        value 1;
        description
          "asic oper up";
      }
      enum "asic-oper-down" {
        value 2;
        description
          "asic oper down";
      }
      enum "asic-card-down" {
        value 3;
        description
          "asic card down";
      }
    }
    description
      "Asic oper state";
  }

  typedef Slice-state {
    type enumeration {
      enum "slice-oper-unset" {
        value -1;
        description
          "slice oper unset";
      }
      enum "slice-oper-down" {
        value 0;
        description
          "slice oper down";
      }
      enum "slice-oper-up" {
        value 1;
        description
          "slice oper up";
      }
      enum "slice-oper-na" {
        value 2;
        description
          "slice oper na";
      }
    }
    description
      "Slice state";
  }

  typedef Power-opt-freq {
    type enumeration {
      enum "power-opt-freq-none" {
        value 0;
        description
          "power opt freq none";
      }
      enum "power-opt-freq-low" {
        value 1;
        description
          "power opt freq low";
      }
      enum "power-opt-freq-medium" {
        value 2;
        description
          "power opt freq medium";
      }
      enum "power-opt-freq-high" {
        value 3;
        description
          "power opt freq high";
      }
    }
    description
      "Power opt freq";
  }

  typedef Fabric-mode {
    type enumeration {
      enum "fabric-mode-unknown" {
        value 0;
        description
          "fabric mode unknown";
      }
      enum "fabric-mode-fabric" {
        value 1;
        description
          "fabric mode fabric";
      }
      enum "fabric-mode-single" {
        value 2;
        description
          "fabric mode single";
      }
      enum "fabric-mode-mesh" {
        value 3;
        description
          "fabric mode mesh";
      }
    }
    description
      "Fabric mode";
  }

  typedef Functional-role {
    type enumeration {
      enum "driver-role-unknown" {
        value 0;
        description
          "driver role unknown";
      }
      enum "driver-role-active" {
        value 1;
        description
          "driver role active";
      }
      enum "driver-role-standby" {
        value 2;
        description
          "driver role standby";
      }
      enum "driver-role-none" {
        value 3;
        description
          "driver role none";
      }
      enum "driver-role-max" {
        value 4;
        description
          "driver role max";
      }
    }
    description
      "Functional role";
  }

  typedef Npu-edm-fsm-event {
    type enumeration {
      enum "fsm-event-create" {
        value 0;
        description
          "fsm event create";
      }
      enum "fsm-event-learn-wb" {
        value 1;
        description
          "fsm event learn wb";
      }
      enum "fsm-event-create-wb" {
        value 2;
        description
          "fsm event create wb";
      }
      enum "fsm-event-create-oper-up" {
        value 3;
        description
          "fsm event create oper up";
      }
      enum "fsm-event-create-wb-oper-up" {
        value 4;
        description
          "fsm event create wb oper up";
      }
      enum "fsm-event-ena-unshut" {
        value 5;
        description
          "fsm event ena unshut";
      }
      enum "fsm-event-dis-shut" {
        value 6;
        description
          "fsm event dis shut";
      }
      enum "fsm-event-dis-shut-conf" {
        value 7;
        description
          "fsm event dis shut conf";
      }
      enum "fsm-event-dis-destroy" {
        value 8;
        description
          "fsm event dis destroy";
      }
      enum "fsm-event-dis-destroy-conf" {
        value 9;
        description
          "fsm event dis destroy conf";
      }
      enum "fsm-event-dis-destroy-pending" {
        value 10;
        description
          "fsm event dis destroy pending";
      }
      enum "fsm-event-dis-noshut" {
        value 11;
        description
          "fsm event dis noshut";
      }
      enum "fsm-event-link-mon" {
        value 12;
        description
          "fsm event link mon";
      }
      enum "fsm-event-link-up-intr" {
        value 13;
        description
          "fsm event link up intr";
      }
      enum "fsm-event-link-down-intr-be-low-thr" {
        value 14;
        description
          "fsm event link down intr be low thr";
      }
      enum "fsm-event-link-down-intr" {
        value 15;
        description
          "fsm event link down intr";
      }
      enum "fsm-event-asic-isolate" {
        value 16;
        description
          "fsm event asic isolate";
      }
      enum "fsm-event-asic-unisolate" {
        value 17;
        description
          "fsm event asic unisolate";
      }
      enum "fsm-event-dis-perm-shut" {
        value 18;
        description
          "fsm event dis perm shut";
      }
      enum "fsm-event-any" {
        value 19;
        description
          "fsm event any";
      }
      enum "fsm-event-max" {
        value 20;
        description
          "fsm event max";
      }
    }
    description
      "Npu edm fsm event";
  }

  typedef Npu-edm-fsm-state {
    type enumeration {
      enum "link-state-none" {
        value 0;
        description
          "link state none";
      }
      enum "link-state-mac-port-created" {
        value 1;
        description
          "link state mac port created";
      }
      enum "link-state-fab-port-created" {
        value 2;
        description
          "link state fab port created";
      }
      enum "link-state-port-activate-delayed" {
        value 3;
        description
          "link state port activate delayed";
      }
      enum "link-state-activated" {
        value 4;
        description
          "link state activated";
      }
      enum "link-state-signal-wait" {
        value 5;
        description
          "link state signal wait";
      }
      enum "link-state-go-od-sig" {
        value 6;
        description
          "link state go od sig";
      }
      enum "link-state-tune-started" {
        value 7;
        description
          "link state tune started";
      }
      enum "link-state-tuned" {
        value 8;
        description
          "link state tuned";
      }
      enum "link-state-tune-in-progress" {
        value 9;
        description
          "link state tune in progress";
      }
      enum "link-state-tune-check-status" {
        value 10;
        description
          "link state tune check status";
      }
      enum "link-state-tune-check-link-state" {
        value 11;
        description
          "link state tune check link state";
      }
      enum "link-state-mac-up" {
        value 12;
        description
          "link state mac up";
      }
      enum "link-state-peer-discovery" {
        value 13;
        description
          "link state peer discovery";
      }
      enum "link-state-peer-detected" {
        value 14;
        description
          "link state peer detected";
      }
      enum "link-state-topology-check" {
        value 15;
        description
          "link state topology check";
      }
      enum "link-state-sync-wait" {
        value 16;
        description
          "link state sync wait";
      }
      enum "link-state-keep-alive-start" {
        value 17;
        description
          "link state keep alive start";
      }
      enum "link-state-check-reach" {
        value 18;
        description
          "link state check reach";
      }
      enum "link-state-up" {
        value 19;
        description
          "link state up";
      }
      enum "link-state-stopped" {
        value 20;
        description
          "link state stopped";
      }
      enum "link-state-fab-wb-stopped" {
        value 21;
        description
          "link state fab wb stopped";
      }
      enum "link-state-fab-port-permshut" {
        value 22;
        description
          "link state fab port permshut";
      }
      enum "link-state-reset" {
        value 23;
        description
          "link state reset";
      }
      enum "link-state-error" {
        value 24;
        description
          "link state error";
      }
      enum "link-state-destroy-pending" {
        value 25;
        description
          "link state destroy pending";
      }
      enum "link-state-destroyed" {
        value 26;
        description
          "link state destroyed";
      }
      enum "link-state-api-fail" {
        value 27;
        description
          "link state api fail";
      }
      enum "link-state-asic-isolated" {
        value 28;
        description
          "link state asic isolated";
      }
      enum "link-state-unknown" {
        value 29;
        description
          "link state unknown";
      }
      enum "link-state-max" {
        value 30;
        description
          "link state max";
      }
    }
    description
      "Npu edm fsm state";
  }

  typedef Link-error-state {
    type enumeration {
      enum "link-error-unset" {
        value -1;
        description
          "link error unset";
      }
      enum "link-error-none" {
        value 0;
        description
          "link error none";
      }
      enum "link-error-shut" {
        value 1;
        description
          "link error shut";
      }
      enum "link-error-max" {
        value 2;
        description
          "link error max";
      }
    }
    description
      "Link error state";
  }

  typedef Oper-state {
    type enumeration {
      enum "oper-unset" {
        value -1;
        description
          "oper unset";
      }
      enum "oper-unknown" {
        value 0;
        description
          "oper unknown";
      }
      enum "oper-up" {
        value 1;
        description
          "oper up";
      }
      enum "oper-down" {
        value 2;
        description
          "oper down";
      }
      enum "card-down" {
        value 3;
        description
          "card down";
      }
    }
    description
      "Oper state";
  }

  typedef Admin-state {
    type enumeration {
      enum "admin-unset" {
        value -1;
        description
          "admin unset";
      }
      enum "admin-up" {
        value 0;
        description
          "admin up";
      }
      enum "admin-down" {
        value 1;
        description
          "admin down";
      }
    }
    description
      "Admin state";
  }

  typedef Link-stage {
    type enumeration {
      enum "link-stage-unset" {
        value -1;
        description
          "link stage unset";
      }
      enum "link-stage-unused" {
        value 0;
        description
          "link stage unused";
      }
      enum "link-stage-npu" {
        value 1;
        description
          "link stage npu";
      }
      enum "link-stage-s1" {
        value 2;
        description
          "link stage s1";
      }
      enum "link-stage-s2" {
        value 3;
        description
          "link stage s2";
      }
      enum "link-stage-s3" {
        value 4;
        description
          "link stage s3";
      }
      enum "link-stage-unknown" {
        value 5;
        description
          "link stage unknown";
      }
    }
    description
      "Link stage";
  }

  typedef Link {
    type enumeration {
      enum "link-type-unset" {
        value -1;
        description
          "link type unset";
      }
      enum "link-type-unavail" {
        value 0;
        description
          "link type unavail";
      }
      enum "link-type-tx" {
        value 1;
        description
          "link type tx";
      }
      enum "link-type-rx" {
        value 2;
        description
          "link type rx";
      }
    }
    description
      "Link";
  }

  typedef Asic {
    type enumeration {
      enum "asic-unset" {
        value -1;
        description
          "asic unset";
      }
      enum "asic-unavail" {
        value 0;
        description
          "asic unavail";
      }
      enum "asic-npu" {
        value 1;
        description
          "asic npu";
      }
      enum "asic-s123" {
        value 2;
        description
          "asic s123";
      }
      enum "asic-s13" {
        value 3;
        description
          "asic s13";
      }
      enum "asic-s2" {
        value 4;
        description
          "asic s2";
      }
      enum "asic-b2b" {
        value 5;
        description
          "asic b2b";
      }
      enum "asic-type-unknown" {
        value 6;
        description
          "asic type unknown";
      }
    }
    description
      "Asic";
  }

  typedef Rack {
    type enumeration {
      enum "rack-type-unset" {
        value -1;
        description
          "rack type unset";
      }
      enum "rack-type-lcc" {
        value 0;
        description
          "rack type lcc";
      }
      enum "rack-type-fcc" {
        value 1;
        description
          "rack type fcc";
      }
    }
    description
      "Rack";
  }

  grouping NPU-EDM-LINK-OVF-COUNTERS {
    description
      "NPU EDM LINK OVF COUNTERS";
    leaf tx-control-cells-counter {
      type string {
        length "0..6";
      }
      description
        "TX Control cells counter";
    }
    leaf tx-data-64b-frames-counter {
      type string {
        length "0..6";
      }
      description
        "TX Data 64b frames counter";
    }
    leaf tx-data-65to127b-frames-counter {
      type string {
        length "0..6";
      }
      description
        "TX Data 65to127b frames counter";
    }
    leaf tx-data-128to255b-frames-counter {
      type string {
        length "0..6";
      }
      description
        "TX Data 128to255b frames counter";
    }
    leaf tx-data-256to511b-frames-counter {
      type string {
        length "0..6";
      }
      description
        "TX Data 256to511b frames counter";
    }
    leaf tx-data-512to1023b-frames-counter {
      type string {
        length "0..6";
      }
      description
        "TX Data 512to1023b frames counter";
    }
    leaf tx-data-1024to1518b-frames-counter {
      type string {
        length "0..6";
      }
      description
        "TX Data 1024to1518b frames counter";
    }
    leaf tx-data-1519to2500b-frames-counter {
      type string {
        length "0..6";
      }
      description
        "TX Data 1519to2500b frames counter";
    }
    leaf tx-data-2501to9000b-frames-counter {
      type string {
        length "0..6";
      }
      description
        "TX Data 2501to9000b frames counter";
    }
    leaf rx-crc-errors-counter {
      type string {
        length "0..6";
      }
      description
        "RX CRC errors counter";
    }
    leaf rx-lfec-fec-correctable-error {
      type string {
        length "0..6";
      }
      description
        "RX LFEC FEC correctable error";
    }
    leaf rx-8b-10b-disparity-errors {
      type string {
        length "0..6";
      }
      description
        "RX 8b 10b disparity errors";
    }
    leaf rx-control-cells-counter {
      type string {
        length "0..6";
      }
      description
        "RX Control cells counter";
    }
    leaf rx-data-64b-frames-counter {
      type string {
        length "0..6";
      }
      description
        "RX Data 64b frames counter";
    }
    leaf rx-data-65to127b-frames-counter {
      type string {
        length "0..6";
      }
      description
        "RX Data 65to127b frames counter";
    }
    leaf rx-data-128to255b-frames-counter {
      type string {
        length "0..6";
      }
      description
        "RX Data 128to255b frames counter";
    }
    leaf rx-data-256to511b-frames-counter {
      type string {
        length "0..6";
      }
      description
        "RX Data 256to511b frames counter";
    }
    leaf rx-data-512to1023b-frames-counter {
      type string {
        length "0..6";
      }
      description
        "RX Data 512to1023b frames counter";
    }
    leaf rx-data-1024to1518b-frames-counter {
      type string {
        length "0..6";
      }
      description
        "RX Data 1024to1518b frames counter";
    }
    leaf rx-data-1519to2500b-frames-counter {
      type string {
        length "0..6";
      }
      description
        "RX Data 1519to2500b frames counter";
    }
    leaf rx-data-2501to9000b-frames-counter {
      type string {
        length "0..6";
      }
      description
        "RX Data 2501to9000b frames counter";
    }
    leaf rx-dropped-retransmitted-control {
      type string {
        length "0..6";
      }
      description
        "RX dropped retransmitted control";
    }
    leaf tx-asyn-fifo-rate {
      type string {
        length "0..6";
      }
      description
        "TX Asyn fifo rate";
    }
    leaf rx-asyn-fifo-rate {
      type string {
        length "0..6";
      }
      description
        "RX Asyn fifo rate";
    }
    leaf rx-lfec-fec-uncorrectable-errors {
      type string {
        length "0..6";
      }
      description
        "RX LFEC FEC uncorrectable errors";
    }
    leaf rx-8b-10b-code-errors {
      type string {
        length "0..6";
      }
      description
        "RX 8b 10b code errors";
    }
  }

  grouping NPU-EDM-LINK-COUNTERS {
    description
      "NPU EDM LINK COUNTERS";
    leaf tx-control-cells-counter {
      type uint64;
      description
        "TX Control cells counter";
    }
    leaf tx-data-64b-frames-counter {
      type uint64;
      description
        "TX Data 64b frames counter";
    }
    leaf tx-data-65to127b-frames-counter {
      type uint64;
      description
        "TX Data 65to127b frames counter";
    }
    leaf tx-data-128to255b-frames-counter {
      type uint64;
      description
        "TX Data 128to255b frames counter";
    }
    leaf tx-data-256to511b-frames-counter {
      type uint64;
      description
        "TX Data 256to511b frames counter";
    }
    leaf tx-data-512to1023b-frames-counter {
      type uint64;
      description
        "TX Data 512to1023b frames counter";
    }
    leaf tx-data-1024to1518b-frames-counter {
      type uint64;
      description
        "TX Data 1024to1518b frames counter";
    }
    leaf tx-data-1519to2500b-frames-counter {
      type uint64;
      description
        "TX Data 1519to2500b frames counter";
    }
    leaf tx-data-2501to9000b-frames-counter {
      type uint64;
      description
        "TX Data 2501to9000b frames counter";
    }
    leaf rx-crc-errors-counter {
      type uint64;
      description
        "RX CRC errors counter";
    }
    leaf rx-lfec-fec-correctable-error {
      type uint64;
      description
        "RX LFEC FEC correctable error";
    }
    leaf rx-8b-10b-disparity-errors {
      type uint64;
      description
        "RX 8b 10b disparity errors";
    }
    leaf rx-control-cells-counter {
      type uint64;
      description
        "RX Control cells counter";
    }
    leaf rx-data-64b-frames-counter {
      type uint64;
      description
        "RX Data 64b frames counter";
    }
    leaf rx-data-65to127b-frames-counter {
      type uint64;
      description
        "RX Data 65to127b frames counter";
    }
    leaf rx-data-128to255b-frames-counter {
      type uint64;
      description
        "RX Data 128to255b frames counter";
    }
    leaf rx-data-256to511b-frames-counter {
      type uint64;
      description
        "RX Data 256to511b frames counter";
    }
    leaf rx-data-512to1023b-frames-counter {
      type uint64;
      description
        "RX Data 512to1023b frames counter";
    }
    leaf rx-data-1024to1518b-frames-counter {
      type uint64;
      description
        "RX Data 1024to1518b frames counter";
    }
    leaf rx-data-1519to2500b-frames-counter {
      type uint64;
      description
        "RX Data 1519to2500b frames counter";
    }
    leaf rx-data-2501to9000b-frames-counter {
      type uint64;
      description
        "RX Data 2501to9000b frames counter";
    }
    leaf rx-dropped-retransmitted-control {
      type uint64;
      description
        "RX dropped retransmitted control";
    }
    leaf tx-asyn-fifo-rate {
      type uint64;
      description
        "TX Asyn fifo rate";
    }
    leaf rx-asyn-fifo-rate {
      type uint64;
      description
        "RX Asyn fifo rate";
    }
    leaf rx-lfec-fec-uncorrectable-errors {
      type uint64;
      description
        "RX LFEC FEC uncorrectable errors";
    }
    leaf rx-8b-10b-code-errors {
      type uint64;
      description
        "RX 8b 10b code errors";
    }
  }

  grouping NPU-EDM-LINK-ERROR-STATUS {
    description
      "NPU EDM LINK ERROR STATUS";
    leaf link-crc-error {
      type uint32;
      description
        "link crc error";
    }
    leaf link-size-error {
      type uint32;
      description
        "link size error";
    }
    leaf link-mis-align-error {
      type uint32;
      description
        "link mis align error";
    }
    leaf link-code-group-error {
      type uint32;
      description
        "link code group error";
    }
    leaf link-no-sig-lock-error {
      type uint32;
      description
        "link no sig lock error";
    }
    leaf link-no-sig-accept-error {
      type uint32;
      description
        "link no sig accept error";
    }
    leaf link-tokens-error {
      type uint32;
      description
        "link tokens error";
    }
    leaf error-token-count {
      type uint32;
      description
        "error token count";
    }
  }

  grouping NPU-EDM-STATS-ASIC-FMAC {
    description
      "NPU EDM STATS ASIC FMAC";
    container link-error-status {
      description
        "link error status";
      uses NPU-EDM-LINK-ERROR-STATUS;
    }
    container link-counters {
      description
        "link counters";
      uses NPU-EDM-LINK-COUNTERS;
    }
    container ovf-status {
      description
        "ovf status";
      uses NPU-EDM-LINK-OVF-COUNTERS;
    }
  }

  grouping NPU-EDM-STATS-ASIC-FMAC-INFO {
    description
      "NPU EDM STATS ASIC FMAC INFO";
    container aggr-stats {
      description
        "aggr stats";
      uses NPU-EDM-STATS-ASIC-FMAC;
    }
    container incr-stats {
      description
        "incr stats";
      uses NPU-EDM-STATS-ASIC-FMAC;
    }
    leaf valid {
      type boolean;
      description
        "valid";
    }
    leaf rack-no {
      type uint32;
      description
        "rack no";
    }
    leaf slot-no {
      type uint32;
      description
        "slot no";
    }
    leaf asic-instance {
      type uint32;
      description
        "asic instance";
    }
    leaf link-no {
      type uint32;
      description
        "link no";
    }
    leaf num-links-in-port {
      type uint32;
      description
        "num links in port";
    }
    leaf link-valid {
      type boolean;
      description
        "link valid";
    }
  }

  grouping NPU-EDM-TXLINK-STATS {
    description
      "NPU EDM TXLINK STATS";
    leaf dummy {
      type uint32;
      description
        "dummy";
    }
  }

  grouping NPU-EDM-TXLINK {
    description
      "NPU EDM TXLINK";
    container this-link {
      description
        "this link";
      uses NPU-EDM-LINK-IDENTITY;
    }
    container far-end-link {
      description
        "far end link";
      uses NPU-EDM-LINK-IDENTITY;
    }
    container stats {
      description
        "stats";
      uses NPU-EDM-TXLINK-STATS;
    }
    container history {
      description
        "history";
      uses NPU-EDM-HISTORY;
    }
    leaf speed {
      type uint32;
      description
        "speed";
    }
    leaf stage {
      type uint8;
      description
        "stage";
    }
    leaf is-link-valid {
      type boolean;
      description
        "is link valid";
    }
    leaf is-conf-pending {
      type boolean;
      description
        "is conf pending";
    }
    leaf is-power-enabled {
      type boolean;
      description
        "is power enabled";
    }
    leaf coeff1 {
      type uint32;
      description
        "coeff1";
    }
    leaf coeff2 {
      type uint32;
      description
        "coeff2";
    }
    leaf admin-state {
      type Admin-state;
      description
        "Admin State";
    }
    leaf oper-state {
      type Oper-state;
      description
        "Oper State";
    }
    leaf error-state {
      type Link-error-state;
      description
        "Error State";
    }
    leaf num-admin-shuts {
      type uint32;
      description
        "num admin shuts";
    }
  }

  grouping NPU-EDM-CARD-INFO {
    description
      "NPU EDM CARD INFO";
    leaf card-name {
      type string {
        length "0..16";
      }
      description
        "card name";
    }
    leaf si-board-version {
      type uint32;
      description
        "si board version";
    }
    leaf si-param-version {
      type uint32;
      description
        "si param version";
    }
    leaf si-rt-board-version {
      type uint32;
      description
        "si rt board version";
    }
    leaf si-rt-param-version {
      type uint32;
      description
        "si rt param version";
    }
    leaf major-hw-ver {
      type uint32;
      description
        "major hw ver";
    }
    leaf minor-hw-ver {
      type uint32;
      description
        "minor hw ver";
    }
    leaf fp-retimer-type-str {
      type string;
      description
        "fp retimer type str";
    }
  }

  grouping NPU-EDM-DEVICE {
    description
      "NPU EDM DEVICE";
    container asic-id {
      description
        "asic id";
      uses NPU-EDM-ASIC-IDENTITY;
    }
    leaf fapid {
      type uint32;
      description
        "fapid";
    }
    leaf hotplug-event {
      type uint32;
      description
        "hotplug event";
    }
    leaf slice-state {
      type Slice-state;
      description
        "Slice State";
    }
    leaf admin-state {
      type Admin-state;
      description
        "Admin State";
    }
    leaf oper-state {
      type Asic-oper-state;
      description
        "Oper State";
    }
    leaf asic-state {
      type Asic-access-state;
      description
        "Asic State";
    }
    leaf last-init-cause {
      type Asic-init-method;
      description
        "last init cause";
    }
    leaf num-pon-resets {
      type uint32;
      description
        "num pon resets";
    }
    leaf num-hard-resets {
      type uint32;
      description
        "num hard resets";
    }
    leaf fw-major-rev {
      type uint32;
      description
        "fw major rev";
    }
    leaf fw-minor-rev {
      type uint32;
      description
        "fw minor rev";
    }
  }

  grouping NPU-EDM-DRIVER-INFO {
    description
      "NPU EDM DRIVER INFO";
    leaf driver-version {
      type uint32;
      description
        "driver version";
    }
    leaf functional-role {
      type Functional-role;
      description
        "Functional Role";
    }
    leaf node-id {
      type string;
      description
        "node id";
    }
    leaf rack-type {
      type Rack;
      description
        "Rack Type";
    }
    leaf rack-num {
      type uint8;
      description
        "rack num";
    }
    leaf is-driver-ready {
      type boolean;
      description
        "is driver ready";
    }
    leaf card-avail-mask {
      type string {
        length "0..16";
      }
      description
        "card avail mask";
    }
    leaf asic-avail-mask {
      type string {
        length "0..16";
      }
      description
        "asic avail mask";
    }
    leaf exp-asic-avail-mask {
      type string {
        length "0..16";
      }
      description
        "exp asic avail mask";
    }
    leaf asic-oper-notify-to-fsdb-pending-bmap {
      type uint64;
      description
        "asic oper notify to fsdb pending bmap";
    }
    leaf is-full-fgid-download-req {
      type boolean;
      description
        "is full fgid download req";
    }
    leaf is-fgid-download-in-progress {
      type boolean;
      description
        "is fgid download in progress";
    }
    leaf is-fgid-download-completed {
      type boolean;
      description
        "is fgid download completed";
    }
    leaf fsdb-conn-active {
      type boolean;
      description
        "fsdb conn active";
    }
    leaf fgid-conn-active {
      type boolean;
      description
        "fgid conn active";
    }
    leaf issu-mgr-conn-active {
      type boolean;
      description
        "issu mgr conn active";
    }
    leaf fsdb-reg-active {
      type boolean;
      description
        "fsdb reg active";
    }
    leaf fgid-reg-active {
      type boolean;
      description
        "fgid reg active";
    }
    leaf issu-mgr-reg-active {
      type boolean;
      description
        "issu mgr reg active";
    }
    leaf num-pm-conn-reqs {
      type uint8;
      description
        "num pm conn reqs";
    }
    leaf num-fsdb-conn-reqs {
      type uint8;
      description
        "num fsdb conn reqs";
    }
    leaf num-fgid-conn-reqs {
      type uint8;
      description
        "num fgid conn reqs";
    }
    leaf num-cm-conn-reqs {
      type uint8;
      description
        "num cm conn reqs";
    }
    leaf num-issu-mgr-conn-reqs {
      type uint8;
      description
        "num issu mgr conn reqs";
    }
    leaf num-peer-npu-conn-reqs {
      type uint8;
      description
        "num peer npu conn reqs";
    }
    leaf is-sm-registered {
      type boolean;
      description
        "is sm registered";
    }
    leaf is-ael-registered {
      type boolean;
      description
        "is ael registered";
    }
    leaf drvr-initial-startup-timestamp {
      type string;
      description
        "drvr initial startup timestamp";
    }
    leaf drvr-current-startup-timestamp {
      type string;
      description
        "drvr current startup timestamp";
    }
    leaf respawn-count {
      type uint8;
      description
        "respawn count";
    }
    leaf total-asics {
      type uint8;
      description
        "total asics";
    }
    leaf fabric-mode {
      type Fabric-mode;
      description
        "Fixed Vs Distributed";
    }
    leaf fabric-oper-mode {
      type uint32;
      description
        "Fabric Operational Mode";
    }
    leaf power-opt-freq {
      type Power-opt-freq;
      description
        "Power Optimization Frequency";
    }
    leaf is-fwding-supported {
      type uint8;
      description
        "is fwding supported";
    }
    leaf is-node-scoped {
      type uint8;
      description
        "is node scoped";
    }
    leaf sdk-version {
      type string;
      description
        "sdk version";
    }
    list device-info {
      description
        "device info";
      uses NPU-EDM-DEVICE;
    }
    list card-info {
      description
        "card info";
      uses NPU-EDM-CARD-INFO;
    }
  }

  grouping NPU-EDM-FSM-ENTRY {
    description
      "NPU EDM FSM ENTRY";
    leaf fsm-state {
      type Npu-edm-fsm-state;
      description
        "FSM State";
    }
    leaf fsm-event {
      type Npu-edm-fsm-event;
      description
        "FSM Event";
    }
    leaf shown {
      type uint8;
      description
        "shown";
    }
    leaf fsm-timestamp {
      type string {
        length "0..32";
      }
      description
        "fsm timestamp";
    }
  }

  grouping NPU-EDM-FSM {
    description
      "NPU EDM FSM";
    leaf num-entries {
      type uint8;
      description
        "num entries";
    }
    list fsm-entry {
      max-elements "15";
      description
        "fsm entry";
      uses NPU-EDM-FSM-ENTRY;
    }
  }

  grouping NPU-EDM-STATE-CHANGE {
    description
      "NPU EDM STATE CHANGE";
    leaf admin-state {
      type Admin-state;
      description
        "Admin State";
    }
    leaf oper-state {
      type Oper-state;
      description
        "Oper State";
    }
    leaf error-state {
      type Link-error-state;
      description
        "Error State";
    }
    leaf timestamp {
      type string {
        length "0..64";
      }
      description
        "timestamp";
    }
    leaf reasons {
      type string;
      description
        "reasons";
    }
  }

  grouping NPU-EDM-HISTORY {
    description
      "NPU EDM HISTORY";
    leaf histnum {
      type uint8;
      description
        "histnum";
    }
    leaf start-index {
      type uint8;
      description
        "start index";
    }
    list hist {
      max-elements "5";
      description
        "hist";
      uses NPU-EDM-STATE-CHANGE;
    }
  }

  grouping NPU-EDM-ASIC-IDENTITY {
    description
      "NPU EDM ASIC IDENTITY";
    leaf rack-type {
      type Rack;
      description
        "Rack Type";
    }
    leaf asic-type {
      type Asic;
      description
        "Asic Type";
    }
    leaf rack-num {
      type uint32;
      description
        "rack num";
    }
    leaf slot-num {
      type uint32;
      description
        "slot num";
    }
    leaf asic-instance {
      type uint32;
      description
        "asic instance";
    }
  }

  grouping NPU-EDM-LINK-IDENTITY {
    description
      "NPU EDM LINK IDENTITY";
    container asic-id {
      description
        "asic id";
      uses NPU-EDM-ASIC-IDENTITY;
    }
    leaf link-type {
      type Link;
      description
        "Link Type";
    }
    leaf link-stage {
      type Link-stage;
      description
        "Link Stage";
    }
    leaf link-num {
      type uint32;
      description
        "link num";
    }
    leaf log-link-num {
      type uint32;
      description
        "log link num";
    }
  }

  grouping NPU-EDM-RXLINK {
    description
      "NPU EDM RXLINK";
    container this-link {
      description
        "this link";
      uses NPU-EDM-LINK-IDENTITY;
    }
    container far-end-link {
      description
        "far end link";
      uses NPU-EDM-LINK-IDENTITY;
    }
    container far-end-link-in-hw {
      description
        "far end link in hw";
      uses NPU-EDM-LINK-IDENTITY;
    }
    container history {
      description
        "history";
      uses NPU-EDM-HISTORY;
    }
    container link-fsm {
      description
        "link fsm";
      uses NPU-EDM-FSM;
    }
    leaf speed-in-gbps {
      type uint32;
      description
        "speed in gbps";
    }
    leaf stage {
      type Link-stage;
      description
        "Stage";
    }
    leaf is-link-valid {
      type boolean;
      description
        "is link valid";
    }
    leaf is-conf-pending {
      type boolean;
      description
        "is conf pending";
    }
    leaf admin-state {
      type Admin-state;
      description
        "Admin State";
    }
    leaf oper-state {
      type Oper-state;
      description
        "Oper State";
    }
    leaf error-state {
      type Link-error-state;
      description
        "Error State";
    }
    leaf flags {
      type string;
      description
        "flags";
    }
    leaf flap-cnt {
      type uint32;
      description
        "flap cnt";
    }
    leaf num-admin-shuts {
      type uint32;
      description
        "num admin shuts";
    }
    leaf correctable-errors {
      type uint64;
      description
        "correctable errors";
    }
    leaf uncorrectable-errors {
      type uint64;
      description
        "uncorrectable errors";
    }
  }
}
