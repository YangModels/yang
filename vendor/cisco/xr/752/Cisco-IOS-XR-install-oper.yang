module Cisco-IOS-XR-install-oper {
  namespace "http://cisco.com/ns/yang/Cisco-IOS-XR-install-oper";
  prefix install-oper;

  import Cisco-IOS-XR-types {
    prefix xr;
  }
  import cisco-semver {
    prefix semver;
  }
  include Cisco-IOS-XR-install-oper-sub1 {
    revision-date 2021-08-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install package operational data.
     
     This module contains definitions
     for the following management objects:
       install: Install operational data
     
     Copyright (c) 2013-2021 by Cisco Systems, Inc.
     All rights reserved.";

  revision 2021-08-10 {
    description
      "Add force option to package abort.";
    semver:module-version "1.5.0";
  }
  revision 2021-07-15 {
    description
      "Add pre-commit check support.
       2021-05-18
          Modified oper path for upgrade compatibility matrix with iso input
       2021-05-13
          Added optional hash into all package queries.
       2021-04-14
          Add system reload reason and config replace info
       2021-03-22
          Added support for upgrade compatibility matrix feature";
    semver:module-version "1.4.0";
  }
  revision 2021-01-14 {
    description
      "Add DDTS info to rollback queries.
       2020-07-23
           Added optional label into inst_packages_bag.
       2020-07-22
           Update Inst-provides-match-type with additional provide value
       2020-05-27
           Add install and runtime fingerprint
       2020-05-27
           Add install and runtime fingerprint
       2020-05-27
           Add install and runtime fingerprint
       2020-05-13
           Updated version information to add hostname and disk space
       2020-05-13
           Updated version information to add hostname and disk space
       2020-05-13
           Updated version information to add hostname and disk space";
    semver:module-version "1.3.0";
  }
  revision 2020-04-23 {
    description
      "Add categorization of installed software packages into Cisco and Non-Cisco
       2020-04-23
         Add categorization of installed software packages into Cisco and Non-Cisco
       2020-04-23
         Add categorization of installed software packages into Cisco and Non-Cisco
       2020-02-05
         Updated version information to add a GISO label
       2020-02-05
         Updated version information to add a GISO label
       2020-02-05
         Updated version information to add a GISO label
       2020-01-09
         Added optional label into inst_summary_packages_bag.
       2019-10-14
         Combined platform updates including updates to show install rollback list-ids";
    semver:module-version "1.2.0";
  }
  revision 2019-10-13 {
    description
      "NCS540L 7.1.1 release
       2019-10-12
       8000 series 7.0.11 release
       2019-08-13
         Common yang oper model for lindt and eXR install.";
    semver:module-version "1.1.0";
  }
  revision 2019-04-05 {
    description
      "Establish semantic version baseline.";
    semver:module-version "1.0.0";
  }
  revision 2015-11-09 {
    description
      "IOS XR 6.0 revision.";
  }

  grouping SUMMARY {
    description
      "Common node of committed, active";
    container summary {
      description
        "Summary information";
      uses INST-SUMMARY-PACKAGES-BAG;
    }
  }

  grouping NODE-TABLE {
    description
      "Common node of committed, active";
    container nodes {
      description
        "Table for per-node package data";
      list node {
        key "node";
        description
          "Per-node package data";
        leaf node {
          type xr:Node-id;
          description
            "Node name";
        }
        uses INST-PACKAGES-BAG;
      }
    }
  }

  container install {
    config false;
    description
      "Install operational data";
    container upgrade-matrix {
      description
        "Upgrade compatibility matrix information";
      container running {
        description
          "Show matrix for all supported known paths from
           the current active version";
        uses INSTALL-UPGRADE-MATRIX-RUNNING;
      }
      container isos {
        description
          "Show upgrade matrix for the input (G)ISO";
        list iso {
          key "iso-path";
          description
            "Absolute path to the (G)ISO";
          container from-running {
            description
              "Show upgrade matrix from the current active
               version to the input (G)ISO";
            uses INSTALL-UPGRADE-MATRIX-ISO;
          }
          container all {
            description
              "Show upgrade matrix for all supported known
               paths for the input (G)ISO";
            uses INSTALL-UPGRADE-MATRIX-ISO;
          }
          leaf iso-path {
            type string {
              length "1..256";
            }
            description
              "Absolute path to (G)ISO";
          }
        }
      }
    }
    container version {
      description
        "Install version information";
      uses INST-VERSION-BAG;
    }
    container fixes {
      description
        "Information about installed fixes";
      container active {
        description
          "Information about fixes that are active";
        uses INST-FIXES-BAG;
      }
      container committed {
        description
          "Information about fixes that are committed";
        uses INST-FIXES-BAG;
      }
    }
    container packages {
      description
        "Information about packages installed to the
         system";
      container committed {
        description
          "Information about committed packages";
        uses NODE-TABLE;
        uses SUMMARY;
      }
      container active {
        description
          "Information about active packages";
        uses NODE-TABLE;
        uses SUMMARY;
      }
    }
    container request {
      description
        "Information about the latest user request";
      uses INST-REQUEST-BAG;
    }
  }
}
