submodule Cisco-IOS-XR-fretta-bcm-dpa-npu-stats-oper-sub2 {
  belongs-to Cisco-IOS-XR-fretta-bcm-dpa-npu-stats-oper {
    prefix Cisco-IOS-XR-fretta-bcm-dpa-npu-stats-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fretta-bcm-dpa-npu-stats package operational data.
     
     Copyright (c) 2013-2021 by Cisco Systems, Inc.
     All rights reserved.";

  revision 2021-08-13 {
    description
      "Added num_cores and voq_stats_core1";
    semver:module-version "2.2.0";
  }
  revision 2020-10-09 {
    description
      "Added task-id";
    semver:module-version "2.0.0";
  }
  revision 2019-04-05 {
    description
      "Establish semantic version baseline.";
    semver:module-version "1.2.0";
  }
  revision 2015-11-09 {
    description
      "IOS XR 6.0 revision.";
  }

  grouping FIA-EDM-DEVICE-STATS-FIELD-INFO {
    description
      "FIA EDM DEVICE STATS FIELD INFO";
    leaf field-name {
      type string {
        length "0..80";
      }
      description
        "Field Name";
    }
    leaf field-value {
      type uint64;
      description
        "Field Value";
    }
    leaf is-ovf {
      type boolean;
      description
        "Is Ovf";
    }
  }

  grouping FIA-EDM-DEVICE-STATS-BLK-INFO {
    description
      "FIA EDM DEVICE STATS BLK INFO";
    leaf block-name {
      type string {
        length "0..10";
      }
      description
        "Block Name";
    }
    leaf num-fields {
      type uint8;
      description
        "Num Fields";
    }
    list field-info {
      description
        "field info";
      uses FIA-EDM-DEVICE-STATS-FIELD-INFO;
    }
  }

  grouping FIA-EDM-DEVICE-STATS-ASIC-INFO {
    description
      "FIA EDM DEVICE STATS ASIC INFO";
    leaf num-blocks {
      type uint8;
      description
        "Num Blocks";
    }
    list block-info {
      description
        "block info";
      uses FIA-EDM-DEVICE-STATS-BLK-INFO;
    }
  }

  grouping FIA-EDM-STATS-INFO {
    description
      "FIA EDM STATS INFO";
    container stats-info {
      description
        "stats info";
      uses FIA-EDM-DEVICE-STATS-ASIC-INFO;
    }
    leaf valid {
      type boolean;
      description
        "valid";
    }
    leaf rack-no {
      type uint32;
      description
        "rack no";
    }
    leaf slot-no {
      type uint32;
      description
        "slot no";
    }
    leaf asic-instance {
      type uint32;
      description
        "asic instance";
    }
    leaf chip-ver {
      type uint16;
      description
        "chip ver";
    }
  }
}
