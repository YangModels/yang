module Cisco-IOS-XR-adt-config-cfg {
  namespace "http://cisco.com/ns/yang/Cisco-IOS-XR-adt-config-cfg";
  prefix adt-config-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR adt-config package configuration.
     
     This module contains definitions
     for the following management objects:
       adt-config: Container Schema adt configuration
     
     Copyright (c) 2013-2020 by Cisco Systems, Inc.
     All rights reserved.";

  revision 2020-10-05 {
    description
      "Modified to support deletion of all ADT config on disabling feature.";
    semver:module-version "1.0.0";
  }
  revision 2020-04-05 {
    description
      "IOS XR 7.3.1 Initial version.";
  }
  revision 2019-04-05 {
    description
      "Establish semantic version baseline.";
  }
  revision 2015-11-09 {
    description
      "IOS XR 6.0 revision.";
  }

  container adt-config {
    description
      "Container Schema adt configuration";
    container enable-feature {
      presence "CLI submode compatibility.";
      description
        "Enable adt feature";
      container input {
        description
          "Sources for ADT collector";
        container mdt {
          description
            "MDT config for collector";
          container mdt-sensor-group-ids {
            description
              "MDT sensor groups";
            list mdt-sensor-group-id {
              key "groupname";
              description
                "MDT sensor group id";
              leaf groupname {
                type xr:Cisco-ios-xr-string;
                description
                  "Mdt Sensor Group name";
              }
            }
          }
        }
      }
    }
  }
}
