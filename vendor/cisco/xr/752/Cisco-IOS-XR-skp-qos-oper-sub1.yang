submodule Cisco-IOS-XR-skp-qos-oper-sub1 {
  belongs-to Cisco-IOS-XR-skp-qos-oper {
    prefix Cisco-IOS-XR-skp-qos-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR skp-qos package operational data.
     
     Copyright (c) 2013-2021 by Cisco Systems, Inc.
     All rights reserved.";

  revision 2021-04-07 {
    description
      "Added new policy param unit for inverse ratio";
    semver:module-version "1.1.0";
  }
  revision 2019-04-05 {
    description
      "Establish semantic version baseline.";
    semver:module-version "1.0.1";
  }
  revision 2016-02-18 {
    description
      "Implementing Oper Yang Model";
  }
  revision 2015-11-09 {
    description
      "IOS XR 6.0 revision.";
  }

  typedef Action {
    type enumeration {
      enum "police-transmit" {
        description
          "Police action transmit";
      }
      enum "police-set-transmit" {
        description
          "Police action set transmit";
      }
      enum "police-drop" {
        description
          "Police action drop";
      }
      enum "police-unknown" {
        description
          "Police action unknown";
      }
    }
    description
      "Action type";
  }

  typedef Action-opcode {
    type enumeration {
      enum "precedence" {
        value 0;
        description
          "Precedence";
      }
      enum "dscp" {
        value 1;
        description
          "DSCP";
      }
      enum "discard-class" {
        value 2;
        description
          "Discard class";
      }
      enum "qos-group" {
        value 3;
        description
          "QoS group";
      }
      enum "cos-inner" {
        value 4;
        description
          "COS inner";
      }
      enum "cos" {
        value 5;
        description
          "COS";
      }
      enum "exp-top" {
        value 6;
        description
          "EXP top";
      }
      enum "exp-imp" {
        value 7;
        description
          "EXP IMP";
      }
      enum "tunnel-precedence" {
        value 8;
        description
          "Tunnel precedence";
      }
      enum "tunnel-dscp" {
        value 9;
        description
          "Tunnel DSCP";
      }
      enum "itag-dei" {
        value 10;
        description
          "ITAG DEI";
      }
      enum "itag-cos" {
        value 11;
        description
          "ITAG COS";
      }
      enum "cos-imposition" {
        value 12;
        description
          "COS imposition";
      }
      enum "dei-imposition" {
        value 13;
        description
          "DEI imposition";
      }
      enum "dei" {
        value 14;
        description
          "DEI";
      }
      enum "no-marking" {
        value 15;
        description
          "No marking";
      }
    }
    description
      "Action opcode";
  }

  typedef Tb-algorithm {
    type enumeration {
      enum "inactive" {
        value 0;
        description
          "Inactive, configured but disabled";
      }
      enum "single" {
        value 1;
        description
          "Single token bucket";
      }
      enum "single-rate-tcm" {
        value 2;
        description
          "Single rate three color marker";
      }
      enum "two-rate-tcm" {
        value 3;
        description
          "Two rate three color marker";
      }
      enum "mef-tcm" {
        value 4;
        description
          "Allows coupling between CIR and PIR tb's";
      }
      enum "dummy" {
        value 5;
        description
          "Internal dummy token bucket for coupled-policer
           child";
      }
    }
    description
      "Tokenbucket type";
  }

  typedef Qos-unit {
    type enumeration {
      enum "invalid" {
        value 0;
        description
          "Invalid type";
      }
      enum "bytes" {
        value 1;
        description
          "Bytes";
      }
      enum "kilobytes" {
        value 2;
        description
          "Kilobytes";
      }
      enum "megabytes" {
        value 3;
        description
          "Megabytes";
      }
      enum "gigabytes" {
        value 4;
        description
          "Gigabytes";
      }
      enum "bps" {
        value 5;
        description
          "Bits per second";
      }
      enum "kbps" {
        value 6;
        description
          "Kilo bits per second";
      }
      enum "mbps" {
        value 7;
        description
          "Mega bits per second";
      }
      enum "gbps" {
        value 8;
        description
          "Giga bits per second";
      }
      enum "cells-per-second" {
        value 9;
        description
          "Cells per second";
      }
      enum "packets-per-second" {
        value 10;
        description
          "Packets per second";
      }
      enum "microsecond" {
        value 11;
        description
          "Microsecond";
      }
      enum "millisecond" {
        value 12;
        description
          "Millisecond";
      }
      enum "packets" {
        value 13;
        description
          "Number of packets";
      }
      enum "cells" {
        value 14;
        description
          "Number of cells";
      }
      enum "percentage" {
        value 15;
        description
          "Percentage";
      }
      enum "ratio" {
        value 16;
        description
          "Ratio";
      }
    }
    description
      "QoS parameter unit";
  }

  grouping QOS-SHOW-EA-POLICE-RESULT-ST {
    description
      "QoS EA Policer Result";
    leaf token-bucket-id {
      type uint32;
      description
        "Token Bucket ID";
    }
    leaf conform {
      type uint32;
      description
        "Conform Rate";
    }
    leaf exceed {
      type uint32;
      description
        "Exceed Rate";
    }
    leaf violate {
      type uint32;
      description
        "Violate Rate";
    }
  }

  grouping QOS-SHOW-EA-QUEUE-RESULT-ST {
    description
      "QoS EA Queue Result";
    leaf queue-id {
      type uint32;
      description
        "Queue ID";
    }
    leaf commit-tx {
      type uint32;
      description
        "Commit Tx";
    }
    leaf excess-tx {
      type uint32;
      description
        "Excess Tx";
    }
    leaf drop {
      type uint32;
      description
        "Drop";
    }
  }

  grouping QOS-SHOW-EA-RESULT-ST {
    description
      "QoS EA Class Result";
    container queue {
      description
        "QoS EA Queue Result";
      uses QOS-SHOW-EA-QUEUE-RESULT-ST;
    }
    container police {
      description
        "QoS EA Policer Result";
      uses QOS-SHOW-EA-POLICE-RESULT-ST;
    }
    leaf stats-id {
      type uint32;
      description
        "Stats ID";
    }
  }

  grouping QOS-SHOW-EA-POLICE-PARAMS-ST {
    description
      "QoS EA Policer parameters";
    container cir {
      description
        "CIR";
      uses QOS-PARAM;
    }
    container cbs {
      description
        "CBS";
      uses QOS-PARAM;
    }
    leaf color-aware {
      type boolean;
      description
        "Color Aware";
    }
    leaf policer-type {
      type Tb-algorithm;
      description
        "Policer type";
    }
  }

  grouping QOS-SHOW-EA-CONFIG-ST {
    description
      "QoS EA Class Configuration";
    container police {
      description
        "QoS EA Policer parameters";
      uses QOS-SHOW-EA-POLICE-PARAMS-ST;
    }
    container shape {
      description
        "QoS EA Shaper parameters";
      uses QOS-SHOW-EA-SHAPER-PARAMS-ST;
    }
    container wfq {
      description
        "QoS EA WFQ parameters";
      uses QOS-SHOW-EA-WFQ-PARAMS-ST;
    }
    leaf node-config {
      type string {
        length "0..101";
      }
      description
        "Node Config";
    }
  }

  grouping QOS-SHOW-EA-PCLASS-ST {
    description
      "Skywarp QoS EA policy class details";
    list qos-show-ea-pclass-st {
      description
        "qos show ea pclass st";
      container config {
        description
          "QoS EA Class Configuration";
        uses QOS-SHOW-EA-CONFIG-ST;
      }
      container result {
        description
          "QoS EA Class Result";
        uses QOS-SHOW-EA-RESULT-ST;
      }
      leaf index {
        type uint16;
        description
          "Class Index";
      }
      leaf class-level {
        type uint8;
        description
          "Class level";
      }
      leaf class-name {
        type string {
          length "0..65";
        }
        description
          "Class name";
      }
      leaf policy-name {
        type string {
          length "0..65";
        }
        description
          "Policy name";
      }
      leaf node-flags {
        type string {
          length "0..101";
        }
        description
          "Node Flags";
      }
      leaf stats-flags {
        type string {
          length "0..101";
        }
        description
          "Statistical Flags";
      }
    }
  }

  grouping QOS-SHOW-EA-IF-QOS-PARAM-ST {
    description
      "QoS EA Interface Parameters";
    leaf policy-name {
      type string {
        length "0..65";
      }
      description
        "Policy name";
    }
    leaf hierarchical-depth {
      type uint8;
      description
        "Max Hierarchial Depth";
    }
    leaf interface-type {
      type string {
        length "0..101";
      }
      description
        "Interface Type";
    }
    leaf interface-rate {
      type uint32;
      description
        "Interface Programmed Rate";
    }
    leaf port-shaper-rate {
      type uint32;
      description
        "Port Shaper Rate";
    }
    leaf interface-handle {
      type xr:Interface-name;
      description
        "Interface Handle";
    }
    leaf under-line-interface-handle {
      type xr:Interface-name;
      description
        "UnderLineInterface Handle";
    }
    leaf bundle-id {
      type uint16;
      description
        "Bundle Interface ID";
    }
    leaf uidb-index {
      type uint16;
      description
        "UIDB Index";
    }
    leaf qos-interface-handle {
      type uint64;
      description
        "QoS Interface handle";
    }
    leaf port {
      type uint32;
      description
        "Local Port";
    }
    leaf policy-map-id {
      type uint16;
      description
        "Policy Map ID";
    }
  }

  grouping QOS-SHOW-EA-POLICY-ST {
    description
      "QoS EA policy";
    container header {
      description
        "QoS EA policy header";
      uses QOS-SHOW-EA-HEADER-ST;
    }
    container interface-parameters {
      description
        "QoS EA Interface Parameters";
      uses QOS-SHOW-EA-IF-QOS-PARAM-ST;
    }
    container skywarp-qos-policy-class {
      description
        "Skywarp QoS EA policy class details";
      uses QOS-SHOW-EA-PCLASS-ST;
    }
  }

  grouping QOS-EA-CAPABILITY {
    description
      "QoS capability";
    leaf max-policy-maps {
      type uint32;
      description
        "Maximum policy maps per system";
    }
    leaf max-policy-hierarchy {
      type uint32;
      description
        "Maximum policy hierarchy";
    }
    leaf max-policy-name-length {
      type uint32;
      description
        "Maximum policy name length";
    }
    leaf max-classes-per-policy {
      type uint32;
      description
        "Maximum classes per policy";
    }
    leaf max-police-actions-per-class {
      type uint32;
      description
        "Maximum police actions per class";
    }
    leaf max-marking-actions-per-class {
      type uint32;
      description
        "Maximum marking action  per class";
    }
    leaf max-matches-per-class {
      type uint32;
      description
        "Maximum matches per class";
    }
    leaf max-classmap-name-length {
      type uint32;
      description
        "Maximum classmap name length";
    }
    leaf max-bundle-members {
      type uint32;
      description
        "Maximum bundle members";
    }
  }

  grouping MARK-ACTION {
    description
      "Marking parameters";
    leaf mark-value {
      type uint8;
      description
        "Mark value";
    }
    leaf action-opcode {
      type Action-opcode;
      description
        "Action opcode";
    }
  }

  grouping MARK-ACTION-PER-CATEGORY {
    description
      "Marking action";
    leaf action-type {
      type Action;
      description
        "Action type";
    }
    list mark-detail {
      max-elements "2";
      description
        "Mark value";
      uses MARK-ACTION;
    }
  }

  grouping QOS-CLASS-MARK-ACTIONS {
    description
      "QoS Mark parameters";
    container mark-only {
      description
        "Mark Only";
      uses MARK-ACTION-PER-CATEGORY;
    }
    container police-conform {
      description
        "Police conform mark";
      uses MARK-ACTION-PER-CATEGORY;
    }
    container police-exceed {
      description
        "Police exceed mark";
      uses MARK-ACTION-PER-CATEGORY;
    }
  }

  grouping QOS-SHOW-POLICE-PARAMS-ST {
    description
      "QoS Policer parameters";
    container cir {
      description
        "CIR";
      uses QOS-PARAM;
    }
    container cbs {
      description
        "CBS";
      uses QOS-PARAM;
    }
    leaf policer-id {
      type uint32;
      description
        "policer ID";
    }
    leaf policer-type {
      type Tb-algorithm;
      description
        "Policer type";
    }
  }

  grouping QOS-SHOW-EA-WFQ-PARAMS-ST {
    description
      "QoS EA WFQ parameters";
    container bandwidth {
      description
        "Bandwidth";
      uses QOS-PARAM;
    }
    container sum-of-bandwidth {
      description
        "Sum of Bandwidth";
      uses QOS-PARAM;
    }
    leaf excess-ratio {
      type uint16;
      description
        "Excess Ratio";
    }
  }

  grouping QOS-SHOW-WFQ-PARAMS-ST {
    description
      "QoS WFQ parameters";
    container committed-weight {
      description
        "Committed Weight";
      uses QOS-PARAM;
    }
    container programmed-wfq {
      description
        "QoS Programmed WFQ parameters";
      uses QOS-SHOW-EA-WFQ-PARAMS-ST;
    }
    leaf excess-weight {
      type uint16;
      description
        "Excess Weight";
    }
  }

  grouping QOS-SHOW-EA-SHAPER-PARAMS-ST {
    description
      "QoS EA Shaper parameters";
    container pir {
      description
        "PIR in kbps";
      uses QOS-PARAM;
    }
    container pbs {
      description
        "PBS in bytes";
      uses QOS-PARAM;
    }
  }

  grouping QOS-SHOW-QUEUE-PARAMS-ST {
    description
      "QoS Queue parameters";
    leaf queue-id {
      type uint32;
      description
        "Queue ID";
    }
    leaf queue-type {
      type string {
        length "0..101";
      }
      description
        "Queue Type";
    }
  }

  grouping QOS-SHOW-PCLASS-ST {
    description
      "Skywarp QoS policy class details";
    list qos-show-pclass-st {
      description
        "qos show pclass st";
      container queue {
        description
          "QoS Queue parameters";
        uses QOS-SHOW-QUEUE-PARAMS-ST;
      }
      container shape {
        description
          "QoS EA Shaper parameters";
        uses QOS-SHOW-EA-SHAPER-PARAMS-ST;
      }
      container wfq {
        description
          "QoS WFQ parameters";
        uses QOS-SHOW-WFQ-PARAMS-ST;
      }
      container police {
        description
          "QoS Policer parameters";
        uses QOS-SHOW-POLICE-PARAMS-ST;
      }
      container marking {
        description
          "QoS Mark parameters";
        uses QOS-CLASS-MARK-ACTIONS;
      }
      leaf class-level {
        type uint8;
        description
          "Class level";
      }
      leaf class-name {
        type string {
          length "0..65";
        }
        description
          "Class name";
      }
    }
  }

  grouping QOS-PARAM {
    description
      "Config details";
    leaf value {
      type uint32;
      description
        "Config value";
    }
    leaf unit {
      type Qos-unit;
      description
        "Config unit";
    }
  }

  grouping QOS-SHOW-IF-QOS-PARAM-ST {
    description
      "QoS Interface Parameters";
    container interface-config-rate {
      description
        "Interface Configured Rate";
      uses QOS-PARAM;
    }
    container interface-program-rate {
      description
        "Interface Programmed Rate";
      uses QOS-PARAM;
    }
    container port-shaper-rate {
      description
        "Port Shaper Rate";
      uses QOS-PARAM;
    }
  }

  grouping QOS-SHOW-EA-HEADER-ST {
    description
      "QoS EA policy header";
    leaf interface-name {
      type string {
        length "0..101";
      }
      description
        "Interface Name";
    }
    leaf policy-name {
      type string {
        length "0..65";
      }
      description
        "Policy name";
    }
    leaf direction {
      type string {
        length "0..11";
      }
      description
        "Direction";
    }
    leaf classes {
      type uint16;
      description
        "Number of classes";
    }
  }

  grouping QOS-SHOW-POLICY-ST {
    description
      "QoS policy";
    container header {
      description
        "QoS EA policy header";
      uses QOS-SHOW-EA-HEADER-ST;
    }
    container interface-parameters {
      description
        "QoS Interface Parameters";
      uses QOS-SHOW-IF-QOS-PARAM-ST;
    }
    container skywarp-qos-policy-class {
      description
        "Skywarp QoS policy class details";
      uses QOS-SHOW-PCLASS-ST;
    }
  }
}
