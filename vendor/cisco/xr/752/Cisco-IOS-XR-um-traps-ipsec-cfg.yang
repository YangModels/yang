module Cisco-IOS-XR-um-traps-ipsec-cfg {
  namespace "http://cisco.com/ns/yang/Cisco-IOS-XR-um-traps-ipsec-cfg";
  prefix um-traps-ipsec-cfg;

  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps-ipsec package configuration.
     
     This YANG module augments the
     modules with configuration data.
     
     Copyright (c) 2020 by Cisco Systems, Inc.
     All rights reserved.";

  revision 2020-04-17 {
    description
      "Initial release";
    semver:module-version "1.0.0";
  }

  augment "/a1:snmp-server/a1:traps" {
    container ipsec {
      description
        "Enable SNMP IPSec traps";
      container tunnel {
        description
          "Enable SNMP IPsec Tunnel traps";
        container start {
          presence "Indicates a start node is configured.";
          description
            "Enable SNMP IPsec Tunnel Start trap";
        }
        container stop {
          presence "Indicates a stop node is configured.";
          description
            "Enable SNMP IPsec Tunnel Stop trap";
        }
      }
    }
    container isakmp {
      description
        "Enable SNMP ISAKMP traps";
      container tunnel {
        description
          "Enable SNMP ISAKMP Tunnel traps";
        container start {
          presence "Indicates a start node is configured.";
          description
            "Enable SNMP ISAKMP Tunnel Start trap";
        }
        container stop {
          presence "Indicates a stop node is configured.";
          description
            "Enable SNMP ISAKMP Tunnel Stop trap";
        }
      }
    }
  }
}
