submodule Cisco-IOS-XR-lcmode-oper-sub1 {
  belongs-to Cisco-IOS-XR-lcmode-oper {
    prefix Cisco-IOS-XR-lcmode-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR lcmode package operational data.
     
     Copyright (c) 2013-2021 by Cisco Systems, Inc.
     All rights reserved.";

  revision 2021-06-28 {
    description
      "LCMODE for OTUCn-REGEN added";
    semver:module-version "1.1.0";
  }
  revision 2019-04-05 {
    description
      "Establish semantic version baseline.";
    semver:module-version "1.0.0";
  }
  revision 2015-11-09 {
    description
      "IOS XR 6.0 revision.";
  }

  typedef Dp-image-descr {
    type enumeration {
      enum "dp-img-none" {
        value 0;
        description
          "No Image";
      }
      enum "c1b-image" {
        value 1;
        description
          "C1B Image";
      }
      enum "c2b-image" {
        value 2;
        description
          "C2B Image";
      }
      enum "c3b-image" {
        value 3;
        description
          "C3B Image";
      }
      enum "c4b-image" {
        value 4;
        description
          "C4B Image";
      }
      enum "c7b-image" {
        value 7;
        description
          "C7B Image";
      }
      enum "c8b-image" {
        value 8;
        description
          "C8B Image";
      }
    }
    description
      "Dp image descr";
  }

  typedef Lcmode-descr {
    type enumeration {
      enum "lc-mode-none" {
        value 0;
        description
          "LCMODE Not Configured";
      }
      enum "lc-mode10g-grey-mxp" {
        value 1;
        description
          "LCMODE for 10G GREY MXP with QSFP28 Trunk";
      }
      enum "lc-mode100g-txp" {
        value 2;
        description
          "LCMODE for 100G TXP";
      }
      enum "lc-mode4x100g-mxp400g-txp" {
        value 3;
        description
          "LCMODE for 100G MXP and 400G TXP with CFP2 DCO
           Trunk";
      }
      enum "lc-mode40x10g4x100g-mxp" {
        value 4;
        description
          "LCMODE for 10G/100G MXP With CFP2 DCO Trunk";
      }
      enum "lc-mode4x100ge-mxp-dd" {
        value 5;
        description
          "LCMODE for 100GE MXP with QSFP-DD-ZR Trunk";
      }
      enum "lc-mode400ge-txp-dd" {
        value 6;
        description
          "LCMODE for 400GE TXP with QSFP-DD-ZR Trunk";
      }
      enum "lc-mode-fc-mxp" {
        value 7;
        description
          "LCMODE for 24x16G FC and 12x32G FC MXP with
           CFP2 Trunk";
      }
      enum "lc-mode-otu-cnregen" {
        value 8;
        description
          "LCMODE for OTUCn (n= 1,2,3,4) regen";
      }
    }
    description
      "Lcmode descr";
  }

  typedef Config-owner {
    type enumeration {
      enum "config-none" {
        value 0;
        description
          "LCMODE Not Configured";
      }
      enum "config-cli" {
        value 1;
        description
          "Configured by CLI";
      }
      enum "config-oc" {
        value 2;
        description
          "Configured by OC";
      }
    }
    description
      "Config owner";
  }

  grouping LCMODE-CAPABILITY-INFO {
    description
      "LCMODE Capability data";
    leaf lc-mode {
      type uint8;
      description
        "LcMode";
    }
    leaf lcmode-str {
      type string {
        length "0..24";
      }
      description
        "LcmodeStr";
    }
    leaf dp-image-type {
      type Dp-image-descr;
      description
        "DpImageType";
    }
    leaf submode {
      type Lcmode-descr;
      description
        "Submode";
    }
  }

  grouping LCMODE-INFO {
    description
      "LCMODE data";
    leaf lc-mode-supported {
      type boolean;
      description
        "LcModeSupported";
    }
    leaf owner {
      type Config-owner;
      description
        "Owner";
    }
    leaf running-lcmode {
      type Lcmode-descr;
      description
        "RunningLcmode";
    }
    leaf configured-lcmode {
      type Lcmode-descr;
      description
        "ConfiguredLcmode";
    }
    leaf lcmode-cap-rcvd-cnt {
      type uint8;
      description
        "LcmodeCapRcvdCnt";
    }
    list capab-info {
      max-elements "8";
      description
        "capab info";
      uses LCMODE-CAPABILITY-INFO;
    }
  }
}
