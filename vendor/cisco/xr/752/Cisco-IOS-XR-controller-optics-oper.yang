module Cisco-IOS-XR-controller-optics-oper {
  namespace "http://cisco.com/ns/yang/Cisco-IOS-XR-controller-optics-oper";
  prefix controller-optics-oper;

  import Cisco-IOS-XR-types {
    prefix xr;
  }
  import cisco-semver {
    prefix semver;
  }
  include Cisco-IOS-XR-controller-optics-oper-sub1 {
    revision-date 2022-01-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-optics package operational data.
     
     This module contains definitions
     for the following management objects:
       optics-oper: Optics operational data
     
     Copyright (c) 2013-2022 by Cisco Systems, Inc.
     All rights reserved.";

  revision 2022-01-07 {
    description
      "enum added for new Optics Phy Type for 400G SR8 module
       2022-01-06
         New Enum OPTICS_PHY_TYPE_1G_LH are added in enum OpticsPhyType
       2021-12-03
         enumadded for new Optics Phy Type for 200G FR4 modules
       2021-11-03
         Added Dac Rate field in optics_edm_info.";
    semver:module-version "5.1.0";
  }
  revision 2021-09-17 {
    description
      "enumadded for new Optics Phy Type for 200G Cu, 200G AOC, 2x200G CU and 2x200G AOC modules
       2021-07-30
          New Enum OPTICS_PHY_TYPE_100G_ERL are added in enum OpticsPhyType
       2021-07-06
          enum added for new Optics Phy Type for 4x100G LR module
       2021-06-22
          New OPTICS_PHY_TYPE_16G_FC,OPTICS_PHY_TYPE_32G_FC are added in enum OpticsPhyType
       2021-06-21
          New Enums added for FibreChannel 16G and 32G Optics Phy type
       2021-06-10
          New parameters added in bag
       2021-05-27
          DAC rate and Laser temperature and laser age Added for Optics Controller";
    semver:module-version "5.0.0";
  }
  revision 2021-04-14 {
    description
      "New Enums added for Multirate Optics Phy type
       2021-03-22
           New Enums added for Optics Phy type
       2021-02-23
           enum added for new Optics Phy Type for 400G LR4 module
       2021-02-19
           enum added for 1 new Optics Phy Type and new value added to enum EthernetPmdType
       2021-02-17
           New OPTICS_ETH_100GBASE_DR_S added to enum EthernetPmdType
       2021-01-18
           Added 2 enums for New FEC Type.
       2020-12-23
           New value added to enum EthernetPmdType
       2020-11-24
           Enum value in optics_modulation_type is changed from MODE_16QAM_32QAM to MOD_16QAM_32QAM
       2020-11-10
           enum added for 1 new Optics Phy Type for 100G DR-S optics module
       2020-09-10
           removed optics_edm_fastpoll_info and added new bag optics_edm_fastpoll_data
       2020-08-02
           New values added to enum FiberConnectorType
       2020-07-24
           New value added in optics yang for FastPollInfo
       2020-07-14
           New value added to enum EthernetPmdType";
    semver:module-version "4.0.0";
  }
  revision 2020-04-26 {
    description
      "New value added to enum EthernetPmdType
       2020-02-24
         enum added for OTN Application code.
       2020-02-19
         enum added for 1 new Optics Phy Type
       2020-01-31
         enum added for 1 new Optics Phy Type
       2020-01-27
         Added new parameters in optics bag to display parameters which are not configurable
       2019-12-05
         enum added for 2 new OTN Application codes.
       2019-11-30
         Back Reflection data field is added in bag.
       2019-09-30
         chan_num data field is added to support L-Band frequency range.";
    semver:module-version "3.0.0";
  }
  revision 2019-04-05 {
    description
      "Establish semantic version baseline.";
    semver:module-version "2.0.0";
  }
  revision 2017-09-07 {
    description
      "Fixed type translation error.";
  }
  revision 2017-05-01 {
    description
      "Fixing backward compatibility error in module.";
  }
  revision 2015-11-09 {
    description
      "IOS XR 6.0 revision.";
  }

  container optics-oper {
    config false;
    description
      "Optics operational data";
    container optics-ports {
      description
        "All Optics Port operational data";
      list optics-port {
        key "name";
        description
          "Optics operational data";
        container optics-dwdm-carrier-channel-map {
          description
            "Optics operational data";
          uses OPTICS-EDM-WAVE-INFO;
        }
        container ots-spectrum-info {
          description
            "Ots Spectrum Operational data";
          uses OPTICS-EDM-SPECTRUM-INFO;
        }
        container optics-dwdm-carrier-channel-map-flexi {
          description
            "Optics operational data";
          uses OPTICS-EDM-WAVE-INFO;
        }
        container optics-info {
          description
            "Optics operational data";
          uses OPTICS-EDM-INFO;
        }
        container optics-fastpolls {
          description
            "All Optics Fastpoll operational data";
          list optics-fastpoll {
            key "unique-id";
            description
              "Fastpoll Information";
            leaf unique-id {
              type uint32;
              description
                "Fastpoll Index";
            }
            uses OPTICS-EDM-FASTPOLL-DATA;
          }
        }
        container optics-lanes {
          description
            "All Optics Port operational data";
          list optics-lane {
            key "number";
            description
              "Lane Information";
            leaf number {
              type uint32;
              description
                "Lane Index";
            }
            uses OPTICS-EDM-LANE-DATA;
          }
        }
        container optics-db-info {
          description
            "Optics operational data";
          uses OPTICS-DB-INFO;
        }
        leaf name {
          type xr:Interface-name;
          description
            "Port name";
        }
      }
    }
  }
}
