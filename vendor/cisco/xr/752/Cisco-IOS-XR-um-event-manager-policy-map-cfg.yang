module Cisco-IOS-XR-um-event-manager-policy-map-cfg {
  namespace "http://cisco.com/ns/yang/Cisco-IOS-XR-um-event-manager-policy-map-cfg";
  prefix um-event-manager-policy-map-cfg;

  import Cisco-IOS-XR-types {
    prefix xr;
  }
  import Cisco-IOS-XR-um-event-manager-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR event-manager-policy-map package configuration.
     
     This YANG module augments the
     modules with configuration data.
     
     Copyright (c) 2021 by Cisco Systems, Inc.
     All rights reserved.";

  revision 2021-08-13 {
    description
      "Added timer, track and telemetry event-types under event-trigger;
       Added rate-limit;
       Added multi-event support";
  }
  revision 2021-06-16 {
    description
      "Initial release";
  }

  augment "/a1:event/a1:manager" {
    container event-trigger {
      description
        "Configure event-trigger";
      list event {
        key "event-name";
        description
          "Name of the event";
        leaf event-name {
          type xr:Cisco-ios-xr-string {
            length "1..31" {
              description
                "Name of the event";
            }
          }
          description
            "Name of the event";
        }
        leaf occurrence {
          type uint32 {
            range "1..32" {
              description
                "Integer value for occurrence";
            }
          }
          description
            "No of occurrences before the event is raised";
        }
        container period {
          description
            "Time interval during which configured occurrence should take place";
          leaf seconds {
            type uint32 {
              range "1..4294967295" {
                description
                  "Integer value for time interval";
              }
            }
            description
              "Time interval in seconds";
          }
        }
        container rate-limit {
          description
            "Limit trigger to once per given time period";
          leaf seconds {
            type uint32 {
              range "1..4294967" {
                description
                  "Rate limit in second";
              }
            }
            must "not(../milli-seconds)";
            description
              "Rate limit in second";
          }
          leaf milli-seconds {
            type uint32 {
              range "1..4294967295" {
                description
                  "Rate limit in millisecond";
              }
            }
            must "not(../seconds)";
            description
              "Rate limit in millisecond";
          }
        }
        container type {
          description
            "Configure the type of event";
          container syslog {
            must "not(../timer/watchdog or ../timer/cron or ../track or ../telemetry)";
            presence "Indicates a syslog node is configured.";
            description
              "Configure syslog event";
            leaf pattern {
              type string {
                length "1..800" {
                  description
                    "Syslog pattern or regex";
                }
              }
              mandatory true;
              description
                "Configure syslog pattern or regex";
            }
            container severity {
              description
                "Configure the syslog message severity to be screened (default: all)";
              container emergency {
                presence "Indicates a emergency node is configured.";
                description
                  "Syslog priority 0 (highest)";
              }
              container alert {
                presence "Indicates a alert node is configured.";
                description
                  "Syslog priority 1";
              }
              container critical {
                presence "Indicates a critical node is configured.";
                description
                  "Syslog priority 2";
              }
              container error {
                presence "Indicates a error node is configured.";
                description
                  "Syslog priority 3";
              }
              container warning {
                presence "Indicates a warning node is configured.";
                description
                  "Syslog priority 4";
              }
              container notice {
                presence "Indicates a notice node is configured.";
                description
                  "Syslog priority 5";
              }
              container info {
                presence "Indicates a info node is configured.";
                description
                  "Syslog priority 6";
              }
              container debug {
                presence "Indicates a debug node is configured.";
                description
                  "Syslog priority 7 (lowest)";
              }
            }
          }
          container timer {
            description
              "Configure timer event";
            container watchdog {
              must "not(../../syslog or ../cron or ../../track or ../../telemetry)";
              presence "Indicates a watchdog node is configured.";
              description
                "Watchdog timer";
              leaf value {
                type uint32 {
                  range "10..86400" {
                    description
                      "Timer value in seconds";
                  }
                }
                mandatory true;
                description
                  "Timer value in seconds";
              }
            }
            container cron {
              must "not(../../syslog or ../watchdog or ../../track or ../../telemetry)";
              presence "Indicates a cron node is configured.";
              description
                "Cron timer";
              leaf cron-entry {
                type string {
                  length "1..800" {
                    description
                      "Timer cron entry";
                  }
                }
                mandatory true;
                description
                  "Enter cron entry";
              }
            }
          }
          container telemetry {
            must "not(../syslog or ../timer/cron or ../timer/watchdog or ../track)";
            presence "Indicates a telemetry node is configured.";
            description
              "Configure telemetry event";
            leaf sensor-path {
              type string {
                length "1..1024" {
                  description
                    "Telemetry sensor path";
                }
              }
              must "../sample-interval";
              mandatory true;
              description
                "Telemetry sensor path";
            }
            leaf sample-interval {
              type uint32 {
                range "15..4294967" {
                  description
                    "Sample interval in second";
                }
              }
              must "../sensor-path";
              description
                "Time interval for querying telemetry path";
            }
          }
          container track {
            presence "Indicates a track node is configured.";
            description
              "Configure track event";
            leaf name {
              type xr:Cisco-ios-xr-string {
                length "1..800" {
                  description
                    "Name of the track";
                }
              }
              must "(../status/up or ../status/down or ../status/any)";
              mandatory true;
              description
                "Name of the track";
            }
            container status {
              description
                "Configure track status (default : any)";
              container up {
                must "not(../down or ../any)";
                presence "Indicates a up node is configured.";
                description
                  "Trigger event when track is up";
              }
              container down {
                must "not(../up or ../any)";
                presence "Indicates a down node is configured.";
                description
                  "Trigger event when track is down";
              }
              container any {
                must "not(../up or ../down)";
                presence "Indicates a any node is configured.";
                description
                  "Trigger event when track changes up/down";
              }
            }
          }
        }
        container query {
          description
            "Query string to query a single telemetry value";
          leaf json-path {
            type string {
              length "1..253" {
                description
                  "json-path query string";
              }
            }
            description
              "json-path query string";
          }
        }
        container match-criteria {
          description
            "Match criteria for raising event";
          container exact-match {
            must "not(../threshold or ../rate)";
            presence "Indicates a exact-match node is configured.";
            description
              "Trigger event when exact-match occurs";
            leaf value {
              type xr:Cisco-ios-xr-string {
                length "1..31" {
                  description
                    "String value to trigger event";
                }
              }
              description
                "String value to trigger event";
            }
          }
          container threshold {
            must "not(../exact-match or ../rate)";
            presence "Indicates a threshold node is configured.";
            description
              "Trigger event based on a threshold";
            leaf greater-than {
              type uint32 {
                range "0..4294967294" {
                  description
                    "Threshold value to trigger event";
                }
              }
              must
                "not(../greater-equal-to or ../equal-to
                 or ../not-equal-to or ../less-equal-to
                 or ../less-than)";
              description
                "Match when value is greater than threshold";
            }
            leaf greater-equal-to {
              type uint32 {
                range "0..4294967294" {
                  description
                    "Threshold value to trigger event";
                }
              }
              must
                "not(../greater-than or ../equal-to
                 or ../not-equal-to or ../less-equal-to
                 or ../less-than)";
              description
                "Match when value is greater than or equal to threshold";
            }
            leaf equal-to {
              type uint32 {
                range "0..4294967295" {
                  description
                    "Threshold value to trigger event";
                }
              }
              must
                "not(../greater-than or ../greater-equal-to
                 or ../not-equal-to or ../less-equal-to
                 or ../less-than)";
              description
                "Match when value is equal to threshold";
            }
            leaf not-equal-to {
              type uint32 {
                range "0..4294967295" {
                  description
                    "Threshold value to trigger event";
                }
              }
              must
                "not(../greater-than or ../greater-equal-to
                 or ../equal-to or ../less-equal-to
                 or ../less-than)";
              description
                "Match when value is not equal to threshold";
            }
            leaf less-equal-to {
              type uint32 {
                range "1..4294967295" {
                  description
                    "Threshold value to trigger event";
                }
              }
              must
                "not(../greater-than or ../greater-equal-to
                 or ../equal-to or ../not-equal-to
                 or ../less-than)";
              description
                "Match when value is less than or equal to threshold";
            }
            leaf less-than {
              type uint32 {
                range "1..4294967295" {
                  description
                    "Threshold value to trigger event";
                }
              }
              must
                "not(../greater-than or ../greater-equal-to
                 or ../equal-to or ../not-equal-to
                 or ../less-equal-to)";
              description
                "Match when value is less than threshold";
            }
          }
          container rate {
            must "not(../exact-match or ../threshold)";
            presence "Indicates a rate node is configured.";
            description
              "Rate of change to trigger event";
            container direction {
              must "../value";
              description
                "Direction of rate of change: increase/decrease/any";
              container increasing {
                must "not(../decreasing or ../any)";
                presence "Indicates a increasing node is configured.";
                description
                  "Rate of increase in percent";
              }
              container decreasing {
                must "not(../increasing or ../any)";
                presence "Indicates a decreasing node is configured.";
                description
                  "Rate of decrease in percent";
              }
              container any {
                must "not(../increasing or ../decreasing)";
                presence "Indicates a any node is configured.";
                description
                  "Rate of change in percent (increase or decrease)";
              }
            }
            container value {
              must "../direction";
              description
                "Value of rate of change";
              leaf greater-than {
                type uint32 {
                  range "0..4294967294" {
                    description
                      "Rate of change in percent";
                  }
                }
                must
                  "not(../greater-equal-to or ../equal-to
                   or ../not-equal-to or ../less-equal-to
                   or ../less-than)";
                description
                  "Match when value is greater than threshold";
              }
              leaf greater-equal-to {
                type uint32 {
                  range "0..4294967294" {
                    description
                      "Rate of change in percent";
                  }
                }
                must
                  "not(../greater-than or ../equal-to
                   or ../not-equal-to or ../less-equal-to
                   or ../less-than)";
                description
                  "Match when value is greater than or equal to threshold";
              }
              leaf equal-to {
                type uint32 {
                  range "0..4294967295" {
                    description
                      "Rate of change in percent";
                  }
                }
                must
                  "not(../greater-than or ../greater-equal-to
                   or ../not-equal-to or ../less-equal-to
                   or ../less-than)";
                description
                  "Match when value is equal to threshold";
              }
              leaf not-equal-to {
                type uint32 {
                  range "0..4294967295" {
                    description
                      "Rate of change in percent";
                  }
                }
                must
                  "not(../greater-than or ../greater-equal-to
                   or ../equal-to or ../less-equal-to
                   or ../less-than)";
                description
                  "Match when value is not equal to threshold";
              }
              leaf less-equal-to {
                type uint32 {
                  range "1..4294967295" {
                    description
                      "Rate of change in percent";
                  }
                }
                must
                  "not(../greater-than or ../greater-equal-to
                   or ../equal-to or ../not-equal-to
                   or ../less-than)";
                description
                  "Match when value is less than or equal to threshold";
              }
              leaf less-than {
                type uint32 {
                  range "1..4294967295" {
                    description
                      "Rate of change in percent";
                  }
                }
                must
                  "not(../greater-than or ../greater-equal-to
                   or ../equal-to or ../not-equal-to
                   or ../less-equal-to)";
                description
                  "Match when value is less than threshold";
              }
            }
          }
        }
      }
    }
    container actions {
      description
        "Configure action";
      list action {
        key "action-name";
        description
          "Name of the action";
        leaf action-name {
          type xr:Cisco-ios-xr-string {
            length "1..31" {
              description
                "Name of the action";
            }
          }
          description
            "Name of the action";
        }
        container type {
          description
            "Type of action";
          container script {
            must "../../username and checksum/sha256";
            presence "Indicates a script node is configured.";
            description
              "Configure a Python script as action";
            leaf script-name {
              type xr:Cisco-ios-xr-string {
                length "1..31" {
                  description
                    "Python script name (must have .py extension)";
                }
              }
              mandatory true;
              description
                "Name of Python script (must have .py extension)";
            }
            container maxrun {
              description
                "Configure the max run time of script (default: 20seconds)";
              leaf seconds {
                type uint32 {
                  range "10..4294967295" {
                    description
                      "Maxrun in seconds";
                  }
                }
                description
                  "Maxrun in seconds";
              }
            }
            container checksum {
              description
                "Configure script checksum";
              leaf sha256 {
                type xr:Cisco-ios-xr-string {
                  length "64" {
                    description
                      "Checksum value";
                  }
                }
                description
                  "Configure sha256 checksum";
              }
            }
          }
        }
        leaf username {
          type xr:Cisco-ios-xr-string {
            length "1..253" {
              description
                "A configured user name";
            }
          }
          must "../type/script";
          description
            " Username under whom this policy will execute";
        }
      }
    }
    container policy-maps {
      description
        "Configure eem policy map";
      list policy-map {
        key "policy-map-name";
        description
          "Name of the policy-map";
        leaf policy-map-name {
          type xr:Cisco-ios-xr-string {
            length "1..31" {
              description
                "Name of the policy-map";
            }
          }
          description
            "Name of the policy-map";
        }
        leaf occurrence {
          type uint32 {
            range "1..32" {
              description
                "Integer value for occurrence";
            }
          }
          description
            "No of occurrences before the policy becomes active (default 1)";
        }
        leaf period {
          type uint32 {
            range "1..4294967295" {
              description
                "time in seconds";
            }
          }
          description
            "Time in seconds during which configured occurrence should take place";
        }
        container trigger {
          description
            "Configure trigger for this policy-map";
          leaf event {
            type xr:Cisco-ios-xr-string {
              length "1..1024" {
                description
                  "Name of event to map with this policy-map";
              }
            }
            description
              "Set an event as trigger for this policy-map";
          }
          leaf multi-event {
            type string {
              length "1..128" {
                description
                  "Configure multiple events with boolean correlation (AND,OR)";
              }
              pattern "\".*.\"";
            }
            must "not(../event)";
            description
              "Set multiple events as trigger for this policy-map";
          }
        }
        container actions {
          description
            "Map action for policy-map (Maximum 5)";
          list action {
            key "action-name";
            description
              "Name of action";
            leaf action-name {
              type xr:Cisco-ios-xr-string {
                length "1..31" {
                  description
                    "Name of action";
                }
              }
              description
                "Name of action";
            }
          }
        }
      }
    }
  }
}
