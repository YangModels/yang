module Cisco-IOS-XR-um-environment-cfg {
  namespace "http://cisco.com/ns/yang/Cisco-IOS-XR-um-environment-cfg";
  prefix um-environment-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR environment package configuration.
     
     This YANG module augments the
     modules with configuration data.
     
     Copyright (c) 2020 by Cisco Systems, Inc.
     All rights reserved.";

  revision 2020-12-14 {
    description
      "Initial release";
    semver:module-version "1.0.0";
  }

  feature altitude {
    description
      "altitude";
  }

  container environment {
    description
      "Global environment configuration commands";
    leaf altitude {
      if-feature "altitude";
      type uint32 {
        range "0..4000" {
          description
            "meters";
        }
      }
      description
        "Altitude of the chassis in meters";
    }
    container air-filter {
      description
        "chassis air-filter status";
      container replaced {
        description
          "air-filter replaced date";
        leaf date {
          type xr:Cisco-ios-xr-string {
            length "1..800" {
              description
                "CCYY-MM-DD format";
            }
          }
          description
            "";
        }
      }
    }
    leaf min-fan-speed {
      type uint32 {
        range "0..100" {
          description
            "pwm";
        }
      }
      description
        "Min default fan speed in PWM (the speed cannot go lower, but can go higher based on environmental conditions)";
    }
    container chassis-door-alarm {
      description
        "Control chassis door alarm";
      container enable {
        presence "Indicates a enable node is configured.";
        description
          "Enable chassis door alarm";
      }
    }
  }
}
