module Cisco-IOS-XR-rgmgr-cfg {

  /*** NAMESPACE / PREFIX DEFINITION ***/

  namespace "http://cisco.com/ns/yang/Cisco-IOS-XR-rgmgr-cfg";


  prefix "rgmgr-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR rgmgr package configuration.

     This module contains definitions
     for the following management objects:
       redundancy-group-manager: Redundancy Group Manager
         Configuration

     Copyright (c) 2013-2015 by Cisco Systems, Inc.
     All rights reserved.";

  revision "2015-01-07" {
    description
      "IOS XR 5.3.1 revision.";
  }

  typedef Iccp-mode {
    type enumeration {
      enum singleton {
        value 1;
        description "Run the ICCP group in Singleton mode";
      }
    }
    description "Iccp mode";
  }

  container redundancy-group-manager {
    xr:xr-xml-map "infra_rgmgr_cfg:RedundancyGroupManager";
    description "Redundancy Group Manager Configuration";

    container aps {
      xr:xr-xml-map "infra_rgmgr_aps_cfg:APS";
      description "MR-APS groups";

      container default-redundancy-group {
        xr:xr-xml-map "infra_rgmgr_aps_cfg:DefaultRedundancyGroup";
        description "Default SONET controller backup configuration";
        leaf next-hop-address {
          xr:xr-xml-map "infra_rgmgr_aps_cfg:NextHopAddress";
          type inet:ipv4-address-no-zone;
          description "IPv4 address of remote peer";
        }
        leaf backup-interface-name {
          xr:xr-xml-map "infra_rgmgr_aps_cfg:BackupInterfaceName";
          type xr:Interface-name;
          description "Backup interface name";
        }
      }

      container groups {
        xr:xr-xml-map "infra_rgmgr_aps_cfg:GroupTable";
        description "Redundancy Group Table";

        list group {
          xr:xr-xml-map "infra_rgmgr_aps_cfg:Group";
          key "group-id";
          description "Redundancy Group Configuration";

          container controllers {
            xr:xr-xml-map "infra_rgmgr_aps_cfg:ControllerTable";
            description "Controller configuration";

            list controller {
              xr:xr-xml-map "infra_rgmgr_aps_cfg:Controller";
              xr:xr-cli-map "redundancy multi-router aps group <num"+
                "ber> controller member ipv4 <IPv4 address> backup-"+
                "interface <interface> ";
              key "controller-name";
              description "none";
              leaf controller-name {
                xr:xr-xml-map "infra_rgmgr_aps_cfg:ControllerName";
                type xr:Interface-name;
                description "Controller Name";
              }
              leaf next-hop-address {
                xr:xr-xml-map "infra_rgmgr_aps_cfg:NextHopAddress";
                type inet:ipv4-address-no-zone;
                description "IPv4 address of remote peer";
              }
              leaf backup-interface-name {
                xr:xr-xml-map "infra_rgmgr_aps_cfg:BackupInterfaceN"+
                  "ame";
                type xr:Interface-name;
                description "Backup interface name";
              }
            }
          }
          leaf group-id {
            xr:xr-xml-map "infra_rgmgr_aps_cfg:GroupID";
            type uint32 {
              range "1..32";
            }
            description "The redundancy group ID";
          }
        }
      }
    }

    container iccp {
      xr:xr-xml-map "infra_rgmgr_iccp_cfg:ICCP";
      description "ICCP configuration";

      container iccp-groups {
        xr:xr-xml-map "infra_rgmgr_iccp_cfg:ICCPGroupTable";
        description "Redundancy Group Table Configuration";

        list iccp-group {
          xr:xr-xml-map "infra_rgmgr_iccp_cfg:ICCPGroup";
          key "group-number";
          description "Redundancy Group Configuration";

          container backbones {
            xr:xr-xml-map "infra_rgmgr_iccp_cfg:BackboneTable";
            description "ICCP backbone configuration";

            list backbone {
              xr:xr-xml-map "infra_rgmgr_iccp_cfg:Backbone";
              key "backbone-name";
              description "ICCP backbone interface configuration";
              leaf backbone-name {
                xr:xr-xml-map "infra_rgmgr_iccp_cfg:BackboneName";
                type xr:Interface-name;
                description "none";
              }
            }
          }

          container members {
            xr:xr-xml-map "infra_rgmgr_iccp_cfg:MemberTable";
            description "ICCP member configuration";

            list member {
              xr:xr-xml-map "infra_rgmgr_iccp_cfg:Member";
              key "neighbor-address";
              description "ICCP member configuration";
              leaf neighbor-address {
                xr:xr-xml-map "infra_rgmgr_iccp_cfg:NeighborAddress";
                type inet:ipv4-address-no-zone;
                description "Neighbor IP address";
              }
            }
          }
          leaf isolation-recovery-delay {
            xr:xr-xml-map "infra_rgmgr_iccp_cfg:IsolationRecoveryDe"+
              "lay";
            xr:xr-cli-map "redundancy iccp group <number> isolation"+
              " recovery-delay <number> ";
            type uint32 {
              range "30..600";
            }
            units "second";
            description "Time (seconds)";
          }
          leaf mode {
            xr:xr-xml-map "infra_rgmgr_iccp_cfg:Mode";
            xr:xr-cli-map "redundancy iccp group <number> mode sing"+
              "leton ";
            type Iccp-mode;
            description "Mode";
          }
          leaf group-number {
            xr:xr-xml-map "infra_rgmgr_iccp_cfg:GroupNumber";
            type uint32 {
              range "1..4294967295";
            }
            description "The redundancy icc group number";
          }
        }
      }
    }
    leaf enable {
      xr:xr-xml-map "infra_rgmgr_cfg:Enable";
      type empty;
      description "Enable redundancy group manager";
    }
  }
}
