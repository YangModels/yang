module Cisco-IOS-XR-infra-alarm-logger-cfg {

  /*** NAMESPACE / PREFIX DEFINITION ***/

  namespace "http://cisco.com/ns/yang"+
    "/Cisco-IOS-XR-infra-alarm-logger-cfg";


  prefix "infra-alarm-logger-cfg";

  /*** LINKAGE (IMPORTS / INCLUDES) ***/

  import Cisco-IOS-XR-types { prefix "xr"; }

  import Cisco-IOS-XR-infra-alarm-logger-datatypes { prefix "dt1"; }

  import Cisco-IOS-XR-infra-syslog-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-alarm-logger package configuration.

     This YANG module augments the
       Cisco-IOS-XR-infra-syslog-cfg
     module with configuration data.

     Copyright (c) 2013-2015 by Cisco Systems, Inc.
     All rights reserved.";

  revision "2015-01-07" {
    description
      "IOS XR 5.3.1 revision.";
  }


  augment "/a1:syslog" {

    container alarm-logger {
      xr:xr-xml-map "infra_alarm_logger_cfg:AlarmLogger";
      description "Alarm Logger Properties";
      leaf severity-level {
        xr:xr-xml-map "infra_alarm_logger_cfg:SeverityLevel";
        type dt1:Alarm-logger-severity-level;
        description "Severity Level";
      }
      leaf buffer-size {
        xr:xr-xml-map "infra_alarm_logger_cfg:BufferSize";
        type uint32 {
          range "1024..1024000";
        }
        description "Size of the local event buffer";
      }
      leaf source-location {
        xr:xr-xml-map "infra_alarm_logger_cfg:SourceLocation";
        type empty;
        description "Enable alarm source location in message text";
      }
      leaf threshold {
        xr:xr-xml-map "infra_alarm_logger_cfg:Threshold";
        type uint32 {
          range "10..100";
        }
        default "90";
        description "Capacity alarm threshold";
      }
    }
    description
      "This augment extends the configuration data of
      'Cisco-IOS-XR-infra-syslog-cfg'";
  }
}
