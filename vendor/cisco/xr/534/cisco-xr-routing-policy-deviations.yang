module cisco-xr-routing-policy-deviations {

  /*** NAMESPACE / PREFIX DEFINITION ***/

  namespace "http://cisco.com/ns/yang/cisco-xr-routing-policy-deviations";

  prefix "cisco-xr-rpol-devs";

  /*** LINKAGE (IMPORTS / INCLUDES) ***/
  import routing-policy { prefix rpol; }

  /*** META INFORMATION ***/
  organization "Cisco Systems, Inc.";

  contact
    "Cisco Systems, Inc.
     Custome Service

     Postal: 170 West Tasman Dive
     San Jose, CA 95134

     Tel: +1 800 553-NETS

     E-mail: cs-yang@cisco.com";

  description 
    "This module contains the deviations of Open Config Routing Policy YANG 
    set fo Cisco IOS-XR.

     Copyight (c) 2015-2016 by Cisco Systems, Inc.
     All ights reserved.";

  revision "2015-09-16" {
    description
      "Initial evision applicable to IOS-XR 5.3.2 and 6.0";
  }

  /* einann: see if we can deviate the entire container */
  deviation /rpol:routing-policy/rpol:defined-sets/rpol:neighbor-sets {
    deviate not-supported;
  }
/*
  deviation /rpol:routing-policy/rpol:defined-sets/rpol:neighbor-sets/rpol:neighbor-set/rpol:neighbor-set-name {
    deviate not-supported;
  }

  deviation /rpol:routing-policy/rpol:defined-sets/rpol:neighbor-sets/rpol:neighbor-set/rpol:neighbor/rpol:address {
    deviate not-supported;
  }
*/

  /* einann: another container deviation */
  deviation /rpol:routing-policy/rpol:policy-definitions/rpol:policy-definition/rpol:statements/rpol:statement/rpol:conditions/rpol:match-neighbor-set {
    deviate not-supported;
  }
/*
  deviation /rpol:routing-policy/rpol:policy-definitions/rpol:policy-definition/rpol:statements/rpol:statement/rpol:conditions/rpol:match-neighbor-set/rpol:neighbor-set {
    deviate not-supported;
  }

  deviation /rpol:routing-policy/rpol:policy-definitions/rpol:policy-definition/rpol:statements/rpol:statement/rpol:actions/rpol:igp-actions/rpol:set-tag {
    deviate not-supported;
  }
*/
}
