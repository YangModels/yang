module Cisco-IOS-XR-policy-repository-cfg {

  /*** NAMESPACE / PREFIX DEFINITION ***/

  namespace "http://cisco.com/ns/yang"+
    "/Cisco-IOS-XR-policy-repository-cfg";


  prefix "policy-repository-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR policy-repository package configuration.

     This module contains definitions
     for the following management objects:
       routing-policy: Routing policy configuration

     Copyright (c) 2013-2015 by Cisco Systems, Inc.
     All rights reserved.";

  revision "2015-08-27" {
    description
      "IOS XR 5.3.2 revision.";
  }


  container routing-policy {
    xr:xr-xml-map "rpl_cfg:RoutingPolicy";
    description "Routing policy configuration";

    container route-policies {
      xr:xr-xml-map "rpl_cfg:RoutePolicyTable";
      description "All configured policies";

      list route-policy {
        xr:xr-xml-map "rpl_cfg:RoutePolicy";
        key "route-policy-name";
        description "Information about an individual policy";
        leaf rpl-route-policy {
          type string;
          description "RPLRoutePolicy";
        }
        leaf route-policy-name {
          xr:xr-xml-map "rpl_cfg:RoutePolicyName";
          type xr:Cisco-ios-xr-string;
          description "Route policy name";
        }
      }
    }

    container sets {
      xr:xr-xml-map "rpl_cfg:Sets";
      description "All configured sets";

      container prefix-sets {
        xr:xr-xml-map "rpl_cfg:PrefixSetTable";
        description "Information about Prefix sets";

        list prefix-set {
          xr:xr-xml-map "rpl_cfg:PrefixSet";
          key "set-name";
          description "Information about an individual set";
          leaf rpl-prefix-set {
            type string;
            description "RPLPrefixSet";
          }
          leaf set-name {
            xr:xr-xml-map "rpl_cfg:SetName";
            type xr:Cisco-ios-xr-string;
            description "Set name";
          }
        }
      }

      container append-extended-community-opaque-sets {
        xr:xr-xml-map "rpl_cfg:AppendExtendedCommunityOpaqueSetTabl"+
          "e";
        description "Information about Opaque sets";

        list append-extended-community-opaque-set {
          xr:xr-xml-map "rpl_cfg:AppendExtendedCommunityOpaqueSet";
          key "set-name";
          description "Append the entries to the existing set";
          leaf rpl-extended-community-opaque-set {
            type string;
            description "RPLExtendedCommunityOpaqueSet";
          }
          leaf set-name {
            xr:xr-xml-map "rpl_cfg:SetName";
            type xr:Cisco-ios-xr-string;
            description "Set name";
          }
        }
      }

      container append-extended-community-seg-nh-sets {
        xr:xr-xml-map "rpl_cfg:AppendExtendedCommunitySegNHSetTable";
        description "Information about SegNH sets";

        list append-extended-community-seg-nh-set {
          xr:xr-xml-map "rpl_cfg:AppendExtendedCommunitySegNHSet";
          key "set-name";
          description "Append the entries to the existing set";
          leaf rpl-extended-community-seg-nh-set {
            type string;
            description "RPLExtendedCommunitySegNHSet";
          }
          leaf set-name {
            xr:xr-xml-map "rpl_cfg:SetName";
            type xr:Cisco-ios-xr-string;
            description "Set name";
          }
        }
      }

      container remove-extended-community-opaque-sets {
        xr:xr-xml-map "rpl_cfg:RemoveExtendedCommunityOpaqueSetTabl"+
          "e";
        description "Information about Opaque sets";

        list remove-extended-community-opaque-set {
          xr:xr-xml-map "rpl_cfg:RemoveExtendedCommunityOpaqueSet";
          key "set-name";
          description "Remove the entries from the existing set";
          leaf rpl-extended-community-opaque-set {
            type string;
            description "RPLExtendedCommunityOpaqueSet";
          }
          leaf set-name {
            xr:xr-xml-map "rpl_cfg:SetName";
            type xr:Cisco-ios-xr-string;
            description "Set name";
          }
        }
      }

      container extended-community-opaque-sets {
        xr:xr-xml-map "rpl_cfg:ExtendedCommunityOpaqueSetTable";
        description "Information about Opaque sets";

        list extended-community-opaque-set {
          xr:xr-xml-map "rpl_cfg:ExtendedCommunityOpaqueSet";
          key "set-name";
          description "Information about an individual set";
          leaf rpl-extended-community-opaque-set {
            type string;
            description "RPLExtendedCommunityOpaqueSet";
          }
          leaf set-name {
            xr:xr-xml-map "rpl_cfg:SetName";
            type xr:Cisco-ios-xr-string;
            description "Set name";
          }
        }
      }

      container remove-extended-community-seg-nh-sets {
        xr:xr-xml-map "rpl_cfg:RemoveExtendedCommunitySegNHSetTable";
        description "Information about SegNH sets";

        list remove-extended-community-seg-nh-set {
          xr:xr-xml-map "rpl_cfg:RemoveExtendedCommunitySegNHSet";
          key "set-name";
          description "Remove the entries from the existing set";
          leaf rpl-extended-community-seg-nh-set {
            type string;
            description "RPLExtendedCommunitySegNHSet";
          }
          leaf set-name {
            xr:xr-xml-map "rpl_cfg:SetName";
            type xr:Cisco-ios-xr-string;
            description "Set name";
          }
        }
      }

      container remove-ospf-area-sets {
        xr:xr-xml-map "rpl_cfg:RemoveOSPFAreaSetTable";
        description "Information about OSPF Area sets";

        list remove-ospf-area-set {
          xr:xr-xml-map "rpl_cfg:RemoveOSPFAreaSet";
          key "set-name";
          description "Remove the entries from the existing set.";
          leaf rplospf-area-set {
            type string;
            description "RPLOSPFAreaSet";
          }
          leaf set-name {
            xr:xr-xml-map "rpl_cfg:SetName";
            type xr:Cisco-ios-xr-string;
            description "Set name";
          }
        }
      }

      container ospf-area-sets {
        xr:xr-xml-map "rpl_cfg:OSPFAreaSetTable";
        description "Information about OSPF Area sets";

        list ospf-area-set {
          xr:xr-xml-map "rpl_cfg:OSPFAreaSet";
          key "set-name";
          description
            "Information about an individual OSPF area set.
            Usage: OSPF area set allows to define named
            set of area numbers        which can be
            referenced in the route-policy. Area sets     
            may be used during redistribution of the ospf
            protocol.  Example: ospf-area-set EXAMPLE     
            1,                                            
            192.168.1.255                                 
            end-set                                       
            Syntax: OSPF area number can be entered as 32
            bit number or in          the ip address
            format. See example.                    
            Semantic: Area numbers listed in the set will
            be searched for             a match. In the
            example these are areas 1 and                 
            192.168.1.255.                                ";
          leaf rplospf-area-set {
            type string;
            description "RPLOSPFAreaSet";
          }
          leaf set-name {
            xr:xr-xml-map "rpl_cfg:SetName";
            type xr:Cisco-ios-xr-string;
            description "Set name";
          }
        }
      }

      container extended-community-cost-sets {
        xr:xr-xml-map "rpl_cfg:ExtendedCommunityCostSetTable";
        description "Information about Cost sets";

        list extended-community-cost-set {
          xr:xr-xml-map "rpl_cfg:ExtendedCommunityCostSet";
          key "set-name";
          description "Information about an individual set";
          leaf rpl-extended-community-cost-set {
            type string;
            description "RPLExtendedCommunityCostSet";
          }
          leaf set-name {
            xr:xr-xml-map "rpl_cfg:SetName";
            type xr:Cisco-ios-xr-string;
            description "Set name";
          }
        }
      }

      container extended-community-soo-sets {
        xr:xr-xml-map "rpl_cfg:ExtendedCommunitySOOSetTable";
        description "Information about SOO sets";

        list extended-community-soo-set {
          xr:xr-xml-map "rpl_cfg:ExtendedCommunitySOOSet";
          key "set-name";
          description "Information about an individual set";
          leaf rpl-extended-community-soo-set {
            type string;
            description "RPLExtendedCommunitySOOSet";
          }
          leaf set-name {
            xr:xr-xml-map "rpl_cfg:SetName";
            type xr:Cisco-ios-xr-string;
            description "Set name";
          }
        }
      }

      container prepend-extended-community-opaque-sets {
        xr:xr-xml-map "rpl_cfg:PrependExtendedCommunityOpaqueSetTab"+
          "le";
        description "Information about Opaque sets";

        list prepend-extended-community-opaque-set {
          xr:xr-xml-map "rpl_cfg:PrependExtendedCommunityOpaqueSet";
          key "set-name";
          description "Prepend the entries to the existing set";
          leaf rpl-extended-community-opaque-set {
            type string;
            description "RPLExtendedCommunityOpaqueSet";
          }
          leaf set-name {
            xr:xr-xml-map "rpl_cfg:SetName";
            type xr:Cisco-ios-xr-string;
            description "Set name";
          }
        }
      }

      container extended-community-seg-nh-sets {
        xr:xr-xml-map "rpl_cfg:ExtendedCommunitySegNHSetTable";
        description "Information about SegNH sets";

        list extended-community-seg-nh-set {
          xr:xr-xml-map "rpl_cfg:ExtendedCommunitySegNHSet";
          key "set-name";
          description "Information about an individual set";
          leaf rpl-extended-community-seg-nh-set {
            type string;
            description "RPLExtendedCommunitySegNHSet";
          }
          leaf set-name {
            xr:xr-xml-map "rpl_cfg:SetName";
            type xr:Cisco-ios-xr-string;
            description "Set name";
          }
        }
      }

      container rd-sets {
        xr:xr-xml-map "rpl_cfg:RDSetTable";
        description "Information about RD sets";

        list rd-set {
          xr:xr-xml-map "rpl_cfg:RDSet";
          key "set-name";
          description "Information about an individual set";
          leaf rplrd-set {
            type string;
            description "RPLRDSet";
          }
          leaf set-name {
            xr:xr-xml-map "rpl_cfg:SetName";
            type xr:Cisco-ios-xr-string;
            description "Set name";
          }
        }
      }

      container policy-global-set-table {
        xr:xr-xml-map "rpl_cfg:PolicyGlobalSetTable";
        description "Information about PolicyGlobal sets";
        leaf policy-global-set {
          xr:xr-xml-map "rpl_cfg:PolicyGlobalSet";
          type string;
          description "RPLPolicyGlobalSet";
        }
      }

      container prepend-extended-community-seg-nh-sets {
        xr:xr-xml-map "rpl_cfg:PrependExtendedCommunitySegNHSetTabl"+
          "e";
        description "Information about SegNH sets";

        list prepend-extended-community-seg-nh-set {
          xr:xr-xml-map "rpl_cfg:PrependExtendedCommunitySegNHSet";
          key "set-name";
          description "Prepend the entries to the existing set";
          leaf rpl-extended-community-seg-nh-set {
            type string;
            description "RPLExtendedCommunitySegNHSet";
          }
          leaf set-name {
            xr:xr-xml-map "rpl_cfg:SetName";
            type xr:Cisco-ios-xr-string;
            description "Set name";
          }
        }
      }

      container extended-community-bandwidth-sets {
        xr:xr-xml-map "rpl_cfg:ExtendedCommunityBandwidthSetTable";
        description "Information about Bandwidth sets";

        list extended-community-bandwidth-set {
          xr:xr-xml-map "rpl_cfg:ExtendedCommunityBandwidthSet";
          key "set-name";
          description "Information about an individual set";
          leaf rpl-extended-community-bandwidth-set {
            type string;
            description "RPLExtendedCommunityBandwidthSet";
          }
          leaf set-name {
            xr:xr-xml-map "rpl_cfg:SetName";
            type xr:Cisco-ios-xr-string;
            description "Set name";
          }
        }
      }

      container community-sets {
        xr:xr-xml-map "rpl_cfg:CommunitySetTable";
        description "Information about Community sets";

        list community-set {
          xr:xr-xml-map "rpl_cfg:CommunitySet";
          key "set-name";
          description "Information about an individual set";
          leaf rpl-community-set {
            type string;
            description "RPLCommunitySet";
          }
          leaf set-name {
            xr:xr-xml-map "rpl_cfg:SetName";
            type xr:Cisco-ios-xr-string;
            description "Set name";
          }
        }
      }

      container prepend-ospf-area-sets {
        xr:xr-xml-map "rpl_cfg:PrependOSPFAreaSetTable";
        description "Information about OSPF Area sets";

        list prepend-ospf-area-set {
          xr:xr-xml-map "rpl_cfg:PrependOSPFAreaSet";
          key "set-name";
          description "Prepend the entries to the existing set";
          leaf rplospf-area-set {
            type string;
            description "RPLOSPFAreaSet";
          }
          leaf set-name {
            xr:xr-xml-map "rpl_cfg:SetName";
            type xr:Cisco-ios-xr-string;
            description "Set name";
          }
        }
      }

      container append-ospf-area-sets {
        xr:xr-xml-map "rpl_cfg:AppendOSPFAreaSetTable";
        description "Information about OSPF Area sets";

        list append-ospf-area-set {
          xr:xr-xml-map "rpl_cfg:AppendOSPFAreaSet";
          key "set-name";
          description "Append the entries to the existing set";
          leaf rplospf-area-set {
            type string;
            description "RPLOSPFAreaSet";
          }
          leaf set-name {
            xr:xr-xml-map "rpl_cfg:SetName";
            type xr:Cisco-ios-xr-string;
            description "Set name";
          }
        }
      }

      container as-path-sets {
        xr:xr-xml-map "rpl_cfg:ASPathSetTable";
        description "Information about AS Path sets";

        list as-path-set {
          xr:xr-xml-map "rpl_cfg:ASPathSet";
          key "set-name";
          description "Information about an individual set";
          leaf rplas-path-set {
            type string;
            description "RPLASPathSet";
          }
          leaf set-name {
            xr:xr-xml-map "rpl_cfg:SetName";
            type xr:Cisco-ios-xr-string;
            description "Set name";
          }
        }
      }

      container tag-sets {
        xr:xr-xml-map "rpl_cfg:TagSetTable";
        description "Information about Tag sets";

        list tag-set {
          xr:xr-xml-map "rpl_cfg:TagSet";
          key "set-name";
          description "Information about an individual set";
          leaf rpl-tag-set {
            type string;
            description "RPLTagSet";
          }
          leaf set-name {
            xr:xr-xml-map "rpl_cfg:SetName";
            type xr:Cisco-ios-xr-string;
            description "Set name";
          }
        }
      }

      container extended-community-rt-sets {
        xr:xr-xml-map "rpl_cfg:ExtendedCommunityRTSetTable";
        description "Information about RT sets";

        list extended-community-rt-set {
          xr:xr-xml-map "rpl_cfg:ExtendedCommunityRTSet";
          key "set-name";
          description "Information about an individual set";
          leaf rpl-extended-community-rt-set {
            type string;
            description "RPLExtendedCommunityRTSet";
          }
          leaf set-name {
            xr:xr-xml-map "rpl_cfg:SetName";
            type xr:Cisco-ios-xr-string;
            description "Set name";
          }
        }
      }
    }

    container limits {
      xr:xr-xml-map "rpl_cfg:Limits";
      description "Limits for Routing Policy";
      leaf maximum-lines-of-policy {
        xr:xr-xml-map "rpl_cfg:MaximumLinesOfPolicy";
        type int32;
        default "131072";
        description
          "Maximum total number of lines of policy
          configuration";
      }
      leaf maximum-number-of-policies {
        xr:xr-xml-map "rpl_cfg:MaximumNumberOfPolicies";
        type int32;
        default "5000";
        description "Maximum number of configured policies";
      }
    }
    leaf editor {
      xr:xr-xml-map "rpl_cfg:Editor";
      xr:xr-cli-map "rpl editor (emacs)|(nano)|(vim) ";
      type string;
      description "'emacs' or 'vim' or 'nano'";
    }
  }
}
