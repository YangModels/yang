module Cisco-IOS-XR-snmp-agent-oper {

  /*** NAMESPACE / PREFIX DEFINITION ***/

  namespace "http://cisco.com/ns/yang/Cisco-IOS-XR-snmp-agent-oper";


  prefix "snmp-agent-oper";

  /*** LINKAGE (IMPORTS / INCLUDES) ***/

  import ietf-inet-types { prefix "inet"; }

  import Cisco-IOS-XR-types { prefix "xr"; }

  include Cisco-IOS-XR-snmp-agent-oper-sub3 {
    revision-date 2015-01-07;
  }

  include Cisco-IOS-XR-snmp-agent-oper-sub2 {
    revision-date 2015-01-07;
  }

  include Cisco-IOS-XR-snmp-agent-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-agent package operational data.

     This module contains definitions
     for the following management objects:
       snmp: SNMP operational data

     Copyright (c) 2013-2015 by Cisco Systems, Inc.
     All rights reserved.";

  revision "2015-01-07" {
    description
      "IOS XR 5.3.1 revision.";
  }


  container snmp {
    xr:xr-xml-map "snmp_oper:SNMP";
    config false;
    description "SNMP operational data";

    container trap-servers {
      xr:xr-xml-map "snmp_oper:TrapServerTable";
      description "List of trap hosts";

      list trap-server {
        xr:xr-xml-map "snmp_oper:TrapServer";
        description
          "Trap server and port to which the trap is to be
          sent and statistics";
        leaf trap-host {
          xr:xr-xml-map "snmp_oper:TrapHost";
          type string;
          description "Trap Host";
        }
        leaf port {
          xr:xr-xml-map "snmp_oper:Port";
          type inet:port-number;
          description "Trap port";
        }
        uses SNMP-TRAP-STATS;
      }
    }

    container information {
      xr:xr-xml-map "snmp_oper:Information";
      description "SNMP operational information";

      container system-up-time {
        xr:xr-xml-map "snmp_oper:SystemUpTime";
        description "System up time";
        uses SNMP-SYSUPTIME;
      }

      container engine-id {
        xr:xr-xml-map "snmp_oper:EngineID";
        description "SNMP engine ID";
        uses SNMP-ENGINEID;
      }

      container bulk-stats-transfers {
        xr:xr-xml-map "snmp_oper:BulkStatsTransferTable";
        description "List of bulkstats transfer on the system";

        list bulk-stats-transfer {
          xr:xr-xml-map "snmp_oper:BulkStatsTransfer";
          key "transfer-name";
          description "SNMP bulkstats transfer name";
          leaf transfer-name {
            xr:xr-xml-map "snmp_oper:TransferName";
            type xr:Cisco-ios-xr-string;
            description "Transfer name";
          }
          uses SNMP-BULKSTATS-B;
        }
      }

      container statistics {
        xr:xr-xml-map "snmp_oper:Statistics";
        description "SNMP statistics";
        uses SNMP-STATS;
      }

      container mibs {
        xr:xr-xml-map "snmp_oper:MIBTable";
        description "List of MIBS supported on the system";

        list mib {
          xr:xr-xml-map "snmp_oper:MIB";
          key "name";
          description "SNMP MIB Name";

          container oids {
            xr:xr-xml-map "snmp_oper:OIDTable";
            description "List of OIDs per MIB";

            list oid {
              xr:xr-xml-map "snmp_oper:OID";
              key "oid";
              description "Object identifiers of a mib";
              leaf oid {
                xr:xr-xml-map "snmp_oper:OID";
                type string;
                description "Object Identifier";
              }
              leaf oid-name {
                xr:xr-xml-map "snmp_oper:OIDName";
                type string;
                mandatory true;
                description "MIB OID Name";
              }
            }
          }

          container mib-information {
            xr:xr-xml-map "snmp_oper:MIBInformation";
            description "MIB state and information";
            uses SNMP-MIB-INFO;
          }
          leaf name {
            xr:xr-xml-map "snmp_oper:Name";
            type xr:Cisco-ios-xr-string;
            description "MIB Name";
          }
        }
      }

      container statistics-extension {
        xr:xr-xml-map "snmp_oper:StatisticsExtension";
        description "SNMP Statistics Extension";
        uses SNMP-STATISTICS;
      }
    }

    container interfaces {
      xr:xr-xml-map "snmp_oper:InterfaceTable";
      description "List of interfaces";

      list interface {
        xr:xr-xml-map "snmp_oper:Interface";
        key "name";
        description "Interface Name";
        leaf name {
          xr:xr-xml-map "snmp_oper:Name";
          type xr:Interface-name;
          description "Interface Name";
        }
        leaf interface-index {
          xr:xr-xml-map "snmp_oper:InterfaceIndex";
          type int32;
          mandatory true;
          description "Interface Index as used by MIB tables";
        }
      }
    }

    container correlator {
      xr:xr-xml-map "snmp_corr_oper:Correlator";
      description "Trap Correlator operational data";

      container rule-details {
        xr:xr-xml-map "snmp_corr_oper:RuleDetailTable";
        description
          "Table that contains the database of correlation
          rule details";

        list rule-detail {
          xr:xr-xml-map "snmp_corr_oper:RuleDetail";
          key "rule-name";
          description "Details of one of the correlation rules";
          leaf rule-name {
            xr:xr-xml-map "snmp_corr_oper:RuleName";
            type string {
              length "0..32";
            }
            description "Correlation Rule Name";
          }
          uses SNMP-CORR-RULE-DETAIL-BAG;
        }
      }

      container buffer-status {
        xr:xr-xml-map "snmp_corr_oper:BufferStatus";
        description
          "Describes buffer utilization and parameters
          configured";
        uses SNMP-CORR-BUFFER-INFO-BAG;
      }

      container rule-set-details {
        xr:xr-xml-map "snmp_corr_oper:RulesetDetailTable";
        description "Table that contains the ruleset detail info";

        list rule-set-detail {
          xr:xr-xml-map "snmp_corr_oper:RulesetDetail";
          key "rule-set-name";
          description "Detail of one of the correlation rulesets";
          leaf rule-set-name {
            xr:xr-xml-map "snmp_corr_oper:RulesetName";
            type string {
              length "0..32";
            }
            description "Ruleset Name";
          }
          uses SNMP-CORR-RULESET-DETAIL-BAG;
        }
      }

      container traps {
        xr:xr-xml-map "snmp_corr_oper:TrapTable";
        description "Correlated traps Table";

        list trap {
          xr:xr-xml-map "snmp_corr_oper:Trap";
          key "entry-id";
          description "One of the correlated traps";
          leaf entry-id {
            xr:xr-xml-map "snmp_corr_oper:EntryID";
            type int32;
            description "Entry ID";
          }
          uses SNMP-CORR-TRAP-BUFFER-BAG;
        }
      }
    }

    container interface-indexes {
      xr:xr-xml-map "snmp_oper:InterfaceIndexTable";
      description "List of index";

      list interface-index {
        xr:xr-xml-map "snmp_oper:InterfaceIndex";
        key "interface-index";
        description "Interface Index";
        leaf interface-index {
          xr:xr-xml-map "snmp_oper:InterfaceIndex";
          type int32;
          description "Interface Index as used by MIB tables";
        }
        leaf interface-name {
          xr:xr-xml-map "snmp_oper:InterfaceName";
          type string;
          mandatory true;
          description "Interface Name";
        }
      }
    }
  }
}
