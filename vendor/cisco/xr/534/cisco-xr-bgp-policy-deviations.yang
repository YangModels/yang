module cisco-xr-bgp-policy-deviations {

  /*** NAMESPACE / PREFIX DEFINITION ***/

  namespace "http://cisco.com/ns/yang/cisco-xr-bgp-policy-deviations";

  prefix "cisco-xr-bgp-pol-devs";

  /*** LINKAGE (IMPORTS / INCLUDES) ***/
  import routing-policy { prefix rpol; }
  import bgp-policy { prefix bgp-pol; }

  /*** META INFORMATION ***/
  organization "Cisco Systems, Inc.";

  contact
    "Cisco Systems, Inc.
     Custome Service

     Postal: 170 West Tasman Dive
     San Jose, CA 95134

     Tel: +1 800 553-NETS

     E-mail: cs-yang@cisco.com";

  description 
    "This module contains the deviations of Open Config BGP Policy YANG 
    set fo Cisco IOS-XR.

     Copyight (c) 2015-2016 by Cisco Systems, Inc.
     All ights reserved.";

  revision "2015-09-16" {
    description
      "Initial evision applicable to IOS-XR 5.3.2 and 6.0";
  }

  /* einann: container deviation */
  deviation /rpol:routing-policy/rpol:defined-sets/bgp-pol:bgp-defined-sets/bgp-pol:ext-community-sets/bgp-pol:ext-community-set {
    deviate not-supported;
  }
/*
  deviation /rpol:routing-policy/rpol:defined-sets/bgp-pol:bgp-defined-sets/bgp-pol:ext-community-sets/bgp-pol:ext-community-set/bgp-pol:ext-community-set-name {
    deviate not-supported;
  }

  deviation /rpol:routing-policy/rpol:defined-sets/bgp-pol:bgp-defined-sets/bgp-pol:ext-community-sets/bgp-pol:ext-community-set/bgp-pol:ext-community-member {
    deviate not-supported;
  }
*/

  /* einann: container deviation */
  deviation /rpol:routing-policy/rpol:policy-definitions/rpol:policy-definition/rpol:statements/rpol:statement/rpol:conditions/bgp-pol:bgp-conditions/bgp-pol:match-ext-community-set {
    deviate not-supported;
  }
/*
deviation /rpol:routing-policy/rpol:policy-definitions/rpol:policy-definition/rpol:statements/rpol:statement/rpol:conditions/bgp-pol:bgp-conditions/bgp-pol:match-ext-community-set/bgp-pol:ext-community-set {
    deviate not-supported;
  }

  deviation /rpol:routing-policy/rpol:policy-definitions/rpol:policy-definition/rpol:statements/rpol:statement/rpol:conditions/bgp-pol:bgp-conditions/bgp-pol:route-type {
    deviate not-supported;
  }
*/
  deviation /rpol:routing-policy/rpol:policy-definitions/rpol:policy-definition/rpol:statements/rpol:statement/rpol:actions/bgp-pol:bgp-actions/bgp-pol:set-ext-community/bgp-pol:options {
    deviate not-supported;
  }
}
