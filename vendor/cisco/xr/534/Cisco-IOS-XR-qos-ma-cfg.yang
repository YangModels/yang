module Cisco-IOS-XR-qos-ma-cfg {

  /*** NAMESPACE / PREFIX DEFINITION ***/

  namespace "http://cisco.com/ns/yang/Cisco-IOS-XR-qos-ma-cfg";


  prefix "qos-ma-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR qos-ma package configuration.

     This YANG module augments the
       Cisco-IOS-XR-subscriber-infra-tmplmgr-cfg
     module with configuration data.

     Copyright (c) 2013-2015 by Cisco Systems, Inc.
     All rights reserved.";

  revision "2015-01-07" {
    description
      "IOS XR 5.3.1 revision.";
  }

  typedef Qosl2-data-link {
    type enumeration {
      enum aal5 {
        value 0;
        description "ATM adaption layer AAL5";
      }
    }
    description "Qosl2 data link";
  }
  typedef Qosl2-encap {
    type enumeration {
      enum snap-pppoa {
        value 1;
        description
          "snap-pppoa encap used between the DSLAM and CPE";
      }
      enum mux-pppoa {
        value 2;
        description
          "mux-pppoa encap used between the DSLAM and CPE";
      }
      enum snap1483-routed {
        value 3;
        description
          "snap-1483routed encap used between the DSLAM
          and CPE";
      }
      enum mux1483-routed {
        value 4;
        description
          "mux-1483routed encap used between the DSLAM and
          CPE";
      }
      enum snap-rbe {
        value 5;
        description "snap-rbe encap used between the DSLAM and CPE";
      }
      enum snap-dot1qrbe {
        value 6;
        description
          "snap-dot1q-rbe encap used between the DSLAM and
          CPE";
      }
      enum mux-rbe {
        value 7;
        description "mux-rbe encap used between the DSLAM and CPE";
      }
      enum mux-dot1qrbe {
        value 8;
        description
          "mux-dot1q-rbe encap used between the DSLAM and
          CPE";
      }
    }
    description "Qosl2 encap";
  }
  typedef Qos-policy-account {
    type enumeration {
      enum no-preference {
        value 0;
        description "No account turn off preference";
      }
      enum layer2 {
        value 1;
        description "Turn on layer 2 accounting";
      }
      enum no-layer2 {
        value 2;
        description "Turn off layer 2 accounting";
      }
      enum user-defined {
        value 4;
        description "User defined accounting";
      }
      enum layer1 {
        value 8;
        description "Turn on layer 1 accounting";
      }
    }
    description "Qos policy account";
  }

  grouping QOS {
    description
      "Common node of ppp, ip-subscriber,
      subscriber-service";

    container qos {
      xr:xr-xml-map "qos_ma_dyn_tmpl_cfg:QoS";
      description "QoS dynamically applied configuration template";

      container service-policy {
        xr:xr-xml-map "qos_ma_dyn_tmpl_cfg:ServicePolicy";
        description
          "Service policy to be applied in ingress/egress
          direction";

        container input {
          xr:xr-xml-map "qos_ma_dyn_tmpl_cfg:Input";
          presence "Indicates a input node is configured.";
          description "Subscriber ingress policy";
          leaf policy-name {
            xr:xr-xml-map "qos_ma_dyn_tmpl_cfg:PolicyName";
            type string;
            mandatory true;
            description "Name of policy-map";
          }
          leaf account-type {
            xr:xr-xml-map "qos_ma_dyn_tmpl_cfg:AccountType";
            type Qos-policy-account;
            description "Turn off L2 or L3 accounting";
          }
          leaf spi-name {
            xr:xr-xml-map "qos_ma_dyn_tmpl_cfg:SPIName";
            type string;
            description "Name of the SPI";
          }
          leaf merge {
            xr:xr-xml-map "qos_ma_dyn_tmpl_cfg:Merge";
            type boolean;
            description
              "TRUE for merge enabled for service-policy
              applied on dynamic template.";
          }
          leaf merge-id {
            xr:xr-xml-map "qos_ma_dyn_tmpl_cfg:MergeID";
            type uint32 {
              range "0..255";
            }
            description "Merge ID value";
          }
          leaf account-stats {
            xr:xr-xml-map "qos_ma_dyn_tmpl_cfg:AccountStats";
            type boolean;
            description
              "TRUE for account stats enabled for
              service-policy applied on dynamic template.
              Note: account stats not supported for
              subscriber type 'ppp' and 'ipsubscriber'.";
          }
        }

        container output {
          xr:xr-xml-map "qos_ma_dyn_tmpl_cfg:Output";
          presence "Indicates a output node is configured.";
          description "Subscriber egress policy";
          leaf policy-name {
            xr:xr-xml-map "qos_ma_dyn_tmpl_cfg:PolicyName";
            type string;
            mandatory true;
            description "Name of policy-map";
          }
          leaf account-type {
            xr:xr-xml-map "qos_ma_dyn_tmpl_cfg:AccountType";
            type Qos-policy-account;
            description "Turn off L2 or L3 accounting";
          }
          leaf spi-name {
            xr:xr-xml-map "qos_ma_dyn_tmpl_cfg:SPIName";
            type string;
            description "Name of the SPI";
          }
          leaf merge {
            xr:xr-xml-map "qos_ma_dyn_tmpl_cfg:Merge";
            type boolean;
            description
              "TRUE for merge enabled for service-policy
              applied on dynamic template.";
          }
          leaf merge-id {
            xr:xr-xml-map "qos_ma_dyn_tmpl_cfg:MergeID";
            type uint32 {
              range "0..255";
            }
            description "Merge ID value";
          }
          leaf account-stats {
            xr:xr-xml-map "qos_ma_dyn_tmpl_cfg:AccountStats";
            type boolean;
            description
              "TRUE for account stats enabled for
              service-policy applied on dynamic template.
              Note: account stats not supported for
              subscriber type 'ppp' and 'ipsubscriber'.";
          }
        }
      }

      container account {
        xr:xr-xml-map "qos_ma_dyn_tmpl_cfg:Account";
        description "QoS L2 overhead accounting";
        leaf aal {
          xr:xr-xml-map "qos_ma_dyn_tmpl_cfg:AAL";
          type Qosl2-data-link;
          description "ATM adaptation layer AAL";
        }
        leaf encapsulation {
          xr:xr-xml-map "qos_ma_dyn_tmpl_cfg:Encapsulation";
          type Qosl2-encap;
          description "Specify encapsulation type";
        }
        leaf atm-cell-tax {
          xr:xr-xml-map "qos_ma_dyn_tmpl_cfg:ATMCellTax";
          type empty;
          description "ATM cell tax to L2 overhead";
        }
        leaf user-defined {
          xr:xr-xml-map "qos_ma_dyn_tmpl_cfg:UserDefined";
          type int32 {
            range "-63..63";
          }
          description "Numeric L2 overhead offset";
        }
      }

      container output {
        xr:xr-xml-map "qos_ma_dyn_tmpl_cfg:Output";
        description "QoS to be applied in egress direction";
        leaf minimum-bandwidth {
          xr:xr-xml-map "qos_ma_dyn_tmpl_cfg:MinimumBandwidth";
          type uint32 {
            range "1..4294967295";
          }
          units "kbit/s";
          description "Bandwidth in kbps";
        }
      }
    }
  }

  augment "/a1:dynamic-template/a1:subscriber-services"+
    "/a1:subscriber-service" {
    description
      "This augment extends the configuration data of
      'Cisco-IOS-XR-subscriber-infra-tmplmgr-cfg'";
    uses QOS;
  }

  augment "/a1:dynamic-template/a1:ip-subscribers/a1:ip-subscriber" {
    description
      "This augment extends the configuration data of
      'Cisco-IOS-XR-subscriber-infra-tmplmgr-cfg'";
    uses QOS;
  }

  augment "/a1:dynamic-template/a1:ppps/a1:ppp" {
    description
      "This augment extends the configuration data of
      'Cisco-IOS-XR-subscriber-infra-tmplmgr-cfg'";
    uses QOS;
  }
}
