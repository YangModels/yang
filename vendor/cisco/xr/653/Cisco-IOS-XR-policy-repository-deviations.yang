module Cisco-IOS-XR-policy-repository-deviations {
  namespace "http://cisco.com/ns/yang/Cisco-IOS-XR-policy-repository-deviations";
  prefix cisco-xr-rpol-xrvr-devs;

  import Cisco-IOS-XR-policy-repository-cfg {
    prefix rpol-xrvr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations of routing policy data
     model set for Cisco IOS-XR.
     
     Copyright (c) 2016 by Cisco Systems, Inc.
     All rights reserved.";

  revision 2016-09-13 {
    description
      "Initial revision applicable to IOS-XR 6.1.2 and above";
  }

  deviation "/rpol-xrvr:routing-policy/rpol-xrvr:limits/rpol-xrvr:maximum-number-of-policies" {
    deviate replace {
      default "15000";
    }
  }
}
