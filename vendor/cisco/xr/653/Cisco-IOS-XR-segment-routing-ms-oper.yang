module Cisco-IOS-XR-segment-routing-ms-oper {
  namespace "http://cisco.com/ns/yang/Cisco-IOS-XR-segment-routing-ms-oper";
  prefix segment-routing-ms-oper;

  import Cisco-IOS-XR-types {
    prefix xr;
  }
  include Cisco-IOS-XR-segment-routing-ms-oper-sub3 {
    revision-date 2017-09-07;
  }
  include Cisco-IOS-XR-segment-routing-ms-oper-sub2 {
    revision-date 2017-09-07;
  }
  include Cisco-IOS-XR-segment-routing-ms-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-ms package operational data.
     
     This module contains definitions
     for the following management objects:
       srms: Segment Routing Mapping Server operational data
       srlb: srlb
     
     Copyright (c) 2013-2018 by Cisco Systems, Inc.
     All rights reserved.";

  revision 2017-09-07 {
    description
      "Fixed type translation error.";
  }
  revision 2015-11-09 {
    description
      "IOS XR 6.0 revision.";
  }

  typedef Sid-type-enum {
    type enumeration {
      enum "absolute" {
        value 1;
        description
          "Absolute SID";
      }
      enum "index" {
        value 2;
        description
          "Index SID";
      }
    }
    description
      "Sid type enum";
  }

  grouping MAPPING-MI {
    description
      "Common node of mapping-ipv4, mapping-ipv6";
    list mapping-mi {
      description
        "IP prefix to SID mapping item. It's not possible
         to list all of the IP prefix to SID mappings, as
         the set of valid prefixes could be very large.
         Instead, SID map information must be retrieved
         individually for each prefix of interest.";
      leaf ip {
        type xr:Cisco-ios-xr-string;
        description
          "IP";
      }
      leaf prefix {
        type uint32;
        description
          "Prefix";
      }
      uses SRMS-MI-T-B;
    }
  }

  grouping POLICY-MI {
    description
      "Common node of policy-ipv4-active,
       policy-ipv4-backup, policy-ipv6-active,
       policy-ipv6-backup";
    list policy-mi {
      key "mi-id";
      description
        "Mapping Item";
      leaf mi-id {
        type xr:Cisco-ios-xr-string;
        description
          "Mapping Item ID (0, 1, 2, ...)";
      }
      uses SRMS-MI-T-B;
    }
  }

  grouping SID-RECORD {
    description
      "Common node of ipv4, ipv6";
    list sid-record {
      description
        "SID record";
      leaf sid-type {
        type Sid-type-enum;
        description
          "SID type";
      }
      leaf sid-value {
        type uint32;
        description
          "SID value";
      }
      uses SRMS-L2-ADJ-T-B;
    }
  }

  container srms {
    config false;
    description
      "Segment Routing Mapping Server operational data";
    container mapping {
      description
        "IP prefix to SID mappings";
      container mapping-ipv4 {
        description
          "IPv4 prefix to SID mappings";
        uses MAPPING-MI;
      }
      container mapping-ipv6 {
        description
          "IPv6 prefix to SID mappings";
        uses MAPPING-MI;
      }
    }
    container adjacency-sid {
      description
        "Adjacency SID";
      container l2-adjacency {
        description
          "L2 Adjacency Option";
        container interfaces {
          description
            "Interface directory";
          list interface {
            key "interface-name";
            description
              "Segment Routing Adjacency SID Interface";
            container address-family {
              description
                "address family container";
              container ipv4 {
                description
                  "IP version 4";
                uses SID-RECORD;
              }
              container ipv6 {
                description
                  "IP version 6";
                uses SID-RECORD;
              }
            }
            leaf interface-name {
              type xr:Interface-name;
              description
                "Interface name";
            }
          }
        }
      }
    }
    container policy {
      description
        "Policy operational data";
      container policy-ipv4 {
        description
          "IPv4 policy operational data";
        container policy-ipv4-backup {
          description
            "IPv4 backup policy operational data";
          uses POLICY-MI;
        }
        container policy-ipv4-active {
          description
            "IPv4 active policy operational data";
          uses POLICY-MI;
        }
      }
      container policy-ipv6 {
        description
          "IPv6 policy operational data";
        container policy-ipv6-backup {
          description
            "IPv6 backup policy operational data";
          uses POLICY-MI;
        }
        container policy-ipv6-active {
          description
            "IPv6 active policy operational data";
          uses POLICY-MI;
        }
      }
    }
  }
  container srlb {
    config false;
    description
      "srlb";
    container srlb-inconsistency {
      description
        "SRLB Inconsistencies";
      uses MPLS-LSD-SRLB-INCONSISTENCY;
    }
  }
}
