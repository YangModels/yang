module Cisco-IOS-XR-ip-iep-oper {
  namespace "http://cisco.com/ns/yang/Cisco-IOS-XR-ip-iep-oper";
  prefix ip-iep-oper;

  import Cisco-IOS-XR-types {
    prefix xr;
  }
  include Cisco-IOS-XR-ip-iep-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-iep package operational data.
     
     This module contains definitions
     for the following management objects:
       explicit-paths: Configured IP explicit paths
     
     Copyright (c) 2013-2018 by Cisco Systems, Inc.
     All rights reserved.";

  revision 2017-09-07 {
    description
      "Fixed type translation error.";
  }
  revision 2015-11-09 {
    description
      "IOS XR 6.0 revision.";
  }

  container explicit-paths {
    config false;
    description
      "Configured IP explicit paths";
    container identifiers {
      description
        "List of configured IP explicit path identifiers,
         this corresponds to mplsTunnelHopTable in TE MIB";
      list identifier {
        key "identifier-id";
        description
          "IP explicit path configured for a particular
           identifier";
        leaf identifier-id {
          type uint32;
          description
            "Identifier ID";
        }
        uses IEP-EXPLICIT-PATH;
      }
    }
    container names {
      description
        "List of configured IP explicit path names, this
         corresponds to mplsTunnelHopTable in TE MIB";
      list name {
        key "path-name";
        description
          "IP explicit path configured for a particular
           path name";
        leaf path-name {
          type xr:Cisco-ios-xr-string;
          description
            "Path name";
        }
        uses IEP-EXPLICIT-PATH;
      }
    }
  }
}
