module Cisco-IOS-XR-drivers-media-eth-oper {
  namespace "http://cisco.com/ns/yang/Cisco-IOS-XR-drivers-media-eth-oper";
  prefix drivers-media-eth-oper;

  import Cisco-IOS-XR-types {
    prefix xr;
  }
  include Cisco-IOS-XR-drivers-media-eth-oper-sub1 {
    revision-date 2017-05-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-media-eth package operational data.
     
     This module contains definitions
     for the following management objects:
       ethernet-interface: Ethernet operational data
     
     Copyright (c) 2013-2018 by Cisco Systems, Inc.
     All rights reserved.";

  revision 2017-05-01 {
    description
      "Fixing backward compatibility error in module.";
  }
  revision 2017-04-04 {
    description
      "Added new fields to phy data.";
  }
  revision 2015-01-07 {
    description
      "IOS XR 5.3.1 revision.";
  }

  container ethernet-interface {
    config false;
    description
      "Ethernet operational data";
    container statistics {
      description
        "Ethernet controller statistics table";
      list statistic {
        key "interface-name";
        description
          "Ethernet statistics information";
        leaf interface-name {
          type xr:Interface-name;
          description
            "The name of the interface";
        }
        uses ETHERNET-PORT-STATS-TYPE;
      }
    }
    container interfaces {
      description
        "Ethernet controller info table";
      list interface {
        key "interface-name";
        description
          "Ethernet controller information";
        leaf interface-name {
          type xr:Interface-name;
          description
            "The name of the interface";
        }
        uses ETHERNET-CONTROLLER-DRIVER-BAG-V2-TYPE;
      }
    }
    container berts {
      description
        "Ethernet controller BERT table";
      list bert {
        key "interface-name";
        description
          "Ethernet BERT information";
        leaf interface-name {
          type xr:Interface-name;
          description
            "The name of the interface";
        }
        uses ETH-SHOWCTRL-BERT;
      }
    }
  }
}
