module SNMP-USER-BASED-SM-MIB {
  namespace "http://tail-f.com/ns/mibs/SNMP-USER-BASED-SM-MIB/200210160000Z";
  prefix SNMP_USER_BASED_SM_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }

  revision 2002-10-16 {
    description
      "";
  }

  typedef KeyChange {
    type tailf:hex-list {
      pattern "(((([0-9A-Fa-f]{2}):)*([0-9A-Fa-f]{2}))){0,1}";
    }
  }

  typedef usmUserNameType {
    type string {
      length "1 .. 32";
    }
  }

  typedef usmUserPublicType {
    type tailf:hex-list {
      pattern "(((([0-9A-Fa-f]{2}):){0,31}([0-9A-Fa-f]{2}))){0,1}";
      tailf:value-length "min .. 32";
    }
  }
  tailf:id "";
  tailf:snmp-mib-module-name "SNMP-USER-BASED-SM-MIB";

  container SNMP-USER-BASED-SM-MIB {
    container usmStats {
      config false;
      tailf:snmp-oid "1.3.6.1.6.3.15.1.1";
      leaf usmStatsUnsupportedSecLevels {
        type yang:counter32;
        config false;
        tailf:snmp-oid "1.3.6.1.6.3.15.1.1.1";
      }
      leaf usmStatsNotInTimeWindows {
        type yang:counter32;
        config false;
        tailf:snmp-oid "1.3.6.1.6.3.15.1.1.2";
      }
      leaf usmStatsUnknownUserNames {
        type yang:counter32;
        config false;
        tailf:snmp-oid "1.3.6.1.6.3.15.1.1.3";
      }
      leaf usmStatsUnknownEngineIDs {
        type yang:counter32;
        config false;
        tailf:snmp-oid "1.3.6.1.6.3.15.1.1.4";
      }
      leaf usmStatsWrongDigests {
        type yang:counter32;
        config false;
        tailf:snmp-oid "1.3.6.1.6.3.15.1.1.5";
      }
      leaf usmStatsDecryptionErrors {
        type yang:counter32;
        config false;
        tailf:snmp-oid "1.3.6.1.6.3.15.1.1.6";
      }
    }
    container usmUserTable {
      list usmUserEntry {
        key "usmUserEngineID usmUserName";
        unique "usmUserEngineID usmUserSecurityName";
        tailf:sort-order "snmp";
        tailf:snmp-oid "1.3.6.1.6.3.15.1.2.2";
        leaf usmUserEngineID {
          type SNMP_FRAMEWORK_MIB:SnmpEngineID;
          tailf:snmp-oid "1.3.6.1.6.3.15.1.2.2.1.1";
        }
        leaf usmUserName {
          type usmUserNameType;
          tailf:snmp-oid "1.3.6.1.6.3.15.1.2.2.1.2";
        }
        leaf usmUserSecurityName {
          type SNMP_FRAMEWORK_MIB:SnmpAdminString;
          mandatory true;
          tailf:snmp-oid "1.3.6.1.6.3.15.1.2.2.1.3";
        }
        leaf usmUserCloneFrom {
          type SNMPv2_TC:RowPointer;
          tailf:snmp-oid "1.3.6.1.6.3.15.1.2.2.1.4";
        }
        leaf usmUserAuthProtocol {
          type SNMPv2_TC:AutonomousType;
          default "1.3.6.1.6.3.10.1.1.1";
          tailf:snmp-oid "1.3.6.1.6.3.15.1.2.2.1.5";
        }
        leaf usmUserAuthKeyChange {
          type KeyChange;
          tailf:snmp-oid "1.3.6.1.6.3.15.1.2.2.1.6";
        }
        leaf usmUserOwnAuthKeyChange {
          type KeyChange;
          tailf:snmp-oid "1.3.6.1.6.3.15.1.2.2.1.7";
        }
        leaf usmUserPrivProtocol {
          type SNMPv2_TC:AutonomousType;
          default "1.3.6.1.6.3.10.1.2.1";
          tailf:snmp-oid "1.3.6.1.6.3.15.1.2.2.1.8";
        }
        leaf usmUserPrivKeyChange {
          type KeyChange;
          tailf:snmp-oid "1.3.6.1.6.3.15.1.2.2.1.9";
        }
        leaf usmUserOwnPrivKeyChange {
          type KeyChange;
          tailf:snmp-oid "1.3.6.1.6.3.15.1.2.2.1.10";
        }
        leaf usmUserPublic {
          type usmUserPublicType;
          tailf:snmp-oid "1.3.6.1.6.3.15.1.2.2.1.11";
        }
        leaf usmUserStorageType {
          type SNMPv2_TC:StorageType;
          default "nonVolatile";
          tailf:snmp-oid "1.3.6.1.6.3.15.1.2.2.1.12";
        }
        leaf usmUserAuthKey {
          type KeyChange;
        }
        leaf usmUserPrivKey {
          type KeyChange;
        }
      }
    }
  }
}
