module Cisco-IOS-XR-sysadmin-ethsw-esdma-fdb {
  namespace "http://www.cisco.com/ns/yang/Cisco-IOS-XR-sysadmin-ethsw-esdma-fdb";
  prefix esdma_fdb;

  import ietf-yang-types {
    prefix ietf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains the YANG definitions
     for the Cisco IOS-XR SysAdmin
     'show controller switch fdb' commands.
     
     Copyright(c) 2011-2017 by Cisco Systems, Inc.
     All rights reserved.
     
     Copyright (c) 2012-2018 by Cisco Systems, Inc.
     All rights reserved.";

  revision 2018-10-26 {
    description
      "Modified FDB port leaf to use new ESDMA type esdma-switch-fdb-ports";
  }

  grouping switch-fdb-location {
    container switch-fdb-common {
      list location {
        key "rack card switch-id";
        leaf rack {
          type esdma_types:esdma-rack-num-enum;
        }
        leaf card {
          type esdma_types:esdma-cpu;
          description
            "Card to list the switch FDB information for";
        }
        leaf switch-id {
          type esdma_types:esdma-switch-type-enum;
          description
            "Switch type";
        }
        leaf num-entries {
          type uint32;
          description
            "Number of FDB entries in the table.";
        }
        leaf has-trunk-entry {
          type uint8;
          description
            "FDB entries contain an entry from the trunk";
        }
        leaf trunk-entry-message {
          type string;
          description
            "Message displayed when an FDB entry contains an entry for a trunk member port";
        }
        container fdb-block {
          list fdb-entry {
            key "fdb-index";
            leaf fdb-index {
              type uint32;
            }
            leaf fdb-mac-addr {
              type ietf:mac-address;
            }
            leaf fdb-vlan {
              type esdma_types:vlan-id-type;
            }
            leaf fdb-vlan-hex {
              type leafref {
                path "../fdb-vlan";
              }
            }
            leaf fdb-port {
              type esdma_types:esdma-switch-fdb-ports;
              description
                "Switch port MAC address learned on.";
            }
            leaf fdb-trap-entry {
              type esdma_types:esdma-switch-yes-no-enum;
            }
            leaf fdb-static-entry {
              type esdma_types:esdma-switch-yes-no-enum;
            }
            leaf-list fdb-synced-cores {
              type uint8;
            }
          }
        }
      }
    }
  }

  grouping switch-fdb-group {
    container fdb {
      container vlan {
        list vlan-iter {
          key "vlan";
          leaf vlan {
            type esdma_types:vlan-id-type;
          }
          uses switch-fdb-location;
        }
      }
      container mac {
        list mac-iter {
          key "mac";
          leaf mac {
            type ietf:mac-address;
          }
          uses switch-fdb-location;
        }
      }
      container port {
        list port-iter {
          key "port";
          leaf port {
            type esdma_types:esdma-switch-port-type;
            description
              "Switch port used for filtering";
          }
          uses switch-fdb-location;
        }
      }
      container statistics {
        list location {
          key "rack card switch-id";
          leaf rack {
            type esdma_types:esdma-rack-num-enum;
          }
          leaf card {
            type esdma_types:esdma-cpu;
            description
              "Card";
          }
          leaf switch-id {
            type esdma_types:esdma-switch-type-enum;
            description
              "Switch type";
          }
          container counter-info {
            leaf fdb-shadow-entries {
              type uint32;
            }
            leaf fdb-max-shadow-entries {
              type uint32;
            }
            leaf fdb-max-hash-chain {
              type uint32;
            }
            leaf fdb-entries-added {
              type uint32;
            }
            leaf fdb-entries-deleted {
              type uint32;
            }
            leaf fdb-entries-updated {
              type uint32;
            }
            leaf fdb-flushes {
              type uint32;
            }
            leaf fdb-address-updates {
              type uint32;
            }
            leaf fdb-new-addresses {
              type uint32;
            }
            leaf fdb-aged-updates {
              type uint32;
            }
            leaf fdb-transplant-updates {
              type uint32;
            }
            leaf fdb-forwarding-updates {
              type uint32;
            }
            leaf fdb-address-insert-errors {
              type uint32;
            }
            leaf fdb-address-update-errors {
              type uint32;
            }
            leaf fdb-memory-errors {
              type uint32;
            }
            leaf fdb-allocation-errors {
              type uint32;
            }
            leaf fdb-address-updates-queued {
              type uint32;
            }
            leaf fdb-address-queue-full {
              type esdma_types:esdma-switch-yes-no-enum;
            }
            leaf fdb-forwarding-updates-queued {
              type uint32;
            }
            leaf fdb-forwarding-queue-full {
              type esdma_types:esdma-switch-yes-no-enum;
            }
          }
          list core-id {
            key "core";
            leaf core {
              type int32;
            }
            leaf core-entries {
              type uint32;
            }
            leaf core-static-entries {
              type uint32;
            }
          }
        }
      }
      uses switch-fdb-location;
    }
  }
}
