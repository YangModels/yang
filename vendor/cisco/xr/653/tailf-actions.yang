module tailf-actions {
  namespace "http://tail-f.com/ns/netconf/actions/1.0";
  prefix act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains YANG definitions
     for Cisco IOS-XR and Tail-F action support.
     
     Copyright (c) 2017 by Cisco Systems, Inc.
     All rights reserved.";

  revision 2017-02-28 {
    description
      "Descriptions Initial support for Tail-F actions.
       IOS XR 6.3.1 revision.";
  }

  rpc action {
    description
      "Support Tail-F actions rpc format.";
    reference "RFC 6241, Section 7.1";
    input {
      anyxml data {
        description
          "Data section of the YANG action hierarchy.";
      }
    }
    output {
      anyxml data {
        description
          "Data and messages returned by the Tail-F ConfD agent.";
      }
    }
  }
}
