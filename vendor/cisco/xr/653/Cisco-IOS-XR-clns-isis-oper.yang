module Cisco-IOS-XR-clns-isis-oper {
  namespace "http://cisco.com/ns/yang/Cisco-IOS-XR-clns-isis-oper";
  prefix clns-isis-oper;

  import ietf-inet-types {
    prefix inet;
  }
  import Cisco-IOS-XR-types {
    prefix xr;
  }
  import Cisco-IOS-XR-clns-isis-datatypes {
    prefix dt1;
  }
  include Cisco-IOS-XR-clns-isis-oper-sub3 {
    revision-date 2019-02-16;
  }
  include Cisco-IOS-XR-clns-isis-oper-sub2 {
    revision-date 2019-02-16;
  }
  include Cisco-IOS-XR-clns-isis-oper-sub1 {
    revision-date 2019-02-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clns-isis package operational data.
     
     This module contains definitions
     for the following management objects:
       ocni-isis: An OpenConfig description of a network-instance
       isis: isis
     
     Copyright (c) 2013-2018 by Cisco Systems, Inc.
     All rights reserved.";

  revision 2019-02-16 {
    description
      "Added interface link-group name";
  }
  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  grouping POLICY-MI {
    description
      "Common node of policy-ipv4-active,
       policy-ipv4-backup, policy-ipv6-active,
       policy-ipv6-backup";
    list policy-mi {
      key "mi-id";
      description
        "Mapping Item";
      leaf mi-id {
        type xr:Cisco-ios-xr-string;
        description
          "Mapping Item ID (0, 1, 2, ...)";
      }
      uses SRMS-MI-T-B;
    }
  }

  container ocni-isis {
    config false;
    description
      "An OpenConfig description of a network-instance";
    container network-instances {
      description
        "Network instances configured on the local system";
      list network-instance {
        key "name";
        description
          "Network instances configured on the local
           system";
        container interfaces {
          description
            "An interface associated with the network
             instance";
          list interface {
            key "id";
            description
              "An interface associated with the network
               instance";
            leaf id {
              type string;
              description
                "A reference to an identifier for this
                 interface which acts as a key for this list";
            }
            uses OVERLAY-OCNI-ISIS-INTERFACE;
          }
        }
        container protocols {
          description
            "A process (instance) of a routing protocol";
          list protocol {
            description
              "A process (instance) of a routing protocol";
            container protocols-state {
              description
                "State parameters relating to the routing
                 protocol instance";
              uses OVERLAY-OCNI-ISIS-PROTOCOL-STATE;
            }
            container isis {
              description
                "This container defines top-level ISIS
                 configuration and state information";
              container isis-interfaces {
                description
                  "This list contains ISIS interfaces";
                list isis-interface {
                  key "interface-id";
                  description
                    "This list contains ISIS interfaces";
                  container interfaces-afi-safis {
                    description
                      "Address-family/Subsequent Address-family
                       list";
                    list interfaces-afi-safi {
                      description
                        "Address-family/Subsequent Address-family
                         list";
                      leaf afi-name {
                        type string;
                        description
                          "Reference to address-family type";
                      }
                      leaf safi-name {
                        type string;
                        description
                          "Reference to subsequent address-family
                           type";
                      }
                      uses OVERLAY-OCNI-ISIS-AFI-SAFI-AF;
                    }
                  }
                  container interfaces-state {
                    description
                      "This container defines state information
                       for ISIS interfaces";
                    uses OVERLAY-OCNI-ISIS-INTERFACE-STATE;
                  }
                  container interfaces-levels {
                    description
                      "Configuration and operational state
                       parameters related to a particular level
                       on an IS-IS enabled interface";
                    list interfaces-level {
                      key "level-number";
                      description
                        "Configuration and operational state
                         parameters related to a particular level
                         on an IS-IS enabled interface";
                      container hello-authentication {
                        description
                          "This container defines ISIS
                           authentication";
                        uses OVERLAY-OCNI-ISIS-HELLO-AUTHENTICATION;
                      }
                      container interfaces-levels-state {
                        description
                          "This container defines interface ISIS
                           level state information";
                        uses OVERLAY-OCNI-ISIS-LEVELS-LEVEL-STATE;
                      }
                      container packet-counters {
                        description
                          "This container defines ISIS interface
                           packet counters";
                        uses OVERLAY-OCNI-ISIS-PACKET-COUNTERS;
                      }
                      container adjacencies {
                        description
                          "List of the local system's IS-IS
                           adjacencies";
                        list adjacency {
                          key "system-id";
                          description
                            "List of the local system's IS-IS
                             adjacencies";
                          leaf system-id {
                            type string;
                            description
                              "Reference to the IS neighbor";
                          }
                          uses OVERLAY-OCNI-ISIS-ADJACENCY;
                        }
                      }
                      container levels-timers {
                        description
                          "This container defines ISIS timers";
                        uses OVERLAY-OCNI-ISIS-LEVEL-TIMERS;
                      }
                      container levels-afi-safis {
                        description
                          "Address-family/Subsequent
                           Address-family list";
                        list levels-afi-safi {
                          description
                            "Address-family/Subsequent
                             Address-family list";
                          container afi-safi-state {
                            description
                              "This container defines AFI-SAFI State
                               information";
                            uses OVERLAY-OCNI-ISIS-AF-STATE;
                          }
                          container afi-safi-segment-routing {
                            description
                              "Configuration and operatioanl state
                               parameters relating to segment
                               routing for an interface within the
                               IGP";
                            container segment-routing-prefix-sids {
                              description
                                "An IGP prefix that should have a
                                 segment routing IGP-Prefix SID
                                 allocated to it";
                              list segment-routing-prefix-sid {
                                key "prefix";
                                description
                                  "An IGP prefix that should have a
                                   segment routing IGP-Prefix SID
                                   allocated to it";
                                leaf prefix {
                                  type string;
                                  description
                                    "Reference to the prefix for which
                                     the IGP-Prefix SID is to be
                                     advertised";
                                }
                                uses OVERLAY-OCNI-ISIS-SEGMENT-ROUTING-PREFIX-SIDS-PREFIX-SID;
                              }
                            }
                          }
                          leaf afi-name {
                            type string;
                            description
                              "Reference to address-family type";
                          }
                          leaf safi-name {
                            type string;
                            description
                              "Reference to subsequent
                               address-family type";
                          }
                        }
                      }
                      leaf level-number {
                        type uint32;
                        description
                          "Reference to ISIS level-number";
                      }
                    }
                  }
                  container circuit-counters {
                    description
                      "This container defines state information
                       for ISIS circuit counters";
                    uses OVERLAY-OCNI-ISIS-CIRCUIT-COUNTERS;
                  }
                  container interfaces-authentication {
                    description
                      "This container defines ISIS
                       authentication";
                    uses OVERLAY-OCNI-ISIS-INTERFACE-AUTHENTICATION;
                  }
                  container interfaces-timers {
                    description
                      "This container describes ISIS interface
                       timers configuration";
                    uses OVERLAY-OCNI-ISIS-INTERFACE-TIMERS;
                  }
                  leaf interface-id {
                    type string;
                    description
                      "Reference to interface-id";
                  }
                }
              }
              container global {
                description
                  "This container defines global ISIS
                   configuration and state information";
                container segment-routing {
                  description
                    "Configuration and operational state
                     relating to segment routing";
                  uses OVERLAY-OCNI-ISIS-SEGMENT-ROUTING;
                }
                container lsp-bit {
                  description
                    "This container defines ISIS LSP
                     Operational Bits";
                  container overload-bit {
                    description
                      "This container defines Overload Bit
                       configuration";
                    container overload-bit-state {
                      description
                        "This container defines state for ISIS
                         Overload Bit";
                      uses OVERLAY-OCNI-ISIS-OVERLOAD-BIT-STATE;
                    }
                    container reset-triggers {
                      description
                        "This list describes ISIS Overload reset
                         trigger reasons";
                      list reset-trigger {
                        key "reset-trigger";
                        description
                          "This list describes ISIS Overload reset
                           trigger reasons";
                        leaf reset-trigger {
                          type string;
                          description
                            "Reference to the reset trigger reason";
                        }
                        uses OVERLAY-OCNI-ISIS-RESET-TRIGGER;
                      }
                    }
                  }
                  container attached-bit {
                    description
                      "This container defines Attached Bit";
                    uses OVERLAY-OCNI-ISIS-ATTACHED-BIT;
                  }
                }
                container nsr {
                  description
                    "This container defines ISIS Non-Stop
                     Routing";
                  uses OVERLAY-OCNI-ISIS-NSR;
                }
                container graceful-restart {
                  description
                    "This container defines ISIS Graceful
                     Restart";
                  uses OVERLAY-OCNI-ISIS-GRACEFUL-RESTART;
                }
                container global-state {
                  description
                    "This container defines state for ISIS
                     global router";
                  uses OVERLAY-OCNI-ISIS-GLOBAL-STATE;
                }
                container inter-level-propagation-policies {
                  description
                    "Policies to propagate prefixes between
                     IS-IS levels";
                  uses OVERLAY-OCNI-ISIS-INTER-LEVEL-PROPAGATION-POLICIES;
                }
                container afi-safis {
                  description
                    "Address-family/Subsequent Address-family
                     list";
                  list afi-safi {
                    description
                      "Address-family/Subsequent Address-family
                       list";
                    leaf afi-name {
                      type string;
                      description
                        "Reference to address-family type";
                    }
                    leaf safi-name {
                      type string;
                      description
                        "Reference to subsequent address-family
                         type";
                    }
                    uses OVERLAY-OCNI-ISIS-AF;
                  }
                }
                container timers {
                  description
                    "This container defines ISIS timers";
                  uses OVERLAY-OCNI-ISIS-TIMERS;
                }
                container transport {
                  description
                    "This container defines ISIS transport";
                  uses OVERLAY-OCNI-ISIS-TRANSPORT;
                }
              }
              container levels {
                description
                  "Configuration and operational state
                   parameters related to a particular level
                   within the IS-IS protocol instance";
                list level {
                  key "level-number";
                  description
                    "Configuration and operational state
                     parameters related to a particular level
                     within the IS-IS protocol instance";
                  container route-preference {
                    description
                      "This container defines Administrative
                       Distance (or preference) assigned to ISIS
                       routes (level1 internal, level2 internal,
                       level1 external, level2 external)";
                    uses OVERLAY-OCNI-ISIS-ROUTE-PREFERENCE;
                  }
                  container levels-state {
                    description
                      "This container defines ISIS level state
                       information";
                    uses OVERLAY-OCNI-ISIS-LEVEL-STATE;
                  }
                  container traffic-engineering {
                    description
                      "This container defines ISIS TE";
                    uses OVERLAY-OCNI-ISIS-TRAFFIC-ENGINEERING;
                  }
                  container levels-authentication {
                    description
                      "This container defines ISIS
                       authentication";
                    uses OVERLAY-OCNI-ISIS-LEVEL-AUTHENTICATION;
                  }
                  container system-level-counters {
                    description
                      "This container defines ISIS system level
                       counters";
                    uses OVERLAY-OCNI-ISIS-SYSTEM-LEVEL-COUNTERS;
                  }
                  container link-state-databases {
                    description
                      "This list describes LSPs in the LSDB";
                    list link-state-database {
                      key "lsp-id";
                      description
                        "This list describes LSPs in the LSDB";
                      container undefined-tlvs {
                        description
                          "List of TLVs that are not defined
                           within the model, or are not recognised
                           by the system";
                        list undefined-tlv {
                          key "type";
                          description
                            "List of TLVs that are not defined
                             within the model, or are not
                             recognised by the system";
                          leaf type {
                            type uint32;
                            description
                              "Reference to the undefined TLV's type";
                          }
                          uses OVERLAY-OCNI-ISIS-UNDEFINED-TLV;
                        }
                      }
                      container link-state-database-state {
                        description
                          "State parameters of Link State PDU";
                        uses OVERLAY-OCNI-ISIS-LSP-STATE;
                      }
                      container tlvses {
                        description
                          "List of TLV types in the LSDB for the
                           specified LSP";
                        list tlvs {
                          key "type";
                          description
                            "List of TLV types in the LSDB for the
                             specified LSP";
                          container area-address {
                            description
                              "This container defines TLV 1";
                            uses OVERLAY-OCNI-ISIS-AREA-ADDRESS;
                          }
                          container authentication {
                            description
                              "This container defines authentication
                               information of the node";
                            uses OVERLAY-OCNI-ISIS-AUTHENTICATION;
                          }
                          container ipv4-interface-addresses {
                            description
                              "This container defines TLV 132";
                            uses OVERLAY-OCNI-ISIS-IPV4-INTERFACE-ADDRESSES;
                          }
                          container router-capabilities {
                            description
                              "This list describes IS Router
                               capabilities";
                            list router-capability {
                              key "instance-number";
                              description
                                "This list describes IS Router
                                 capabilities";
                              container router-capabilities-state {
                                description
                                  "State parameters of TLV 242";
                                uses OVERLAY-OCNI-ISIS-ROUTER-CAPABILITY-STATE;
                              }
                              container undefined-subtlvs {
                                description
                                  "Sub-TLVs that are not defined in
                                   the model or not recognised by
                                   system";
                                list undefined-subtlv {
                                  key "type";
                                  description
                                    "Sub-TLVs that are not defined in
                                     the model or not recognised by
                                     system";
                                  leaf type {
                                    type uint32;
                                    description
                                      "Reference to the type of the
                                       undefined sub-TLV";
                                  }
                                  uses OVERLAY-OCNI-ISIS-UNDEFINED-SUBTLV;
                                }
                              }
                              container subtlvs {
                                description
                                  "List of subTLV types in the LSDB
                                   for the specified TLV";
                                list subtlv {
                                  key "type";
                                  description
                                    "List of subTLV types in the LSDB
                                     for the specified TLV";
                                  container subtlvs-state {
                                    description
                                      "State parameters of IS Router
                                       Capabilities";
                                    uses OVERLAY-OCNI-ISIS-SUBTLV-STATE;
                                  }
                                  container segment-routing-algorithms {
                                    description
                                      "List of the segment routing
                                       algorithsm advertised within the
                                       TLV";
                                    list segment-routing-algorithm {
                                      key "algorithm";
                                      description
                                        "List of the segment routing
                                         algorithsm advertised within the
                                         TLV";
                                      leaf algorithm {
                                        type enumeration {
                                          enum "spf" {
                                            value 0;
                                            description
                                              "Shortest Path First (SPF)
                                               algorithm based on link
                                               metric.  This is the
                                               well-known shortest path
                                               algorithm as computed by the
                                               IS-IS Decision process.
                                               Consistent with the deployed
                                               practice for link- state
                                               protocols, algorithm 0
                                               permits any node to overwrite
                                               the SPF path with a different
                                               path based on local policy.";
                                          }
                                          enum "strict-spf" {
                                            value 1;
                                            description
                                              "Strict Shortest Path First
                                               (SPF) algorithm based on link
                                               metric. The algorithm is
                                               identical to algorithm 0 but
                                               algorithm 1 requires that all
                                               nodes along the path will
                                               honor the SPF routing
                                               decision. Local policy MUST
                                               NOT alter the forwarding
                                               decision computed by
                                               algorithm 1 at the node
                                               claiming to support algorithm
                                               1.";
                                          }
                                        }
                                        description
                                          "Reference to the SR algorithm
                                           that the subTLV describes";
                                      }
                                      uses OVERLAY-OCNI-ISIS-SEGMENT-ROUTING-ALGORITHM;
                                    }
                                  }
                                  container segment-routing-capability {
                                    description
                                      "This container defines SR
                                       Capability sub-TLV 2";
                                    uses OVERLAY-OCNI-ISIS-SEGMENT-ROUTING-CAPABILITY;
                                  }
                                  leaf type {
                                    type string;
                                    description
                                      "Reference to the sub-TLV type";
                                  }
                                }
                              }
                              leaf instance-number {
                                type uint32;
                                description
                                  "Reference to the instance number of
                                   the router capability TLV";
                              }
                            }
                          }
                          container mt-ipv4-reachability {
                            description
                              "This container defines list of IPv4
                               reachability Information in
                               multi-topology environment";
                            container mt-ipv4-reachability-prefixes {
                              description
                                "IPv4 prefixes that are contained
                                 within MT reachability TLV";
                              list mt-ipv4-reachability-prefixe {
                                description
                                  "IPv4 prefixes that are contained
                                   within MT reachability TLV";
                                container mt-ipv4-reachability-prefixes-state {
                                  description
                                    "State parameters of an IPv4
                                     extended prefix";
                                  uses OVERLAY-OCNI-ISIS-PREFIXES-PREFIX-STATE;
                                }
                                container mt-ipv4-reachability-prefixes-undefined-subtlvs {
                                  description
                                    "Sub-TLVs that are not defined in
                                     the model or not recognised by
                                     system";
                                  list mt-ipv4-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-PREFIXES-PREFIX-UNDEFINED-SUBTLVS-UNDEFINED-SUBTLV;
                                  }
                                }
                                container mt-ipv4-reachability-prefixes-subtlvs {
                                  description
                                    "List of subTLV types in the LSDB
                                     for the specified TLV";
                                  list mt-ipv4-reachability-prefixes-subtlv {
                                    key "type";
                                    description
                                      "List of subTLV types in the LSDB
                                       for the specified TLV";
                                    container prefixes-subtlvs-tag64 {
                                      description
                                        "This container defines sub-TLV 2";
                                      uses OVERLAY-OCNI-ISIS-SUBTLVS-SUBTLV-TAG64;
                                    }
                                    container prefixes-subtlvs-tag {
                                      description
                                        "This container defines sub-TLV 1";
                                      uses OVERLAY-OCNI-ISIS-SUBTLVS-SUBTLV-TAG;
                                    }
                                    container mt-ipv4-reachability-prefixes-subtlvs-state {
                                      description
                                        "State parameters for a prefix";
                                      uses OVERLAY-OCNI-ISIS-PREFIX-SUBTLVS-SUBTLV-STATE;
                                    }
                                    container prefixes-subtlvs-ipv4-source-router-id {
                                      description
                                        "This container defines sub-TLV
                                         11";
                                      uses OVERLAY-OCNI-ISIS-SUBTLVS-SUBTLV-IPV4-SOURCE-ROUTER-ID;
                                    }
                                    container prefixes-subtlvs-ipv6-source-router-id {
                                      description
                                        "This container defines sub-TLV
                                         12";
                                      uses OVERLAY-OCNI-ISIS-SUBTLVS-SUBTLV-IPV6-SOURCE-ROUTER-ID;
                                    }
                                    container prefixes-subtlvs-prefix-sids {
                                      description
                                        "Prefix Segment-ID list";
                                      list prefixes-subtlvs-prefix-sid {
                                        key "value";
                                        description
                                          "Prefix Segment-ID list";
                                        leaf value {
                                          type uint32;
                                          description
                                            "Reference to the value of the
                                             prefix SID";
                                        }
                                        uses OVERLAY-OCNI-ISIS-SUBTLV-PREFIX-SIDS-PREFIX-SID;
                                      }
                                    }
                                    container prefixes-subtlvs-flags {
                                      description
                                        "This container defines sub-TLV 4";
                                      uses OVERLAY-OCNI-ISIS-SUBTLVS-SUBTLV-FLAGS;
                                    }
                                    leaf type {
                                      type string;
                                      description
                                        "Reference to the sub-TLV type";
                                    }
                                  }
                                }
                                leaf mt-id {
                                  type uint32;
                                  description
                                    "Reference to the topology ID of
                                     the topology that the prefix is
                                     within";
                                }
                                leaf prefix {
                                  type string;
                                  description
                                    "Reference to the prefix to which
                                     reachability is being advertised";
                                }
                              }
                            }
                          }
                          container mt-isn {
                            description
                              "This container defines list of ISIS
                               multi-topology neighbors";
                            container mt-isn-neighbors {
                              description
                                "This container describes IS
                                 neighbors";
                              list mt-isn-neighbor {
                                description
                                  "This container describes IS
                                   neighbors";
                                container mt-isn-neighbors-subtlvs {
                                  description
                                    "List of subTLV types in the LSDB
                                     for the specified TLV";
                                  list mt-isn-neighbors-subtlv {
                                    key "type";
                                    description
                                      "List of subTLV types in the LSDB
                                       for the specified TLV";
                                    container subtlvs-ipv6-neighbor-address {
                                      description
                                        "This container defines sub-TLV
                                         13";
                                      uses OVERLAY-OCNI-ISIS-SUBTLV-IPV6-NEIGHBOR-ADDRESS;
                                    }
                                    container subtlvs-ipv4-interface-address {
                                      description
                                        "This container defines sub-TLV 6";
                                      uses OVERLAY-OCNI-ISIS-SUBTLV-IPV4-INTERFACE-ADDRESS;
                                    }
                                    container subtlvs-max-reservable-link-bandwidth {
                                      description
                                        "This container defines sub-TLV
                                         10";
                                      uses OVERLAY-OCNI-ISIS-SUBTLV-MAX-RESERVABLE-LINK-BANDWIDTH;
                                    }
                                    container subtlvs-max-link-bandwidth {
                                      description
                                        "This container defines sub-TLV 9";
                                      uses OVERLAY-OCNI-ISIS-SUBTLV-MAX-LINK-BANDWIDTH;
                                    }
                                    container subtlvs-adjacency-sids {
                                      description
                                        "Adjacency Segment-IDs List";
                                      list subtlvs-adjacency-sid {
                                        key "value";
                                        description
                                          "Adjacency Segment-IDs List";
                                        leaf value {
                                          type uint32;
                                          description
                                            "Reference to the value of the
                                             Adjacency-SID";
                                        }
                                        uses OVERLAY-OCNI-ISIS-ADJACENCY-SIDS-ADJACENCY-SID;
                                      }
                                    }
                                    container subtlvs-bandwidth-constraints {
                                      description
                                        "List of the Bandwidth
                                         Constraints sub-TLV instances
                                         present in the TLV";
                                      list subtlvs-bandwidth-constraint {
                                        key "model-id";
                                        description
                                          "List of the Bandwidth
                                           Constraints sub-TLV instances
                                           present in the TLV";
                                        container bandwidth-constraints-constraints {
                                          description
                                            "List of the constraints within
                                             the Bandwidth Constraints
                                             sub-TLV";
                                          list bandwidth-constraints-constraint {
                                            key "constraint-id";
                                            description
                                              "List of the constraints
                                               within the Bandwidth
                                               Constraints sub-TLV";
                                            leaf constraint-id {
                                              type uint32;
                                              description
                                                "Reference to the unique ID
                                                 for the BCN level";
                                            }
                                            uses OVERLAY-OCNI-ISIS-CONSTRAINTS-CONSTRAINT;
                                          }
                                        }
                                        container subtlvs-bandwidth-constraints-state {
                                          description
                                            "State parameters of IS
                                             Extended Reachability sub-TLV
                                             22";
                                          uses OVERLAY-OCNI-ISIS-BANDWIDTH-CONSTRAINTS-BANDWIDTH-CONSTRAINT-STATE;
                                        }
                                        leaf model-id {
                                          type uint32;
                                          description
                                            "Reference to the model ID
                                             associated with the instance
                                             of the Bandwidth Constraints
                                             sub-TLV";
                                        }
                                      }
                                    }
                                    container subtlvs-unreserved-bandwidths {
                                      description
                                        "Setup priority (0 through 7) for
                                         unreserved bandwidth";
                                      list subtlvs-unreserved-bandwidth {
                                        key "priority";
                                        description
                                          "Setup priority (0 through 7)
                                           for unreserved bandwidth";
                                        leaf priority {
                                          type uint32;
                                          description
                                            "Reference to the setup
                                             priority to which the
                                             unreserved bandwidth
                                             corresponds";
                                        }
                                        uses OVERLAY-OCNI-ISIS-UNRESERVED-BANDWIDTH-SETUP-PRIORITY;
                                      }
                                    }
                                    container subtlvs-ipv4-neighbor-address {
                                      description
                                        "This container defines sub-TLV 8";
                                      uses OVERLAY-OCNI-ISIS-SUBTLV-IPV4-NEIGHBOR-ADDRESS;
                                    }
                                    container subtlvs-te-default-metric {
                                      description
                                        "This container defines sub-TLV
                                         18";
                                      uses OVERLAY-OCNI-ISIS-SUBTLV-TE-DEFAULT-METRIC;
                                    }
                                    container subtlvs-ipv6-interface-address {
                                      description
                                        "This container defines sub-TLV
                                         12";
                                      uses OVERLAY-OCNI-ISIS-SUBTLV-IPV6-INTERFACE-ADDRESS;
                                    }
                                    container subtlvs-admin-group {
                                      description
                                        "This container defines sub-TLV 3";
                                      uses OVERLAY-OCNI-ISIS-SUBTLV-ADMIN-GROUP;
                                    }
                                    container subtlvs-lan-adjacency-sids {
                                      description
                                        "Adjacency Segment-IDs List";
                                      list subtlvs-lan-adjacency-sid {
                                        key "value";
                                        description
                                          "Adjacency Segment-IDs List";
                                        leaf value {
                                          type uint32;
                                          description
                                            "Reference to the value of the
                                             LAN Adjacency-SID";
                                        }
                                        uses OVERLAY-OCNI-ISIS-LAN-ADJACENCY-SIDS-LAN-ADJACENCY-SID;
                                      }
                                    }
                                    container subtlvs-extended-admin-group {
                                      description
                                        "This container defines sub-TLV
                                         14";
                                      uses OVERLAY-OCNI-ISIS-SUBTLV-EXTENDED-ADMIN-GROUP;
                                    }
                                    leaf type {
                                      type string;
                                      description
                                        "Reference to the sub-TLV type";
                                    }
                                  }
                                }
                                container mt-isn-neighbors-state {
                                  description
                                    "State parameters of MT neighbor";
                                  uses OVERLAY-OCNI-ISIS-NEIGHBOR-STATE;
                                }
                                container mt-isn-neighbors-undefined-subtlvs {
                                  description
                                    "Sub-TLVs that are not defined in
                                     the model or not recognised by
                                     system";
                                  list mt-isn-neighbors-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-NEIGHBOR-UNDEFINED-SUBTLVS-UNDEFINED-SUBTLV;
                                  }
                                }
                                leaf mt-id {
                                  type uint32;
                                  description
                                    "       Reference to the topology
                                     that the neighbor is within";
                                }
                                leaf system-id {
                                  type string;
                                  description
                                    "Reference to the System ID of the
                                     neighbor";
                                }
                              }
                            }
                          }
                          container ipv6-srlgs {
                            description
                              "Instance of the IPv6 SRLG TLV";
                            list ipv6-srlg {
                              key "instance-number";
                              description
                                "Instance of the IPv6 SRLG TLV";
                              leaf instance-number {
                                type uint32;
                                description
                                  "Reference to the instance number of
                                   the IPv6 Shared Risk Link Group
                                   (SRLG) TLV";
                              }
                              uses OVERLAY-OCNI-ISIS-IPV6-SRLG;
                            }
                          }
                          container tlvs-state {
                            description
                              "Operational state parameters relating
                               to the specified LSP";
                            uses OVERLAY-OCNI-ISIS-TLV-STATE;
                          }
                          container purge-oi {
                            description
                              "This container defines ISIS purge TLV";
                            uses OVERLAY-OCNI-ISIS-PURGE-OI;
                          }
                          container host-name {
                            description
                              "This container defines TLV 137";
                            uses OVERLAY-OCNI-ISIS-HOSTNAME;
                          }
                          container ipv6-reachability {
                            description
                              "This container defines list of IPv6
                               reachability information";
                            container ipv6-reachability-prefixes {
                              description
                                "This list defines IPv6 extended
                                 prefix attributes";
                              list ipv6-reachability-prefixe {
                                key "prefix";
                                description
                                  "This list defines IPv6 extended
                                   prefix attributes";
                                container ipv6-reachability-prefixes-state {
                                  description
                                    "State parameters of IPv6 prefix
                                     attributes";
                                  uses OVERLAY-OCNI-ISIS-PREFIXES-STATE;
                                }
                                container ipv6-reachability-prefixes-subtlvs {
                                  description
                                    "List of subTLV types in the LSDB
                                     for the specified TLV";
                                  list ipv6-reachability-prefixes-subtlv {
                                    key "type";
                                    description
                                      "List of subTLV types in the LSDB
                                       for the specified TLV";
                                    container subtlvs-tag {
                                      description
                                        "This container defines sub-TLV 1";
                                      uses OVERLAY-OCNI-ISIS-SUBTLV-TAG;
                                    }
                                    container subtlvs-tag64 {
                                      description
                                        "This container defines sub-TLV 2";
                                      uses OVERLAY-OCNI-ISIS-SUBTLV-TAG64;
                                    }
                                    container subtlvs-prefix-sids {
                                      description
                                        "Prefix Segment-ID list";
                                      list subtlvs-prefix-sid {
                                        key "value";
                                        description
                                          "Prefix Segment-ID list";
                                        leaf value {
                                          type uint32;
                                          description
                                            "Reference to the value of the
                                             prefix SID";
                                        }
                                        uses OVERLAY-OCNI-ISIS-PREFIX-SIDS-PREFIX-SID;
                                      }
                                    }
                                    container subtlvs-ipv4-source-router-id {
                                      description
                                        "This container defines sub-TLV
                                         11";
                                      uses OVERLAY-OCNI-ISIS-SUBTLV-IPV4-SOURCE-ROUTER-ID;
                                    }
                                    container ipv6-reachability-prefixes-subtlvs-state {
                                      description
                                        "State parameters for a prefix";
                                      uses OVERLAY-OCNI-ISIS-PREFIXES-SUBTLVS-SUBTLV-STATE;
                                    }
                                    container subtlvs-ipv6-source-router-id {
                                      description
                                        "This container defines sub-TLV
                                         12";
                                      uses OVERLAY-OCNI-ISIS-SUBTLV-IPV6-SOURCE-ROUTER-ID;
                                    }
                                    container subtlvs-flags {
                                      description
                                        "This container defines sub-TLV 4";
                                      uses OVERLAY-OCNI-ISIS-SUBTLV-FLAGS;
                                    }
                                    leaf type {
                                      type string;
                                      description
                                        "Reference to the sub-TLV type";
                                    }
                                  }
                                }
                                container ipv6-reachability-prefixes-undefined-subtlvs {
                                  description
                                    "Sub-TLVs that are not defined in
                                     the model or not recognised by
                                     system";
                                  list ipv6-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-PREFIXES-UNDEFINED-SUBTLVS-UNDEFINED-SUBTLV;
                                  }
                                }
                                leaf prefix {
                                  type string;
                                  description
                                    "Reference to the IPv6 prefix that
                                     the TLV corresponds to";
                                }
                              }
                            }
                          }
                          container ipv6-te-router-id {
                            description
                              "This container defines TLV 140";
                            uses OVERLAY-OCNI-ISIS-IPV6-TE-ROUTER-ID;
                          }
                          container ipv4-internal-reachability {
                            description
                              "This container defines list of IPv4
                               internal reachability information";
                            container prefixes {
                              description
                                "IPv4 prefixes and internal
                                 reachability attributes";
                              list prefixe {
                                key "prefix";
                                description
                                  "IPv4 prefixes and internal
                                   reachability attributes";
                                leaf prefix {
                                  type string;
                                  description
                                    "Reference to the IPv4 prefix";
                                }
                                uses OVERLAY-OCNI-ISIS-PREFIXES;
                              }
                            }
                          }
                          container ipv6-interface-addresses {
                            description
                              "This container defines TLV 232";
                            uses OVERLAY-OCNI-ISIS-IPV6-INTERFACE-ADDRESSES;
                          }
                          container extended-is-reachability {
                            description
                              "This container defines list of ISIS
                               extended reachability neighbors";
                            container extended-is-reachability-neighbors {
                              description
                                "This list describes ISIS extended
                                 neigbors and reachability attributes";
                              list extended-is-reachability-neighbor {
                                key "system-id";
                                description
                                  "This list describes ISIS extended
                                   neigbors and reachability
                                   attributes";
                                container neighbors-subtlvs {
                                  description
                                    "List of subTLV types in the LSDB
                                     for the specified TLV";
                                  list neighbors-subtlv {
                                    key "type";
                                    description
                                      "List of subTLV types in the LSDB
                                       for the specified TLV";
                                    container max-link-bandwidth {
                                      description
                                        "This container defines sub-TLV 9";
                                      uses OVERLAY-OCNI-ISIS-MAX-LINK-BANDWIDTH;
                                    }
                                    container ipv6-neighbor-address {
                                      description
                                        "This container defines sub-TLV
                                         13";
                                      uses OVERLAY-OCNI-ISIS-IPV6-NEIGHBOR-ADDRESS;
                                    }
                                    container ipv6-interface-address {
                                      description
                                        "This container defines sub-TLV
                                         12";
                                      uses OVERLAY-OCNI-ISIS-IPV6-INTERFACE-ADDRESS;
                                    }
                                    container lan-adjacency-sids {
                                      description
                                        "Adjacency Segment-IDs List";
                                      list lan-adjacency-sid {
                                        key "value";
                                        description
                                          "Adjacency Segment-IDs List";
                                        leaf value {
                                          type uint32;
                                          description
                                            "Reference to the value of the
                                             LAN Adjacency-SID";
                                        }
                                        uses OVERLAY-OCNI-ISIS-LAN-ADJACENCY-SID;
                                      }
                                    }
                                    container adjacency-sids {
                                      description
                                        "Adjacency Segment-IDs List";
                                      list adjacency-sid {
                                        key "value";
                                        description
                                          "Adjacency Segment-IDs List";
                                        leaf value {
                                          type uint32;
                                          description
                                            "Reference to the value of the
                                             Adjacency-SID";
                                        }
                                        uses OVERLAY-OCNI-ISIS-ADJACENCY-SID;
                                      }
                                    }
                                    container te-default-metric {
                                      description
                                        "This container defines sub-TLV
                                         18";
                                      uses OVERLAY-OCNI-ISIS-TE-DEFAULT-METRIC;
                                    }
                                    container admin-group {
                                      description
                                        "This container defines sub-TLV 3";
                                      uses OVERLAY-OCNI-ISIS-ADMIN-GROUP;
                                    }
                                    container max-reservable-link-bandwidth {
                                      description
                                        "This container defines sub-TLV
                                         10";
                                      uses OVERLAY-OCNI-ISIS-MAX-RESERVABLE-LINK-BANDWIDTH;
                                    }
                                    container extended-admin-group {
                                      description
                                        "This container defines sub-TLV
                                         14";
                                      uses OVERLAY-OCNI-ISIS-EXTENDED-ADMIN-GROUP;
                                    }
                                    container unreserved-bandwidths {
                                      description
                                        "Setup priority (0 through 7) for
                                         unreserved bandwidth";
                                      list unreserved-bandwidth {
                                        key "priority";
                                        description
                                          "Setup priority (0 through 7)
                                           for unreserved bandwidth";
                                        leaf priority {
                                          type uint32;
                                          description
                                            "Reference to the setup
                                             priority to which the
                                             unreserved bandwidth
                                             corresponds";
                                        }
                                        uses OVERLAY-OCNI-ISIS-SETUP-PRIORITY;
                                      }
                                    }
                                    container ipv4-interface-address {
                                      description
                                        "This container defines sub-TLV 6";
                                      uses OVERLAY-OCNI-ISIS-IPV4-INTERFACE-ADDRESS;
                                    }
                                    container ipv4-neighbor-address {
                                      description
                                        "This container defines sub-TLV 8";
                                      uses OVERLAY-OCNI-ISIS-IPV4-NEIGHBOR-ADDRESS;
                                    }
                                    container bandwidth-constraints {
                                      description
                                        "List of the Bandwidth
                                         Constraints sub-TLV instances
                                         present in the TLV";
                                      list bandwidth-constraint {
                                        key "model-id";
                                        description
                                          "List of the Bandwidth
                                           Constraints sub-TLV instances
                                           present in the TLV";
                                        container constraints {
                                          description
                                            "List of the constraints within
                                             the Bandwidth Constraints
                                             sub-TLV";
                                          list constraint {
                                            key "constraint-id";
                                            description
                                              "List of the constraints
                                               within the Bandwidth
                                               Constraints sub-TLV";
                                            leaf constraint-id {
                                              type uint32;
                                              description
                                                "Reference to the unique ID
                                                 for the BCN level";
                                            }
                                            uses OVERLAY-OCNI-ISIS-CONSTRAINT;
                                          }
                                        }
                                        container bandwidth-constraints-state {
                                          description
                                            "State parameters of IS
                                             Extended Reachability sub-TLV
                                             22";
                                          uses OVERLAY-OCNI-ISIS-BANDWIDTH-CONSTRAINT-STATE;
                                        }
                                        leaf model-id {
                                          type uint32;
                                          description
                                            "Reference to the model ID
                                             associated with the instance
                                             of the Bandwidth Constraints
                                             sub-TLV";
                                        }
                                      }
                                    }
                                    leaf type {
                                      type string;
                                      description
                                        "Reference to the sub-TLV type";
                                    }
                                  }
                                }
                                container neighbors-undefined-subtlvs {
                                  description
                                    "Sub-TLVs that are not defined in
                                     the model or not recognised by
                                     system";
                                  list neighbors-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-UNDEFINED-SUBTLVS-UNDEFINED-SUBTLV;
                                  }
                                }
                                container neighbors-state {
                                  description
                                    "State parameters of extended
                                     neighbor";
                                  uses OVERLAY-OCNI-ISIS-NEIGHBORS-STATE;
                                }
                                leaf system-id {
                                  type string;
                                  description
                                    "Reference to the neighboring
                                     system's system ID";
                                }
                              }
                            }
                          }
                          container instance-ids {
                            description
                              "A list of instance IDs received
                               within TLV 7 within an IS-IS LSP";
                            list instance-id {
                              key "instance-id";
                              description
                                "A list of instance IDs received
                                 within TLV 7 within an IS-IS LSP";
                              leaf instance-id {
                                type uint32;
                                description
                                  "Reference to the unique instance ID";
                              }
                              uses OVERLAY-OCNI-ISIS-INSTANCE-ID;
                            }
                          }
                          container ipv4-srlgs {
                            description
                              "Instance of the IPv4 SRLG TLV";
                            list ipv4-srlg {
                              key "instance-number";
                              description
                                "Instance of the IPv4 SRLG TLV";
                              leaf instance-number {
                                type uint32;
                                description
                                  "Reference to the instance number of
                                   TLV 138";
                              }
                              uses OVERLAY-OCNI-ISIS-IPV4-SRLG;
                            }
                          }
                          container is-reachability {
                            description
                              "This container describes list of ISIS
                               neighbors and attributes";
                            container neighbors {
                              description
                                "IS reachability neighbor attributes";
                              list neighbor {
                                key "system-id";
                                description
                                  "IS reachability neighbor attributes";
                                leaf system-id {
                                  type string;
                                  description
                                    "Reference to the system ID of the
                                     neighbor";
                                }
                                uses OVERLAY-OCNI-ISIS-NEIGHBORS;
                              }
                            }
                          }
                          container ipv4-te-router-id {
                            description
                              "This container defines TLV 134";
                            uses OVERLAY-OCNI-ISIS-IPV4-TE-ROUTER-ID;
                          }
                          container nlpid {
                            description
                              "This container defines TLV 129";
                            uses OVERLAY-OCNI-ISIS-NLPID;
                          }
                          container extended-ipv4-reachability {
                            description
                              "This container defines list of IPv4
                               extended reachability information";
                            container extended-ipv4-reachability-prefixes {
                              description
                                "This list describes IPv4 extended
                                 prefixes and attributes";
                              list extended-ipv4-reachability-prefixe {
                                key "prefix";
                                description
                                  "This list describes IPv4 extended
                                   prefixes and attributes";
                                container prefixes-state {
                                  description
                                    "State parameters of an IPv4
                                     extended prefix";
                                  uses OVERLAY-OCNI-ISIS-PREFIX-STATE;
                                }
                                container prefixes-subtlvs {
                                  description
                                    "List of subTLV types in the LSDB
                                     for the specified TLV";
                                  list prefixes-subtlv {
                                    key "type";
                                    description
                                      "List of subTLV types in the LSDB
                                       for the specified TLV";
                                    container tag {
                                      description
                                        "This container defines sub-TLV 1";
                                      uses OVERLAY-OCNI-ISIS-TAG;
                                    }
                                    container ipv4-source-router-id {
                                      description
                                        "This container defines sub-TLV
                                         11";
                                      uses OVERLAY-OCNI-ISIS-IPV4-SOURCE-ROUTER-ID;
                                    }
                                    container ipv6-source-router-id {
                                      description
                                        "This container defines sub-TLV
                                         12";
                                      uses OVERLAY-OCNI-ISIS-IPV6-SOURCE-ROUTER-ID;
                                    }
                                    container prefixes-subtlvs-state {
                                      description
                                        "State parameters for a prefix";
                                      uses OVERLAY-OCNI-ISIS-SUBTLVS-SUBTLV-STATE;
                                    }
                                    container flags {
                                      description
                                        "This container defines sub-TLV 4";
                                      uses OVERLAY-OCNI-ISIS-FLAGS;
                                    }
                                    container tag64 {
                                      description
                                        "This container defines sub-TLV 2";
                                      uses OVERLAY-OCNI-ISIS-TAG64;
                                    }
                                    container prefix-sids {
                                      description
                                        "Prefix Segment-ID list";
                                      list prefix-sid {
                                        key "value";
                                        description
                                          "Prefix Segment-ID list";
                                        leaf value {
                                          type uint32;
                                          description
                                            "Reference to the value of the
                                             prefix SID";
                                        }
                                        uses OVERLAY-OCNI-ISIS-PREFIX-SID;
                                      }
                                    }
                                    leaf type {
                                      type string;
                                      description
                                        "Reference to the sub-TLV type";
                                    }
                                  }
                                }
                                container prefixes-undefined-subtlvs {
                                  description
                                    "Sub-TLVs that are not defined in
                                     the model or not recognised by
                                     system";
                                  list prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-PREFIX-UNDEFINED-SUBTLVS-UNDEFINED-SUBTLV;
                                  }
                                }
                                leaf prefix {
                                  type string;
                                  description
                                    "Reference to the IPv4 prefix that
                                     the TLV describes the attributes
                                     of";
                                }
                              }
                            }
                          }
                          container multi-topology {
                            description
                              "This container defines the topology
                               supported";
                            container topologies {
                              description
                                "This list describes a topology";
                              list topology {
                                key "mt-id";
                                description
                                  "This list describes a topology";
                                leaf mt-id {
                                  type uint32;
                                  description
                                    "Reference to the multi-topology ID
                                     being described by the list entry";
                                }
                                uses OVERLAY-OCNI-ISIS-TOPOLOGY;
                              }
                            }
                          }
                          container ipv4-external-reachability {
                            description
                              "This container defines list of IPv4
                               external reachability information";
                            container ipv4-external-reachability-prefixes {
                              description
                                "IPv4 external prefixes and
                                 reachability attributes";
                              list ipv4-external-reachability-prefixe {
                                key "prefix";
                                description
                                  "IPv4 external prefixes and
                                   reachability attributes";
                                leaf prefix {
                                  type string;
                                  description
                                    "Reference to the IPv4 prefix";
                                }
                                uses OVERLAY-OCNI-ISIS-PREFIXES-PREFIXES;
                              }
                            }
                          }
                          container mt-ipv6-reachability {
                            description
                              "This container defines list of IPv6
                               reachability information in multi -
                               topology environment";
                            container mt-ipv6-reachability-prefixes {
                              description
                                "List of IPv6 prefixes contained
                                 within MT reachability TLV";
                              list mt-ipv6-reachability-prefixe {
                                description
                                  "List of IPv6 prefixes contained
                                   within MT reachability TLV";
                                container mt-ipv6-reachability-prefixes-state {
                                  description
                                    "State parameters relating an IPv6
                                     prefix attribute";
                                  uses OVERLAY-OCNI-ISIS-MT-IPV6-REACHABILITY-PREFIXES-PREFIX-STATE;
                                }
                                container mt-ipv6-reachability-prefixes-subtlvs {
                                  description
                                    "List of subTLV types in the LSDB
                                     for the specified TLV";
                                  list mt-ipv6-reachability-prefixes-subtlv {
                                    key "type";
                                    description
                                      "List of subTLV types in the LSDB
                                       for the specified TLV";
                                    container mt-ipv6-reachability-prefixes-subtlvs-prefix-sids {
                                      description
                                        "Prefix Segment-ID list";
                                      list mt-ipv6-reachability-prefixes-subtlvs-prefix-sid {
                                        key "value";
                                        description
                                          "Prefix Segment-ID list";
                                        leaf value {
                                          type uint32;
                                          description
                                            "Reference to the value of the
                                             prefix SID";
                                        }
                                        uses OVERLAY-OCNI-ISIS-SUBTLVS-SUBTLV-PREFIX-SIDS-PREFIX-SID;
                                      }
                                    }
                                    container mt-ipv6-reachability-prefixes-subtlvs-flags {
                                      description
                                        "This container defines sub-TLV 4";
                                      uses OVERLAY-OCNI-ISIS-PREFIX-SUBTLVS-SUBTLV-FLAGS;
                                    }
                                    container mt-ipv6-reachability-prefixes-subtlvs-ipv4-source-router-id {
                                      description
                                        "This container defines sub-TLV
                                         11";
                                      uses OVERLAY-OCNI-ISIS-PREFIX-SUBTLVS-SUBTLV-IPV4-SOURCE-ROUTER-ID;
                                    }
                                    container mt-ipv6-reachability-prefixes-subtlvs-tag64 {
                                      description
                                        "This container defines sub-TLV 2";
                                      uses OVERLAY-OCNI-ISIS-PREFIX-SUBTLVS-SUBTLV-TAG64;
                                    }
                                    container mt-ipv6-reachability-prefixes-subtlvs-ipv6-source-router-id {
                                      description
                                        "This container defines sub-TLV
                                         12";
                                      uses OVERLAY-OCNI-ISIS-PREFIX-SUBTLVS-SUBTLV-IPV6-SOURCE-ROUTER-ID;
                                    }
                                    container mt-ipv6-reachability-prefixes-subtlvs-tag {
                                      description
                                        "This container defines sub-TLV 1";
                                      uses OVERLAY-OCNI-ISIS-PREFIX-SUBTLVS-SUBTLV-TAG;
                                    }
                                    container mt-ipv6-reachability-prefixes-subtlvs-state {
                                      description
                                        "State parameters for a prefix";
                                      uses OVERLAY-OCNI-ISIS-PREFIXES-PREFIX-SUBTLVS-SUBTLV-STATE;
                                    }
                                    leaf type {
                                      type string;
                                      description
                                        "Reference to the sub-TLV type";
                                    }
                                  }
                                }
                                container mt-ipv6-reachability-prefixes-undefined-subtlvs {
                                  description
                                    "Sub-TLVs that are not defined in
                                     the model or not recognised by
                                     system";
                                  list mt-ipv6-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-MT-IPV6-REACHABILITY-PREFIXES-PREFIX-UNDEFINED-SUBTLVS-UNDEFINED-SUBTLV;
                                  }
                                }
                                leaf prefix {
                                  type string;
                                  description
                                    "Reference to the IPv6 prefix
                                     described by the TLV";
                                }
                                leaf mt-id {
                                  type uint32;
                                  description
                                    "Reference to the multi-topology ID";
                                }
                              }
                            }
                          }
                          leaf type {
                            type string;
                            description
                              "Reference to the TLV's type";
                          }
                        }
                      }
                      leaf lsp-id {
                        type string;
                        description
                          "A reference to the Link State PDU ID";
                      }
                    }
                  }
                  leaf level-number {
                    type uint32;
                    description
                      "Reference to ISIS level-number";
                  }
                }
              }
            }
            leaf identifier {
              type string;
              description
                "The protocol name for the routing or
                 forwarding protocol to be instantiated";
            }
            leaf name {
              type string;
              description
                "An operator-assigned identifier for the
                 routing or forwarding protocol";
            }
          }
        }
        container state {
          description
            "Operational state parameters relating to a
             network instance";
          uses OVERLAY-OCNI-ISIS-STATE;
        }
        leaf name {
          type string;
          description
            "A unique name identifying the network instance";
        }
      }
    }
  }
  container isis {
    config false;
    description
      "isis";
    container instances {
      description
        "Per-instance operational data";
      list instance {
        key "instance-name";
        description
          "IS-IS instance";
        container neighbors {
          description
            "Neighbor table";
          list neighbor {
            description
              "A single neighbor router";
            leaf system-id {
              type xr:Osi-system-id;
              description
                "System ID";
            }
            leaf interface-name {
              type xr:Interface-name;
              description
                "Interface name";
            }
            uses ISIS-SH-NBR;
          }
        }
        container host-names {
          description
            "Hostname table";
          list host-name {
            key "system-id";
            description
              "Hostname table entry";
            leaf system-id {
              type xr:Osi-system-id;
              description
                "System ID";
            }
            uses ISIS-SH-HOST;
          }
        }
        container statistics-global {
          description
            "Per-instance statistics";
          uses ISIS-SH-TRAFFIC-GLOBAL;
        }
        container levels {
          description
            "Level table";
          list level {
            key "level";
            description
              "Per-level operational data";
            container adjacency-log {
              description
                "Log of adjacency changes within a single
                 level";
              uses ISIS-SH-ADJ-LOG-STRUC;
            }
            container lsp-table-summary {
              description
                "Summary information for one level's LSP
                 database";
              uses ISIS-SH-LSP-DB-SUMMARY;
            }
            container adjacencies {
              description
                "Adjacency table";
              list adjacency {
                description
                  "A single IS-IS adjacency";
                leaf system-id {
                  type xr:Osi-system-id;
                  description
                    "System ID";
                }
                leaf interface-name {
                  type xr:Interface-name;
                  description
                    "Interface name";
                }
                uses ISIS-SH-ADJ;
              }
            }
            container detailed-lsps {
              description
                "Detailed LSP table. Use to retrieve LSPs
                 with TLV content.";
              list detailed-lsp {
                key "lsp-id";
                description
                  "An IS-IS LSP with detailed TLV data
                   included";
                leaf lsp-id {
                  type xr:Isis-lsp-id;
                  description
                    "LSP ID";
                }
                uses ISIS-SH-LSP;
              }
            }
            container lsps {
              description
                "LSP table";
              list lsp {
                key "lsp-id";
                description
                  "An IS-IS LSP (header information only)";
                leaf lsp-id {
                  type xr:Isis-lsp-id;
                  description
                    "LSP ID";
                }
                uses ISIS-SH-LSP;
              }
            }
            container lsp-log {
              description
                "LSP-log for a single level";
              uses ISIS-SH-LSP-LOG-STRUC;
            }
            container database-log {
              description
                "Database-log for a single level";
              uses ISIS-SH-LSP-DB-LOG-STRUC;
            }
            leaf level {
              type dt1:Isis-internal-level;
              description
                "Level";
            }
          }
        }
        container topologies {
          description
            "Topology table";
          list topology {
            description
              "Per-topology data";
            container ipv6-flex-route-tables {
              description
                "IPv6 Flex-Algo local route tables";
              list ipv6-flex-route-table {
                key "flex-alg";
                description
                  "IPv6 Flex-Algo local route table";
                leaf flex-alg {
                  type uint32;
                  description
                    "Flex Algo";
                }
                list ipv6-flex-route {
                  description
                    "An IPv6 route known to IS-IS";
                  leaf prefix {
                    type inet:ipv6-address-no-zone;
                    description
                      "Prefix";
                  }
                  leaf prefix-length {
                    type dt1:Isis-ipv6-prefix-length;
                    description
                      "Prefix Length";
                  }
                  uses ISIS-SH-IPV6-ROUTE;
                }
              }
            }
            container frr-summary {
              description
                "FRR summary information for a particular
                 IS-IS topology";
              uses ISIS-SH-FRR-SUMMARY;
            }
            container srv6-locators {
              description
                "SRv6 Locator Table";
              list srv6-locator {
                description
                  "An SRv6 Locator";
                leaf prefix {
                  type inet:ipv6-address-no-zone;
                  description
                    "Prefix";
                }
                leaf prefix-length {
                  type dt1:Isis-ipv6-prefix-length;
                  description
                    "Prefix Length";
                }
                uses ISIS-SH-SRV6-LOCATOR;
              }
            }
            container topology-levels {
              description
                "Per-topology level table";
              list topology-level {
                key "level";
                description
                  "Per-level topology operational data";
                container te-advertisements {
                  description
                    "TE advertisements for a single level and
                     topology. Only available within the IPv4
                     Unicast topology.";
                  uses ISIS-SH-TE-ADV;
                }
                container te-adjacency-log {
                  description
                    "TE adjacency-log for a single level and
                     topology. Only available within the IPv4
                     Unicast topology.";
                  uses ISIS-SH-TE-LOG-STRUC;
                }
                container spf-log {
                  description
                    "Log of route calculations for a single
                     level and topology";
                  uses ISIS-SH-SPF-LOG-STRUC;
                }
                container te-tunnels {
                  description
                    "TE tunnels table. Only available within
                     the IPv4 Unicast topology.";
                  list te-tunnel {
                    description
                      "A single TE tunnel advertized by IS-IS";
                    leaf system-id {
                      type xr:Osi-system-id;
                      description
                        "System ID";
                    }
                    leaf interface-name {
                      type xr:Interface-name;
                      description
                        "Interface name";
                    }
                    uses ISIS-SH-TE-TUNNEL;
                  }
                }
                container ipv4-link-topologies {
                  description
                    "IPv4 IS Topology table";
                  list ipv4-link-topology {
                    key "system-id";
                    description
                      "An IS in an IPv4 Link Topology";
                    leaf system-id {
                      type xr:Osi-system-id;
                      description
                        "System ID";
                    }
                    uses ISIS-SH-IPV4-TOPO-ENTRY;
                  }
                }
                container topology-summary {
                  description
                    "Summary information for a particular IS
                     Topology";
                  uses ISIS-SH-TOPO-SUMMARY;
                }
                container ipv6-link-topologies {
                  description
                    "IPv6 IS Topology table";
                  list ipv6-link-topology {
                    key "system-id";
                    description
                      "An IS in an IPv6 Link Topology";
                    leaf system-id {
                      type xr:Osi-system-id;
                      description
                        "System ID";
                    }
                    uses ISIS-SH-IPV6-TOPO-ENTRY;
                  }
                }
                leaf level {
                  type dt1:Isis-internal-level;
                  description
                    "Level";
                }
              }
            }
            container ipv6-routes {
              description
                "IPv6 local route";
              list ipv6-route {
                description
                  "An IPv6 route known to IS-IS";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
            container ipv6frr-backups {
              description
                "IPv6 FRR table";
              list ipv6frr-backup {
                description
                  "FRR backup for an IPv6 network";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
            container ipv4frr-backups {
              description
                "IPv4 FRR table";
              list ipv4frr-backup {
                description
                  "FRR backup for an IPv4 network";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
            container ipv4-flex-route-tables {
              description
                "IPv4 Flex-Algo local route tables";
              list ipv4-flex-route-table {
                key "flex-alg";
                description
                  "IPv4 Flex-Algo local route table";
                leaf flex-alg {
                  type uint32;
                  description
                    "Flex Algo";
                }
                list ipv4-flex-route {
                  description
                    "An IPv4 route known to IS-IS";
                  leaf prefix {
                    type inet:ipv4-address-no-zone;
                    description
                      "Prefix";
                  }
                  leaf prefix-length {
                    type dt1:Isis-ipv4-prefix-length;
                    description
                      "Prefix Length";
                  }
                  uses ISIS-SH-IPV4-ROUTE;
                }
              }
            }
            container ipv4-routes {
              description
                "IPv4 local route table";
              list ipv4-route {
                description
                  "An IPv4 route known to IS-IS";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
            leaf af-name {
              type dt1:Isis-address-family;
              description
                "Address family";
            }
            leaf saf-name {
              type dt1:Isis-sub-address-family;
              description
                "Sub address family";
            }
            leaf topology-name {
              type dt1:Isis-topology-name;
              description
                "Topology Name";
            }
          }
        }
        container nsr-status {
          description
            "NSR Status information";
          uses ISIS-SH-NSR-STATUS-GLOBAL;
        }
        container interfaces {
          description
            "Interface table";
          list interface {
            key "interface-name";
            description
              "Information about one IS-IS interface";
            leaf interface-name {
              type xr:Interface-name;
              description
                "Interface name";
            }
            uses ISIS-SH-IF;
          }
        }
        container checkpoint-adjacencies {
          description
            "Checkpointed adjacency table";
          list checkpoint-adjacency {
            description
              "A checkpointed IS-IS adjacency";
            leaf level {
              type dt1:Isis-internal-level;
              description
                "Level";
            }
            leaf system-id {
              type xr:Osi-system-id;
              description
                "System ID";
            }
            leaf interface-name {
              type xr:Interface-name;
              description
                "Interface name";
            }
            uses ISIS-SH-CHKPT-ADJ;
          }
        }
        container flex-algos {
          description
            "Flex-Algo Table";
          list flex-algo {
            key "flex-alg";
            description
              "Flex-Algo Definition Data";
            leaf flex-alg {
              type uint32;
              description
                "Flex Algo";
            }
            uses ISIS-SH-FLEX-ALGO;
          }
        }
        container srms {
          description
            "Segment Routing Mapping Server operational
             data";
          container policy {
            description
              "Policy operational data";
            container policy-ipv4 {
              description
                "IPv4 policy operational data";
              container policy-ipv4-active {
                description
                  "IPv4 active policy operational data";
                uses POLICY-MI;
              }
              container policy-ipv4-backup {
                description
                  "IPv4 backup policy operational data";
                uses POLICY-MI;
              }
            }
            container policy-ipv6 {
              description
                "IPv6 policy operational data";
              container policy-ipv6-backup {
                description
                  "IPv6 backup policy operational data";
                uses POLICY-MI;
              }
              container policy-ipv6-active {
                description
                  "IPv6 active policy operational data";
                uses POLICY-MI;
              }
            }
          }
        }
        container error-log {
          description
            "Log of errors and warnings";
          uses ISIS-SH-ERR-LOG-STRUC;
        }
        container checkpoint-interfaces {
          description
            "Checkpointed interface table";
          list checkpoint-interface {
            key "interface-name";
            description
              "Checkpointed information about one IS-IS
               interface";
            leaf interface-name {
              type xr:Interface-name;
              description
                "Interface name";
            }
            uses ISIS-SH-CHKPT-IDB;
          }
        }
        container sr-labels {
          description
            "SR Label table";
          list sr-label {
            key "label";
            description
              "SrLabel table entry";
            leaf label {
              type uint32;
              description
                "SR Label";
            }
            uses ISIS-SH-LABEL;
          }
        }
        container interface-statistics {
          description
            "Interface statistics table";
          list interface-statistic {
            key "interface-name";
            description
              "Statistics data for one IS-IS interface";
            leaf interface-name {
              type xr:Interface-name;
              description
                "Interface name";
            }
            uses ISIS-SH-TRAFFIC-INTF;
          }
        }
        container protocol {
          description
            "Basic protocol information about an IS-IS
             instance";
          uses ISIS-SH-PROTO;
        }
        container neighbor-summaries {
          description
            "Neighbor-summary table";
          list neighbor-summary {
            key "interface-name";
            description
              "Neighbor-summary data for a single interface";
            leaf interface-name {
              type xr:Interface-name;
              description
                "Interface name";
            }
            uses ISIS-SH-NBR-SUMM;
          }
        }
        container checkpoint-lsps {
          description
            "Checkpointed LSP table";
          list checkpoint-lsp {
            description
              "A checkpointed IS-IS LSP";
            leaf level {
              type dt1:Isis-internal-level;
              description
                "Level";
            }
            leaf lsp-id {
              type xr:Isis-lsp-id;
              description
                "LSP ID";
            }
            uses ISIS-SH-CHKPT-LSP;
          }
        }
        container mesh-groups {
          description
            "Mesh-group information";
          uses ISIS-SH-MESH-GROUPS;
        }
        container nsr-statistics {
          description
            "NSR Statistics information";
          uses ISIS-SH-NSR-STATS-GLOBAL;
        }
        container checkpoint-te-tunnels {
          description
            "Checkpointed TE tunnel table";
          list checkpoint-te-tunnel {
            description
              "A checkpointed TE tunnel";
            leaf level {
              type dt1:Isis-internal-level;
              description
                "Level";
            }
            leaf interface-name {
              type xr:Interface-name;
              description
                "Interface name";
            }
            uses ISIS-SH-CHKPT-TE-TUNNEL;
          }
        }
        leaf instance-name {
          type dt1:Isis-instance-name;
          description
            "Instance identifier";
        }
      }
    }
  }
}
