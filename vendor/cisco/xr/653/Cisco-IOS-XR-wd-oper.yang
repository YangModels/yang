module Cisco-IOS-XR-wd-oper {
  namespace "http://cisco.com/ns/yang/Cisco-IOS-XR-wd-oper";
  prefix wd-oper;

  import Cisco-IOS-XR-types {
    prefix xr;
  }
  include Cisco-IOS-XR-wd-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wd package operational data.
     
     This module contains definitions
     for the following management objects:
       watchdog: Watchdog information
     
     Copyright (c) 2013-2018 by Cisco Systems, Inc.
     All rights reserved.";

  revision 2015-11-09 {
    description
      "IOS XR 6.0 revision.";
  }

  container watchdog {
    config false;
    description
      "Watchdog information";
    container nodes {
      description
        "List of nodes";
      list node {
        key "node-name";
        description
          "Node ID";
        container threshold-memory {
          description
            "Threshold memory";
          container default {
            description
              "System default memory";
            uses MEMORY-THRESHOLD;
          }
          container configured {
            description
              "Memory configured by user";
            uses CONF-MEM-THRESHOLD;
          }
        }
        container memory-state {
          description
            "Memory state";
          uses MEMORY-DETAILS;
        }
        container overload-state {
          description
            "Display overload control state";
          uses OVERLOAD-CONTROL;
        }
        leaf node-name {
          type xr:Node-id;
          description
            "Node name";
        }
      }
    }
  }
}
