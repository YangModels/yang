submodule Cisco-IOS-XR-ocni-local-routing-oper-sub1 {
  belongs-to Cisco-IOS-XR-ocni-local-routing-oper {
    prefix Cisco-IOS-XR-ocni-local-routing-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ocni-local-routing package operational data.
     
     Copyright (c) 2013-2018 by Cisco Systems, Inc.
     All rights reserved.";

  revision 2015-11-09 {
    description
      "IOS XR 6.0 revision.";
  }

  typedef Yang2bag-string {
    type string;
    description
      "Yang2bag string";
  }

  grouping OVERLAY-OCNI-STATIC-STATE {
    description
      "Operational state data for static routes";
    leaf prefix {
      type Yang2bag-string;
      description
        "Destination prefix for the static route, either
         IPv4 or IPv6.";
    }
    leaf set-tag {
      type Yang2bag-string;
      description
        "Set a generic tag value on the route. This tag
         can be used for filtering routes that are
         distributed to other routing protocols.";
    }
  }

  grouping INTERFACE-REF-STATE {
    description
      "INTERFACE REF STATE";
    leaf interface {
      type Yang2bag-string;
      description
        "Reference to a base interface.  If a reference
         to a subinterface is required, this leaf must be
         specified to indicate the base interface.";
    }
    leaf subinterface {
      type uint32;
      description
        "Reference to a subinterface -- this requires the
         base interface to be specified using the
         interface leaf in this container.  If only a
         reference to a base interface is requuired, this
         leaf should not be set.";
    }
  }

  grouping INTERFACE-REF {
    description
      "INTERFACE REF";
    container state {
      description
        "Operational state for interface-ref";
      uses INTERFACE-REF-STATE;
    }
  }

  grouping STATE {
    description
      "STATE";
    leaf index {
      type Yang2bag-string;
      description
        "An user-specified identifier utilised to
         uniquely reference the next-hop entry in the
         next-hop list. The value of this index has no
         semantic meaning other than for referencing the
         entry.";
    }
    leaf next-hop {
      type Yang2bag-string;
      description
        "The next-hop that is to be used for the static
         route - this may be specified as an IP address,
         an interface or a pre-defined next-hop type -
         for instance, DROP or LOCAL_LINK. When this leaf
         is not set, and the interface-ref value is
         specified for the next-hop, then the system
         should treat the prefix as though it is directly
         connected to the interface.";
    }
    leaf metric {
      type uint32;
      description
        "A metric which is utilised to specify the
         preference of the next-hop entry when it is
         injected into the RIB. The lower the metric, the
         more preferable the prefix is. When this value
         is not specified the metric is inherited from
         the default metric utilised for static routes
         within the network instance that the static
         routes are being instantiated. When multiple
         next-hops are specified for a static route, the
         metric is utilised to determine which of the
         next-hops is to be installed in the RIB. When
         multiple next-hops have the same metric (be it
         specified, or simply the default) then these
         next-hops should all be installed in the RIB";
    }
  }

  grouping OVERLAY-OCNI-NEXT-HOP {
    description
      "A list of next-hops to be utilised for the static
       route being specified.";
    container state {
      description
        "Operational state parameters relating to the
         next-hop entry";
      uses STATE;
    }
    container interface-ref {
      description
        "Reference to an interface or subinterface";
      uses INTERFACE-REF;
    }
  }

  grouping OVERLAY-OCNI-STATE {
    description
      "State parameters relating to the routing protocol
       instance";
    leaf identifier {
      type Yang2bag-string;
      description
        "The protocol identifier for the instance";
    }
    leaf name {
      type Yang2bag-string;
      description
        "A unique name for the protocol instance";
    }
    leaf enabled {
      type boolean;
      description
        "A boolean value indicating whether the local
         protocol instance is enabled.";
    }
    leaf default-metric {
      type uint32;
      description
        "The default metric within the RIB for entries
         that are installed by this protocol instance.
         This value may be overridden by protocol
         specific configuration options. The lower the
         metric specified the more preferable the RIB
         entry is to be selected for use within the
         network instance. Where multiple entries have
         the same metric value then these equal cost
         paths should be treated according to the
         specified ECMP path selection behaviour for the
         instance";
    }
  }
}
