module Cisco-IOS-XR-lmp-cfg {
  namespace "http://cisco.com/ns/yang/Cisco-IOS-XR-lmp-cfg";
  prefix lmp-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lmp package configuration.
     
     This module contains definitions
     for the following management objects:
       lmp: Main common OLM/LMP configuration container
     
     Copyright (c) 2013-2018 by Cisco Systems, Inc.
     All rights reserved.";

  revision 2015-11-09 {
    description
      "IOS XR 6.0 revision.";
  }

  typedef Olm-addr {
    type enumeration {
      enum "ipv4" {
        value 101;
        description
          "IPv4 address";
      }
      enum "ipv6" {
        value 102;
        description
          "IPv6 address";
      }
      enum "unnumbered" {
        value 103;
        description
          "Unnumbered address";
      }
      enum "nsap" {
        value 104;
        description
          "NSAP address";
      }
    }
    description
      "Olm addr";
  }

  typedef Olm-switching-cap {
    type enumeration {
      enum "lsc" {
        value 150;
        description
          "Lambda switch capable";
      }
      enum "fsc" {
        value 200;
        description
          "Fiber switch capable";
      }
    }
    description
      "Olm switching cap";
  }

  container lmp {
    description
      "Main common OLM/LMP configuration container";
    container gmpls-uni {
      description
        "GMPLS UNI specific OLM/LMP configuration";
      container neighbors {
        description
          "Neighbor configuration";
        list neighbor {
          key "neighbor-name";
          description
            "Neighbor configuration";
          container ipcc {
            description
              "IPCC configuration";
            container routed {
              description
                "Routed IPCC configuration";
              leaf enable {
                type empty;
                description
                  "Routed IPCC creation";
              }
            }
          }
          leaf enable {
            type empty;
            description
              "Neighbor creation";
          }
          leaf neighbor-router-id {
            type inet:ipv4-address-no-zone;
            description
              "Neighbor router ID (IPv4 Address)";
          }
          leaf neighbor-name {
            type xr:Cisco-ios-xr-string {
              length "1..64";
            }
            description
              "Neighbor name";
          }
        }
      }
      container router-id {
        presence "enable router-id";
        description
          "Local GMPLS UNI router ID";
        leaf interface-name {
          type xr:Interface-name;
          description
            "Name of interface";
        }
        leaf address {
          type inet:ipv4-address-no-zone;
          description
            "Local router ID (IPv4 Address)";
        }
      }
      container controllers {
        description
          "Configure GMPLS UNI OLM/LMP controllers";
        list controller {
          key "controller-name";
          description
            "Configure an GMPLS UNI OLM/LMP contoller";
          container local-link-id {
            description
              "Local Link ID configuration";
            leaf address-type {
              type Olm-addr;
              description
                "Local link ID address type";
            }
            leaf unnumbered {
              when "../address-type = 'unnumbered'" {
                description
                  "../AddressType = Unnumbered";
              }
              type uint32;
              description
                "Local address unnumbered ";
            }
            leaf address {
              when "../address-type = 'ipv4'" {
                description
                  "../AddressType = IPv4";
              }
              type inet:ipv4-address-no-zone;
              description
                "Local link ID address IPv4";
            }
          }
          container adjacency {
            description
              "Neighbor controller adjacency configuration";
            container remote-neighbor {
              description
                "Neighbor data";
              container interface-id {
                description
                  "Neighbor Interface ID configuration";
                leaf address-type {
                  type Olm-addr;
                  description
                    "Local link ID address type";
                }
                leaf unnumbered {
                  when "../address-type = 'unnumbered'" {
                    description
                      "../AddressType = Unnumbered";
                  }
                  type uint32;
                  description
                    "Local address unnumbered ";
                }
                leaf address {
                  when "../address-type = 'ipv4'" {
                    description
                      "../AddressType = IPv4";
                  }
                  type inet:ipv4-address-no-zone;
                  description
                    "Local link ID address IPv4";
                }
              }
              container link-id {
                description
                  "Neighbor Link ID configuration";
                leaf address-type {
                  type Olm-addr;
                  description
                    "Neighbor link ID address type";
                }
                leaf unnumbered {
                  when "../address-type = 'unnumbered'" {
                    description
                      "../AddressType = Unnumbered";
                  }
                  type uint32;
                  description
                    "Neighbor address unnumbered [Not
                     supported]";
                }
                leaf address {
                  when "../address-type = 'ipv4'" {
                    description
                      "../AddressType = IPv4";
                  }
                  type inet:ipv4-address-no-zone;
                  description
                    "Neighbor ID address IPv4";
                }
              }
              leaf neighbor-association {
                type xr:Cisco-ios-xr-string {
                  length "1..64";
                }
                description
                  "Create LMP controller to neighbor
                   association";
              }
              leaf link-switching-capability {
                type Olm-switching-cap;
                default "lsc";
                description
                  "Neighbor link switching capability
                   configuration";
              }
              leaf flexi-grid-capable {
                type uint32;
                description
                  "Remote node flexi grid capability ";
              }
            }
          }
          leaf enable {
            type empty;
            description
              "Enable the OLM/LMP application on this
               controller";
          }
          leaf controller-name {
            type xr:Interface-name;
            description
              "Controller name";
          }
        }
      }
    }
    leaf enable {
      type empty;
      description
        "Enable the OLM/LMP application";
    }
  }
}
