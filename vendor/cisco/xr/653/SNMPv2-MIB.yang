module SNMPv2-MIB {
  namespace "http://tail-f.com/ns/mibs/SNMPv2-MIB/200210160000Z";
  prefix SNMPv2_MIB;

  import ietf-yang-types {
    prefix yang;
  }
  import tailf-common {
    prefix tailf;
  }
  import SNMPv2-TC {
    prefix SNMPv2_TC;
  }

  revision 2002-10-16 {
    description
      "";
  }

  typedef sysDescrType {
    type string {
      length "min .. 255";
    }
  }

  typedef sysContactType {
    type string {
      length "min .. 255";
    }
  }

  typedef sysNameType {
    type string {
      length "min .. 255";
    }
  }

  typedef sysLocationType {
    type string {
      length "min .. 255";
    }
  }

  typedef sysServicesType {
    type int32 {
      range "0 .. 127";
    }
  }

  typedef snmpEnableAuthenTrapsType {
    type enumeration {
      enum "enabled" {
        value 1;
      }
      enum "disabled" {
        value 2;
      }
    }
  }

  typedef sysORIndexType {
    type int32 {
      range "1 .. 2147483647";
    }
  }
  tailf:id "";
  tailf:snmp-mib-module-name "SNMPv2-MIB";

  container SNMPv2-MIB {
    container system {
      tailf:snmp-oid "1.3.6.1.2.1.1";
      leaf sysDescr {
        type sysDescrType;
        config false;
        tailf:snmp-oid "1.3.6.1.2.1.1.1";
      }
      leaf sysObjectID {
        type yang:object-identifier;
        config false;
        tailf:snmp-oid "1.3.6.1.2.1.1.2";
      }
      leaf sysUpTime {
        type yang:timeticks;
        config false;
        tailf:snmp-oid "1.3.6.1.2.1.1.3";
      }
      leaf sysContact {
        type sysContactType;
        default "";
        tailf:snmp-oid "1.3.6.1.2.1.1.4";
      }
      leaf sysName {
        type sysNameType;
        default "";
        tailf:snmp-oid "1.3.6.1.2.1.1.5";
      }
      leaf sysLocation {
        type sysLocationType;
        default "";
        tailf:snmp-oid "1.3.6.1.2.1.1.6";
      }
      leaf sysServices {
        type sysServicesType;
        config false;
        tailf:snmp-oid "1.3.6.1.2.1.1.7";
      }
      leaf sysORLastChange {
        type yang:timestamp;
        config false;
        tailf:snmp-oid "1.3.6.1.2.1.1.8";
      }
    }
    container snmp {
      tailf:snmp-oid "1.3.6.1.2.1.11";
      leaf snmpInPkts {
        type yang:counter32;
        config false;
        tailf:snmp-oid "1.3.6.1.2.1.11.1";
      }
      leaf snmpInBadVersions {
        type yang:counter32;
        config false;
        tailf:snmp-oid "1.3.6.1.2.1.11.3";
      }
      leaf snmpInBadCommunityNames {
        type yang:counter32;
        config false;
        tailf:snmp-oid "1.3.6.1.2.1.11.4";
      }
      leaf snmpInBadCommunityUses {
        type yang:counter32;
        config false;
        tailf:snmp-oid "1.3.6.1.2.1.11.5";
      }
      leaf snmpInASNParseErrs {
        type yang:counter32;
        config false;
        tailf:snmp-oid "1.3.6.1.2.1.11.6";
      }
      leaf snmpEnableAuthenTraps {
        type snmpEnableAuthenTrapsType;
        default "disabled";
        tailf:snmp-oid "1.3.6.1.2.1.11.30";
      }
      leaf snmpSilentDrops {
        type yang:counter32;
        config false;
        tailf:snmp-oid "1.3.6.1.2.1.11.31";
      }
      leaf snmpProxyDrops {
        type yang:counter32;
        config false;
        tailf:snmp-oid "1.3.6.1.2.1.11.32";
      }
    }
    container snmpSet {
      tailf:snmp-oid "1.3.6.1.6.3.1.1.6";
      leaf snmpSetSerialNo {
        type SNMPv2_TC:TestAndIncr;
        config false;
        tailf:snmp-oid "1.3.6.1.6.3.1.1.6.1";
      }
    }
    container sysORTable {
      list sysOREntry {
        key "sysORIndex";
        tailf:sort-order "snmp";
        tailf:snmp-oid "1.3.6.1.2.1.1.9";
        leaf sysORIndex {
          type sysORIndexType;
          tailf:snmp-oid "1.3.6.1.2.1.1.9.1.1";
        }
        leaf sysORID {
          type yang:object-identifier;
          config false;
          tailf:snmp-oid "1.3.6.1.2.1.1.9.1.2";
        }
        leaf sysORDescr {
          type string {
            length "0 .. 255";
          }
          config false;
          tailf:snmp-oid "1.3.6.1.2.1.1.9.1.3";
        }
        leaf sysORUpTime {
          type yang:timestamp;
          config false;
          tailf:snmp-oid "1.3.6.1.2.1.1.9.1.4";
        }
      }
    }
  }
}
