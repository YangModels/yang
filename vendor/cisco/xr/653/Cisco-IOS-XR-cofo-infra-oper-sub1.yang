submodule Cisco-IOS-XR-cofo-infra-oper-sub1 {
  belongs-to Cisco-IOS-XR-cofo-infra-oper {
    prefix Cisco-IOS-XR-cofo-infra-oper;
  }

  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cofo-infra package operational data.
     
     Copyright (c) 2013-2018 by Cisco Systems, Inc.
     All rights reserved.";

  revision 2015-11-09 {
    description
      "IOS XR 6.0 revision.";
  }

  grouping COFO-TIMESPEC {
    description
      "COFO TIMESPEC";
    leaf tv-sec {
      type uint32;
      description
        "tv sec";
    }
    leaf tv-nsec {
      type uint32;
      description
        "tv nsec";
    }
  }

  grouping COFO-OBJECT-INFO {
    description
      "Cofo client object published";
    container object-add-time {
      description
        "Cofo object add time";
      uses COFO-TIMESPEC;
    }
    container object-delete-time {
      description
        "Cofo object delete time";
      uses COFO-TIMESPEC;
    }
    container object-txl-add-time {
      description
        "Cofo object txl add time";
      uses COFO-TIMESPEC;
    }
    container object-txl-encode-time {
      description
        "Cofo object txl encode time";
      uses COFO-TIMESPEC;
    }
    leaf client-id {
      type uint32;
      description
        "Client ID";
    }
    leaf object-id {
      type uint32;
      description
        "Object ID";
    }
    leaf insert-count {
      type uint32;
      description
        "Insert Count";
    }
    leaf item-state {
      type uint32;
      description
        "Item State";
    }
    leaf cofo-infra-object-key {
      type yang:hex-string;
      description
        "Cofo infra object key";
    }
    leaf cofo-infra-object-value {
      type yang:hex-string;
      description
        "Cofo infra object value";
    }
  }

  grouping COFO-PER-CLIENT-DB-INFO {
    description
      "Cofo per client database info struct";
    leaf total-objects {
      type uint32;
      description
        "Total objects";
    }
    leaf total-valid-items-in-db {
      type uint32;
      description
        "Total valid items in db";
    }
    list cofo-object-published-array {
      description
        "Cofo object published array";
      uses COFO-OBJECT-INFO;
    }
  }

  grouping COFO-PER-SDR-DB-INFO {
    description
      "Cofo per sdr database info struct";
    leaf sdr-id {
      type uint32;
      description
        "SDR ID";
    }
    list client-db-info-struct {
      description
        "Client db info struct";
      uses COFO-PER-CLIENT-DB-INFO;
    }
  }

  grouping COFO-DATABASE-BAG {
    description
      "Cofo database info bag";
    leaf topic-id {
      type uint32;
      description
        "Topic ID";
    }
    list database-info-struct {
      description
        "Database info struct";
      uses COFO-PER-SDR-DB-INFO;
    }
  }

  grouping COFO-CLIENT-DATA-BAG {
    description
      "Cofo client info bag";
    leaf connection-handle {
      type uint32;
      description
        "Connection Handle";
    }
    leaf peer-handle {
      type uint32;
      description
        "Peer Handle";
    }
    leaf client-id {
      type uint32;
      description
        "Client ID";
    }
    leaf purge-timeout {
      type uint32;
      description
        "Purge timeout";
    }
    leaf host-client {
      type boolean;
      description
        "host client";
    }
    leaf connection-state {
      type uint32;
      description
        "Connection state";
    }
    leaf-list topic-subscribed {
      type uint32;
      description
        "Topic Subscribed";
    }
    leaf-list topic-published {
      type uint32;
      description
        "Topic Published";
    }
  }
}
