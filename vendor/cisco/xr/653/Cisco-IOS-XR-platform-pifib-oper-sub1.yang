submodule Cisco-IOS-XR-platform-pifib-oper-sub1 {
  belongs-to Cisco-IOS-XR-platform-pifib-oper {
    prefix Cisco-IOS-XR-platform-pifib-oper;
  }

  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR platform-pifib package operational data.
     
     Copyright (c) 2013-2018 by Cisco Systems, Inc.
     All rights reserved.";

  revision 2016-02-22 {
    description
      "Initial revision.";
  }
  revision 2015-11-09 {
    description
      "IOS XR 6.0 revision.";
  }

  grouping PL-PIFIB-HARDWARE-INFO {
    description
      "PL PIFIB HARDWARE INFO";
    leaf policer {
      type uint32;
      description
        "Policer Pointer";
    }
    leaf stats-ptr {
      type uint32;
      description
        "Stats Pointer";
    }
    leaf accepted {
      type uint64;
      description
        "Accepted Packets Counter";
    }
    leaf dropped {
      type uint64;
      description
        "Dropped Packets Counter";
    }
    leaf sort-start-offset {
      type int32;
      description
        "Relative position in sorting order";
    }
    leaf tm-start-offset {
      type int32;
      description
        "Relative position in TCAM";
    }
  }

  grouping PL-PIFIB-SHOW-ENTRY {
    description
      "LPTS TCAM Pre-IFIB Entry Information";
    leaf l3protocol {
      type uint32;
      description
        "Layer 3 Protocol";
    }
    leaf l4protocol {
      type uint32;
      description
        "Layer 4 Protocol";
    }
    leaf intf-handle {
      type uint32;
      description
        "Interface Handle";
    }
    leaf intf-name {
      type string;
      description
        "Interface Name";
    }
    leaf uidb-index {
      type uint32;
      description
        "Interface uidb index";
    }
    leaf local-addr {
      type string;
      description
        "Local IP Address";
    }
    leaf local-prefix-len {
      type uint32;
      description
        "Local Prefix Length";
    }
    leaf remote-addr {
      type string;
      description
        "Remote IP Address";
    }
    leaf remote-prefix-len {
      type uint32;
      description
        "Remote Prefix Length";
    }
    leaf vrf-id {
      type uint32;
      description
        "VRF ID";
    }
    leaf u-value {
      type uint32;
      description
        "Remote Port/ICMP Type/IGMP Type";
    }
    leaf u-len {
      type uint32;
      description
        "Union Key Length";
    }
    leaf local-port {
      type uint32;
      description
        "Local port";
    }
    leaf is-frag {
      type uint8;
      description
        "Is Fragment";
    }
    leaf is-syn {
      type uint8;
      description
        "Is SYN";
    }
    leaf action {
      type uint8;
      description
        "Action";
    }
    leaf action-string {
      type string;
      description
        "Action String";
    }
    leaf listener-tag {
      type uint8;
      description
        "Listener Tag";
    }
    leaf is-fgid {
      type uint8;
      description
        "Is FGID or not";
    }
    leaf is-vrf {
      type uint8;
      description
        "Is VRF or not";
    }
    leaf is-optimized {
      type uint8;
      description
        "Is optimized or not";
    }
    leaf is-uidb-opt-bit {
      type uint8;
      description
        "Is uidb set for optimized entry or not";
    }
    leaf fgid-or-sfp {
      type uint32;
      description
        "fabric group id or swith fabric port";
    }
    leaf remote-rack {
      type uint8;
      description
        "Is entry remote or not";
    }
    leaf rack-id {
      type uint32;
      description
        "Remote racknum if remote";
    }
    leaf rslot {
      type uint32;
      description
        "Remote slotnum if remote";
    }
    leaf cir {
      type uint64;
      description
        "Committed Information Rate";
    }
    leaf flow-type {
      type uint32;
      description
        "Flow type";
    }
    leaf priority {
      type uint32;
      description
        "Flow priority or COS";
    }
    leaf sid {
      type uint32;
      description
        "Stream ID";
    }
    leaf policer-avgrate {
      type uint32;
      description
        "Policer avg. rate limit";
    }
    leaf policer-burst {
      type uint32;
      description
        "Policer burst";
    }
    leaf lookup-priority {
      type int32;
      description
        "Lookup priority";
    }
    leaf storage-priority {
      type int32;
      description
        "Storage priority";
    }
    leaf num-tm-entries {
      type int32;
      description
        "Number of TCAM entries used";
    }
    leaf entry-ptr {
      type uint32;
      description
        "ptr to ifib_entry_st";
    }
    leaf entry-shadow-ptr {
      type uint32;
      description
        "ptr to ifib_entry_shadow_st";
    }
    leaf list-node-ptr {
      type uint32;
      description
        "ptr to dlqueue list node";
    }
    leaf state {
      type uint8;
      description
        "state of pifib entry";
    }
    leaf retry-fail-cause {
      type uint8;
      description
        "failure cause";
    }
    leaf num-retries {
      type uint8;
      description
        "retries count";
    }
    leaf min-ttl {
      type uint8;
      description
        "Minimum TTL";
    }
    leaf u-type {
      type uint8;
      description
        "Union Key Type";
    }
    leaf remote-fgid {
      type uint32;
      description
        "Remote FGID";
    }
    leaf acl-str {
      type yang:hex-string;
      description
        "Acl name";
    }
    leaf no-stats {
      type uint8;
      description
        "Stats not available";
    }
    list hw-info {
      description
        "Per pipe type hardware info";
      uses PL-PIFIB-HARDWARE-INFO;
    }
  }

  grouping PL-PIFIB-SHOW-STATS {
    description
      "Pre-IFIB global statistics";
    leaf accepted {
      type uint64;
      description
        "Deleted-entry accepted packets counter";
    }
    leaf dropped {
      type uint64;
      description
        "Deleted-entry dropped packets counter";
    }
    leaf clear-ts {
      type uint64;
      description
        "Statistics clear timestamp";
    }
    leaf no-stats-mem-err {
      type uint64;
      description
        "No statistics memory error";
    }
  }

  grouping PL-PIFIB-SHOW-BFD-DISC-ENTRY-INFO {
    description
      "PL PIFIB SHOW BFD DISC ENTRY INFO";
    leaf index {
      type uint8;
      description
        "index";
    }
    leaf is-mcast {
      type uint8;
      description
        "is mcast";
    }
    leaf fgid-or-vqi {
      type uint32;
      description
        "fgid or vqi";
    }
    leaf is-valid {
      type uint8;
      description
        "is valid";
    }
    leaf policer-id {
      type uint32;
      description
        "policer id";
    }
  }

  grouping PL-PIFIB-SHOW-BFD-DISC-ENTRY {
    description
      "Pre-IFIB platform specific bfd discriminator
       table entry data structure";
    list bfd-entry-info {
      description
        "Per bfd disc entry info";
      uses PL-PIFIB-SHOW-BFD-DISC-ENTRY-INFO;
    }
  }

  grouping PL-PIFIB-SHOW-STATIC-POLICE-INFO {
    description
      "PL PIFIB SHOW STATIC POLICE INFO";
    leaf punt-reason {
      type uint32;
      description
        "punt reason";
    }
    leaf sid {
      type uint32;
      description
        "sid";
    }
    leaf flow-rate {
      type uint32;
      description
        "flow rate";
    }
    leaf burst-rate {
      type uint32;
      description
        "burst rate";
    }
    leaf accepted {
      type uint64;
      description
        "accepted";
    }
    leaf dropped {
      type uint64;
      description
        "dropped";
    }
    leaf punt-reason-string {
      type yang:hex-string;
      description
        "punt reason string";
    }
    leaf change-type {
      type uint8;
      description
        "change type";
    }
  }

  grouping PL-PIFIB-SHOW-STATIC-POLICE {
    description
      "Pre-IFIB platform specific punt reason data
       structure";
    list static-info {
      description
        "Per punt reason info";
      uses PL-PIFIB-SHOW-STATIC-POLICE-INFO;
    }
  }

  grouping PL-PIFIB-POLICE-INFO {
    description
      "PL PIFIB POLICE INFO";
    leaf avgrate {
      type uint32;
      description
        "avgrate";
    }
    leaf burst {
      type uint32;
      description
        "burst";
    }
    leaf static-avgrate {
      type uint32;
      description
        "static avgrate";
    }
    leaf avgrate-type {
      type uint32;
      description
        "avgrate type";
    }
    leaf accepted-stats {
      type uint64;
      description
        "accepted stats";
    }
    leaf dropped-stats {
      type uint64;
      description
        "dropped stats";
    }
    leaf policer {
      type uint32;
      description
        "policer";
    }
    leaf iptos-value {
      type uint8;
      description
        "iptos value";
    }
    leaf change-type {
      type uint8;
      description
        "change type";
    }
    leaf acl-config {
      type uint8;
      description
        "acl config";
    }
    leaf acl-str {
      type yang:hex-string;
      description
        "acl str";
    }
  }

  grouping PL-PIFIB-SHOW-POLICE {
    description
      "Pre-IFIB platform specific police data structure";
    list police-info {
      description
        "Per flow type police info";
      uses PL-PIFIB-POLICE-INFO;
    }
  }

  grouping PL-PIFIB-USAGE-INFO {
    description
      "PL PIFIB USAGE INFO";
    leaf pipe-id {
      type uint8;
      description
        "Pipe ID";
    }
    leaf region {
      type uint8;
      description
        "Region Type";
    }
    leaf region-id {
      type uint8;
      description
        "Region ID";
    }
    leaf size {
      type uint32;
      description
        "Maximum Number of Entries in the Region";
    }
    leaf used {
      type uint32;
      description
        "Used Number of Entries in the Region";
    }
  }

  grouping PL-PIFIB-SHOW-USAGE {
    description
      "Pre-IFIB platform specific usage data structure";
    list usage-info {
      description
        "Per TCAM type usage info";
      uses PL-PIFIB-USAGE-INFO;
    }
  }
}
