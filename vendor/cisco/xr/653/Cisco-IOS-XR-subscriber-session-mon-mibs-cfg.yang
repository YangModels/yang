module Cisco-IOS-XR-subscriber-session-mon-mibs-cfg {
  namespace "http://cisco.com/ns/yang/Cisco-IOS-XR-subscriber-session-mon-mibs-cfg";
  prefix subscriber-session-mon-mibs-cfg;

  import Cisco-IOS-XR-types {
    prefix xr;
  }
  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-session-mon-mibs package configuration.
     
     This YANG module augments the
       Cisco-IOS-XR-snmp-agent-cfg
     module with configuration data.
     
     Copyright (c) 2013-2018 by Cisco Systems, Inc.
     All rights reserved.";

  revision 2015-11-09 {
    description
      "IOS XR 6.0 revision.";
  }

  grouping NODE-TABLE {
    description
      "Common node of rising, falling, percent,
       evaluation";
    container nodes {
      description
        "Table of Node";
      list node {
        key "node-name";
        description
          "Rising node level";
        leaf session-count {
          type uint32 {
            range "1..4294967294";
          }
          description
            "Session count";
        }
        leaf interval {
          type uint32 {
            range "30..3600";
          }
          description
            "interval value in multiples of 10";
        }
        leaf node-name {
          type xr:Node-id;
          description
            "location";
        }
      }
    }
  }

  grouping ACCESS-INTERFACE-TABLE {
    description
      "Common node of rising, falling, percent,
       evaluation";
    container access-interfaces {
      description
        "Table of AccessInterface";
      list access-interface {
        key "interface-name";
        description
          "Access interface";
        leaf session-count {
          type uint32 {
            range "1..4294967294";
          }
          description
            "Session count";
        }
        leaf interval {
          type uint32 {
            range "30..3600";
          }
          description
            "Interval value in multiples of 10";
        }
        leaf interface-name {
          type xr:Interface-name;
          description
            "Interface name";
        }
      }
    }
  }

  augment "/a1:mib" {
    description
      "This augment extends the configuration data of
       'Cisco-IOS-XR-snmp-agent-cfg'";
    container subscriber {
      description
        "Subscriber threshold commands";
      container threshold {
        description
          "Subscriber threshold commands";
        container delta {
          description
            "Delta loss keyword";
          container evaluation {
            description
              "Evaluation keyword";
            uses ACCESS-INTERFACE-TABLE;
            uses NODE-TABLE;
          }
          container percent {
            description
              "Delta loss percent";
            uses ACCESS-INTERFACE-TABLE;
            uses NODE-TABLE;
          }
        }
        container access-interface-sub {
          description
            "Access interface for regular expression";
          container subsets {
            description
              "Table of Subset";
            list subset {
              key "subset-id";
              description
                "Subset command";
              container regular-expression {
                description
                  "Regular expression";
                container notification {
                  description
                    "Notification keyword";
                  container rising-falling {
                    description
                      "Rising-falling threshold";
                    leaf disable {
                      type string;
                      description
                        "Disable the notifications on access
                         interfaces";
                    }
                  }
                }
              }
              leaf subset-id {
                type uint32 {
                  range "1..255";
                }
                description
                  "Subset number";
              }
            }
          }
        }
        container falling {
          description
            "Falling threshold";
          uses ACCESS-INTERFACE-TABLE;
          uses NODE-TABLE;
        }
        container rising {
          description
            "Rising threshold";
          uses ACCESS-INTERFACE-TABLE;
          uses NODE-TABLE;
        }
      }
    }
  }
  augment "/a1:snmp/a1:notification" {
    description
      "This augment extends the configuration data of
       'Cisco-IOS-XR-snmp-agent-cfg'";
    container subscriber-mib {
      description
        "Subscriber notification commands";
      container session-aggregate {
        description
          "Session aggregation";
        leaf node {
          type empty;
          description
            "Subscriber notification at node level";
        }
        leaf access-interface {
          type empty;
          description
            "Subscriber notification at access interface
             level";
        }
      }
    }
  }
}
