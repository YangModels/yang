submodule Cisco-IOS-XR-asr9k-sc-diag-admin-oper-sub1 {
  belongs-to Cisco-IOS-XR-asr9k-sc-diag-admin-oper {
    prefix Cisco-IOS-XR-asr9k-sc-diag-admin-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-sc-diag-admin package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Diag-slot {
    type enumeration {
      enum "fan-tray" {
        description
          "Slot type is fan tray";
      }
      enum "power-module" {
        description
          "Slot type is power module";
      }
      enum "module" {
        description
          "Slot type is module";
      }
    }
    description
      "Slot types";
  }

  typedef Diag-node {
    type enumeration {
      enum "node" {
        description
          "Node type is node";
      }
      enum "spa" {
        description
          "Node type is SPA";
      }
    }
    description
      "Node types";
  }

  typedef Diag-processor {
    type enumeration {
      enum "mpc8614d" {
        description
          "Processor type 8614D";
      }
    }
    description
      "Processor types";
  }

  typedef Node-state {
    type enumeration {
      enum "not-present" {
        value 0;
        description
          "Not present";
      }
      enum "present" {
        value 1;
        description
          "Present";
      }
      enum "reset" {
        value 2;
        description
          "Reset";
      }
      enum "rommon" {
        value 3;
        description
          "Card booting or rommon";
      }
      enum "mbi-boot" {
        value 4;
        description
          "MBI booting";
      }
      enum "mbi-run" {
        value 5;
        description
          "Running MBI";
      }
      enum "xr-run" {
        value 6;
        description
          "Running ENA";
      }
      enum "bring-down" {
        value 7;
        description
          "Bringdown";
      }
      enum "xr-fail" {
        value 8;
        description
          "ENA failure";
      }
      enum "fdiag-run" {
        value 9;
        description
          "Running FDIAG";
      }
      enum "fdiag-fail" {
        value 10;
        description
          "FDIAG failure";
      }
      enum "power" {
        value 11;
        description
          "Powered";
      }
      enum "unpower" {
        value 12;
        description
          "Unpowered";
      }
      enum "mdr-warm-reload" {
        value 13;
        description
          "MDR warm reload";
      }
      enum "mdr-mbi-run" {
        value 14;
        description
          "MDR running MBI";
      }
      enum "maintenance-mode" {
        value 15;
        description
          "Maintenance mode";
      }
      enum "admin-down" {
        value 16;
        description
          "Admin down";
      }
      enum "not-monitor" {
        value 17;
        description
          "No MON";
      }
      enum "unknown-card" {
        value 18;
        description
          "Unknown";
      }
      enum "failed" {
        value 19;
        description
          "Failed";
      }
      enum "ok" {
        value 20;
        description
          "OK";
      }
      enum "missing" {
        value 21;
        description
          "Missing";
      }
      enum "diag-download" {
        value 22;
        description
          "Field diag downloading";
      }
      enum "diag-not-monitor" {
        value 23;
        description
          "Field diag unmonitor";
      }
      enum "fabric-diag-not-monitor" {
        value 24;
        description
          "Fabric field diag unmonitor";
      }
      enum "diag-rp-launch" {
        value 25;
        description
          "Field diag RP launching";
      }
      enum "diag-run" {
        value 26;
        description
          "Field diag running";
      }
      enum "diag-pass" {
        value 27;
        description
          "Field diag pass";
      }
      enum "diag-fail" {
        value 28;
        description
          "Field diag fail";
      }
      enum "diag-timeout" {
        value 29;
        description
          "Field diag timeout";
      }
      enum "disable" {
        value 30;
        description
          "Disable";
      }
      enum "spa-boot" {
        value 31;
        description
          "SPA booting";
      }
      enum "not-allowed-online" {
        value 32;
        description
          "Not allowed online";
      }
      enum "stop" {
        value 33;
        description
          "Stopped";
      }
      enum "incomp-version" {
        value 34;
        description
          "Incompatible FW version";
      }
      enum "fpd-hold" {
        value 35;
        description
          "FPD hold";
      }
      enum "xr-preparation" {
        value 36;
        description
          "XR preparation";
      }
      enum "sync-ready" {
        value 37;
        description
          "Sync ready state";
      }
      enum "xr-isolate" {
        value 38;
        description
          "Node isolate state";
      }
      enum "ready" {
        value 39;
        description
          "Ready";
      }
      enum "invalid" {
        value 40;
        description
          "Invalid";
      }
      enum "operational" {
        value 41;
        description
          "Operational";
      }
      enum "operational-lock" {
        value 42;
        description
          "Operational lock";
      }
      enum "going-down" {
        value 43;
        description
          "Going down";
      }
      enum "going-offline" {
        value 44;
        description
          "Going offline";
      }
      enum "going-online" {
        value 45;
        description
          "Going online";
      }
      enum "offline" {
        value 46;
        description
          "Offline";
      }
      enum "up" {
        value 47;
        description
          "Up";
      }
      enum "down" {
        value 48;
        description
          "Down";
      }
      enum "max" {
        value 49;
        description
          "Max";
      }
      enum "unknown" {
        value 50;
        description
          "Unknown";
      }
      enum "not-applicable" {
        value 51;
        description
          "N/A";
      }
    }
    description
      "Node state detail";
  }

  grouping DIAG-SUMMARY-ENTRY {
    description
      "Diag summary of a node";
    leaf type {
      type Diag-node;
      description
        "Node type";
    }
    leaf node {
      type xr:Node-id;
      description
        "Node ID";
    }
    leaf slot-type {
      type Diag-slot;
      description
        "Slot type";
    }
    leaf description {
      type string;
      description
        "Description";
    }
  }

  grouping DIAG-SUMMARY {
    description
      "Diag summary information";
    list summary {
      description
        "Summary data";
      uses DIAG-SUMMARY-ENTRY;
    }
  }

  grouping DIAG-CHASSIS {
    description
      "Diag chassis information";
    leaf serial-number {
      type string;
      description
        "Serial number";
    }
    leaf pid {
      type string;
      description
        "PID";
    }
    leaf vid {
      type string;
      description
        "VID";
    }
    leaf description {
      type string;
      description
        "Describes in user-readable terms";
    }
    leaf clei {
      type string;
      description
        "CLEI";
    }
    leaf tan {
      type string;
      description
        "Top assembly number";
    }
  }

  grouping DIAG-SLOT-DETAIL {
    description
      "Slot detail information";
    list node-detail {
      description
        "Detail information for slot";
      uses DIAG-NODE;
    }
    list spa-detail {
      description
        "Detail information for spa";
      uses DIAG-SPA;
    }
  }

  grouping DIAG-EDM-MAIN {
    description
      "Main information";
    leaf board-type {
      type uint32;
      description
        "Board type";
    }
    leaf tan {
      type string;
      description
        "Top assembly number";
    }
    leaf tan-revision {
      type string;
      description
        "Top assembly number revision";
    }
    leaf deviation-number {
      type uint32;
      description
        "Deviation number";
    }
    leaf serial-number {
      type string;
      description
        "Serial number";
    }
  }

  grouping DIAG-SPA {
    description
      "Diag details";
    container main {
      description
        "Main";
      uses DIAG-EDM-MAIN;
    }
    container hardware-revision {
      description
        "Hardware revision";
      uses DIAG-EDM-REVISION;
    }
    leaf node {
      type xr:Node-id;
      description
        "Node";
    }
    leaf name {
      type string;
      description
        "SPA name";
    }
    leaf pca-unit-number {
      type string;
      description
        "Format is C-BN-V where C = Class Code, BN = Base
         Number, and V = Version";
    }
    leaf pca-revision {
      type string;
      description
        "PCA revision information";
    }
    leaf pid {
      type string;
      description
        "PID";
    }
    leaf vid {
      type string;
      description
        "VID";
    }
    leaf clei {
      type string;
      description
        "CLEI";
    }
    leaf node-state {
      type Node-state;
      description
        "Node state";
    }
  }

  grouping DIAG-SSD-REVISION {
    description
      "SSD information";
    leaf number {
      type string;
      description
        "SSD number";
    }
    leaf fw-rev {
      type string;
      description
        "Firmware revision";
    }
    leaf serial-number {
      type string;
      description
        "Serial number";
    }
  }

  grouping DIAG-DIMM-REVISION {
    description
      "DIMM version information";
    leaf size {
      type uint32;
      description
        "Size in MB";
    }
    leaf speed {
      type uint32;
      description
        "Speed in MHz";
    }
    leaf locator {
      type string;
      description
        "Locator information";
    }
    leaf cas {
      type uint32;
      description
        "Column address strobe latency in clock cycles";
    }
  }

  grouping DIAG-REVISION-NUMBER {
    description
      "Revision detail";
    leaf major-revision {
      type uint32;
      description
        "Major revision";
    }
    leaf minor-revision {
      type uint32;
      description
        "Minor revision";
    }
  }

  grouping DIAG-HARDWARE-REVISION {
    description
      "Hardware revision";
    container hw-rev {
      description
        "Hardware version";
      uses DIAG-REVISION-NUMBER;
    }
    container fw-rev {
      description
        "Firmware version";
      uses DIAG-REVISION-NUMBER;
    }
    container sw-rev {
      description
        "Software version";
      uses DIAG-REVISION-NUMBER;
    }
    container dimm-rev {
      description
        "DIMM version information";
      uses DIAG-DIMM-REVISION;
    }
    container ssd-rev {
      description
        "SSD version information";
      uses DIAG-SSD-REVISION;
    }
    leaf node-description {
      type string;
      description
        "Node decsription";
    }
    leaf version {
      type string;
      description
        "Version information";
    }
  }

  grouping DIAG-EDM-REVISION {
    description
      "Board FPGA/CPLD/ASIC hardware revision
       information";
    list hardware-revision {
      description
        "Board FPGA/CPLD/ASIC hardware revision";
      uses DIAG-HARDWARE-REVISION;
    }
  }

  grouping DIAG-EDM-PLD-VERSION {
    description
      "PLD version information";
    leaf type {
      type uint32;
      description
        "Processor PLD version";
    }
    leaf processor-higher-version {
      type uint32;
      description
        "HigherVerion";
    }
    leaf processor-lower-version {
      type uint32;
      description
        "LowerVersion";
    }
  }

  grouping DIAG-NODE {
    description
      "Diag node information";
    container pld {
      description
        "Programmable logic device information";
      uses DIAG-EDM-PLD-VERSION;
    }
    container hardware-revision {
      description
        "Hardware revision";
      uses DIAG-EDM-REVISION;
    }
    container cbc-active-partition {
      description
        "CBC active partition";
      uses DIAG-REVISION-NUMBER;
    }
    container cbc-inactive-partition {
      description
        "CBC inactive partition";
      uses DIAG-REVISION-NUMBER;
    }
    leaf description {
      type string;
      description
        "Describes in user-readable terms";
    }
    leaf serial-number {
      type string;
      description
        "Main serial number";
    }
    leaf tan {
      type string;
      description
        "Top assembly number";
    }
    leaf pid {
      type string;
      description
        "PID";
    }
    leaf vid {
      type string;
      description
        "VID";
    }
    leaf chip-hardware-revision {
      type string;
      description
        "Chip hardware revision";
    }
    leaf new-deviation-number {
      type uint32;
      description
        "New deviation number";
    }
    leaf clei {
      type string;
      description
        "CLEI";
    }
    leaf board-state {
      type Node-state;
      description
        "Module operational state";
    }
    leaf pld-motherboard {
      type string;
      description
        "Motherboard PLD version";
    }
    leaf pld-power {
      type string;
      description
        "Power PLD version";
    }
    leaf monlib {
      type string;
      description
        "MONLIB version";
    }
    leaf rommon {
      type string;
      description
        "ROMMON version";
    }
    leaf cpu0 {
      type Diag-processor;
      description
        "Processor type";
    }
  }

  grouping DIAG-DETAIL {
    description
      "Diag detail";
    container node {
      description
        "Node information";
      uses DIAG-NODE;
    }
    container spa {
      description
        "SPA information";
      uses DIAG-SPA;
    }
  }
}
