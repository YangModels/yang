module Cisco-IOS-XR-mpls-lsd-oper {
  namespace "http://cisco.com/ns/yang/Cisco-IOS-XR-mpls-lsd-oper";
  prefix mpls-lsd-oper;

  import ietf-inet-types {
    prefix inet;
  }
  import Cisco-IOS-XR-types {
    prefix xr;
  }
  import cisco-semver {
    prefix semver;
  }
  include Cisco-IOS-XR-mpls-lsd-oper-sub1 {
    revision-date 2020-11-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-lsd package operational data.
     
     This module contains definitions
     for the following management objects:
       mpls-lsd-nodes: Location MPLS LSD operational data
       mpls-lsd: MPLS LSD operational data
     
     Copyright (c) 2013-2020 by Cisco Systems, Inc.
     All rights reserved.";

  revision 2020-11-22 {
    description
      "New Label Context type defined, SR_Pfx_node
       2020-08-13
         Modify mpls_lsd to include label flags in mpls_lsd_fpi_lbl bag";
    semver:module-version "1.1.1m";
  }
  revision 2019-10-22 {
    description
      "Modify mpls_lsd_lbl_ctx_recycle_lbl to take 64 bit field instead of 32 Extend mpls_lsd_moi_pop_and_lkup to include QoS fields Extend mpls_lsd_moi_ipv6 to include load metric field Extend mpls_lsd_moi_ipv4 to include recursion length fields Extend mpls_lsd_moi_ipv4 to include QoS fields Extend MPLS_LSDLabelContextType to include CBF block type Extend mpls_lsd_lbl_ctx_l3vpn_nh_set to include type field";
    semver:module-version "1.1.0";
  }
  revision 2019-05-22 {
    description
      "Extended schema for FRRDatabase, Rewrite, LabelHistoryTable";
    semver:module-version "1.0.0";
  }
  revision 2019-04-05 {
    description
      "Establish semantic version baseline.";
  }
  revision 2019-01-03 {
    description
      "Yang evaluator: updates to schema descriptions and ranges";
  }
  revision 2017-09-07 {
    description
      "Fixed type translation error.";
  }
  revision 2017-05-01 {
    description
      "Fixing backward compatibility error in module.";
  }
  revision 2015-11-09 {
    description
      "IOS XR 6.0 revision.";
  }

  grouping REWRITE-SUMMARY {
    description
      "Common node of mpls-lsd, mpls-lsd-node";
    container rewrite-summary {
      description
        "Rewrite Summary across all VRFs";
      uses MPLS-LSD-RW-SUM;
    }
  }

  grouping LABEL-SUMMARY {
    description
      "Common node of mpls-lsd, mpls-lsd-node";
    container label-summary {
      description
        "Dynamic label range";
      uses MPLS-LSD-LBL-SUM;
    }
  }

  grouping LABEL-TABLE {
    description
      "Common node of mpls-lsd, mpls-lsd-node";
    container labels {
      description
        "Table of labels";
      list label {
        key "label-id";
        description
          "Data for label";
        leaf label-id {
          type uint32 {
            range "0..1048575";
          }
          description
            "Label value";
        }
        uses MPLS-LSD-LBL;
      }
    }
  }

  grouping FRR-DATABASE {
    description
      "Common node of mpls-lsd, mpls-lsd-node";
    container frr-database {
      description
        "FRR database";
      container tunnel-midpoints {
        description
          "Table of FRR database entries - Tunnel
           midpoints";
        list tunnel-midpoint {
          key "label";
          description
            "Data for FRR database entry - Tunnel midpoint";
          leaf label {
            type uint32 {
              range "0..1048575";
            }
            description
              "Label value";
          }
          uses MPLS-LSD-FRR-DB-ENTRY;
        }
      }
      container tunnel-heads {
        description
          "Table of FRR database entries - Tunnel heads";
        list tunnel-head {
          key "interface-name";
          description
            "Data for FRR database entry - Tunnel head";
          leaf interface-name {
            type xr:Interface-name;
            description
              "Tunnel interface";
          }
          uses MPLS-LSD-FRR-DB-ENTRY;
        }
      }
      container tunnel-head-summary {
        description
          "Summary data for FRR database entry - Tunnel
           head";
        uses MPLS-LSD-FRR-DB-SUM;
      }
      container summary-protected-interfaces {
        description
          "Sumary table of Protected Interfaces";
        list summary-protected-interface {
          key "interface-name";
          description
            "Data for MPLS interface";
          leaf interface-name {
            type xr:Interface-name;
            description
              "Interface";
          }
          uses MPLS-LSD-FRR-DB-SUM;
        }
      }
      container summary-backup-interfaces {
        description
          "Summary Backup Interface Table";
        list summary-backup-interface {
          key "interface-name";
          description
            "Data for Summary Backup Interface";
          leaf interface-name {
            type xr:Interface-name;
            description
              "Tunnel interface";
          }
          uses MPLS-LSD-FRR-DB-SUM;
        }
      }
      container tunnel-summary {
        description
          "Summary data for FRR database entry";
        uses MPLS-LSD-FRR-DB-SUM;
      }
      container tunnel-midpoint-summary {
        description
          "Summary data for FRR database entry - Tunnel
           midpoint";
        uses MPLS-LSD-FRR-DB-SUM;
      }
    }
  }

  grouping LABEL-RANGE {
    description
      "Common node of mpls-lsd, mpls-lsd-node";
    container label-range {
      description
        "MPLS label range information for both static and
         dynamic labels";
      uses MPLS-LSD-LBL-RANGE;
    }
  }

  grouping CLIENT-TABLE {
    description
      "Common node of mpls-lsd, mpls-lsd-node";
    container clients {
      description
        "Table of MPLS clients using LSD";
      list client {
        key "client-name";
        description
          "Data for MPLS client using LSD";
        leaf client-name {
          type xr:Cisco-ios-xr-string;
          description
            "Client Instance name in the form of
             'Application-<client_name>' or
             'BCDL_Agent-<index:parent_index>'";
        }
        uses MPLS-LSD-CLIENT;
      }
    }
  }

  grouping LABEL-SUMMARY-VRF-TABLE {
    description
      "Common node of mpls-lsd, mpls-lsd-nodeCommon node
       of mpls-lsd, mpls-lsd-node";
    container label-summary-vrfs {
      description
        "Dynamic label range summary by VRF";
      list label-summary-vrf {
        key "vrf-name";
        description
          "Dynamic label range summary by VRF";
        leaf vrf-name {
          type xr:Cisco-ios-xr-string;
          description
            "VRF name";
        }
        uses MPLS-LSD-LBL-SUM;
      }
    }
  }

  grouping APPLICATION-TABLE {
    description
      "Common node of mpls-lsd, mpls-lsd-node";
    container applications {
      description
        "Table of MPLS applications using LSD";
      list application {
        key "application-name";
        description
          "Data for MPLS application using LSD";
        leaf application-name {
          type xr:Cisco-ios-xr-string;
          description
            "Application Instance name in the form of
             '<app_type_name>[:<instance>]'";
        }
        uses MPLS-LSD-APP;
      }
    }
  }

  grouping REWRITE-SUMMARY-VRF-TABLE {
    description
      "Common node of mpls-lsd, mpls-lsd-node";
    container rewrite-summary-vrfs {
      description
        "Rewrite Summary by VRF";
      list rewrite-summary-vrf {
        key "vrf-name";
        description
          "Rewrite summary by VRF VRF-name";
        leaf vrf-name {
          type xr:Cisco-ios-xr-string;
          description
            "VRF name";
        }
        uses MPLS-LSD-RW-SUM;
      }
    }
  }

  grouping INTERFACE-TABLE {
    description
      "Common node of mpls-lsd, mpls-lsd-node";
    container interfaces {
      description
        "Table of MPLS interfaces";
      list interface {
        key "interface-name";
        description
          "Data for MPLS interface";
        leaf interface-name {
          type xr:Interface-name;
          description
            "Interface";
        }
        uses MPLS-LSD-INTF;
      }
    }
  }

  grouping LABEL-HISTORY-TABLE {
    description
      "Common node of mpls-lsd, mpls-lsd-node";
    container label-histories {
      description
        "MPLS Label Hist";
      list label-history {
        key "label-id";
        description
          "MPLS Label Tabel Label";
        container label-history-records {
          description
            "MPLS Label History Record Table";
          list label-history-record {
            key "record-num";
            description
              "MPLS Label Record Num";
            leaf record-num {
              type uint32;
              description
                "Record Number";
            }
            uses MPLS-LSD-LBL-HIST;
          }
        }
        leaf label-id {
          type uint32 {
            range "0..1048575";
          }
          description
            "Label value";
        }
      }
    }
  }

  grouping REWRITE {
    description
      "Common node of mpls-lsd, mpls-lsd-node";
    container rewrite {
      description
        "Table of rewrites";
      container rewrite-label-range-cnts {
        description
          "Table of Label Range Counters";
        list rewrite-label-range-cnt {
          description
            "Label Range Counters";
          leaf label-range-type {
            type uint32 {
              range "0..4";
            }
            description
              "Label range type for SRLB/SRGB opaque data to
               FIB";
          }
          leaf label-range-index {
            type uint32 {
              range "0..2";
            }
            description
              "Label range index for SRLB/SRGB opaque data
               to FIB";
          }
          uses MPLS-LSD-RW;
        }
      }
      container rewrite-ipv6s {
        description
          "Table of IPv6 Rewrites";
        list rewrite-ipv6 {
          description
            "FPI rewrite for label";
          leaf rsi-table-id {
            type xr:Hex-integer;
            description
              "RSI table ID";
          }
          leaf address {
            type inet:ipv6-address-no-zone;
            description
              "Network Address ";
          }
          leaf prefix-length {
            type uint32 {
              range "0..128";
            }
            description
              "IPv6 Prefix length";
          }
          uses MPLS-LSD-RW;
        }
      }
      container rewrite-pws {
        description
          "Table of Rewrites";
        list rewrite-pw {
          key "pw-list-id";
          description
            "FPI rewrite for PW List";
          leaf pw-list-id {
            type uint32 {
              range "0..65535";
            }
            description
              "PW List ID";
          }
          uses MPLS-LSD-RW;
        }
      }
      container traffic-collector-interfaces {
        description
          "Table of Rewrite Table Collector";
        list traffic-collector-interface {
          key "interface-name";
          description
            "Data for Traffic Collector Interface";
          leaf interface-name {
            type xr:Interface-name;
            description
              "External interface";
          }
          uses MPLS-LSD-RW;
        }
      }
      container rewrite-ipv4s {
        description
          "Table of Rewrites";
        list rewrite-ipv4 {
          description
            "FPI rewrite for label";
          leaf rsi-table-name {
            type xr:Cisco-ios-xr-string;
            description
              "RSI table name";
          }
          leaf rsi-table-id {
            type xr:Hex-integer;
            description
              "RSI table ID";
          }
          leaf prefix {
            type inet:ipv4-address-no-zone;
            description
              "IPv4 Prefix";
          }
          leaf prefix-length {
            type uint32 {
              range "0..32";
            }
            description
              "IPv4 Prefix length";
          }
          uses MPLS-LSD-RW;
        }
      }
      container rewrite-tes {
        description
          "Table of Traffic Engineering Rewrites";
        list rewrite-te {
          key "interface-name";
          description
            "FPI rewrite for TE";
          leaf interface-name {
            type xr:Interface-name;
            description
              "Tunnel interface";
          }
          uses MPLS-LSD-RW;
        }
      }
      container rewrite-labels {
        description
          "Table of Rewrites";
        list rewrite-label {
          key "label-id";
          description
            "FPI rewrite for label";
          leaf label-id {
            type uint32 {
              range "0..1048575";
            }
            description
              "Label value";
          }
          uses MPLS-LSD-RW;
        }
      }
    }
  }

  container mpls-lsd-nodes {
    config false;
    description
      "Location MPLS LSD operational data";
    list mpls-lsd-node {
      key "node-name";
      description
        "The MPLS LSD operational data for a particular
         node";
      leaf node-name {
        type xr:Node-id;
        description
          "The identifier for the node";
      }
      uses CLIENT-TABLE;
      uses LABEL-SUMMARY;
      uses LABEL-TABLE;
      uses FRR-DATABASE;
      uses REWRITE;
      uses REWRITE-SUMMARY;
      uses APPLICATION-TABLE;
      uses LABEL-SUMMARY-VRF-TABLE;
      uses LABEL-RANGE;
      uses REWRITE-SUMMARY-VRF-TABLE;
      uses INTERFACE-TABLE;
      uses LABEL-HISTORY-TABLE;
    }
  }
  container mpls-lsd {
    config false;
    description
      "MPLS LSD operational data";
    uses CLIENT-TABLE;
    uses LABEL-SUMMARY;
    uses LABEL-TABLE;
    uses FRR-DATABASE;
    uses REWRITE;
    uses REWRITE-SUMMARY;
    uses APPLICATION-TABLE;
    uses LABEL-SUMMARY-VRF-TABLE;
    uses LABEL-RANGE;
    uses REWRITE-SUMMARY-VRF-TABLE;
    uses INTERFACE-TABLE;
    uses LABEL-HISTORY-TABLE;
  }
}
