submodule Cisco-IOS-XR-infra-xtc-oper-sub1 {
  belongs-to Cisco-IOS-XR-infra-xtc-oper {
    prefix Cisco-IOS-XR-infra-xtc-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-xtc package operational data.
     
     Copyright (c) 2013-2019 by Cisco Systems, Inc.
     All rights reserved.";

  revision 2019-10-02 {
    description
      "Added REST peer statistic information.";
    semver:module-version "1.3.0";
  }
  revision 2019-04-05 {
    description
      "Establish semantic version baseline.";
    semver:module-version "1.0.0";
  }
  revision 2017-09-07 {
    description
      "Fixed type translation error.";
  }
  revision 2017-08-24 {
    description
      "Added C flag to pcep flags.";
  }
  revision 2017-06-26 {
    description
      "Change identifiers to be more readable.";
  }
  revision 2017-05-01 {
    description
      "Fixing backward compatibility error in module.";
  }
  revision 2016-05-31 {
    description
      "Revision description string.";
  }
  revision 2015-11-09 {
    description
      "IOS XR 6.0 revision.";
  }

  typedef Pce-headend-swap {
    type enumeration {
      enum "pcehs-none" {
        description
          "Headends not swapped";
      }
      enum "pcehs-plain" {
        description
          "Headends swapped";
      }
      enum "pcehs-rwi" {
        description
          "Headends swapped with increment";
      }
    }
    description
      "PCE Headends Swap Code";
  }

  typedef Path-work-node {
    type enumeration {
      enum "path-work-bag-node-type-work" {
        value 0;
        description
          "work";
      }
      enum "path-work-bag-node-type-worker-prio-1" {
        value 1;
        description
          "reoptimization worker";
      }
      enum "path-work-bag-node-type-region" {
        value 2;
        description
          "region";
      }
    }
    description
      "Path work node type";
  }

  typedef Pce-treesid-state {
    type enumeration {
      enum "none" {
        description
          "No state";
      }
      enum "programming" {
        description
          "Programming non-root nodes";
      }
      enum "programming-root" {
        description
          "Programming the root node";
      }
      enum "pruning" {
        description
          "Pruning stale legs on non-root nodes";
      }
      enum "pruning-root" {
        description
          "Pruning stale legs on root node";
      }
      enum "deleting" {
        description
          "TreeSID is being deleted";
      }
    }
    description
      "Pce treesid state";
  }

  typedef Pce-treesid-role {
    type enumeration {
      enum "none" {
        description
          "No role";
      }
      enum "ingress" {
        description
          "Ingress";
      }
      enum "transit" {
        description
          "Transit";
      }
      enum "egress" {
        description
          "Egress";
      }
      enum "bud-node" {
        description
          "Bud Node";
      }
    }
    description
      "Pce treesid role";
  }

  typedef Pce-cspf-rc {
    type enumeration {
      enum "pce-cspf-not-set" {
        description
          "Not set";
      }
      enum "pce-cspf-src-not-found" {
        description
          "Source not found";
      }
      enum "pce-cspf-dst-not-found" {
        description
          "Destination not found";
      }
      enum "pce-cspf-second-src-not-found" {
        description
          "Second source not found";
      }
      enum "pce-cspf-second-dst-not-found" {
        description
          "Second destination not found";
      }
      enum "pce-cspf-no-mem" {
        description
          "No memory";
      }
      enum "pce-cspf-ex-path-not-resolved" {
        description
          "Second path not resolved";
      }
      enum "pce-cspf-no-path" {
        description
          "No path";
      }
      enum "pce-cspf-sp-success" {
        description
          "Shortest path success";
      }
      enum "pce-cspf-error" {
        description
          "Error";
      }
      enum "pce-cspf-fallback-srlg-node-node" {
        description
          "Fallback from SRLG-NODE to NODE";
      }
      enum "pce-cspf-fallback-srlg-node-link" {
        description
          "Fallback from SRLG-NODE to LINK";
      }
      enum "pce-cspf-fallback-srlg-node-sp" {
        description
          "Fallback from SRLG-NODE to SP";
      }
      enum "pce-cspf-fallback-node-link" {
        description
          "Fallback from NODE to LINK";
      }
      enum "pce-cspf-fallback-link-sp" {
        description
          "Fallback from LINK to SP";
      }
      enum "pce-cspf-fallback-node-sp" {
        description
          "Fallback from NODE to SP";
      }
      enum "pce-cspf-fallback-srlg-link" {
        description
          "Fallback from SRLG to LINK";
      }
      enum "pce-cspf-fallback-srlg-sp" {
        description
          "Fallback from SRLG to SP";
      }
      enum "pce-cspf-dp-success" {
        description
          "Disjoint path success";
      }
      enum "pce-cspf-latency-bound-exceeded" {
        description
          "Latency bound exceeded for computed path";
      }
    }
    description
      "PCE CSPF Result Code";
  }

  typedef Cmn-ha-case {
    type enumeration {
      enum "ha-case-migration" {
        description
          "HA Case Migration";
      }
      enum "ha-case-restart" {
        description
          "HA Case Restart";
      }
      enum "ha-case-switchover" {
        description
          "HA Case Switchover";
      }
      enum "ha-case-startup" {
        description
          "HA Case Startup";
      }
      enum "ha-case-invalid" {
        description
          "HA Case Invalid";
      }
    }
    description
      "Various HA cases";
  }

  typedef Sid {
    type enumeration {
      enum "sr-protected-adj-sid" {
        value 1;
        description
          "Protected Adjacency SID";
      }
      enum "sr-unprotected-adj-sid" {
        value 2;
        description
          "Unprotected Adjacency SID";
      }
      enum "sr-bgp-egress-peer-engineering-sid" {
        value 3;
        description
          "BGP egress peer engineering SID";
      }
      enum "sr-reqular-prefix-sid" {
        value 4;
        description
          "Regular prefix SID";
      }
      enum "sr-strict-prefix-sid" {
        value 5;
        description
          "Strict prefix SID";
      }
    }
    description
      "SID Types";
  }

  typedef Pce-igp-info-id {
    type enumeration {
      enum "isis" {
        value 1;
        description
          "ISIS";
      }
      enum "ospf" {
        value 2;
        description
          "OSPF";
      }
      enum "bgp" {
        value 3;
        description
          "BGP";
      }
    }
    description
      "IGP IDs";
  }

  typedef Pcep-state {
    type enumeration {
      enum "tcp-close" {
        description
          "TCP close";
      }
      enum "tcp-listen" {
        description
          "TCP listen";
      }
      enum "tcp-connect" {
        description
          "TCP connect";
      }
      enum "pcep-closed" {
        description
          "PCEP closed";
      }
      enum "pcep-opening" {
        description
          "PCEP opening";
      }
      enum "pcep-open" {
        description
          "PCEP open";
      }
    }
    description
      "PCEP State";
  }

  typedef Pce-proto {
    type enumeration {
      enum "pcep" {
        description
          "PCE protocol";
      }
      enum "netconf" {
        description
          "Netconf protocol";
      }
    }
    description
      "PCE peer protocol";
  }

  typedef Pce-rro {
    type enumeration {
      enum "rro-type-ipv4-address" {
        description
          "IPv4 Address";
      }
      enum "rro-type-mpls-label" {
        description
          "MPLS Label";
      }
      enum "rro-type-sripv4-node-sid" {
        description
          "Segment Routing IPv4 Node SID";
      }
      enum "rro-type-sripv4-adjacency-sid" {
        description
          "Segment Routing IPv4 Adjacency SID";
      }
      enum "rro-type-sr-nai-null" {
        description
          "Segment Routing with NAI null";
      }
    }
    description
      "PCE RRO type";
  }

  typedef Pce-sr-sid {
    type enumeration {
      enum "ipv4-node-sid" {
        description
          "IPv4 Node SID";
      }
      enum "ipv4-adjacency-sid" {
        description
          "IPv4 Adjacency SID";
      }
      enum "ipv6-node-sid" {
        description
          "IPv6 Node SID";
      }
      enum "ipv6-adjacency-sid" {
        description
          "IPv6 Adjacency SID";
      }
      enum "ipv4-unnumbered-adjacency-sid" {
        description
          "IPv4 unnumbered adjacency segment identifier";
      }
      enum "unknown-sid" {
        description
          "Unknown SID";
      }
    }
    description
      "PCE SR SID type";
  }

  typedef Lsp-state {
    type enumeration {
      enum "lsp-down" {
        description
          "LSP is down";
      }
      enum "lsp-up" {
        description
          "LSP is up";
      }
    }
    description
      "LSP setup type";
  }

  typedef Pcep-lsp-state {
    type enumeration {
      enum "lsp-down" {
        description
          "LSP is down";
      }
      enum "lsp-up" {
        description
          "LSP is up";
      }
      enum "lsp-active" {
        description
          "LSP is active (carrying traffic)";
      }
      enum "lsp-going-down" {
        description
          "LSP is going down";
      }
      enum "lsp-being-signaled" {
        description
          "LSP is being signaled";
      }
    }
    description
      "PCEP operation protocol";
  }

  typedef Lsp-setup {
    type enumeration {
      enum "setup-rsvp" {
        description
          "LSP is established using RSVP-TE";
      }
      enum "setup-sr" {
        description
          "LSP is established using SR-TE";
      }
      enum "setup-unknown" {
        description
          "Unknown LSP establishment method";
      }
    }
    description
      "LSP setup type";
  }

  typedef Pce-ipv6-address {
    type inet:ipv6-address;
    description
      "Pce ipv6 address";
  }

  typedef Pce-ipv4-address {
    type inet:ipv4-address;
    description
      "Pce ipv4 address";
  }

  typedef Pce-af-id {
    type enumeration {
      enum "none" {
        value 0;
        description
          "None";
      }
      enum "ipv4" {
        value 1;
        description
          "IPv4";
      }
      enum "ipv6" {
        value 2;
        description
          "IPv6";
      }
    }
    description
      "Pce af id";
  }

  grouping REST-PEER-STATS-INFO {
    description
      "Stats info struct";
    leaf type {
      type uint32;
      description
        "REST peer operation types";
    }
    leaf state {
      type uint32;
      description
        "REST peer state";
    }
    leaf id {
      type uint32;
      description
        "Unique Identifier for stats";
    }
    leaf failed {
      type boolean;
      description
        "Indicates failure";
    }
    leaf st-time {
      type uint32;
      description
        "Indicates start time";
    }
    leaf ls-time {
      type uint32;
      description
        "Indicates Last seen time";
    }
    leaf queue-valid-time {
      type uint32;
      description
        "Timestamp, when something was sent from queue or
         when it was empty.";
    }
    leaf send-queue-size {
      type uint64;
      units "byte";
      description
        "Size of data in send queue in bytes";
    }
    leaf rest-query {
      type string;
      description
        "query string";
    }
  }

  grouping REST-PEER-STATS-BAG {
    description
      "REST PEER STATS BAG";
    container ip-addr {
      description
        "Indicates the rest peer IP";
      uses PCE-IP-ADDR-TYPE;
    }
    leaf uid {
      type uint32;
      description
        "Indicates the UID for the peer";
    }
    leaf count {
      type uint32;
      description
        "Stats array index";
    }
    list stats {
      description
        "Stats info";
      uses REST-PEER-STATS-INFO;
    }
  }

  grouping PCE-PATH-LIST-BAG {
    description
      "PCE path list";
    leaf headends-swapped {
      type Pce-headend-swap;
      description
        "Headends swapped";
    }
    leaf cspf-result {
      type Pce-cspf-rc;
      description
        "CSPF Result";
    }
    leaf iterations-done {
      type uint32;
      description
        "Iterations of the Suurballe-Tarjan algorithm";
    }
    list output-path {
      description
        "Output PCE paths";
      uses PCE-PATH-BAG;
    }
  }

  grouping PCE-ADDR-BAG {
    description
      "PCE Address Information";
    leaf address-family {
      type uint8;
      description
        "Address Family";
    }
    leaf ipv4-prefix {
      type inet:ipv4-address;
      description
        "IPv4 prefix";
    }
    leaf ipv6-prefix {
      type inet:ipv6-address;
      description
        "IPv6 prefix";
    }
  }

  grouping PCE-PATH-BAG {
    description
      "PCE path information";
    container source-xr {
      description
        "Source of path";
      uses PCE-IP-ADDR-TYPE;
    }
    container destination-xr {
      description
        "Destination of path";
      uses PCE-IP-ADDR-TYPE;
    }
    leaf cost {
      type uint64;
      description
        "Cost";
    }
    list hops {
      description
        "Hop addresses";
      uses PCE-ADDR-BAG;
    }
  }

  grouping PATH-WORK-CACHE-STATS {
    description
      "Statistics about a particular cache";
    leaf work-consumed {
      type uint64;
      description
        "Number of work nodes consumed";
    }
    leaf cache-hit {
      type uint64;
      description
        "How many times we were able to use the cache";
    }
    leaf cache-miss {
      type uint64;
      description
        "How many times we had to recompute the cache";
    }
    leaf cache-miss-time-usec {
      type uint64;
      units "microsecond";
      description
        "How many microseconds the last computation took";
    }
    leaf average-cache-miss-time-usec {
      type uint64;
      units "microsecond";
      description
        "How many microseconds the average computation
         took";
    }
    leaf error {
      type uint64;
      description
        "Number of errors";
    }
    leaf run-time-usec {
      type uint64;
      units "microsecond";
      description
        "How many microseconds it took to verify one
         region";
    }
  }

  grouping PATH-WORK-GROUP-STATS {
    description
      "Path work group stats";
    list last {
      description
        "Last several computations";
      uses PATH-WORK-CACHE-STATS;
    }
  }

  grouping PATH-WORK-REGION {
    description
      "Path work region";
    leaf work-count {
      type uint32;
      description
        "Number of work elements";
    }
  }

  grouping XTC-AFFINITY-COLOR {
    description
      "XTC AFFINITY COLOR";
    leaf color {
      type string;
      description
        "An affinity color";
    }
  }

  grouping XTC-AFFINITY-CONSTRAINT {
    description
      "XTC AFFINITY CONSTRAINT";
    leaf type {
      type uint8;
      description
        "Affinity type";
    }
    leaf value {
      type uint32;
      description
        "Affinity value";
    }
    leaf-list extended-value {
      type uint32;
      description
        "Extended Affinity values";
    }
    list color {
      description
        "Colors";
      uses XTC-AFFINITY-COLOR;
    }
  }

  grouping PATH-WORK-GROUP-KEY {
    description
      "Identifies path work group";
    leaf maximum-segments {
      type uint16;
      description
        "Max number of segments to impose";
    }
    leaf metric-type {
      type uint8;
      description
        "Metric type being optimized";
    }
    leaf non-ocspf {
      type boolean;
      description
        "Constraints are something other than O-CSPF";
    }
    list affinity-constraint {
      description
        "Affinity constraints list";
      uses XTC-AFFINITY-CONSTRAINT;
    }
  }

  grouping PATH-WORK-GROUP {
    description
      "Path work group";
    container key {
      description
        "Unique key to identify group";
      uses PATH-WORK-GROUP-KEY;
    }
    container region-1 {
      description
        "First region of the group";
      uses PATH-WORK-REGION;
    }
    container region-2 {
      description
        "Second region of the group";
      uses PATH-WORK-REGION;
    }
    container stats {
      description
        "Group statistics";
      uses PATH-WORK-GROUP-STATS;
    }
    leaf works-count {
      type uint64;
      description
        "Number of works in this group";
    }
    leaf worker-past-region1 {
      type boolean;
      description
        "Is the worker past region_1";
    }
  }

  grouping PCE-ASSO-LSP-INFO {
    description
      "Association LSP common information";
    container pcc-address {
      description
        "PCC address";
      uses PCE-IP-ADDR-TYPE;
    }
    leaf tunnel-id {
      type uint32;
      description
        "Tunnel ID";
    }
    leaf lspid {
      type uint32;
      description
        "LSP ID";
    }
    leaf tunnel-name {
      type string;
      description
        "Tunnel Name";
    }
    leaf pce-based {
      type boolean;
      description
        "PCE Based";
    }
    leaf plsp-id {
      type uint32;
      description
        "PLSP ID";
    }
  }

  grouping PCE-ASSO-BAG {
    description
      "PCE Association information";
    container association-source {
      description
        "Association Source";
      uses PCE-IP-ADDR-TYPE;
    }
    leaf association-type {
      type uint32;
      description
        "Association Type";
    }
    leaf association-id {
      type uint32;
      description
        "Association ID";
    }
    leaf strict {
      type boolean;
      description
        "Association Strict Mode";
    }
    leaf status {
      type uint32;
      description
        "Association Status";
    }
    leaf headends-swapped {
      type uint32;
      description
        "Headends Swapped";
    }
    list association-lsp {
      description
        "Association LSP Info";
      uses PCE-ASSO-LSP-INFO;
    }
  }

  grouping CMN-TRACE-BUFFER-SUMMARY-BAG {
    description
      "Trace buffer summary";
    leaf trace-buffer-name {
      type string;
      description
        "Name of trace buffer";
    }
    leaf unique-trace-count {
      type uint32;
      description
        "Unique trace count";
    }
    leaf wrapping-trace-count-default {
      type uint32;
      description
        "Default value of wrapping trace count";
    }
    leaf wrapping-trace-count-programmed {
      type uint32;
      description
        "Programmed value of wrapping trace count";
    }
    leaf string-buffer-size-default {
      type uint32;
      units "byte";
      description
        "Default string buffer size for wrapping traces
         in bytes";
    }
    leaf string-buffer-size-programmed {
      type uint32;
      units "byte";
      description
        "Programmed string buffer size for wrapping
         traces in bytes";
    }
  }

  grouping PATH-WORK-NODE {
    description
      "Path work node";
    leaf type {
      type Path-work-node;
      description
        "Node type";
    }
    leaf repr {
      type string;
      description
        "String representation";
    }
  }

  grouping PCE-PEER-PROTO-SUMMARY-BAG {
    description
      "Peer summary for specified protocol";
    leaf peer-count-up {
      type uint32;
      description
        "Number of peers in up state";
    }
    leaf peer-count-down {
      type uint32;
      description
        "Number of peers in down state";
    }
    leaf peer-count-all {
      type uint32;
      description
        "Number of all peers";
    }
  }

  grouping PCE-PEER-SUMMARY-BAG {
    description
      "Peer summary information";
    container pcep-peers {
      description
        "PCEP peers summary information";
      uses PCE-PEER-PROTO-SUMMARY-BAG;
    }
  }

  grouping PCE-TREESID-HOP-BAG {
    description
      "TreeSID hop information";
    leaf next-hop-address {
      type inet:ipv4-address;
      description
        "Next hop remote address";
    }
    leaf next-hop-label {
      type uint32;
      description
        "Next hop outgoing label";
    }
    leaf next-hop-node-address {
      type inet:ipv4-address;
      description
        "Next hop node address";
    }
    leaf stale {
      type boolean;
      description
        "Stale hop; will be removed in next update";
    }
    leaf central-control-identifier {
      type uint32;
      description
        "Identifier for Central Control instructions";
    }
  }

  grouping PCE-TREESID-NODE-BAG {
    description
      "TreeSID node information";
    leaf prefix-address {
      type inet:ipv4-address;
      description
        "Node prefix address";
    }
    leaf name {
      type string;
      description
        "Node name";
    }
    leaf role {
      type Pce-treesid-role;
      description
        "Node role";
    }
    leaf awaiting-report {
      type boolean;
      description
        "Awaiting report";
    }
    leaf stale {
      type boolean;
      description
        "Stale node";
    }
    list next-hop {
      description
        "Next hops";
      uses PCE-TREESID-HOP-BAG;
    }
  }

  grouping PCE-TREESID-BAG {
    description
      "TreeSID information";
    leaf name-xr {
      type string;
      description
        "Name of the TreeSID";
    }
    leaf error {
      type string;
      description
        "Last path computation error";
    }
    leaf label {
      type uint32;
      description
        "SID of the TreeSID";
    }
    leaf source-address {
      type inet:ipv4-address;
      description
        "Address of the source node";
    }
    leaf operational-state {
      type boolean;
      description
        "Operational state";
    }
    leaf administrative-state {
      type boolean;
      description
        "Administrative state";
    }
    leaf state {
      type Pce-treesid-state;
      description
        "State of the TreeSID (ie, pending operation)";
    }
    leaf uptime {
      type uint32;
      units "second";
      description
        "Uptime of the tunnel in seconds";
    }
    leaf transition-count {
      type uint32;
      description
        "Number of transitions between operational
         up/down";
    }
    leaf-list destination-address {
      type inet:ipv4-address;
      description
        "List of destination addresses";
    }
    list nodes {
      description
        "List of nodes associated with this TreeSID";
      uses PCE-TREESID-NODE-BAG;
    }
    list event {
      description
        "Events";
      uses PCE-EVENT-INFO;
    }
  }

  grouping PCE-SR-MPLS-PATH-BAG {
    description
      "PCE SR path information";
    container source {
      description
        "Source of path";
      uses PCE-IP-ADDR-TYPE;
    }
    container destination {
      description
        "Destination of path";
      uses PCE-IP-ADDR-TYPE;
    }
    leaf cost {
      type uint64;
      description
        "Cost";
    }
    list hops {
      description
        "SR hops";
      uses PCE-SR-HOP-TYPE;
    }
  }

  grouping PCE-SR-MPLS-PATH-LIST-BAG {
    description
      "PCE SR MPLS path list";
    leaf cspf-result {
      type Pce-cspf-rc;
      description
        "Result of the computation";
    }
    leaf iterations-done {
      type uint32;
      description
        "Iterations performed of the Suurballe-Tarjan
         algorithm";
    }
    list output-path {
      description
        "Output SR MPLS paths";
      uses PCE-SR-MPLS-PATH-BAG;
    }
  }

  grouping PCE-PFX-ENTRY {
    description
      "PCE prefix etnry";
    container ip {
      description
        "Prefix IP address";
      uses PCE-IP-ADDR-TYPE;
    }
  }

  grouping PCE-PFX-BAG {
    description
      "PCE Prefix Information";
    container node-protocol-identifier {
      description
        "Node protocol identifier";
      uses PCE-NODE-PID-BAG;
    }
    leaf node-identifier-xr {
      type uint32;
      description
        "Node identifier";
    }
    list address {
      description
        "Prefix address";
      uses PCE-PFX-ENTRY;
    }
  }

  grouping CMN-TIMER-INFO {
    description
      "Timer information";
    leaf running {
      type boolean;
      description
        "Whether the timer is running";
    }
    leaf remaining-seconds {
      type int64;
      units "second";
      description
        "Number of remaining seconds";
    }
    leaf remaining-nano-seconds {
      type int64;
      units "nanosecond";
      description
        "Number of remaining nanoseconds";
    }
  }

  grouping XTC-TOPO-READY-BAG {
    description
      "XTC Topology Readiness Information";
    container timer {
      description
        "Topology readiness timer";
      uses CMN-TIMER-INFO;
    }
    leaf ready {
      type boolean;
      description
        "Topology readiness";
    }
    leaf pcep-allowed {
      type boolean;
      description
        "Whether PCEP is allowed";
    }
    leaf ha-case {
      type Cmn-ha-case;
      description
        "Last HA case";
    }
    leaf timer-value {
      type uint32;
      description
        "Topology ready timer value selected at start";
    }
  }

  grouping PCE-TOPO-STATS-BAG {
    description
      "Statistics on topology update";
    leaf num-nodes-added {
      type uint32;
      description
        "Number of nodes added";
    }
    leaf num-nodes-deleted {
      type uint32;
      description
        "Number of nodes deleted";
    }
    leaf num-links-added {
      type uint32;
      description
        "Number of links added";
    }
    leaf num-links-deleted {
      type uint32;
      description
        "Number of links deleted";
    }
    leaf num-prefixes-added {
      type uint32;
      description
        "Number of prefixes added";
    }
    leaf num-prefixes-deleted {
      type uint32;
      description
        "Number of prefixes deleted";
    }
  }

  grouping PCE-NODE-SUMMARY-BAG {
    description
      "PCE Node Summary Information";
    container stats-topology-update {
      description
        "Statistics on topology update";
      uses PCE-TOPO-STATS-BAG;
    }
    container topology-ready-summary {
      description
        "Topology ready summary";
      uses XTC-TOPO-READY-BAG;
    }
    leaf nodes {
      type uint32;
      description
        "Number of PCE nodes";
    }
    leaf lookup-nodes {
      type uint32;
      description
        "Number of lookup nodes";
    }
    leaf prefixes {
      type uint32;
      description
        "Number of prefixes";
    }
    leaf prefix-sids {
      type uint32;
      description
        "Number of total prefix SIDs";
    }
    leaf regular-prefix-sids {
      type uint32;
      description
        "Number of reguar prefix SIDs";
    }
    leaf strict-prefix-sids {
      type uint32;
      description
        "Number of strict prefix SIDs";
    }
    leaf links {
      type uint32;
      description
        "Number of links";
    }
    leaf epe-links {
      type uint32;
      description
        "Number of EPE links";
    }
    leaf adjacency-sids {
      type uint32;
      description
        "Number of total adjacency SIDs";
    }
    leaf epesids {
      type uint32;
      description
        "Number of total EPE SIDs";
    }
    leaf protected-adjacency-sids {
      type uint32;
      description
        "Number of protected adjacency SIDs";
    }
    leaf un-protected-adjacency-sids {
      type uint32;
      description
        "Number of unprotected adjacency SIDs";
    }
    leaf topology-consistent {
      type boolean;
      description
        "True if topology is consistent";
    }
  }

  grouping PCE-IPV6-LINK-BAG {
    description
      "PCE IPv6 Link Information";
    container local-igp-information {
      description
        "Local node IGP information";
      uses PCE-IGP-INFO-BAG;
    }
    container remote-node-protocol-identifier {
      description
        "Remote node protocol identifier";
      uses PCE-NODE-PID-BAG;
    }
    leaf local-ipv6-address {
      type inet:ipv6-address;
      description
        "Local IPv6 address";
    }
    leaf remote-ipv6-address {
      type inet:ipv6-address;
      description
        "Remote IPv6 address";
    }
    leaf igp-metric {
      type uint32;
      description
        "IGP Metric";
    }
    leaf te-metric {
      type uint32;
      description
        "TE Metric";
    }
    leaf maximum-link-bandwidth {
      type uint64;
      description
        "Max link bandwidth";
    }
    leaf max-reservable-bandwidth {
      type uint64;
      description
        "Max Reservable bandwidth";
    }
    list adjacency-sid {
      description
        "Adjacency SIDs";
      uses PCE-SID-BAG;
    }
  }

  grouping PCE-LINK-PM-METRICS {
    description
      "Link performance metric information";
    leaf unidirectional-minimum-delay-microseconds {
      type uint32;
      units "microsecond";
      description
        "Min delay in microseconds";
    }
  }

  grouping PCE-IPV4-LINK-BAG {
    description
      "PCE IPv4 Link Information";
    container local-igp-information {
      description
        "Local node IGP information";
      uses PCE-IGP-INFO-BAG;
    }
    container remote-node-protocol-identifier {
      description
        "Remote node protocol identifier";
      uses PCE-NODE-PID-BAG;
    }
    container performance-metrics {
      description
        "Performance metrics";
      uses PCE-LINK-PM-METRICS;
    }
    leaf is-unnumbered {
      type boolean;
      description
        "True if this is an IPv4 Unnumbered link";
    }
    leaf local-interface-index {
      type uint32;
      description
        "Non-zero if IsUnnumbered is True";
    }
    leaf remote-interface-index {
      type uint32;
      description
        "Non-zero if IsUnnumbered is True";
    }
    leaf local-ipv4-address {
      type inet:ipv4-address;
      description
        "Local IPv4 address";
    }
    leaf remote-ipv4-address {
      type inet:ipv4-address;
      description
        "Remote IPv4 address";
    }
    leaf igp-metric {
      type uint32;
      description
        "IGP Metric";
    }
    leaf te-metric {
      type uint32;
      description
        "TE Metric";
    }
    leaf maximum-link-bandwidth {
      type uint64;
      description
        "Max link bandwidth";
    }
    leaf max-reservable-bandwidth {
      type uint64;
      description
        "Max Reservable bandwidth";
    }
    leaf administrative-groups {
      type uint32;
      description
        "Link admin-groups";
    }
    leaf-list srlgs {
      type uint32;
      description
        "SRLG Values";
    }
    list adjacency-sid {
      description
        "Adjacency SIDs";
      uses PCE-SID-BAG;
    }
  }

  grouping PCE-SID-BAG {
    description
      "PCE SID bags";
    container sid-prefix {
      description
        "Prefix";
      uses PCE-IP-ADDR-TYPE;
    }
    leaf sid-type {
      type Sid;
      description
        "SID Type";
    }
    leaf mpls-label {
      type uint32;
      description
        "MPLS Label";
    }
    leaf rflag {
      type boolean;
      description
        "R Flag";
    }
    leaf nflag {
      type boolean;
      description
        "N Flag";
    }
    leaf pflag {
      type boolean;
      description
        "P Flag";
    }
    leaf eflag {
      type boolean;
      description
        "E Flag";
    }
    leaf vflag {
      type boolean;
      description
        "V Flag";
    }
    leaf lflag {
      type boolean;
      description
        "L Flag";
    }
  }

  grouping PCE-PREFIX-BAG {
    description
      "PCE Prefix bag";
    container pfx-sid {
      description
        "Prefix SID";
      uses PCE-SID-BAG;
    }
    container node-id {
      description
        "Link-state node identifier";
      uses PCE-NODE-ID-BAG;
    }
    leaf domain-identifier {
      type uint64;
      description
        "Domain identifier";
    }
  }

  grouping PCE-SRGB-INFO-BAG {
    description
      "PCE SRGB information bag";
    container node-id {
      description
        "Link-state node identifier";
      uses PCE-NODE-ID-BAG;
    }
    leaf start {
      type uint32;
      description
        "SRGB start";
    }
    leaf size {
      type uint32;
      description
        "SRGB size";
    }
    leaf domain-identifier {
      type uint64;
      description
        "Domain identifier";
    }
  }

  grouping PCE-IGP-INFO-BGP {
    description
      "PCE BGP Information";
    leaf router-id {
      type Pce-ipv4-address;
      description
        "BGP router ID";
    }
    leaf confed-asn {
      type uint32;
      description
        "Confederation ASN";
    }
  }

  grouping PCE-IGP-INFO-OSPF {
    description
      "PCE OSPF Information";
    leaf router-id {
      type Pce-ipv4-address;
      description
        "OSPF router ID";
    }
    leaf area {
      type uint32;
      description
        "OSPF area";
    }
  }

  grouping PCE-IGP-INFO-ISIS {
    description
      "PCE ISIS Information";
    leaf system-id {
      type string;
      description
        "ISIS system ID";
    }
    leaf level {
      type uint32;
      description
        "ISIS level";
    }
    leaf area {
      type string;
      description
        "ISIS area";
    }
  }

  grouping PCE-IGP-INFO-TYPE {
    description
      "PCE IGP INFO TYPE";
    container isis {
      when "../igp-id = 'isis'" {
        description
          "../IGP_ID = 'ISIS'";
      }
      description
        "ISIS information";
      uses PCE-IGP-INFO-ISIS;
    }
    container ospf {
      when "../igp-id = 'ospf'" {
        description
          "../IGP_ID = 'OSPF'";
      }
      description
        "OSPF information";
      uses PCE-IGP-INFO-OSPF;
    }
    container bgp {
      when "../igp-id = 'bgp'" {
        description
          "../IGP_ID = 'BGP'";
      }
      description
        "BGP information";
      uses PCE-IGP-INFO-BGP;
    }
    leaf igp-id {
      type Pce-igp-info-id;
      description
        "IGP ID";
    }
  }

  grouping PCE-NODE-ID-BAG {
    description
      "PCE Node ID information";
    container igp {
      description
        "IGP-specific information";
      uses PCE-IGP-INFO-TYPE;
    }
    leaf autonomous-system-number {
      type uint32;
      description
        "Autonomous System Number";
    }
    leaf ls-identifier {
      type uint32;
      description
        "Link-State identifier";
    }
  }

  grouping PCE-IGP-INFO-BAG {
    description
      "PCE IGP information bag";
    container node-id {
      description
        "Link-state node identifier";
      uses PCE-NODE-ID-BAG;
    }
    leaf domain-identifier {
      type uint64;
      description
        "Domain identifier";
    }
  }

  grouping PCE-NODE-PID-BAG {
    description
      "PCE Node Protocol Identifier Information";
    leaf node-name {
      type string;
      description
        "Node Name";
    }
    leaf ipv4-bgp-router-id-set {
      type boolean;
      description
        "True if IPv4 BGP router ID is set";
    }
    leaf ipv4-bgp-router-id {
      type inet:ipv4-address;
      description
        "IPv4 TE router ID";
    }
    leaf ipv4te-router-id-set {
      type boolean;
      description
        "True if IPv4 TE router ID is set";
    }
    leaf ipv4te-router-id {
      type inet:ipv4-address;
      description
        "IPv4 BGP router ID";
    }
    list igp-information {
      description
        "IGP information";
      uses PCE-IGP-INFO-BAG;
    }
    list srgb-information {
      description
        "SRGB information";
      uses PCE-SRGB-INFO-BAG;
    }
  }

  grouping PCE-XTC-NODE-BAG {
    description
      "PCE XTC Node Information";
    container node-protocol-identifier {
      description
        "Node protocol identifier";
      uses PCE-NODE-PID-BAG;
    }
    leaf node-identifier-xr {
      type uint32;
      description
        "Node identifier";
    }
    leaf overload {
      type boolean;
      description
        "Node Overload Bit";
    }
    list prefixe {
      description
        "Prefixes";
      uses PCE-PREFIX-BAG;
    }
    list ipv4-link {
      description
        "IPv4 Link information";
      uses PCE-IPV4-LINK-BAG;
    }
    list ipv6-link {
      description
        "IPv6 Link information";
      uses PCE-IPV6-LINK-BAG;
    }
  }

  grouping PCE-PEER-BAG {
    description
      "Peer information";
    container peer-address-xr {
      description
        "Peer address";
      uses PCE-IP-ADDR-TYPE;
    }
    container brief-pcep-information {
      description
        "PCE protocol information";
      uses PCE-PCEP-BAG;
    }
    leaf peer-protocol {
      type Pce-proto;
      description
        "Protocol between PCE and peer";
    }
  }

  grouping PCE-PCEP-ERROR-BAG {
    description
      "PCEP Error information";
    leaf pc-error-type {
      type uint8;
      description
        "PCEP Error type";
    }
    leaf pc-error-value {
      type uint8;
      description
        "PCEP Error Value";
    }
  }

  grouping PCE-PCEP-BAG {
    description
      "PCEP information";
    leaf pcep-state {
      type Pcep-state;
      description
        "PCEP State";
    }
    leaf stateful {
      type boolean;
      description
        "Stateful";
    }
    leaf capability-update {
      type boolean;
      description
        "Update capability";
    }
    leaf capability-instantiate {
      type boolean;
      description
        "Instantiation capability";
    }
    leaf capability-segment-routing {
      type boolean;
      description
        "Segment Routing capability";
    }
    leaf capability-triggered-sync {
      type boolean;
      description
        "Triggered Synchronization capability";
    }
    leaf capability-db-version {
      type boolean;
      description
        "DB version capability";
    }
    leaf capability-delta-sync {
      type boolean;
      description
        "Delta Synchronization capability";
    }
  }

  grouping PCE-PCEP-DETAIL-BAG {
    description
      "Detailed PCE protocol information";
    container brief-pcep-information {
      description
        "Brief PCE protocol information";
      uses PCE-PCEP-BAG;
    }
    container last-error-rx {
      description
        "Last PCError received";
      uses PCE-PCEP-ERROR-BAG;
    }
    container last-error-tx {
      description
        "Last PCError sent";
      uses PCE-PCEP-ERROR-BAG;
    }
    leaf error {
      type string;
      description
        "Error (for display only)";
    }
    leaf speaker-id {
      type string;
      description
        "Speaker Entity ID";
    }
    leaf pcep-up-time {
      type uint32;
      description
        "PCEP Up Time";
    }
    leaf keepalives {
      type uint32;
      description
        "Keepalive count";
    }
    leaf md5-enabled {
      type boolean;
      description
        "MD5 Authentication Enabled";
    }
    leaf keychain-enabled {
      type boolean;
      description
        "Keychain based Authentication Enabled";
    }
    leaf negotiated-local-keepalive {
      type uint32;
      description
        "Negotiated KA";
    }
    leaf negotiated-remote-keepalive {
      type uint32;
      description
        "Negotiated KA";
    }
    leaf negotiated-dead-time {
      type uint32;
      description
        "Negotiated DT";
    }
    leaf pce-request-rx {
      type uint32;
      description
        "PCEReq Rx";
    }
    leaf pce-request-tx {
      type uint32;
      description
        "PCEReq Tx";
    }
    leaf pce-reply-rx {
      type uint32;
      description
        "PCERep Rx";
    }
    leaf pce-reply-tx {
      type uint32;
      description
        "PCERep Tx";
    }
    leaf pce-error-rx {
      type uint32;
      description
        "PCEErr Rx";
    }
    leaf pce-error-tx {
      type uint32;
      description
        "PCEErr Tx";
    }
    leaf pce-open-tx {
      type uint32;
      description
        "PCEOpen Tx";
    }
    leaf pce-open-rx {
      type uint32;
      description
        "PCEOpen Rx";
    }
    leaf pce-report-rx {
      type uint32;
      description
        "PCERpt Rx";
    }
    leaf pce-report-tx {
      type uint32;
      description
        "PCERpt Tx";
    }
    leaf pce-update-rx {
      type uint32;
      description
        "PCEUpd Rx";
    }
    leaf pce-update-tx {
      type uint32;
      description
        "PCEUpd Tx";
    }
    leaf pce-initiate-rx {
      type uint32;
      description
        "PCEInit Rx";
    }
    leaf pce-initiate-tx {
      type uint32;
      description
        "PCEInit Tx";
    }
    leaf pce-keepalive-tx {
      type uint64;
      description
        "PCE Keepalive Tx";
    }
    leaf pce-keepalive-rx {
      type uint64;
      description
        "PCE Keepalive Rx";
    }
    leaf local-session-id {
      type uint8;
      description
        "Local PCEP session ID";
    }
    leaf remote-session-id {
      type uint8;
      description
        "Remote PCEP session ID";
    }
    leaf minimum-keepalive-interval {
      type uint8;
      description
        "Minimum keepalive interval for the peer";
    }
    leaf maximum-dead-interval {
      type uint8;
      description
        "Maximum dead interval for the peer";
    }
    leaf max-sid-depth {
      type uint8;
      description
        "Maximum number of labels the peer can impose";
    }
  }

  grouping PCE-PEER-DETAIL-BAG {
    description
      "Detailed PCEP peer information";
    container peer-address-xr {
      description
        "Peer address";
      uses PCE-IP-ADDR-TYPE;
    }
    container detail-pcep-information {
      description
        "Detailed PCE protocol information";
      uses PCE-PCEP-DETAIL-BAG;
    }
    leaf peer-protocol {
      type Pce-proto;
      description
        "Protocol between PCE and peer";
    }
    leaf max-sid-depth {
      type uint32;
      description
        "Maximum SID Depth";
    }
  }

  grouping PCE-EVENT-INFO {
    description
      "PCE Event information";
    leaf event-id {
      type uint32;
      description
        "Event ID in range 1 - 0xFFFFFFFF. 0 is invalid.";
    }
    leaf event-message {
      type string;
      description
        "Event message";
    }
    leaf time-stamp {
      type uint64;
      description
        "Event time, relative to Jan 1, 1970";
    }
  }

  grouping PCE-EVENT-BAG {
    description
      "Private LSP information";
    list event-buffer {
      description
        "LSP Event buffer";
      uses PCE-EVENT-INFO;
    }
  }

  grouping PCE-LSPA-INFO {
    description
      "PCE LSP attribute information";
    leaf affinity-exclude-any {
      type uint32;
      description
        "Affinity exclude any";
    }
    leaf affinity-include-any {
      type uint32;
      description
        "Affinity include any";
    }
    leaf affinity-include-all {
      type uint32;
      description
        "Affinity include all";
    }
    leaf setup-priority {
      type uint8;
      description
        "Setup Priority";
    }
    leaf hold-priority {
      type uint8;
      description
        "Hold Priority";
    }
    leaf local-protection {
      type boolean;
      description
        "True, if local protection is desired";
    }
  }

  grouping PCE-ASSO-INFO {
    description
      "PCE LSP association information";
    container association-source {
      description
        "Association Source";
      uses PCE-IP-ADDR-TYPE;
    }
    leaf association-type {
      type uint32;
      description
        "Association Type";
    }
    leaf association-id {
      type uint32;
      description
        "Association ID";
    }
  }

  grouping PCE-LSP-RSVP-ERROR-BAG {
    description
      "RSVP error information";
    leaf node-address {
      type inet:ipv4-address;
      description
        "RSVP error node address";
    }
    leaf error-flags {
      type uint8;
      description
        "RSVP error flags";
    }
    leaf error-code {
      type uint8;
      description
        "RSVP error code";
    }
    leaf error-value {
      type uint16;
      description
        "RSVP error value";
    }
  }

  grouping PCE-PCEP-INFO {
    description
      "PCEP LSP information";
    container rsvp-error {
      description
        "RSVP error info";
      uses PCE-LSP-RSVP-ERROR-BAG;
    }
    leaf pcepid {
      type uint32;
      description
        "PCE protocol identifier";
    }
    leaf pcep-flag-d {
      type boolean;
      description
        "PCEP LSP delegation flag";
    }
    leaf pcep-flag-s {
      type boolean;
      description
        "PCEP LSP state-sync flag";
    }
    leaf pcep-flag-r {
      type boolean;
      description
        "PCEP LSP remove flag";
    }
    leaf pcep-flag-a {
      type boolean;
      description
        "PCEP LSP admin flag";
    }
    leaf pcep-flag-o {
      type uint8;
      description
        "PCEP LSP operation flag";
    }
    leaf pcep-flag-c {
      type uint8;
      description
        "PCEP LSP initiated flag";
    }
  }

  grouping PCE-RRO-INFO {
    description
      "RRO information";
    container sr-rro {
      description
        "Segment Routing RRO info";
      uses PCE-SR-HOP-TYPE;
    }
    leaf rro-type {
      type Pce-rro;
      description
        "RRO Type";
    }
    leaf ipv4-address {
      type inet:ipv4-address;
      description
        "IPv4 address of RRO";
    }
    leaf mpls-label {
      type uint32;
      description
        "MPLS label of RRO";
    }
    leaf flags {
      type uint8;
      description
        "RRO Flags";
    }
  }

  grouping PCE-SR-HOP-TYPE {
    description
      "SR hop type";
    container local-addr {
      description
        "Local Address";
      uses PCE-IP-ADDR-TYPE;
    }
    container remote-addr {
      description
        "Remote Address";
      uses PCE-IP-ADDR-TYPE;
    }
    leaf sid-type {
      type Pce-sr-sid;
      description
        "SID type";
    }
    leaf mpls-label {
      type uint32;
      description
        "Label";
    }
    leaf local-interface-index {
      type uint32;
      description
        "SNMP index of the upstream interface of this hop";
    }
    leaf remote-interface-index {
      type uint32;
      description
        "SNMP index of the downstream interface of this
         hop";
    }
  }

  grouping PCE-RSVP-HOP-TYPE {
    description
      "RSVP hop type";
    leaf hop-address {
      type inet:ipv4-address;
      description
        "RSVP hop address";
    }
    leaf loose {
      type boolean;
      description
        "Loose hop";
    }
  }

  grouping PCE-ERO-INFO {
    description
      "ERO information";
    leaf reported-metric-type {
      type uint32;
      description
        "Reported Metric Type";
    }
    leaf reported-metric-value {
      type uint32;
      description
        "Reported Metric Value";
    }
    leaf computed-metric-type {
      type uint32;
      description
        "Computed Metric Type";
    }
    leaf computed-metric-value {
      type uint32;
      description
        "Computed Metric Value";
    }
    leaf computed-hop-list-time {
      type uint32;
      description
        "Computed Hop List Time";
    }
    list reported-rsvp-path {
      description
        "Reported RSVP path";
      uses PCE-RSVP-HOP-TYPE;
    }
    list reported-sr-path {
      description
        "Reported SR path";
      uses PCE-SR-HOP-TYPE;
    }
    list computed-rsvp-path {
      description
        "Computed RSVP path";
      uses PCE-RSVP-HOP-TYPE;
    }
    list computed-sr-path {
      description
        "Computed SR path";
      uses PCE-SR-HOP-TYPE;
    }
  }

  grouping PCE-LSP-DETAIL-INFO {
    description
      "Detailed LSP information";
    container brief-lsp-information {
      description
        "Brief LSP information";
      uses PCE-LSP-INFO;
    }
    container er-os {
      description
        "Paths";
      uses PCE-ERO-INFO;
    }
    container lsppcep-information {
      description
        "PCEP related LSP information";
      uses PCE-PCEP-INFO;
    }
    container lsp-association-info {
      description
        "LSP association information";
      uses PCE-ASSO-INFO;
    }
    container lsp-attributes {
      description
        "LSP attributes";
      uses PCE-LSPA-INFO;
    }
    container sub-delegated-pce {
      description
        "Sub delegated PCE";
      uses PCE-IP-ADDR-TYPE;
    }
    container state-sync-pce {
      description
        "State-sync PCE";
      uses PCE-IP-ADDR-TYPE;
    }
    container reporting-pcc-address {
      description
        "Reporting PCC address";
      uses PCE-IP-ADDR-TYPE;
    }
    leaf signaled-bandwidth-specified {
      type boolean;
      description
        "True if router notifies signal bandwidth";
    }
    leaf signaled-bandwidth {
      type uint64;
      description
        "Signaled Bandwidth";
    }
    leaf actual-bandwidth-specified {
      type boolean;
      description
        "True if router notifies actual bandwidth";
    }
    leaf actual-bandwidth {
      type uint64;
      description
        "Actual bandwidth utilized in the data-plane";
    }
    leaf lsp-role {
      type uint32;
      description
        "LSP Role";
    }
    leaf computing-pce {
      type uint32;
      description
        "Computing PCE";
    }
    leaf preference {
      type uint32;
      description
        "Preference";
    }
    leaf-list srlg-info {
      type uint32;
      description
        "List of SLRGs used by LSP";
    }
    list rro {
      description
        "RRO";
      uses PCE-RRO-INFO;
    }
  }

  grouping PCE-TUN-DETAIL-BAG {
    description
      "Tunnel detail information";
    container pcc-address {
      description
        "PCC address";
      uses PCE-IP-ADDR-TYPE;
    }
    container private-lsp-information {
      description
        "Private LSP information";
      uses PCE-EVENT-BAG;
    }
    leaf tunnel-name-xr {
      type string;
      description
        "Tunnel Name";
    }
    leaf xtc-controlled {
      type boolean;
      description
        "Allow XTC reoptimizations";
    }
    leaf color {
      type uint32;
      description
        "Color";
    }
    leaf interface-name {
      type string;
      description
        "Interface name";
    }
    leaf profile-id {
      type uint16;
      description
        "Profile ID";
    }
    list detail-lsp-information {
      description
        "Detail LSP information";
      uses PCE-LSP-DETAIL-INFO;
    }
  }

  grouping PCE-LSP-COUNTS-BAG {
    description
      "Number of LSPs";
    leaf all-ls-ps {
      type uint32;
      description
        "Number of all LSPs";
    }
    leaf up-ls-ps {
      type uint32;
      description
        "Number of operational LSPs";
    }
    leaf admin-up-ls-ps {
      type uint32;
      description
        "Number of administratively up LSPs";
    }
    leaf sr-ls-ps {
      type uint32;
      description
        "Number of LSPs with Segment routing setup type";
    }
    leaf rsvp-ls-ps {
      type uint32;
      description
        "Number of LSPs with RSVP setup type";
    }
  }

  grouping PCE-LSP-PER-PEER-SUMMARY-BAG {
    description
      "Number of LSPs for specific peer";
    container lsp-summary {
      description
        "Number of LSPs for specific peer";
      uses PCE-LSP-COUNTS-BAG;
    }
    container peer-address {
      description
        "Peer address";
      uses PCE-IP-ADDR-TYPE;
    }
  }

  grouping PCE-LSP-SUMMARY-BAG {
    description
      "PCE LSP summary information";
    container all-ls-ps {
      description
        "Summary for all peers";
      uses PCE-LSP-COUNTS-BAG;
    }
    list peer-ls-ps-info {
      description
        "Number of LSPs for specific peer";
      uses PCE-LSP-PER-PEER-SUMMARY-BAG;
    }
  }

  grouping PCE-LSP-INFO {
    description
      "LSP common information";
    container source-address {
      description
        "Source address";
      uses PCE-IP-ADDR-TYPE;
    }
    container destination-address {
      description
        "Destination address";
      uses PCE-IP-ADDR-TYPE;
    }
    leaf tunnel-id {
      type uint32;
      description
        "Tunnel ID";
    }
    leaf lspid {
      type uint32;
      description
        "LSP ID";
    }
    leaf binding-sid {
      type uint32;
      description
        "Binding SID";
    }
    leaf lsp-setup-type {
      type Lsp-setup;
      description
        "LSP Setup Type";
    }
    leaf operational-state {
      type Pcep-lsp-state;
      description
        "Operational state";
    }
    leaf administrative-state {
      type Lsp-state;
      description
        "Administrative state";
    }
    leaf msd {
      type uint32;
      description
        "Maximum SID Depth";
    }
    leaf absolute-margin {
      type uint32;
      description
        "Absolute Margin";
    }
    leaf relative-margin {
      type uint32;
      description
        "Relative Margin";
    }
    leaf igp-bound {
      type uint32;
      description
        "IGP Metric Bound";
    }
    leaf te-bound {
      type uint32;
      description
        "TE Metric Bound";
    }
    leaf latency-bound {
      type uint32;
      description
        "Latency Metric Bound";
    }
    leaf hop-count-bound {
      type uint32;
      description
        "HopCount Metric Bound";
    }
    leaf anycast-sid-inclusion {
      type uint32;
      description
        "Anycast SID Inclusion";
    }
  }

  grouping PCE-IP-ADDR-TYPE {
    description
      "PCE IP ADDR TYPE";
    leaf af-name {
      type Pce-af-id;
      description
        "AFName";
    }
    leaf ipv4 {
      when "../af-name = 'ipv4'" {
        description
          "../AFName = 'IPv4'";
      }
      type Pce-ipv4-address;
      description
        "IPv4 address type";
    }
    leaf ipv6 {
      when "../af-name = 'ipv6'" {
        description
          "../AFName = 'IPv6'";
      }
      type Pce-ipv6-address;
      description
        "IPv6 address type";
    }
  }

  grouping PCE-TUN-BAG {
    description
      "Tunnel information";
    container pcc-address {
      description
        "PCC address";
      uses PCE-IP-ADDR-TYPE;
    }
    leaf tunnel-name-xr {
      type string;
      description
        "Tunnel Name";
    }
    list brief-lsp-information {
      description
        "Brief LSP information";
      uses PCE-LSP-INFO;
    }
  }
}
