module Cisco-IOS-XR-infra-fti-cfg {
  namespace "http://cisco.com/ns/yang/Cisco-IOS-XR-infra-fti-cfg";
  prefix infra-fti-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-fti package configuration.
     
     This module contains definitions
     for the following management objects:
       dci-fabric-interconnect: Configure FTI
         parameters/sub-parameters
     
     Copyright (c) 2013-2019 by Cisco Systems, Inc.
     All rights reserved.";

  revision 2019-04-05 {
    description
      "Establish semantic version baseline.";
    semver:module-version "1.0.1";
  }
  revision 2017-11-13 {
    description
      "Initial Revision.";
  }
  revision 2015-11-09 {
    description
      "IOS XR 6.0 revision.";
  }

  container dci-fabric-interconnect {
    description
      "Configure FTI parameters/sub-parameters";
    container fabrics {
      description
        "Configure fabric parameters";
      list fabric {
        key "id1";
        description
          "Enter fabric identifier";
        container controllers {
          description
            "Enter Opflex peer info";
          list controller {
            key "ip1";
            description
              "Enter Spine IP address";
            leaf ip1 {
              type inet:ipv4-address-no-zone;
              description
                "Enter Spine IP address";
            }
          }
        }
        leaf ssl {
          type string;
          description
            "Disabled or Path to certificate";
        }
        leaf id1 {
          type uint32 {
            range "1000..9999";
          }
          description
            "fabric identifier";
        }
      }
    }
    container acp {
      description
        "Configure Auto Config Pool parameters";
      container bd-range {
        description
          "Specify BD pool range";
        leaf bd-min {
          type uint32 {
            range "1..4000";
          }
          description
            "BD Range:min value";
        }
        leaf bd-max {
          type uint32;
          description
            "BD Range:max value";
        }
      }
      container vni-range {
        description
          "Specify VNI pool range";
        leaf vni-min {
          type uint32 {
            range "1..4000";
          }
          description
            "VNI Range:min value";
        }
        leaf vni-max {
          type uint32;
          description
            "VNI Range:max value";
        }
      }
      container bvi-range {
        description
          "Specify BVI pool range";
        leaf bvi-min {
          type uint32 {
            range "1..4000";
          }
          description
            "BVI Range:min value";
        }
        leaf bvi-max {
          type uint32;
          description
            "BVI Range:max value";
        }
      }
      container vrfs {
        description
          "Configure local VRF parameters";
        list vrf {
          key "vrf-name";
          description
            "vrf name";
          leaf bvi-vrf-ip {
            type inet:ipv4-address-no-zone;
            description
              "BVI override IP address";
          }
          leaf vrf-name {
            type xr:Cisco-ios-xr-string;
            description
              "vrf name";
          }
        }
      }
      leaf nve-id {
        type uint32;
        description
          "Specify NVE interface id";
      }
      leaf bgp-as {
        type uint32;
        description
          "Specify BGP AS number";
      }
      leaf bg-name {
        type string;
        description
          "Specify Bridge-group name";
      }
    }
    leaf identity {
      type inet:ipv4-address-no-zone;
      description
        "Identity (Loopback IP address)<x.x.x.x>";
    }
  }
}
