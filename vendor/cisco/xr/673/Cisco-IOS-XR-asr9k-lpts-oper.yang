module Cisco-IOS-XR-asr9k-lpts-oper {
  namespace "http://cisco.com/ns/yang/Cisco-IOS-XR-asr9k-lpts-oper";
  prefix asr9k-lpts-oper;

  import Cisco-IOS-XR-types {
    prefix xr;
  }
  import cisco-semver {
    prefix semver;
  }
  include Cisco-IOS-XR-asr9k-lpts-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lpts package operational data.
     
     This module contains definitions
     for the following management objects:
       platform-lptsp-ifib-static: ASR9K platform ifib operational
         data
       platform-lptsp-ifib: ASR9K platform ifib operational data
       platform-lptsp-ifib-np-stats: ASR9K platform ifib operational
         data
     
     Copyright (c) 2013-2019 by Cisco Systems, Inc.
     All rights reserved.";

  revision 2019-04-05 {
    description
      "Establish semantic version baseline.";
    semver:module-version "3.0.0";
  }
  revision 2015-11-09 {
    description
      "IOS XR 6.0 revision.";
  }

  typedef Np-type-lpts {
    type string {
      pattern "(np0)|(np1)|(np2)|(np3)|(np4)|(np5)|(np6)|(np7)|(np8)|(np9)";
    }
    description
      "np0:NP0, np1:NP1, np2:NP2, np3:NP3, np4:NP4, np5
       :NP5, np6:NP6, np7:NP7, np8:NP8, np9:NP9";
  }

  container platform-lptsp-ifib-static {
    config false;
    description
      "ASR9K platform ifib operational data ";
    container node-statics {
      description
        "List of nodes with platform specific lpts
         operation data";
      list node-static {
        key "node-name";
        description
          "Node with platform specific lpts data";
        container police {
          description
            "pl_pifib police data";
          uses PL-PIFIB-SHOW-STATIC-POLICE;
        }
        container stats {
          description
            "pl_pifib stats";
          uses PL-PIFIB-SHOW-STATS;
        }
        leaf node-name {
          type xr:Node-id;
          description
            "Node name";
        }
      }
    }
  }
  container platform-lptsp-ifib {
    config false;
    description
      "ASR9K platform ifib operational data ";
    container nodes {
      description
        "List of nodes with platform specific lpts
         operation data";
      list node {
        key "node-name";
        description
          "Node with platform specific lpts data";
        container police {
          description
            "pl_pifib police data";
          uses PL-PIFIB-SHOW-POLICE;
        }
        container stats {
          description
            "pl_pifib stats";
          uses PL-PIFIB-SHOW-STATS;
        }
        leaf node-name {
          type xr:Node-id;
          description
            "Node name";
        }
      }
    }
  }
  container platform-lptsp-ifib-np-stats {
    config false;
    description
      "ASR9K platform ifib operational data ";
    container node-np-stats {
      description
        "List of nodes with platform specific lpts
         operation data";
      list node-np-stat {
        key "node-name";
        description
          "Node with platform specific lpts data";
        container nps {
          description
            "List of all NP";
          list np {
            key "np-name";
            description
              "np0 to np9";
            container np-police {
              description
                "pl_pifib police data";
              uses PL-PIFIB-SHOW-POLICE;
            }
            leaf np-name {
              type Np-type-lpts;
              description
                "NP name";
            }
          }
        }
        leaf node-name {
          type xr:Node-id;
          description
            "Node name";
        }
      }
    }
  }
}
