submodule Cisco-IOS-XR-segment-routing-srv6-oper-sub1 {
  belongs-to Cisco-IOS-XR-segment-routing-srv6-oper {
    prefix Cisco-IOS-XR-segment-routing-srv6-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR segment-routing-srv6 package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef Sid-state {
    type enumeration {
      enum "unknown" {
        description
          "Unknown";
      }
      enum "in-use" {
        description
          "In Use";
      }
      enum "pending" {
        description
          "Pending";
      }
      enum "stale" {
        description
          "Stale";
      }
    }
    description
      "SID manager SID state";
  }

  typedef Srv6-end-function {
    type enumeration {
      enum "unknown" {
        description
          "Unknown";
      }
      enum "end" {
        description
          "End (no PSP/USP)";
      }
      enum "end-with-psp" {
        description
          "End with PSP";
      }
      enum "end-with-usp" {
        description
          "End with USP";
      }
      enum "end-with-psp-usp" {
        description
          "End with PSP/USP";
      }
      enum "end-x" {
        description
          "End.X (no PSP/USP)";
      }
      enum "end-x-with-psp" {
        description
          "End.X with PSP";
      }
      enum "end-x-with-usp" {
        description
          "End.X with USP";
      }
      enum "end-x-with-psp-usp" {
        description
          "End.X with PSP/USP";
      }
      enum "end-tbl" {
        description
          "End.T (no PSP/USP)";
      }
      enum "end-tbl-with-psp" {
        description
          "End.T with PSP";
      }
      enum "end-tbl-with-usp" {
        description
          "End.T with USP";
      }
      enum "end-tbl-with-psp-usp" {
        description
          "End.T with PSP/USP";
      }
      enum "end-b6" {
        description
          "End.B6";
      }
      enum "end-b6-encaps" {
        description
          "End.B6.Encaps";
      }
      enum "end-bm" {
        description
          "End.BM";
      }
      enum "end-dx6" {
        description
          "End.DX6";
      }
      enum "end-dx4" {
        description
          "End.DX4";
      }
      enum "end-dt6" {
        description
          "End.DT6";
      }
      enum "end-dt4" {
        description
          "End.DT4";
      }
      enum "end-dt46" {
        description
          "End.DT46";
      }
      enum "end-dx2" {
        description
          "End.DX2";
      }
      enum "end-dx2v" {
        description
          "End.DX2V";
      }
      enum "end-dx2u" {
        description
          "End.DX2U";
      }
      enum "end-dx2m" {
        description
          "End.DX2M";
      }
      enum "end-otp" {
        description
          "End.OTP";
      }
      enum "end-op" {
        description
          "End.OP";
      }
      enum "end-s" {
        description
          "End.S";
      }
    }
    description
      "SRv6 End Function Type";
  }

  typedef Sid-allocation {
    type enumeration {
      enum "unknown" {
        description
          "Unknown";
      }
      enum "dynamic" {
        description
          "Dynamic";
      }
      enum "explicit" {
        description
          "Explicit";
      }
    }
    description
      "SID allocation type";
  }

  typedef Srv6-out-of-resource-state {
    type enumeration {
      enum "oor-green" {
        description
          "Resources Available";
      }
      enum "oor-yellow" {
        description
          "Resources Warning. Have exceeded minor
           threshold";
      }
      enum "oor-red" {
        description
          "Out of Resources. Have exceeded major threshold";
      }
    }
    description
      "SRv6 Out of Resource State";
  }

  grouping SRV6-LOCATOR-INTF-INFO {
    description
      "SRv6 locator interface";
    leaf name {
      type string;
      description
        "Interface name";
    }
    leaf if-handle {
      type xr:Hex-integer;
      description
        "Interface handle";
    }
    leaf programmed-prefix {
      type string;
      description
        "Interface prefix/addr programmed";
    }
  }

  grouping SRV6-LOCATOR-INFO {
    description
      "SRv6 Locator info";
    container interface {
      description
        "Locator IM intf info";
      uses SRV6-LOCATOR-INTF-INFO;
    }
    container create-timestamp {
      description
        "Creation timestamp";
      uses MGMT-SIDMGR-TIMESTAMP;
    }
    leaf name {
      type string;
      description
        "Locator Name";
    }
    leaf id {
      type uint32;
      description
        "Locator ID";
    }
    leaf prefix {
      type string;
      description
        "Locator Prefix";
    }
    leaf is-operational {
      type boolean;
      description
        "Locator status is Up or Down";
    }
    leaf out-of-resources-state {
      type Srv6-out-of-resource-state;
      description
        "Locator Resources State for SIDs";
    }
  }

  grouping MGMT-SIDMGR-TIMESTAMP {
    description
      "SID Manager Generic Timestamp";
    leaf time-in-nano-seconds {
      type uint64;
      units "nanosecond";
      description
        "Timestamp in nano seconds";
    }
    leaf age-in-nano-seconds {
      type uint64;
      units "nanosecond";
      description
        "Age in nano seconds";
    }
  }

  grouping SID-OWNER {
    description
      "SID Owner";
    leaf owner {
      type string;
      description
        "Owner";
    }
  }

  grouping MGMT-SRV6-SID-CTX-DX2 {
    description
      "SRv6 End.DX2 SID context";
    leaf evi {
      type uint32;
      description
        "EVI";
    }
    leaf eth-tag {
      type uint32;
      description
        "Ethernet Tag ID";
    }
  }

  grouping MGMT-SRV6-SID-CTX-DT {
    description
      "SRv6 End.DT4/6 SID context";
    leaf table-id {
      type uint32;
      description
        "Table ID";
    }
  }

  grouping MGMT-SRV6-SID-CTX-DX {
    description
      "SRv6 End.DX4/6 SID context";
    leaf table-id {
      type uint32;
      description
        "Table ID";
    }
    leaf next-hop-set-id {
      type uint32;
      description
        "Next Hop Set ID";
    }
  }

  grouping MGMT-SRV6-SID-CTX-X {
    description
      "SRv6 End.X SID context";
    leaf is-protected {
      type boolean;
      description
        "Is protected?";
    }
    leaf opaque-id {
      type uint8;
      description
        "Additional differentiator - opaque to SIDMgr";
    }
    leaf interface {
      type xr:Interface-name;
      description
        "Nexthop interface";
    }
    leaf nexthop-address {
      type inet:ipv6-address;
      description
        "Nexthop IP address";
    }
  }

  grouping MGMT-SRV6-SID-CTX-X-PSP {
    description
      "SRv6 End.X (PSP) SID context";
    container xctx {
      description
        "Common End.X context for End.X (PSP) SID";
      uses MGMT-SRV6-SID-CTX-X;
    }
  }

  grouping MGMT-SRV6-SID-CTX-RSVD {
    description
      "SRv6 Reserved SID context";
    leaf table-id {
      type uint32;
      description
        "Table Id";
    }
  }

  grouping MGMT-SRV6-SID-CTX-OP {
    description
      "SRv6 End.OP SID context";
    container op-ctx {
      description
        "Common reserved context for End.OP SID";
      uses MGMT-SRV6-SID-CTX-RSVD;
    }
  }

  grouping MGMT-SRV6-SID-CTX1 {
    description
      "SRv6 End SID context";
    leaf table-id {
      type uint32;
      description
        "Table Id";
    }
    leaf opaque-id {
      type uint8;
      description
        "Additional differentiator - opaque to SIDMgr";
    }
  }

  grouping MGMT-SRV6-SID-CTX-E-PSP {
    description
      "SRv6 End (PSP) SID context";
    container ectx {
      description
        "Common End context for End (PSP) SID";
      uses MGMT-SRV6-SID-CTX1;
    }
  }

  grouping MGMT-SRV6-SID-CTX-KEY {
    description
      "MGMT SRV6 SID CTX KEY";
    container e-psp {
      when "../sid-context-type = 'end-with-psp'" {
        description
          "../SIDContextType = 'EndWithPSP'";
      }
      description
        "End (PSP) SID context";
      uses MGMT-SRV6-SID-CTX-E-PSP;
    }
    container op {
      when "../sid-context-type = 'end-op'" {
        description
          "../SIDContextType = 'EndOP'";
      }
      description
        "End.OP SID context";
      uses MGMT-SRV6-SID-CTX-OP;
    }
    container x-psp {
      when "../sid-context-type = 'end-x-with-psp'" {
        description
          "../SIDContextType = 'EndXWithPSP'";
      }
      description
        "End.X (PSP) SID context";
      uses MGMT-SRV6-SID-CTX-X-PSP;
    }
    container dx4 {
      when "../sid-context-type = 'end-dx4'" {
        description
          "../SIDContextType = 'EndDX4'";
      }
      description
        "End.DX4 SID context";
      uses MGMT-SRV6-SID-CTX-DX;
    }
    container dt4 {
      when "../sid-context-type = 'end-dt4'" {
        description
          "../SIDContextType = 'EndDT4'";
      }
      description
        "End.DT4 SID context";
      uses MGMT-SRV6-SID-CTX-DT;
    }
    container dx2 {
      when "../sid-context-type = 'end-dx2'" {
        description
          "../SIDContextType = 'EndDX2'";
      }
      description
        "End.DX2 SID context";
      uses MGMT-SRV6-SID-CTX-DX2;
    }
    leaf sid-context-type {
      type Srv6-end-function;
      description
        "SIDContextType";
    }
  }

  grouping MGMT-SRV6-SID-CTX {
    description
      "SRv6 SID context";
    container key {
      description
        "SID Key";
      uses MGMT-SRV6-SID-CTX-KEY;
    }
    leaf application-data {
      type yang:hex-string;
      description
        "Application opaque data";
    }
  }

  grouping SRV6-SID-INFO {
    description
      "SRv6 SID Manager SID info";
    container sid-context {
      description
        "SID Context";
      uses MGMT-SRV6-SID-CTX;
    }
    container create-timestamp {
      description
        "Creation timestamp";
      uses MGMT-SIDMGR-TIMESTAMP;
    }
    leaf sid {
      type string;
      description
        "SID";
    }
    leaf allocation-type {
      type Sid-allocation;
      description
        "Allocation Type";
    }
    leaf behavior-type {
      type Srv6-end-function;
      description
        "Behavior Type";
    }
    leaf state {
      type Sid-state;
      description
        "State";
    }
    leaf has-forwarding {
      type boolean;
      description
        "Rewrite done or not";
    }
    leaf locator {
      type string;
      description
        "Associated locator";
    }
    list owner {
      description
        "Owner";
      uses SID-OWNER;
    }
  }

  grouping MGMT-SRV6-PLATFORM-SIG-PARAMS {
    description
      "Platform SRv6 params to be signaled";
    leaf max-sl {
      type uint8;
      description
        "Max value of SegmentLeft field in received SRH";
    }
    leaf max-end-pop-srh {
      type uint8;
      description
        "Max num of SIDs in rcvd SRH for pop";
    }
    leaf max-t-insert {
      type uint8;
      description
        "Max num of SIDs for T.Insert op";
    }
    leaf max-t-encap {
      type uint8;
      description
        "Max num of SIDs for T.Encaps op";
    }
    leaf max-end-d {
      type uint8;
      description
        "Max num of SIDs in rcvd SRH for decap";
    }
  }

  grouping MGMT-SIDMGR-STRING {
    description
      "Generic string";
    leaf string {
      type string;
      description
        "String";
    }
  }

  grouping SRV6-PLATFORM-SUPPORT {
    description
      "SRv6 Platform Support";
    container signaled-parameters {
      description
        "Signaled Parameters";
      uses MGMT-SRV6-PLATFORM-SIG-PARAMS;
    }
    leaf srv6 {
      type boolean;
      description
        "SRv6 support";
    }
    leaf tilfa {
      type boolean;
      description
        "TI LFA support";
    }
    leaf microloop-avoidance {
      type boolean;
      description
        "Microloop-avoidance support";
    }
    list end-func {
      description
        "Supported end functions";
      uses MGMT-SIDMGR-STRING;
    }
    list transit-func {
      description
        "Supported Transit functions";
      uses MGMT-SIDMGR-STRING;
    }
    list security-rule {
      description
        "Security rules";
      uses MGMT-SIDMGR-STRING;
    }
    list counter {
      description
        "Counters";
      uses MGMT-SIDMGR-STRING;
    }
  }

  grouping SRV6-PLATFORM-CAPABILITY {
    description
      "Platform Capabilities for SRv6";
    container support {
      description
        "Feature support";
      uses SRV6-PLATFORM-SUPPORT;
    }
    leaf max-sid {
      type uint32;
      description
        "Maximum Sids";
    }
    leaf sid-holdtime-mins {
      type uint32;
      units "minute";
      description
        "Freed SID holdtime in mins";
    }
  }

  grouping SRV6-OOR-SUMMARY {
    description
      "SRv6 SID Manager Out of Resource Summary";
    leaf out-of-resources-state {
      type Srv6-out-of-resource-state;
      description
        "Global Resources State for SIDs";
    }
    leaf oor-yellow-free-sid-threshold {
      type uint32;
      description
        "Threshold for Number of Free SID below which OOR
         Yellow State is reached";
    }
    leaf oor-green-free-sid-threshold {
      type uint32;
      description
        "Threshold for Number of Free SID above which OOR
         Green State is restored";
    }
    leaf oor-green-count {
      type uint32;
      description
        "Number of times Resources Warning or Out of
         Resources state has been cleared";
    }
    leaf oor-yellow-count {
      type uint32;
      description
        "Number of times system went into Resources
         Warning state";
    }
    leaf oor-red-count {
      type uint32;
      description
        "Number of times system went into Out of
         Resources state";
    }
  }

  grouping SRV6-SIDMGR-SUMMARY {
    description
      "SRv6 SID Manager summary";
    container sids-out-of-resource-summary {
      description
        "SIDs Global Out of Resource info";
      uses SRV6-OOR-SUMMARY;
    }
    leaf locators-count {
      type uint16;
      description
        "Number of locators";
    }
    leaf oper-locators-count {
      type uint16;
      description
        "Number of operational locators";
    }
    leaf sids-count {
      type uint32;
      description
        "Number of SIDs";
    }
    leaf stale-sids-count {
      type uint32;
      description
        "Number of Stale SIDs";
    }
    leaf maximum-sids-count {
      type uint32;
      description
        "Global Maximum number of SIDs";
    }
  }

  grouping SRV6-SIDMGR-PARAMS-ENCAP-HOPLIMIT {
    description
      "SRv6 SID Manager Encap Hop-Limit parameters";
    leaf use-default {
      type boolean;
      description
        "Use default IPv6 hop-limit value";
    }
    leaf do-propagate {
      type boolean;
      description
        "Propagate IP TTL to Encap IPv6 hop-limit";
    }
    leaf value {
      type uint8;
      description
        "Specific value set for hop-limit count";
    }
  }

  grouping SRV6-SIDMGR-PARAMS {
    description
      "SRv6 SID Manager parameters";
    container encap-hop-limit {
      description
        "Encap Hop-limit info";
      uses SRV6-SIDMGR-PARAMS-ENCAP-HOPLIMIT;
    }
    leaf srv6-enabled {
      type boolean;
      description
        "Is SRv6 enabled?";
    }
    leaf configured-encap-source-address {
      type inet:ipv6-address;
      description
        "Configured Encap Source address";
    }
    leaf default-encap-source-address {
      type inet:ipv6-address;
      description
        "Default Encap Source address";
    }
    leaf encap-ttl-propagate {
      type boolean;
      description
        "Is TTL propagate enabled?";
    }
    leaf is-sid-holdtime-configured {
      type boolean;
      description
        "Is SID Holdtime configured?";
    }
    leaf sid-holdtime-mins-configured {
      type uint32;
      units "minute";
      description
        "Configured SID Holdtime in mins";
    }
  }

  grouping SRV6-SIDMGR-INFO {
    description
      "SRv6 SID Manager info";
    container sid-mgr-params {
      description
        "SID Mgr parameters";
      uses SRV6-SIDMGR-PARAMS;
    }
    container sid-mgr-summary {
      description
        "SID Mgr summary info";
      uses SRV6-SIDMGR-SUMMARY;
    }
    container platform-capabilities {
      description
        "Platform Capabilities";
      uses SRV6-PLATFORM-CAPABILITY;
    }
  }
}
