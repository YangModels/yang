module Cisco-IOS-XR-sysadmin-debug-trace {
  namespace "http://www.cisco.com/ns/yang/Cisco-IOS-XR-sysadmin-debug-trace";
  prefix debug_trace;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     This module contains definitions
     for the following management objects:
     debug_trace: Calvados debug trace.
     
     Copyright (c) 2015-2020, 2019 by Cisco Systems, Inc.
     All rights reserved.";

  revision 2019-04-15 {
    description
      "Establish semantic version baseline.";
    semver:module-version "1.0.1";
  }
  revision 2017-04-12 {
    description
      "Changed namespace and module name";
  }
  revision 2015-12-03 {
    description
      "Initial version.";
  }

  grouping config-debug-trace-group {
    container config {
      config true;
      container debug {
        list trace {
          key "connection_type";
          max-elements "16";
          leaf connection_type {
            type string;
          }
          choice trace-output {
            leaf enable {
              type empty;
            }
            leaf disable {
              type empty;
            }
          }
        }
      }
    }
  }

  uses config-debug-trace-group;
}
