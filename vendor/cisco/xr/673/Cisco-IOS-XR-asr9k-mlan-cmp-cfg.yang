module Cisco-IOS-XR-asr9k-mlan-cmp-cfg {
  namespace "http://cisco.com/ns/yang/Cisco-IOS-XR-asr9k-mlan-cmp-cfg";
  prefix asr9k-mlan-cmp-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-mlan-cmp package configuration.
     
     This module contains definitions
     for the following management objects:
       mlan-disable-cmp: Disable/Enable CMP
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container mlan-disable-cmp {
    description
      "Disable/Enable CMP";
    container nodes {
      description
        "Fully qualified RSP4/RSP4s/RP2 card
         specification";
      list node {
        key "node-name";
        description
          "A node";
        leaf disable {
          type empty;
          description
            "Disable CMP";
        }
        leaf node-name {
          type xr:Node-id;
          description
            "NodeName";
        }
      }
    }
  }
}
