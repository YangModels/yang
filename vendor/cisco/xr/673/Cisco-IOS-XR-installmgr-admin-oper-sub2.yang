submodule Cisco-IOS-XR-installmgr-admin-oper-sub2 {
  belongs-to Cisco-IOS-XR-installmgr-admin-oper {
    prefix Cisco-IOS-XR-installmgr-admin-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR installmgr-admin package operational data.
     
     Copyright (c) 2013-2019 by Cisco Systems, Inc.
     All rights reserved.";

  revision 2019-04-05 {
    description
      "Establish semantic version baseline.";
    semver:module-version "1.0.0";
  }
  revision 2019-01-03 {
    description
      "Fixing backward compatibility error in modules.";
  }
  revision 2015-11-09 {
    description
      "IOS XR 6.0 revision.";
  }

  typedef Path {
    type string;
    description
      "The path of the file from the root directory of
       the package group";
  }

  typedef Instmgr-group {
    type enumeration {
      enum "inst-pkg-group-undefined" {
        description
          "Undefined grouping";
      }
      enum "inst-pkg-group-grouped" {
        description
          "Packages are grouped";
      }
      enum "inst-pkg-group-individual" {
        description
          "Packages are all individual";
      }
    }
    description
      "Group type";
  }

  typedef Instmgr-pkg {
    type enumeration {
      enum "inst-pkg-type-undefined" {
        description
          "Undefined package";
      }
      enum "inst-pkg-type-root" {
        description
          "Root package";
      }
      enum "inst-pkg-type-standard" {
        description
          "Standard package";
      }
      enum "inst-pkg-type-internal" {
        description
          "Internal package";
      }
    }
    description
      "Package type";
  }

  typedef Instmgr-card {
    type string;
    description
      "A card-type";
  }

  typedef Instmgr-install-phase {
    type enumeration {
      enum "inst-phase-unknown" {
        value 0;
        description
          "Unknown operational phase";
      }
      enum "inst-phase-download" {
        value 10;
        description
          "Downloading";
      }
      enum "inst-phase-sw-change" {
        value 50;
        description
          "Performing software changes";
      }
      enum "inst-phase-cleaning-up" {
        value 1000;
        description
          "Cleaning up after op";
      }
    }
    description
      "Current operation phase";
  }

  typedef Instmgr-bag-ii-state {
    type enumeration {
      enum "idle" {
        value 1;
        description
          "Node to be upraded";
      }
      enum "in-progress" {
        value 2;
        description
          "Node is being upraded";
      }
      enum "completed" {
        value 3;
        description
          "Node upgraded successfully";
      }
      enum "aborted" {
        value 4;
        description
          "Node reverted to the old S/W";
      }
      enum "rebooted" {
        value 5;
        description
          "Node rebooted and held in MBI";
      }
    }
    description
      "The Incremental Install state of an install";
  }

  typedef Instmgr-bag-ii-direction {
    type enumeration {
      enum "not-incremental" {
        description
          "Not incremental install operation";
      }
      enum "installing" {
        description
          "Installing";
      }
      enum "unwinding" {
        description
          "Unwinding";
      }
    }
    description
      "The Incremental Install direction";
  }

  typedef Instmgr-bag-user-msg-category {
    type enumeration {
      enum "user-error" {
        value 1;
        description
          "User error";
      }
      enum "non-specific" {
        value 2;
        description
          "Non-specific message";
      }
      enum "warning" {
        value 3;
        description
          "Warning message";
      }
      enum "information" {
        value 4;
        description
          "Information message";
      }
      enum "user-prompt" {
        value 5;
        description
          "User prompt";
      }
      enum "log" {
        value 6;
        description
          "Log message";
      }
      enum "system-error" {
        value 7;
        description
          "System error";
      }
      enum "user-response" {
        value 8;
        description
          "User response";
      }
    }
    description
      "Instmgr bag user msg category";
  }

  typedef Instmgr-issu-abort-impact {
    type enumeration {
      enum "undefined" {
        description
          "Unknown abort impact";
      }
      enum "hitless" {
        description
          "Abort is hitless";
      }
      enum "traffic-outage" {
        description
          "Abort will not affect traffic";
      }
      enum "not-applicable" {
        description
          "Abort impact: n/a";
      }
    }
    description
      "Abort impact";
  }

  typedef Instmgr-issu-abort-method {
    type enumeration {
      enum "method-undefined" {
        description
          "Unknown abort method";
      }
      enum "method-no-operation" {
        description
          "No abort is required";
      }
      enum "method-standby-reload" {
        description
          "Abort will reload standby nodes";
      }
      enum "method-system-reload" {
        description
          "Abort will reload the whole system";
      }
      enum "method-rollback" {
        description
          "Abort will rollback";
      }
      enum "method-not-possible" {
        description
          "Abort is not possible";
      }
      enum "method-admin-only" {
        description
          "Abort is not possible by SDR user";
      }
    }
    description
      "Abort method";
  }

  typedef Instmgr-bag-abort-state {
    type enumeration {
      enum "abortable" {
        value 1;
        description
          "Operation can be aborted";
      }
      enum "no-longer-abortable" {
        value 2;
        description
          "Operation can no longer be aborted";
      }
      enum "never-abortable" {
        value 3;
        description
          "Operation cannot be aborted";
      }
      enum "already-aborted" {
        value 4;
        description
          "Operation has been aborted";
      }
    }
    description
      "The abortable state of an install command";
  }

  typedef Instmgr-request {
    type enumeration {
      enum "add" {
        value 1;
        description
          "install add";
      }
      enum "accept" {
        value 2;
        description
          "install accept";
      }
      enum "clean" {
        value 3;
        description
          "install clean";
      }
      enum "activate" {
        value 4;
        description
          "install activate";
      }
      enum "deactivate" {
        value 5;
        description
          "install deactivate";
      }
      enum "commit" {
        value 6;
        description
          "install commit";
      }
      enum "verify" {
        value 7;
        description
          "install verify";
      }
      enum "rollback" {
        value 8;
        description
          "install rollback";
      }
      enum "clear-rollback" {
        value 9;
        description
          "install clear rollback oldest";
      }
      enum "clear-log" {
        value 10;
        description
          "install clear historylog";
      }
      enum "health-check" {
        value 11;
        description
          "(Deprecated) install healthcheck";
      }
      enum "operation" {
        value 12;
        description
          "install run/accept/complete";
      }
      enum "stop-timer" {
        value 13;
        description
          "install auto-abort-timer stop";
      }
      enum "label" {
        value 14;
        description
          "install label";
      }
      enum "clear-label" {
        value 15;
        description
          "clear install label";
      }
      enum "extend" {
        value 16;
        description
          "install extend";
      }
    }
    description
      "Instmgr request";
  }

  typedef Instmgr-request-option {
    type int32;
    description
      "Install manager request option bitset";
  }

  typedef Instmgr-bag-request-trigger {
    type enumeration {
      enum "cli" {
        value 1;
        description
          "Request triggered by CLI";
      }
      enum "xr-xml" {
        value 2;
        description
          "Request triggered by XML";
      }
    }
    description
      "The trigger type of an install request";
  }

  typedef Lr-name {
    type string;
    description
      "SDR name";
  }

  typedef Instmgr-node {
    type uint64;
    description
      "Instmgr node";
  }

  grouping BOOT-IMG {
    description
      "Install manager boot image";
    leaf system-image-file {
      type string;
      description
        "The boot image";
    }
  }

  grouping LOCATION-SPECIFIC-LOADPATH {
    description
      "SDR specific load path information";
    leaf request-id {
      type uint32;
      description
        "Install op affecting scope";
    }
    leaf secure-domain-router-name {
      type Lr-name;
      description
        "SDR name";
    }
    leaf node-name {
      type xr:Node-id;
      description
        "Identifier of node";
    }
    list load-path {
      description
        "Location specific load path";
      uses PKG-INFO;
    }
    list standby-load-path {
      description
        "Load paths for standby nodes";
      uses PKG-INFO;
    }
  }

  grouping LR-SPECIFIC-LOADPATH {
    description
      "SDR specific load path information";
    leaf request-id {
      type uint32;
      description
        "Install op affecting scope";
    }
    leaf secure-domain-router-name {
      type Lr-name;
      description
        "SDR name";
    }
    list load-path {
      description
        " Lr specific load path";
      uses PKG-INFO;
    }
    list standby-load-path {
      description
        "Load paths for standby nodes";
      uses PKG-INFO;
    }
  }

  grouping ADMIN-LOADPATH {
    description
      "Admin Resources Load path information";
    leaf request-id {
      type uint32;
      description
        "Install op affecting scope";
    }
    list load-path {
      description
        "Admin Resources load path";
      uses PKG-INFO;
    }
    list standby-load-path {
      description
        "Load paths for standby nodes";
      uses PKG-INFO;
    }
  }

  grouping DEFAULT-LOADPATH {
    description
      "Default Load path information";
    leaf request-id {
      type uint32;
      description
        "Install op affecting scope";
    }
    leaf admin-match {
      type boolean;
      description
        "Does this match the Admin Resources load path?";
    }
    list secure-domain-router-name {
      description
        "Names of SDRs this applies to";
      leaf entry {
        type Lr-name;
        description
          "Names of SDRs this applies to";
      }
    }
    list load-path {
      description
        "Default load path";
      uses PKG-INFO;
    }
    list standby-load-path {
      description
        "Load paths for standby nodes";
      uses PKG-INFO;
    }
  }

  grouping INSTALL-INVENTORY-SUMMARY {
    description
      "Inventory summary information";
    container default-load-path {
      description
        "Install inventory summary load path";
      uses DEFAULT-LOADPATH;
    }
    container admin-load-path {
      description
        "Admin Resources load path";
      uses ADMIN-LOADPATH;
    }
    list sdr-load-path {
      description
        "SDR load paths";
      uses LR-SPECIFIC-LOADPATH;
    }
    list location-load-path {
      description
        "Install inventory location load paths";
      uses LOCATION-SPECIFIC-LOADPATH;
    }
  }

  grouping INSTMGR-COMPONENT-INFO {
    description
      "Information about a single component";
    leaf name {
      type string;
      description
        "Name of the component";
    }
    leaf version {
      type string;
      description
        "Version of the component";
    }
    leaf release {
      type string;
      description
        "Release that the component belongs to";
    }
    leaf description {
      type string;
      description
        "Description of the component";
    }
    list files {
      description
        "The set of files belonging to the component";
      leaf entry {
        type Path;
        description
          "The set of files belonging to the component";
      }
    }
  }

  grouping INSTMGR-SUB-PKG-INFO {
    description
      "INSTMGR SUB PKG INFO";
    leaf name {
      type string;
      description
        "Name of the sub-package";
    }
    leaf node-types {
      type Instmgr-node;
      description
        "Node types of the package";
    }
  }

  grouping INSTMGR-PKG-INFO {
    description
      "Information about a package";
    leaf name {
      type string;
      description
        "Name of the package";
    }
    leaf version {
      type string;
      description
        "Version of the package";
    }
    leaf description {
      type string;
      description
        "Description of the package";
    }
    leaf release {
      type string;
      description
        "Release that the package belongs to";
    }
    leaf vendor {
      type string;
      description
        "Information about the vendor that supplied the
         package";
    }
    leaf date {
      type string;
      description
        "Time and date that the package was built";
    }
    leaf source {
      type string;
      description
        "Identifies the provider of the package";
    }
    leaf base {
      type string;
      description
        "Identifies the base bundle that the package is
         for";
    }
    leaf bootable {
      type boolean;
      description
        "TRUE if package has BOOTIMAGE tag set";
    }
    leaf composite {
      type boolean;
      description
        "TRUE if package is a composite package";
    }
    leaf restart-info {
      type string;
      description
        "Restart info of the package";
    }
    leaf package-type {
      type Instmgr-pkg;
      description
        "Type of the package";
    }
    leaf group-type {
      type Instmgr-group;
      description
        "Group type of the package";
    }
    leaf depth {
      type uint32;
      description
        "Number of layers of parent packages";
    }
    leaf uncompressed-size {
      type uint32;
      description
        "Uncompressed size of package";
    }
    leaf compressed-size {
      type uint32;
      description
        "Compressed size of package";
    }
    list cards {
      description
        "Card types that the package should be installed
         on";
      leaf entry {
        type Instmgr-card;
        description
          "Card types that the package should be installed
           on";
      }
    }
    list sub-pkg {
      description
        "Sub-package info of the package";
      uses INSTMGR-SUB-PKG-INFO;
    }
  }

  grouping INSTMGR-BAG-II-NODE-STATE-TYPE {
    description
      "The state of Incremental Install for a given node";
    leaf node-name {
      type xr:Node-id;
      description
        "Identifier of node";
    }
    leaf state {
      type Instmgr-bag-ii-state;
      description
        "State";
    }
  }

  grouping INSTMGR-BAG-II-INFO-TYPE {
    description
      "Incremental Install info";
    leaf direction {
      type Instmgr-bag-ii-direction;
      description
        "Install direction";
    }
    leaf ii-error {
      type string;
      description
        "First error during incremental install";
    }
    list nodes {
      description
        "Participating nodes";
      uses INSTMGR-BAG-II-NODE-STATE-TYPE;
    }
  }

  grouping INSTMGR-BAG-USER-MSG-SCOPE-TYPE {
    description
      "INSTMGR BAG USER MSG SCOPE TYPE";
    leaf admin-read {
      type boolean;
      description
        "Does the admin want to read this?";
    }
    leaf affected-sd-rs {
      type uint32;
      description
        "Which LRs are affected by the message";
    }
  }

  grouping INSTMGR-BAG-USER-MSG-TYPE {
    description
      "A user message";
    container scope {
      description
        "Scope of the message";
      uses INSTMGR-BAG-USER-MSG-SCOPE-TYPE;
    }
    leaf category {
      type Instmgr-bag-user-msg-category;
      description
        "Category of the message";
    }
    leaf message {
      type string;
      description
        "Message Information";
    }
  }

  grouping INSTMGR-ISSU-ABORT-STATUS {
    description
      "Abort status";
    leaf abort-method {
      type Instmgr-issu-abort-method;
      description
        "Method of abort";
    }
    leaf abort-impact {
      type Instmgr-issu-abort-impact;
      description
        "Impact of abort";
    }
  }

  grouping INSTMGR-BAG-REQUEST-INFO {
    description
      "Request information";
    leaf request-id {
      type uint32;
      description
        "Install id of operation";
    }
    leaf user-id {
      type string;
      description
        "User ID that started the reqeust";
    }
    leaf trigger-type {
      type Instmgr-bag-request-trigger;
      description
        "Request trigger type";
    }
    leaf request-option {
      type Instmgr-request-option;
      description
        "Options affecting processing of install requests";
    }
    leaf operation-type {
      type Instmgr-request;
      description
        "Requested operation type";
    }
    leaf operation-detail {
      type string;
      description
        "Detail operation information";
    }
  }

  grouping INSTMGR-INSTALL-STATUS {
    description
      "Status for an install request";
    container request-information {
      description
        "Requested install operation";
      uses INSTMGR-BAG-REQUEST-INFO;
    }
    container abort-status {
      description
        "How the abort will occur";
      uses INSTMGR-ISSU-ABORT-STATUS;
    }
    container incremental-install-information {
      description
        "Status information of incremental install";
      uses INSTMGR-BAG-II-INFO-TYPE;
    }
    leaf percentage {
      type uint8;
      units "percentage";
      description
        "Percentage completed";
    }
    leaf abort-state {
      type Instmgr-bag-abort-state;
      description
        "Install Abort state";
    }
    leaf downloaded-bytes {
      type uint32;
      units "byte";
      description
        "Install Downloaded bytes";
    }
    leaf unanswered-query {
      type boolean;
      description
        "Whether the operation is blocked waiting for a
         response from the user";
    }
    leaf operation-phase {
      type Instmgr-install-phase;
      description
        "Phase of the operation";
    }
    list issu-message {
      description
        "Messages related to ISSU operations";
      uses INSTMGR-BAG-USER-MSG-TYPE;
    }
    list message {
      description
        "Messages output to the user";
      uses INSTMGR-BAG-USER-MSG-TYPE;
    }
  }

  grouping PKG-GROUP {
    description
      "Package group";
    leaf device-name {
      type string;
      description
        "Device group name";
    }
    leaf name {
      type string;
      description
        "Package group name";
    }
  }

  grouping PKG-INFO {
    description
      "Package information";
    container package {
      description
        "Package name";
      uses PKG-GROUP;
    }
    leaf version {
      type string;
      description
        "Package version";
    }
    leaf build-information {
      type string;
      description
        "Package Build information";
    }
  }

  grouping INVENTORY {
    description
      "Inventory";
    leaf major {
      type uint32;
      description
        "Major data version number";
    }
    leaf minor {
      type uint32;
      description
        "Minor data version number";
    }
    leaf boot-image-name {
      type string;
      description
        "Name of the boot image";
    }
    leaf node-type {
      type Instmgr-node;
      description
        "Node's type";
    }
    leaf secure-domain-router-name {
      type Lr-name;
      description
        "SDR name";
    }
    list load-path {
      description
        "Load path information";
      uses PKG-INFO;
    }
  }
}
