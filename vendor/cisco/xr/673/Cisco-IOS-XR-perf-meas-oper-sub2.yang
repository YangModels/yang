submodule Cisco-IOS-XR-perf-meas-oper-sub2 {
  belongs-to Cisco-IOS-XR-perf-meas-oper {
    prefix Cisco-IOS-XR-perf-meas-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR perf-meas package operational data.
     
     Copyright (c) 2013-2020 by Cisco Systems, Inc.
     All rights reserved.";

  revision 2020-07-23 {
    description
      "Fixed typos in perf-meas oper bag.";
    semver:module-version "3.0.1M";
  }
  revision 2020-06-24 {
    description
      "Update perf-meas oper schema task group.
       2020-04-10
       Added new TX error counter for next hop MAC missing.
       2020-03-25
       Add trace id in PM session bag.
       2020-03-24
       Added new reason for DM probe not running.
       2020-03-17
       Added new types counters to count different types of PM DM sessions.
       2020-02-20
       Modifid type of service knobs from array to integer.
       2020-02-13
       Modifiy delay-measurement hisotry key words.
       2020-01-28
       Added responder src address and num of hops for PM DM.
       2020-01-22
       Added a new advertisement reason for interface delay-measurement.";
    semver:module-version "3.0.0";
  }
  revision 2019-10-19 {
    description
      "Added burst-interval-effective to oper data.";
    semver:module-version "2.0.0";
  }
  revision 2019-04-05 {
    description
      "Establish semantic version baseline.";
    semver:module-version "1.0.0";
  }
  revision 2018-12-13 {
    description
      "Revision IOS XR 7.0.1 Added delay measurment for SR Policy and RSVP-TE LSP.";
  }
  revision 2017-10-17 {
    description
      "Revision Zero.";
  }
  revision 2015-11-09 {
    description
      "IOS XR 6.0 revision.";
  }

  typedef Pm-payload {
    type enumeration {
      enum "payload-type-pm-dm" {
        description
          "Payload type PM DM";
      }
      enum "payload-type-twamp-test" {
        description
          "Payload type TWAMP test";
      }
      enum "payload-type-pm-lm" {
        description
          "Payload type PM LM";
      }
    }
    description
      "PM Payload Type";
  }

  typedef Pm-encap-mode {
    type enumeration {
      enum "encap-mode-mpls" {
        description
          "Encap-mode MPLS";
      }
      enum "encap-mode-udp" {
        description
          "Encap-mode UDP";
      }
    }
    description
      "PM Packet Encapsulation";
  }

  typedef Pm-delay-mode {
    type enumeration {
      enum "delay-mode-one-way" {
        description
          "One-way delay-measurement mode";
      }
      enum "delay-mode-two-way" {
        description
          "Two-way delay-measurement mode";
      }
      enum "delay-mode-loopback" {
        description
          "Loopback delay-measurement mode";
      }
    }
    description
      "PM Delay Mode Type";
  }

  typedef Pm-measurement {
    type enumeration {
      enum "delay-measurement-type" {
        description
          "Delay Measurement Type";
      }
      enum "loss-measurement-type" {
        description
          "Loss Measurement Type";
      }
    }
    description
      "PM Measurement Type";
  }

  typedef Pm-transport {
    type enumeration {
      enum "interface-transport-type" {
        description
          "Transport type for interface";
      }
      enum "rsvp-te-transport-type" {
        description
          "Transport type for RSVP-TE LSP";
      }
      enum "sr-policy-transport-type" {
        description
          "Transport type for SR Policy";
      }
    }
    description
      "PM Transport Type";
  }

  typedef Pm-history {
    type enumeration {
      enum "history-type-probe" {
        description
          "History type for delay measurement probe info";
      }
      enum "history-type-packet" {
        description
          "History type for delay measurement packet info";
      }
      enum "history-type-aggregated" {
        description
          "History type for delay measurement aggregated
           info";
      }
      enum "history-type-advertisement" {
        description
          "History type for delay measurement
           advertisement info";
      }
      enum "history-type-lm-probe" {
        description
          "History type for loss measurement probe info";
      }
      enum "history-type-lm-packet" {
        description
          "History type for loss measurement aggregation
           info";
      }
      enum "history-type-lm-aggregated" {
        description
          "History type for loss measurement advertisement
           info";
      }
      enum "history-type-lm-advertisement" {
        description
          "History type for loss measurement advertisement
           info";
      }
    }
    description
      "PM history types";
  }

  typedef Pm-probe-not-running-reason {
    type enumeration {
      enum "probe-is-running" {
        description
          "Probe is running";
      }
      enum "platform-not-supported" {
        description
          "Measurement is not supported on this plaftorm";
      }
      enum "nonv1-active-node" {
        description
          "Node is not V1 active";
      }
      enum "control-code-error" {
        description
          "An uncleared control code error was received";
      }
      enum "interface-admin-down" {
        description
          "Interface admin down";
      }
      enum "interface-down" {
        description
          "Interface down";
      }
      enum "mpls-capability-not-present" {
        description
          "MPLS is not enabled on interface";
      }
      enum "interface-not-present" {
        description
          "Interface not present or preconfigured";
      }
      enum "ip-address-not-configured" {
        description
          "IP address is not present on interface";
      }
      enum "next-hop-not-configured" {
        description
          "Nexthop address not configured.";
      }
      enum "wrong-next-hop-ip-address-type" {
        description
          "Wrong nexthop address type configured";
      }
      enum "protocol-port-not-configured" {
        description
          "Protocol querier destination port missing";
      }
      enum "protocol-port-failed-to-open" {
        description
          "Protocol querier destination port failed to
           open";
      }
      enum "high-total-interface-packets-per-second" {
        description
          "Total interface delay packets per second
           exceeds 80% of the total maximum packets per
           second allowed";
      }
      enum "client-end-of-data-not-received" {
        description
          "Client end of data message has not been
           received";
      }
      enum "missing-reverse-path" {
        description
          "Missing reverse path for loopback measurement
           mode";
      }
      enum "process-not-in-run-state" {
        description
          "Process is not in run state";
      }
      enum "session-suspended" {
        description
          "Measurement has been suspended by user using
           exec command";
      }
      enum "interface-none-default-vrf" {
        description
          "None-default VRF is not supported";
      }
      enum "interface-type-not-supported" {
        description
          "Delay measurement is not supported for this
           interface type";
      }
      enum "interface-next-hop-mac-missing" {
        description
          "Next hop MAC address missing";
      }
    }
    description
      "PM probe not running reason";
  }

  typedef Pm-advert-reason {
    type enumeration {
      enum "no-advertisements" {
        description
          "Periodic timer expired. No advertisements have
           occured";
      }
      enum "periodic-advertisement-threshold-average" {
        description
          "Periodic timer expired. Average value threshold
           crossed";
      }
      enum "periodic-advertisement-threshold-minimum" {
        description
          "Periodic timer expired. Minimum value threshold
           crossed";
      }
      enum "periodic-advertisement-threshold-maximum" {
        description
          "Periodic timer expired. Maximum value threshold
           crossed";
      }
      enum "periodic-advertisement-threshold-variance" {
        description
          "Periodic timer expired. Variance value
           threshold crossed";
      }
      enum "accelerated-advertisement-threshold-average" {
        description
          "Accelerated average value threshold crossed";
      }
      enum "accelerated-advertisement-threshold-minimum" {
        description
          "Accelerated minimum value threshold crossed";
      }
      enum "accelerated-advertisement-threshold-maximum" {
        description
          "Accelerated maximum value threshold crossed";
      }
      enum "accelerated-advertisement-upper-bound-average" {
        description
          "Accelerated average value upper bound crossed";
      }
      enum "accelerated-advertisement-upper-bound-minimum" {
        description
          "Accelerated minimum value upper bound crossed";
      }
      enum "accelerated-advertisement-upper-bound-maximum" {
        description
          "Accelerated maximum value upper bound crossed";
      }
      enum "advertisement-enabled" {
        description
          "Advertisement enabled";
      }
      enum "advertisement-disabled" {
        description
          "Advertisement disabled";
      }
      enum "session-unconfigured" {
        description
          "Session unconfigured";
      }
      enum "clear-cli-command" {
        description
          "Session cleared via CLI";
      }
      enum "advertise-delay-config" {
        description
          "Advertise delay config";
      }
      enum "advertise-delay-unconfig" {
        description
          "Advertise delay unconfig";
      }
      enum "received-control-code-error" {
        description
          "Recevied control code error, as per RFC 6374,
           from the responder";
      }
      enum "first-advertisement" {
        description
          "First advertisement";
      }
      enum "link-is-down" {
        description
          "Link is in down state";
      }
      enum "new-child-session" {
        description
          "Advertisement occured due to a new child
           session";
      }
      enum "invalid-measurement" {
        description
          "Performance measurement metrics withdrawn due
           to measurement error";
      }
      enum "dynamic-delay-measurement-in-effect" {
        description
          "Advertisement occured due to dynamic delay
           measurement is in effect";
      }
    }
    description
      "PM advertisement reason";
  }

  typedef Pm-xtc-srpolicy-origin {
    type enumeration {
      enum "candidate-path-origin-invalid" {
        value 0;
        description
          "Invalid Origin Type";
      }
      enum "candidate-path-origin-pce" {
        value 10;
        description
          "Candidate-path From PCE";
      }
      enum "candidate-path-origin-bgp" {
        value 20;
        description
          "Candidate-path From BGP";
      }
      enum "candidate-path-origin-configured" {
        value 30;
        description
          "Candidate-path From Configuration";
      }
    }
    description
      "Candidate-path Orign Type Shared By PM And XTC";
  }

  typedef Pm-ipv6-addr {
    type inet:ipv6-address;
    description
      "Pm ipv6 addr";
  }

  typedef Pm-ipv4-addr {
    type inet:ipv4-address;
    description
      "Pm ipv4 addr";
  }

  typedef Pm-addr {
    type enumeration {
      enum "ipv4" {
        description
          "IPv4";
      }
      enum "ipv6" {
        description
          "IPv6";
      }
      enum "unknown" {
        description
          "Unknown";
      }
    }
    description
      "Type of PM address";
  }

  grouping PM-LOSS-TRANSPORT-PROFILE-BAG {
    description
      "PM interface loss measurement profile bag";
    leaf probe-interval {
      type uint32;
      description
        "Probe Interval (sec)";
    }
    leaf encap-mode {
      type Pm-encap-mode;
      description
        "Encap Mode";
    }
    leaf periodic-advertisement-enabled {
      type boolean;
      description
        "Advertisement Periodic Enabled";
    }
    leaf periodic-advertisement-interval {
      type uint32;
      description
        "Advertisement Periodic Interval (sec)";
    }
    leaf effective-periodic-advertisement-interval {
      type uint32;
      description
        "Advertisement Periodic Effective (sec)";
    }
    leaf periodic-advertisement-threshold {
      type uint32;
      description
        "Advertisement Periodic Threshold (%)";
    }
    leaf periodic-advertisement-minimum-change {
      type uint32;
      description
        "Advertisement Periodic Minimum Change (uSec)";
    }
    leaf accelerated-advertisement-threshold {
      type uint32;
      description
        "Advertisement Accelerated Threshold (%)";
    }
    leaf accelerated-advertisement-minimum-change {
      type uint32;
      description
        "Advertisement Accelerated Minimum Change (uSec)";
    }
    leaf accelerated-advertisement-enabled {
      type boolean;
      description
        "Advertisement Accelerated Enabled";
    }
  }

  grouping PM-LOSS-PROFILE-BAG {
    description
      "PM loss measurement profile bag";
    container interface-delay-profile {
      description
        "Profile info of Interface loss measurement";
      uses PM-LOSS-TRANSPORT-PROFILE-BAG;
    }
  }

  grouping PM-LIVENESS-PROFILE-BAG {
    description
      "Liveness detection state information bag";
    leaf multiplier {
      type uint8;
      description
        "Detect multiplier";
    }
  }

  grouping PM-LIVENESS-PROFILE-UNION {
    description
      "PM liveness detection profile union";
    container liveness-profile {
      when "../transport-type = 'sr-policy-transport-type'" {
        description
          "../TransportType = 'SRPolicyTransportType'";
      }
      description
        "Liveness profile info";
      uses PM-LIVENESS-PROFILE-BAG;
    }
    leaf transport-type {
      type Pm-transport;
      description
        "TransportType";
    }
  }

  grouping PM-DELAY-TRANSPORT-PROFILE-BAG {
    description
      "PM interface delay profile bag";
    container destination-sweeping-address {
      description
        "IPv4/IPv6 sweeping address";
      uses PM-IP-ADDR-TYPE;
    }
    container liveness-detection-config {
      description
        "Liveness detection config";
      uses PM-LIVENESS-PROFILE-UNION;
    }
    leaf probe-computation-interval {
      type uint32;
      description
        "Probe Computation Interval (sec)";
    }
    leaf probe-computation-interval-effective {
      type uint32;
      description
        "Effective Probe Computation Interval (sec)";
    }
    leaf tos-traffic-class-value {
      type uint8;
      description
        "TOS Traffic Class value specified for protocol
         PM-MPLS";
    }
    leaf tos-dscp-value {
      type uint8;
      description
        "TOS DSCP value specified for protocol
         TWAMP-LIGHT";
    }
    leaf burst-interval {
      type uint32;
      description
        "Burst Interval (msec)";
    }
    leaf burst-interval-effective {
      type uint32;
      description
        "Effective Burst Interval (msec)";
    }
    leaf burst-count {
      type uint32;
      description
        "Number of burst in one probe";
    }
    leaf delay-measurement-mode {
      type Pm-delay-mode;
      description
        "Delay Measurement Mode Type";
    }
    leaf encap-mode {
      type Pm-encap-mode;
      description
        "Encap Mode";
    }
    leaf payload-type {
      type Pm-payload;
      description
        "Type of the probe packet payload";
    }
    leaf destination-sweeping-mode-enabled {
      type boolean;
      description
        "Measure the delay with ECMP hashing by sweeping
         destination address";
    }
    leaf destination-sweeping-range {
      type uint32;
      description
        "Number of IP addresses to sweep";
    }
    leaf periodic-advertisement-enabled {
      type boolean;
      description
        "Advertisement Periodic Enabled";
    }
    leaf periodic-advertisement-interval {
      type uint32;
      description
        "Advertisement Periodic Interval (sec)";
    }
    leaf periodic-advertisement-interval-effective {
      type uint32;
      description
        "Advertisement Periodic Effective (sec)";
    }
    leaf periodic-advertisement-threshold {
      type uint32;
      description
        "Advertisement Periodic Threshold (%)";
    }
    leaf periodic-advertisement-minimum-change {
      type uint32;
      description
        "Advertisement Periodic Minimum Change (uSec)";
    }
    leaf accelerated-advertisement-threshold {
      type uint32;
      description
        "Advertisement Accelerated Threshold (%)";
    }
    leaf accelerated-advertisement-minimum-change {
      type uint32;
      description
        "Advertisement Accelerated Minimum Change (uSec)";
    }
    leaf accelerated-advertisement-enabled {
      type boolean;
      description
        "Advertisement Accelerated Enabled";
    }
    leaf advertisement-threshold-check-average-delay {
      type boolean;
      description
        "Check Average-delay For Advertisement Threshold
         Crossing";
    }
    leaf advertisement-threshold-check-minimum-delay {
      type boolean;
      description
        "Check Minimum-delay For Advertisement Threshold
         Crossing";
    }
    leaf advertisement-threshold-check-maximum-delay {
      type boolean;
      description
        "Check Maximum-delay For Advertisement Threshold
         Crossing";
    }
  }

  grouping PM-DELAY-PROFILE-BAG {
    description
      "PM Delay Profile bag";
    container interface-delay-profile {
      description
        "Profile of Interface delay measurement";
      uses PM-DELAY-TRANSPORT-PROFILE-BAG;
    }
    container sr-policy-delay-profile {
      description
        "Profile of SR Policy delay measurement";
      uses PM-DELAY-TRANSPORT-PROFILE-BAG;
    }
    container rsvp-te-delay-profile {
      description
        "Profile of RSVP-TE delay measurement";
      uses PM-DELAY-TRANSPORT-PROFILE-BAG;
    }
  }

  grouping PM-PROFILE-BAG {
    description
      "PM Profile bag";
    container delay-profile {
      description
        "Profile info of delay measurement";
      uses PM-DELAY-PROFILE-BAG;
    }
    container loss-profile {
      description
        "Profile info of loss measurement";
      uses PM-LOSS-PROFILE-BAG;
    }
  }

  grouping PM-INTF-LAST-ADVERT-BAG {
    description
      "PM interface delay last advertisement bag";
    container last-advertisement {
      description
        "Last advertisement info for delay measurement";
      uses PM-SCB-LAST-ADVERT-BAG;
    }
  }

  grouping PM-INTF-LAST-PROBE-BAG {
    description
      "PM interface delay last probe bag";
    container last-probe {
      description
        "Last probe info for delay measurement";
      uses PM-PROBE-SAMPLE-BAG;
    }
  }

  grouping PM-INTF-LAST-AGGR-BAG {
    description
      "PM interface delay last aggregation bag";
    container last-aggregation {
      description
        "Last aggregation interval";
      uses PM-AGGR-SAMPLE-BAG;
    }
    leaf interface-name-xr {
      type string;
      description
        "Interface name";
    }
    leaf interface-handle {
      type uint32;
      description
        "Interface handle";
    }
  }

  grouping PM-INTF-HISTORY-BAG {
    description
      "PM interface history bag";
    container history-info {
      description
        "History info of the interface";
      uses PM-HISTORY-SAMPLE-UNION;
    }
    leaf interface-name-xr {
      type string;
      description
        "Name of the interface";
    }
    leaf interface-handle {
      type uint32;
      description
        "Ifhandle of the interface";
    }
  }

  grouping PM-LOSS-ADVERTISEMENT-BAG {
    description
      " PM loss advertisement";
    leaf loss-percentage {
      type uint32;
      units "percentage";
      description
        "Packet loss percentage";
    }
    leaf timestamp-of-advertisement {
      type uint64;
      description
        "Advertisement timestamp";
    }
    leaf advertisement-reason {
      type Pm-advert-reason;
      description
        "Advertisement reason";
    }
  }

  grouping PM-LOSS-WINDOW-BAG {
    description
      "PM loss window";
    leaf last-tx-packet-counter {
      type uint64;
      description
        "Last TX packet counter";
    }
    leaf last-rx-packet-counter {
      type uint64;
      description
        "Last RX packet counter";
    }
    leaf current-packet-tx-in-window {
      type uint64;
      description
        "Current packet TX in window";
    }
    leaf current-packet-rx-in-window {
      type uint64;
      description
        "Current packet RX in window";
    }
    leaf loss-percentage {
      type uint32;
      units "percentage";
      description
        "Packet loss percentage";
    }
  }

  grouping PM-INTF-LOSS-SUB-SESSION-BAG {
    description
      "Interface loss-measurement sub-session bag";
    container probe-window {
      description
        "Probe window loss";
      uses PM-LOSS-WINDOW-BAG;
    }
    container periodic-window {
      description
        "Periodic window loss";
      uses PM-LOSS-WINDOW-BAG;
    }
    leaf interface-name {
      type string;
      description
        "Interface name";
    }
    leaf interface-handle {
      type uint32;
      description
        "Interface handle";
    }
    leaf interface-state-is-up {
      type boolean;
      description
        "True if interface state is up";
    }
    leaf session-id {
      type uint32;
      description
        "Session ID";
    }
    leaf rolling-average {
      type uint32;
      description
        "Rolling average";
    }
  }

  grouping PM-INTF-LOSS-SESSION-BAG {
    description
      "Interface loss-measurement session";
    container probe-window {
      description
        "Probe window loss";
      uses PM-LOSS-WINDOW-BAG;
    }
    container periodic-window {
      description
        "Periodic window loss";
      uses PM-LOSS-WINDOW-BAG;
    }
    container advertisement {
      description
        "Loss advertisement";
      uses PM-LOSS-ADVERTISEMENT-BAG;
    }
    leaf session-id {
      type uint32;
      description
        "Session ID";
    }
    leaf rolling-average {
      type uint32;
      description
        "Rolling average";
    }
    leaf next-probe-start-time-remaining-in-millisec {
      type uint32;
      units "millisecond";
      description
        "Time in milliseconds until the next probe starts";
    }
    leaf probe-not-running-reason {
      type Pm-probe-not-running-reason;
      description
        "Reason why probe is not running";
    }
    list interface-loss-sub-session {
      description
        "Interface loss-measurement sub-sessions";
      uses PM-INTF-LOSS-SUB-SESSION-BAG;
    }
  }

  grouping PM-SCB-BAG {
    description
      "PM interface delay session bag";
    container current-probe {
      description
        "Information for the current probe";
      uses PM-SCB-PROBE-BAG;
    }
    container session-counters {
      description
        "Counters info for the session";
      uses PM-DELAY-COUNTERS-INFO-BAG;
    }
    container last-advertisement-information {
      description
        "Last advertisement information of the session";
      uses PM-SCB-LAST-ADVERT-BAG;
    }
    container next-advertisement-information {
      description
        "Next advertisement information of the session";
      uses PM-SCB-NEXT-ADVERT-BAG;
    }
    container last-notification-control-code {
      description
        "Last notifcation control code received of the
         session";
      uses PM-SCB-CONTROL-CODE;
    }
    container last-error-control-code {
      description
        "Last error control code received of the session";
      uses PM-SCB-CONTROL-CODE;
    }
    container responder-address {
      description
        "Address of the Responder";
      uses PM-IP-ADDR-TYPE;
    }
    leaf session-id {
      type uint32;
      description
        "ID of the session";
    }
    leaf transport-type {
      type Pm-transport;
      description
        "Transport Type of the session";
    }
    leaf measurement-type {
      type Pm-measurement;
      description
        "Measurement Type of the session";
    }
    leaf periodic-advertisement-interval-in-sec {
      type uint32;
      units "second";
      description
        "Interval of periodic advertisement in seconds";
    }
    leaf query-number-of-hops {
      type uint8;
      description
        "Number of hops traversed by the query packet";
    }
    list probe-history {
      description
        "Current probe history";
      uses PM-SCB-SAMPLE-BAG;
    }
  }

  grouping PM-INTF-BAG {
    description
      "PM interface bag";
    container next-hop {
      description
        "Nexthop address of the interface";
      uses PM-IP-ADDR-TYPE;
    }
    container loss-measurement-session {
      description
        "Loss-measurement session";
      uses PM-INTF-LOSS-SESSION-BAG;
    }
    leaf interface-name-xr {
      type string;
      description
        "Name of the interface";
    }
    leaf interface-handle {
      type uint32;
      description
        "Ifhandle of the interface";
    }
    leaf interface-state {
      type boolean;
      description
        "State of the interface";
    }
    leaf source-address {
      type inet:ipv4-address;
      description
        "Source address of the interface";
    }
    leaf source-v6-address {
      type inet:ipv6-address;
      description
        "Source IPv6 Address of the interface";
    }
    leaf link-local-iv6-address {
      type inet:ipv6-address;
      description
        "Link local IPv6 of the interface";
    }
    leaf source-mac-address {
      type yang:mac-address;
      description
        "Source Mac address of the interface";
    }
    leaf next-hop-mac-address {
      type yang:mac-address;
      description
        "Next-hop Mac address of the next-hop IP address";
    }
    leaf primary-vlan-tag {
      type uint16;
      description
        "Primary VLAN Tag of the interface";
    }
    leaf secondary-vlan-tag {
      type uint16;
      description
        "Secondary VLAN Tag of the interface";
    }
    list delay-measurement-session {
      description
        "List of all the Delay-measurement sessions of
         the interface";
      uses PM-SCB-BAG;
    }
  }

  grouping PM-SUMMARY-RATE-LIMITING-BAG {
    description
      "PM Summary Rate Limiting bag";
    leaf maximum-packets-per-second {
      type uint32;
      units "packet/s";
      description
        "Total maximum packets per second allowed";
    }
    leaf interfaces-packets-per-second {
      type uint32;
      units "packet/s";
      description
        "Curent packets per second for interface
         performance measurement";
    }
    leaf multi-hop-maximum-packets-per-second {
      type uint32;
      units "packet/s";
      description
        "Maximum packets per second allowed for all multi
         hops sessions";
    }
    leaf multi-hop-requested-packets-per-second {
      type uint32;
      units "packet/s";
      description
        "Total packets per second requested for multi hop
         sessions";
    }
    leaf current-multi-hop-burst-interval-stretch-factor {
      type uint32;
      units "percentage";
      description
        "Multi hop session's burst interval stretch
         factor percentage current value";
    }
    leaf dampened-multi-hop-burst-interval-stretch-factor {
      type uint32;
      units "percentage";
      description
        "Multi hop session's burst interval stretch
         factor percentage dampened value";
    }
    leaf inuse-multi-hop-burst-interval-stretch-factor {
      type uint32;
      units "percentage";
      description
        "Multi hop session's burst interval stretch
         factor percentage inuse value";
    }
  }

  grouping PM-LOSS-TRANSPORT-SUMMARY-BAG {
    description
      "PM interface loss summary bag";
    container loss-transport-counters {
      description
        "TODO: PM loss counters for a transport types";
      uses PM-DELAY-COUNTERS-INFO-BAG;
    }
    leaf total-loss-sessions {
      type uint32;
      description
        "Number of loss measurement sessions enabled";
    }
  }

  grouping PM-LOSS-SUMMARY-BAG {
    description
      "PM Loss Summary bag";
    container interface-loss-summary {
      description
        "Interface loss summary";
      uses PM-LOSS-TRANSPORT-SUMMARY-BAG;
    }
    container delay-global-counters {
      description
        "PM delay global counters";
      uses PM-DELAY-GLOBAL-COUNTERS-BAG;
    }
  }

  grouping PM-DELAY-GLOBAL-COUNTERS-BAG {
    description
      "PM global counters";
    leaf query-packets-sent {
      type uint64;
      description
        "Number of query packets sent";
    }
    leaf query-packets-received {
      type uint64;
      description
        "Number of received query packets";
    }
    leaf received-packet-error-invalid-session-id {
      type uint64;
      description
        "Number of received packet error caused by
         invalid session ID";
    }
    leaf received-packet-error-no-session {
      type uint64;
      description
        "Number of received packet error caused by no
         session";
    }
  }

  grouping PM-DELAY-SESSION-COUNTER-BAG {
    description
      "PM delay session counter info bag";
    leaf total-delay-sessions {
      type uint32;
      description
        "Number of delay measurement sessions enabled";
    }
    leaf total-probe-running-with-error-delay-sessions {
      type uint32;
      description
        "Number of running with error delay measurement
         sessions";
    }
    leaf total-probe-running-delay-sessions {
      type uint32;
      description
        "Number of running delay measurement sessions";
    }
    leaf total-probe-running-ipv4-delay-sessions {
      type uint32;
      description
        "Number of running ipv4 delay measurement
         sessions";
    }
    leaf total-probe-running-ipv6-delay-sessions {
      type uint32;
      description
        "Number of running ipv6 delay measurement
         sessions";
    }
    leaf total-probe-running-mpls-delay-sessions {
      type uint32;
      description
        "Number of running mpls delay measurement
         sessions";
    }
  }

  grouping PM-DELAY-TRANSPORT-SUMMARY-BAG {
    description
      "PM interface delay summary bag";
    container delay-session-counters {
      description
        "PM delay session counters for a transport type";
      uses PM-DELAY-SESSION-COUNTER-BAG;
    }
    container delay-transport-counters {
      description
        "PM delay counters for a transport types";
      uses PM-DELAY-COUNTERS-INFO-BAG;
    }
  }

  grouping PM-DELAY-SUMMARY-BAG {
    description
      "PM Delay Summary bag";
    container interface-delay-summary {
      description
        "Summary info of Interface delay measurement";
      uses PM-DELAY-TRANSPORT-SUMMARY-BAG;
    }
    container sr-policy-delay-summary {
      description
        "Summary of SR Policy delay measurement";
      uses PM-DELAY-TRANSPORT-SUMMARY-BAG;
    }
    container rsvp-te-delay-summary {
      description
        "Summary of RSVP-TE delay measurement";
      uses PM-DELAY-TRANSPORT-SUMMARY-BAG;
    }
    container delay-global-counters {
      description
        "Global counters for PM delay measurement";
      uses PM-DELAY-GLOBAL-COUNTERS-BAG;
    }
  }

  grouping PM-SUMMARY-BAG {
    description
      "PM Summary bag";
    container delay-summary {
      description
        "Summary info of delay measurement";
      uses PM-DELAY-SUMMARY-BAG;
    }
    container loss-summary {
      description
        "Loss summary";
      uses PM-LOSS-SUMMARY-BAG;
    }
    container rate-limiting-information {
      description
        "Burst interval rate limiting information";
      uses PM-SUMMARY-RATE-LIMITING-BAG;
    }
    leaf total-interfaces {
      type uint32;
      description
        "Number of interfaces";
    }
    leaf total-sr-policies {
      type uint32;
      description
        "Number of SR Policies";
    }
    leaf total-rsvp-te-tunnels {
      type uint32;
      description
        "Number of RSVP-TE tunnels";
    }
  }

  grouping PM-RSVPTE-LSP-HISTORY-BAG {
    description
      "PM RSVP-TE LSP history bag";
    container history-union {
      description
        "History info of the RSVP-TE LSP";
      uses PM-HISTORY-SAMPLE-UNION;
    }
    leaf lsp-id {
      type uint32;
      description
        "LSP ID";
    }
  }

  grouping PM-RSVPTE-HISTORY-BAG {
    description
      "PM RSVP-TE tunnel history bag";
    leaf tunnel-name-xr {
      type string;
      description
        "RSVP-TE tunnel name";
    }
    list lsp {
      description
        "List of LSPs";
      uses PM-RSVPTE-LSP-HISTORY-BAG;
    }
  }

  grouping PM-RSVPTE-LSP-DELAY-METRICS-BAG {
    description
      "PM RSVP-TE LSP delay metrics bag";
    container metrics {
      description
        "LSP metrics";
      uses PM-VALUES-BAG;
    }
    leaf lsp-id {
      type uint32;
      description
        "LSP ID";
    }
    leaf timestamp {
      type uint64;
      units "millisecond";
      description
        "Time when the metrics were computed
         (milliseconds since Jan. 1, 1970)";
    }
  }

  grouping PM-RSVPTE-DELAY-METRICS-BAG {
    description
      "PM RSVP-TE tunnel delay metrics bag";
    leaf tunnel-name-xr {
      type string;
      description
        "RSVP-TE tunnel name";
    }
    list lsp {
      description
        "List of LSPs";
      uses PM-RSVPTE-LSP-DELAY-METRICS-BAG;
    }
  }

  grouping PM-RSVPTE-LSP-DELAY-BAG {
    description
      "PM RSVP-TE LSP delay bag";
    container last-probe-results {
      description
        "Last probe results of LSP";
      uses PM-SCB-PROBE-RESULTS-BAG;
    }
    container current-probe {
      description
        "Information for the current probe of the LSP";
      uses PM-SCB-PROBE-BAG;
    }
    container last-advertisement-information {
      description
        "Last advertisement information of the RSVP-TE
         LSP";
      uses PM-SCB-LAST-ADVERT-BAG;
    }
    container next-advertisement-information {
      description
        "Next advertisement information of the RSVP-TE
         LSP";
      uses PM-SCB-NEXT-ADVERT-BAG;
    }
    container last-notification-control-code {
      description
        "Last notifcation control code received of the
         RSVP-TE LSP";
      uses PM-SCB-CONTROL-CODE;
    }
    container last-error-control-code {
      description
        "Last error control code received of the RSVP-TE
         LSP";
      uses PM-SCB-CONTROL-CODE;
    }
    container responder-address {
      description
        "Address of the Responder";
      uses PM-IP-ADDR-TYPE;
    }
    leaf session-id {
      type uint32;
      description
        "Session ID of the LSP";
    }
    leaf lsp-id {
      type uint32;
      description
        "LSP ID";
    }
    leaf lsp-source-ipv4-address {
      type inet:ipv4-address;
      description
        "LSP Source IPv4 Address";
    }
    leaf periodic-advertisement-interval-in-sec {
      type uint32;
      units "second";
      description
        "Interval of periodic advertisement in seconds";
    }
    leaf query-number-of-hops {
      type uint8;
      description
        "Number of hops traversed by the query packet";
    }
    list probe-history {
      description
        "Current probe history of the LSP";
      uses PM-SCB-SAMPLE-BAG;
    }
  }

  grouping PM-RSVPTE-BAG {
    description
      "PM RSVP-TE bag";
    leaf tunnel-name-xr {
      type string;
      description
        "RSVP-TE tunnel name";
    }
    leaf interface-handle {
      type uint32;
      description
        "Ifhandle of the tunnel";
    }
    leaf tunnel-destination-ipv4-address {
      type inet:ipv4-address;
      description
        "IPv4 address destination of the tunnel";
    }
    list rsvptelsp-delay-session {
      description
        "RSVP-TE LSP delay-measurement sessions";
      uses PM-RSVPTE-LSP-DELAY-BAG;
    }
  }

  grouping PM-RSVPTE-LSP-DELAY-COUNTERS-BAG {
    description
      "RSVP-TE LSP delay counters bag";
    container counters {
      description
        "LSP counters";
      uses PM-DELAY-COUNTERS-INFO-BAG;
    }
    leaf lsp-id {
      type uint32;
      description
        "LSP ID";
    }
  }

  grouping PM-RSVPTE-COUNTERS-BAG {
    description
      "RSVP-TE tunnel counters bag";
    leaf tunnel-name-xr {
      type string;
      description
        "RSVP-TE tunnel name";
    }
    list rsvptelsp-delay-counter {
      description
        "List of LSPs";
      uses PM-RSVPTE-LSP-DELAY-COUNTERS-BAG;
    }
  }

  grouping PM-SRPOLICY-SEGMENT-LIST-COUNTERS-BAG {
    description
      "PM segment-list counters bag";
    container counters {
      description
        "Segment-list counters";
      uses PM-DELAY-COUNTERS-INFO-BAG;
    }
    leaf segment-list-name {
      type string;
      description
        "Segment-list name, not set if path is dynamic";
    }
    list segment {
      description
        "List of segments";
      uses PM-SEGMENT-BAG;
    }
  }

  grouping PM-INTF-EXCLUSIVE-DELAY-COUNTERS-INFO-BAG {
    description
      "PM exclusive counters bag for interface delay";
    leaf query-packet-sent-error-interface-down {
      type uint64;
      description
        "Number of query packets sent error caused by
         interface down";
    }
    leaf query-packet-sent-error-no-mpls-caps {
      type uint64;
      description
        "Number of query packets sent error caused by no
         MPLS caps";
    }
    leaf query-packet-sent-error-next-hop-mac-missing {
      type uint64;
      description
        "Number of query packets sent error caused by
         missing next hop MAC";
    }
  }

  grouping PM-EXCLUSIVE-DELAY-COUNTERS-INFO-UNION {
    description
      "Counters info type for interface, RSVP-TE LSP and
       SR Policy";
    container interface-exclusive-counters {
      when "../transport-type = 'interface-transport-type'" {
        description
          "../TransportType = 'InterfaceTransportType'";
      }
      description
        "Counters exclusive for interface";
      uses PM-INTF-EXCLUSIVE-DELAY-COUNTERS-INFO-BAG;
    }
    leaf transport-type {
      type Pm-transport;
      description
        "TransportType";
    }
  }

  grouping PM-QUERIER-DELAY-COUNTERS-BAG {
    description
      "PM delay querier counters";
    leaf query-packets-sent {
      type uint64;
      description
        "Number of query packets sent";
    }
    leaf query-packet-sent-errors {
      type uint64;
      description
        "Number of query packets sent error";
    }
    leaf query-packet-sent-error-no-ip-address {
      type uint64;
      description
        "Number of query packets sent error caused by no
         IP address";
    }
    leaf query-packets-received {
      type uint64;
      description
        "Number of received query packets";
    }
    leaf received-packet-error-negative-delay {
      type uint64;
      description
        "Number of packet error caused by receiving
         negative delay";
    }
    leaf received-packet-error-delay-exceeds-threshold {
      type uint64;
      description
        "Number of packet error caused by measured delay
         is invalid due to exceeding threshold";
    }
    leaf received-packet-error-missing-tx-timestamp {
      type uint64;
      description
        "Number of packet error caused by received packet
         is missing Tx timestamp";
    }
    leaf received-packet-error-missing-rx-timestamp {
      type uint64;
      description
        "Number of packet error caused by received packet
         is missing Rx timestamp";
    }
    leaf received-packet-error-probe-full {
      type uint64;
      description
        "Number of packet error caused by receiving
         packet when probe is full";
    }
    leaf received-packet-error-probe-not-started {
      type uint64;
      description
        "Number of packet error caused by receiving
         packet when probe is not started";
    }
    leaf received-packet-control-code-error {
      type uint64;
      description
        "Number of packet error caused by a control code
         error from responder";
    }
    leaf received-packet-control-code-notification {
      type uint64;
      description
        "Number of packet error caused by a control code
         notification from responder";
    }
    leaf probes-started {
      type uint64;
      description
        "Number of probes started";
    }
    leaf probes-complete {
      type uint64;
      description
        "Number of probes completed";
    }
    leaf probes-incomplete {
      type uint64;
      description
        "Number of probes incomplete";
    }
    leaf advertisement {
      type uint64;
      description
        "Number of advertisements";
    }
  }

  grouping PM-DELAY-COUNTERS-INFO-BAG {
    description
      "PM delay counters info bag";
    container generic-counters {
      description
        "Generic counters for a PM interface instance";
      uses PM-QUERIER-DELAY-COUNTERS-BAG;
    }
    container exclusive-counters {
      description
        "Exclusive counters for a PM interface instance";
      uses PM-EXCLUSIVE-DELAY-COUNTERS-INFO-UNION;
    }
  }

  grouping PM-SRPOLICY-CANDIDATE-PATH-COUNTERS-BAG {
    description
      "PM candidate-path counters bag";
    container counters {
      description
        "Candidate-path counters";
      uses PM-DELAY-COUNTERS-INFO-BAG;
    }
    leaf instance {
      type uint32;
      description
        "Session instance";
    }
    leaf preference {
      type uint32;
      description
        "Preference of the candidate-path";
    }
    leaf origin {
      type Pm-xtc-srpolicy-origin;
      description
        "Protocol origin";
    }
    leaf discriminator {
      type uint32;
      description
        "Discriminator of the candidate-path";
    }
    list segment-list-counter {
      description
        "List of counters for segment-lists in this
         candidate-path";
      uses PM-SRPOLICY-SEGMENT-LIST-COUNTERS-BAG;
    }
  }

  grouping PM-SRPOLICY-COUNTERS-BAG {
    description
      "PM SR Policy counters bag";
    leaf policy-name-xr {
      type string;
      description
        "Name of the SR Policy";
    }
    list candidate-counter {
      description
        "List of candidate path counters";
      uses PM-SRPOLICY-CANDIDATE-PATH-COUNTERS-BAG;
    }
  }

  grouping PM-SRPOLICY-HISTORY-ATOMIC-PATH-BAG {
    description
      "PM SR Policy atomic path history bag";
    container history-info {
      description
        "History info of the atomic path ";
      uses PM-HISTORY-SAMPLE-UNION;
    }
    list hop-address {
      description
        "Hop addresses list";
      uses PM-IP-ADDR-TYPE;
    }
  }

  grouping PM-SRPOLICY-HISTORY-SEGMENT-LIST-BAG {
    description
      "PM SR Policy segment-list history bag";
    container history-info {
      description
        "History info of the segment-list";
      uses PM-HISTORY-SAMPLE-UNION;
    }
    leaf segment-list-name {
      type string;
      description
        "Segment-list name, not set if path is dynamic";
    }
    list segment {
      description
        "List of segments";
      uses PM-SEGMENT-BAG;
    }
    list atomic-paths-history {
      description
        "List of atomic paths";
      uses PM-SRPOLICY-HISTORY-ATOMIC-PATH-BAG;
    }
  }

  grouping PM-LM-ADV-SAMPLE-BAG {
    description
      "LM advertisement sample";
    leaf timestamp {
      type uint64;
      units "millisecond";
      description
        "Timestamp (milliseconds since Jan. 1, 1970)";
    }
    leaf advertisement-reason {
      type Pm-advert-reason;
      description
        "Advertisement reason";
    }
    leaf loss-percentage {
      type uint32;
      units "percentage";
      description
        "Packet loss percentage";
    }
  }

  grouping PM-LM-ADV-HISTORY-BAG {
    description
      "PM LM advertisement history";
    list lm-advertisement-history {
      description
        "LM advertisement history";
      uses PM-LM-ADV-SAMPLE-BAG;
    }
  }

  grouping PM-LM-AGGR-SAMPLE-BAG {
    description
      "LM probe sample";
    leaf timestamp {
      type uint64;
      units "millisecond";
      description
        "Timestamp (milliseconds since Jan. 1, 1970)";
    }
    leaf num-sent-packet {
      type uint64;
      description
        "Number of packets been sent in this aggregation
         interval";
    }
    leaf num-received-packet {
      type uint64;
      description
        "Number of packets been received in this
         aggregation interval";
    }
    leaf loss-percentage {
      type uint32;
      units "percentage";
      description
        "Packet loss percentage";
    }
  }

  grouping PM-LM-AGGR-HISTORY-BAG {
    description
      "PM LM aggregation history";
    list lm-aggregated-hisotry {
      description
        "LM aggregation history";
      uses PM-LM-AGGR-SAMPLE-BAG;
    }
  }

  grouping PM-LM-PKT-SAMPLE-BAG {
    description
      "LM packet sample";
    leaf timestamp {
      type uint64;
      units "millisecond";
      description
        "Timestamp (milliseconds since Jan. 1, 1970)";
    }
    leaf tx-counter {
      type uint64;
      description
        "TX counter";
    }
    leaf rx-counter {
      type uint64;
      description
        "RX RX counter";
    }
  }

  grouping PM-LM-PKT-HISTORY-BAG {
    description
      "PM LM packet history";
    list lm-packet-hisotry {
      description
        "LM packet history";
      uses PM-LM-PKT-SAMPLE-BAG;
    }
  }

  grouping PM-LM-PROBE-SAMPLE-BAG {
    description
      "LM probe sample";
    leaf timestamp {
      type uint64;
      units "millisecond";
      description
        "Timestamp (milliseconds since Jan. 1, 1970)";
    }
    leaf num-sent-packet {
      type uint64;
      description
        "Number of packets been sent in this probe
         interval";
    }
    leaf num-received-packet {
      type uint64;
      description
        "Number of packets been received in this probe
         interval";
    }
    leaf loss-percentage {
      type uint32;
      units "percentage";
      description
        "Packet loss percentage";
    }
  }

  grouping PM-LM-PROBE-HISTORY-BAG {
    description
      "PM LM probe history";
    list lm-probe-hisotry {
      description
        "LM probe history";
      uses PM-LM-PROBE-SAMPLE-BAG;
    }
  }

  grouping PM-ADV-SAMPLE-BAG {
    description
      "PM advertisement history bag";
    container advertised-values {
      description
        "Advertised delay information";
      uses PM-VALUES-BAG;
    }
    leaf advertisement-timestamp {
      type uint64;
      units "millisecond";
      description
        "Time advertisement was done (milliseconds since
         Jan. 1, 1970)";
    }
    leaf advertisement-reason {
      type Pm-advert-reason;
      description
        "Reason for advertisement";
    }
  }

  grouping PM-ADV-HISTORY-BAG {
    description
      "PM advertisement history";
    list advertisement-history {
      description
        "List of samples of advertisement history records";
      uses PM-ADV-SAMPLE-BAG;
    }
  }

  grouping PM-AGGR-SAMPLE-BAG {
    description
      "PM aggregated delay probe history bag";
    container aggregated-probe-values {
      description
        "Summarised results of the aggregated probe";
      uses PM-VALUES-BAG;
    }
    leaf aggregation-timestamp {
      type uint64;
      units "millisecond";
      description
        "Time probe aggregation was done (milliseconds
         since Jan. 1, 1970)";
    }
  }

  grouping PM-AGGR-HISTORY-BAG {
    description
      "PM aggregated history";
    list aggregated-history {
      description
        "List of samples of aggregation history records";
      uses PM-AGGR-SAMPLE-BAG;
    }
  }

  grouping PM-PROBE-SAMPLE-BAG {
    description
      "PM delay probe history bag";
    container probe-values {
      description
        "Summarized results of the probe";
      uses PM-VALUES-BAG;
    }
    leaf probe-start-timestamp {
      type uint64;
      units "millisecond";
      description
        "Time last probe started (milliseconds since Jan.
         1, 1970)";
    }
    leaf packets-sent {
      type uint32;
      description
        "Number of query packets sent";
    }
    leaf packets-received {
      type uint32;
      description
        "Number of query Packets received";
    }
  }

  grouping PM-PROBE-HISTORY-BAG {
    description
      "PM probe history";
    list probe-history {
      description
        "List of samples of probe history records";
      uses PM-PROBE-SAMPLE-BAG;
    }
  }

  grouping PM-HISTORY-SAMPLE-UNION {
    description
      "PM history sample union";
    container probe-history {
      when "../history-type = 'history-type-probe'" {
        description
          "../HistoryType = 'HistoryTypeProbe'";
      }
      description
        "Info of delay-measurement probe history";
      uses PM-PROBE-HISTORY-BAG;
    }
    container aggregated-history {
      when "../history-type = 'history-type-aggregated'" {
        description
          "../HistoryType = 'HistoryTypeAggregated'";
      }
      description
        "Info of delay-measurement aggregation history";
      uses PM-AGGR-HISTORY-BAG;
    }
    container advertisement-history {
      when "../history-type = 'history-type-advertisement'" {
        description
          "../HistoryType = 'HistoryTypeAdvertisement'";
      }
      description
        "Info of delay-measurement advertisement history";
      uses PM-ADV-HISTORY-BAG;
    }
    container lm-probe-history {
      when "../history-type = 'history-type-lm-probe'" {
        description
          "../HistoryType = 'HistoryTypeLMProbe'";
      }
      description
        "Info of loss-measurement probe history";
      uses PM-LM-PROBE-HISTORY-BAG;
    }
    container lm-packet-history {
      when "../history-type = 'history-type-lm-packet'" {
        description
          "../HistoryType = 'HistoryTypeLMPacket'";
      }
      description
        "Info of loss-measurement packet history";
      uses PM-LM-PKT-HISTORY-BAG;
    }
    container lm-aggregated-history {
      when "../history-type = 'history-type-lm-aggregated'" {
        description
          "../HistoryType = 'HistoryTypeLMAggregated'";
      }
      description
        "Info of loss-measurement aggregation history";
      uses PM-LM-AGGR-HISTORY-BAG;
    }
    container lm-advertisement-history {
      when "../history-type = 'history-type-lm-advertisement'" {
        description
          "../HistoryType = 'HistoryTypeLMAdvertisement'";
      }
      description
        "Info of loss-measurement advertisement history";
      uses PM-LM-ADV-HISTORY-BAG;
    }
    leaf history-type {
      type Pm-history;
      description
        "HistoryType";
    }
  }

  grouping PM-SRPOLICY-HISTORY-CANDIDATE-PATH-BAG {
    description
      "PM SR Policy segment-list history bag";
    container history-info {
      description
        "History info of the candidate-path";
      uses PM-HISTORY-SAMPLE-UNION;
    }
    leaf preference {
      type uint32;
      description
        "Preference of the candidate-path";
    }
    leaf origin {
      type Pm-xtc-srpolicy-origin;
      description
        "Protocol origin";
    }
    leaf discriminator {
      type uint32;
      description
        "Discriminator of the candidate-path";
    }
    list segment-lists-history {
      description
        "List of segment-lists";
      uses PM-SRPOLICY-HISTORY-SEGMENT-LIST-BAG;
    }
  }

  grouping PM-SRPOLICY-HISTORY-BAG {
    description
      "PM SR Policy history bag";
    container end-point-address {
      description
        "IPv4/IPv6 End point address";
      uses PM-IP-ADDR-TYPE;
    }
    leaf color {
      type uint32;
      description
        "Color";
    }
    leaf policy-name {
      type string;
      description
        "Name of the SR Policy";
    }
    list candidate-paths-history {
      description
        "List of candidate-paths";
      uses PM-SRPOLICY-HISTORY-CANDIDATE-PATH-BAG;
    }
  }

  grouping PM-SRPOLICY-METRICS-ATOMIC-PATH-BAG {
    description
      "PM SR Policy atomic path metrics bag";
    container metrics {
      description
        "Atomic Path metrics";
      uses PM-VALUES-BAG;
    }
    list hop-address {
      description
        "Hop addresses list";
      uses PM-IP-ADDR-TYPE;
    }
    list label {
      description
        "MPLS labels";
      leaf entry {
        type uint32;
        description
          "MPLS labels";
      }
    }
  }

  grouping PM-SRPOLICY-SEGMENT-LIST-METRICS-BAG {
    description
      "PM SR Policy segment-list metrics bag";
    container metrics {
      description
        "Segment-list metrics";
      uses PM-VALUES-BAG;
    }
    leaf segment-list-name {
      type string;
      description
        "Segment-list name, not set if path is dynamic";
    }
    list segment {
      description
        "List of segments";
      uses PM-SEGMENT-BAG;
    }
    list atomic-path {
      description
        "List of atomic paths";
      uses PM-SRPOLICY-METRICS-ATOMIC-PATH-BAG;
    }
  }

  grouping PM-SRPOLICY-CANDIDATE-PATH-METRICS-BAG {
    description
      "PM SR Policy candidate-path metrics bag";
    container metrics {
      description
        "Candidate-path metrics";
      uses PM-VALUES-BAG;
    }
    leaf instance {
      type uint32;
      description
        "Session instance";
    }
    leaf preference {
      type uint32;
      description
        "Preference of the candidate-path";
    }
    leaf origin {
      type Pm-xtc-srpolicy-origin;
      description
        "Protocol origin";
    }
    leaf discriminator {
      type uint32;
      description
        "Discriminator of the candidate-path";
    }
    leaf timestamp {
      type uint64;
      units "millisecond";
      description
        "Time when the metrics were computed
         (milliseconds since Jan. 1, 1970)";
    }
    list segment-list {
      description
        "List of segment-lists";
      uses PM-SRPOLICY-SEGMENT-LIST-METRICS-BAG;
    }
  }

  grouping PM-SRPOLICY-METRICS-BAG {
    description
      "PM SR Policy metrics bag";
    leaf policy-name {
      type string;
      description
        "Name of the SR Policy";
    }
    list candidate-path {
      description
        "List of candidate-paths";
      uses PM-SRPOLICY-CANDIDATE-PATH-METRICS-BAG;
    }
  }

  grouping PM-SCB-SAMPLE-BAG {
    description
      "PM delay probe sample bag";
    leaf measurement-value {
      type uint64;
      description
        "Measurement value (nsec)";
    }
    leaf query-timestamp {
      type uint64;
      units "millisecond";
      description
        "Timestamp when the measurement was taken
         (milliseconds since Jan. 1, 1970)";
    }
  }

  grouping PM-SRPOLICY-ATOMIC-PATH-BAG {
    description
      "PM SR Policy atomic path bag";
    container last-advertisement-information {
      description
        "Last advertisement information of the atomic
         path";
      uses PM-SCB-LAST-ADVERT-BAG;
    }
    container next-advertisement-information {
      description
        "Current advertisement information of the atomic
         path";
      uses PM-SCB-NEXT-ADVERT-BAG;
    }
    container current-probe-results {
      description
        "Current probe results of the atomic path";
      uses PM-SCB-PROBE-RESULTS-BAG;
    }
    container last-probe-results {
      description
        "Last probe results of the atomic path";
      uses PM-SCB-PROBE-RESULTS-BAG;
    }
    container liveness-detection-info {
      description
        "Information for liveness detection";
      uses PM-SCB-LIVENESS-STATE-INFO-BAG;
    }
    container last-notification-control-code {
      description
        "Last notifcation control code received of the
         atomic path";
      uses PM-SCB-CONTROL-CODE;
    }
    container last-error-control-code {
      description
        "Last error control code received of the atomic
         path";
      uses PM-SCB-CONTROL-CODE;
    }
    container responder-address {
      description
        "Address of the Responder";
      uses PM-IP-ADDR-TYPE;
    }
    leaf outgoing-interface {
      type uint32;
      description
        "Outgoing interface of the atomic path";
    }
    leaf session-id {
      type uint32;
      description
        "Session ID of the atomic path";
    }
    leaf liveness-detection-enabled {
      type boolean;
      description
        "Liveness detection is enabled";
    }
    leaf query-number-of-hops {
      type uint8;
      description
        "Number of hops traversed by the query packet";
    }
    list hop-address {
      description
        "Hop addresses list";
      uses PM-IP-ADDR-TYPE;
    }
    list label {
      description
        "MPLS labels of the atomic path";
      leaf entry {
        type uint32;
        description
          "MPLS labels of the atomic path";
      }
    }
    list current-probe-history {
      description
        "Current probe history of the atomic path";
      uses PM-SCB-SAMPLE-BAG;
    }
  }

  grouping PM-SEGMENT-BAG {
    description
      "PM segment information";
    container ip-address {
      description
        "Segment IP address";
      uses PM-IP-ADDR-TYPE;
    }
    leaf mpls-label {
      type uint32;
      description
        "Segment mpls label";
    }
  }

  grouping PM-SRPOLICY-SEGMENT-LIST-BAG {
    description
      "PM SR Policy segment-list bag";
    container last-advertisement-information {
      description
        "Last advertisement information of the
         segment-list";
      uses PM-SCB-LAST-ADVERT-BAG;
    }
    container next-advertisement-information {
      description
        "Current advertisement information of the
         segment-list";
      uses PM-SCB-NEXT-ADVERT-BAG;
    }
    container current-probe-results {
      description
        "Current probe results of the segment-list";
      uses PM-SCB-PROBE-RESULTS-BAG;
    }
    container last-probe-results {
      description
        "Last probe results of the segment-list";
      uses PM-SCB-PROBE-RESULTS-BAG;
    }
    container liveness-detection-info {
      description
        "Information for liveness detection";
      uses PM-SCB-LIVENESS-STATE-INFO-BAG;
    }
    container last-notification-control-code {
      description
        "Last notifcation control code received of the
         segment-list";
      uses PM-SCB-CONTROL-CODE;
    }
    container last-error-control-code {
      description
        "Last error control code received of the
         segment-list";
      uses PM-SCB-CONTROL-CODE;
    }
    leaf segment-list-name {
      type string;
      description
        "Name of the segment-list";
    }
    leaf atomic-path-total-count {
      type uint32;
      description
        "Number of atomic paths in the segment-list";
    }
    leaf liveness-detection-enabled {
      type boolean;
      description
        "Liveness detection is enabled";
    }
    list segment {
      description
        "List of segments";
      uses PM-SEGMENT-BAG;
    }
    list atomic-path {
      description
        "List of atomic paths";
      uses PM-SRPOLICY-ATOMIC-PATH-BAG;
    }
  }

  grouping PM-SCB-LIVENESS-STATE-INFO-BAG {
    description
      "Liveness detection session state information";
    leaf session-is-up {
      type boolean;
      description
        "Liveness session state";
    }
    leaf miss-count {
      type uint32;
      description
        "Number of continuously missed probe packets";
    }
    leaf last-session-state-change-timestamp {
      type uint64;
      description
        "Timestamp of the last liveness session state
         change";
    }
  }

  grouping PM-SCB-CONTROL-CODE {
    description
      "Last received control code";
    leaf control-code {
      type uint8;
      description
        "MPLS PM RFC 6374 control code";
    }
    leaf timestamp {
      type uint64;
      units "millisecond";
      description
        "Received timestamp of the control code
         (milliseconds since Jan. 1, 1970)";
    }
  }

  grouping PM-SCB-PROBE-BAG {
    description
      "PM delay probe bag";
    container probe-results {
      description
        "Summarized  results of the current probe";
      uses PM-VALUES-BAG;
    }
    leaf probe-start-time-stamp {
      type uint64;
      units "millisecond";
      description
        "Timestamp in milliseconds of the current probe
         start (milliseconds since Jan. 1, 1970)";
    }
    leaf next-probe-start-time-remaining-in-millisec {
      type uint32;
      units "millisecond";
      description
        "Time in milliseconds until the next probe starts";
    }
    leaf next-packet-sent-time-remaining-in-millisec {
      type uint32;
      units "millisecond";
      description
        "Time in milliseconds until the next packet is
         sent";
    }
    leaf burst-interval {
      type uint32;
      units "millisecond";
      description
        "Burst interval (in milliseconds)";
    }
    leaf burst-interval-is-stretched {
      type boolean;
      description
        "True if the burst interval has been stretched
         for packet rate-limiting";
    }
    leaf number-of-packets-sent {
      type uint32;
      description
        "Number of packets sent in the current probe";
    }
    leaf number-of-packets-received {
      type uint32;
      description
        "Number of packets received in the current probe";
    }
    leaf probe-not-running-reason {
      type Pm-probe-not-running-reason;
      description
        "Reason why probe is not running";
    }
  }

  grouping PM-SCB-PROBE-RESULTS-BAG {
    description
      "PM probe results bag";
    container probe-values {
      description
        "Summarized results of the probe";
      uses PM-VALUES-BAG;
    }
    leaf number-of-packets-sent {
      type uint32;
      description
        "Number of packets sent in the probe";
    }
    leaf number-of-packets-received {
      type uint32;
      description
        "Number of packets received in the probe";
    }
  }

  grouping PM-SCB-NEXT-ADVERT-BAG {
    description
      "PM delay next advertisement bag";
    container advertisement-interval-values {
      description
        "Next advertisement values";
      uses PM-VALUES-BAG;
    }
    leaf advertisement-interval-probes-remaining {
      type uint32;
      description
        "Probes remaining until next periodic
         advertisement check";
    }
    leaf rolling-average {
      type uint32;
      description
        "Rolling average value (uSec)";
    }
  }

  grouping PM-VALUES-BAG {
    description
      "PM delay summarized delay values";
    leaf average {
      type uint32;
      description
        "Average value (uSec)";
    }
    leaf minimum {
      type uint32;
      description
        "Minimum value (uSec)";
    }
    leaf maximum {
      type uint32;
      description
        "Maximum value (uSec)";
    }
    leaf variance {
      type uint32;
      description
        "Variance value (uSec)";
    }
  }

  grouping PM-SCB-LAST-ADVERT-BAG {
    description
      "PM delay last advertisement bag";
    container advertised-values {
      description
        "Advertised delay information";
      uses PM-VALUES-BAG;
    }
    leaf time-of-advertisement {
      type uint64;
      units "millisecond";
      description
        "Time of the advertisement (milliseconds since
         Jan. 1, 1970)";
    }
    leaf advertisement-reason {
      type Pm-advert-reason;
      description
        "Reason for advertisement";
    }
  }

  grouping PM-SRPOLICY-CANDIDATE-PATH-BAG {
    description
      "PM SR Policy candidate-path bag";
    container last-advertisement-information {
      description
        "Last advertisement information of the
         candidate-path";
      uses PM-SCB-LAST-ADVERT-BAG;
    }
    container next-advertisement-information {
      description
        "Current advertisement information of the
         candidate-path";
      uses PM-SCB-NEXT-ADVERT-BAG;
    }
    container last-probe-results {
      description
        "Last probe results of candidate-path";
      uses PM-SCB-PROBE-RESULTS-BAG;
    }
    container current-probe {
      description
        "Information for the current probe";
      uses PM-SCB-PROBE-BAG;
    }
    container last-notification-control-code {
      description
        "Last notifcation control code received of the
         candidate-path";
      uses PM-SCB-CONTROL-CODE;
    }
    container last-error-control-code {
      description
        "Last error control code received of the
         candidate-path";
      uses PM-SCB-CONTROL-CODE;
    }
    container liveness-detection-info {
      description
        "Information for liveness detection";
      uses PM-SCB-LIVENESS-STATE-INFO-BAG;
    }
    leaf instance {
      type uint32;
      description
        "Session instance";
    }
    leaf preference {
      type uint32;
      description
        "Preference of the candidate-path";
    }
    leaf origin {
      type Pm-xtc-srpolicy-origin;
      description
        "Protocol-origin of the candidate-path";
    }
    leaf discriminator {
      type uint32;
      description
        "Discriminator of the candidate-path";
    }
    leaf source-address-v4 {
      type inet:ipv4-address;
      description
        "Source address of the candidate-path";
    }
    leaf reverse-path-label {
      type uint32;
      description
        "Reverse-path label";
    }
    leaf periodic-advertisement-interval-in-sec {
      type uint32;
      units "second";
      description
        "Interval of periodic advertisement in seconds";
    }
    leaf liveness-detection-enabled {
      type boolean;
      description
        "Liveness detection is enabled";
    }
    leaf segment-list-total-count {
      type uint32;
      description
        "Number of segment lists in the candidate-path";
    }
    list segment-list {
      description
        "List of segment-lists";
      uses PM-SRPOLICY-SEGMENT-LIST-BAG;
    }
  }

  grouping PM-IP-ADDR-TYPE {
    description
      "IPv4/IPv6 address type";
    leaf ip-address-type {
      type Pm-addr;
      description
        "IPAddressType";
    }
    leaf ipv4 {
      when "../ip-address-type = 'ipv4'" {
        description
          "../IPAddressType = 'IPv4'";
      }
      type Pm-ipv4-addr;
      description
        "IPv4 address type";
    }
    leaf ipv6 {
      when "../ip-address-type = 'ipv6'" {
        description
          "../IPAddressType = 'IPv6'";
      }
      type Pm-ipv6-addr;
      description
        "IPv6 address type";
    }
  }

  grouping PM-SRPOLICY-BAG {
    description
      "PM SR Policy bag";
    container end-point-address {
      description
        "IPv4/IPv6 End point address";
      uses PM-IP-ADDR-TYPE;
    }
    leaf color {
      type uint32;
      description
        "Color";
    }
    leaf policy-name-xr {
      type string;
      description
        "Name of the SR Policy";
    }
    leaf candidate-path-total-count {
      type uint32;
      description
        "Number of candidate-paths in the SR Policy";
    }
    list candidate-path {
      description
        "List of candidate-paths";
      uses PM-SRPOLICY-CANDIDATE-PATH-BAG;
    }
  }
}
