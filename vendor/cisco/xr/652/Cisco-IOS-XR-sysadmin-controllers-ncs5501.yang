module Cisco-IOS-XR-sysadmin-controllers-ncs5501 {
  namespace "http://www.cisco.com/ns/yang/Cisco-IOS-XR-sysadmin-controllers-NCS5501";
  prefix calvados_controllers;
  import Cisco-IOS-XR-sysadmin-fabric-ncs5501 {
    prefix fabric;
  }
  import Cisco-IOS-XR-sysadmin-card-mgr {
    prefix card_mgr;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

This module defines the top level container for
all hardware devices managed in Sysadmin.

Copyright(c) 2015-2016 by Cisco Systems, Inc.
All rights reserved.

    Copyright (c) 2012-2018 by Cisco Systems, Inc.
     All rights reserved.";
  revision 2017-10-11 {
    description
      "Changed the namespace to unique namespace per unique model";
  }

  container controller {
    uses fabric:fabric;
    uses card_mgr:card_mgr-group;
  }
}
