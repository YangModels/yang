module Cisco-IOS-XR-sysadmin-tacacs-tacacs-server {
  namespace "http://www.cisco.com/ns/yang/Cisco-IOS-XR-sysadmin-tacacs-tacacs-server";
  prefix tacacs-server;
  import tailf-common {
    prefix tailf;
  }
  import ietf-inet-types {
    prefix inet;
  }
  organization "Cisco Systems";
  contact
    "aaa-ng-tacacs-dev@cisco.com";

  description 
    "This module contains definitions
     for the Calvados model objects.

    This module defines the TACACS+ data model.

    Copyright (c) 2012-2018 by Cisco Systems, Inc.
     All rights reserved.";
  revision 2017-05-10 {
    description
      "Namespace changed from tacacs to Cisco-IOS-XR-sysadmin-tacacs-tacacs-server";
  }


  typedef passwdStr {
    type tailf:aes-cfb-128-encrypted-string;
  }
  container tacacs-server {
    list host {
      max-elements "10";
      key "ip port";
      ordered-by user;
      leaf ip {
        type inet:ip-address;
      }
      leaf port {
        type inet:port-number {
          range "1 .. 65535";
        }
      }
      leaf timeout {
        type uint32 {
          range "1 .. 1000";
        }
      }
      leaf key {
        type passwdStr;
      }
    }
    leaf timeout {
      type uint32 {
        range "1 .. 1000";
      }
    }
    leaf key {
      type passwdStr;
    }
  }
}
