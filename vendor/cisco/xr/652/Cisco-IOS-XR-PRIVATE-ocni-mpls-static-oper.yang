module Cisco-IOS-XR-PRIVATE-ocni-mpls-static-oper {
  namespace "http://cisco.com/ns/yang/Cisco-IOS-XR-PRIVATE-ocni-mpls-static-oper";
  prefix private-ocni-mpls-static-oper;

  include Cisco-IOS-XR-PRIVATE-ocni-mpls-static-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR PRIVATE-ocni-mpls-static package operational data.
     
     This module contains definitions
     for the following management objects:
       ocni-mpls-static: An OpenConfig description of a
         network-instance
     
     Copyright (c) 2013-2018 by Cisco Systems, Inc.
     All rights reserved.";

  revision 2015-11-09 {
    description
      "IOS XR 6.0 revision.";
  }

  container ocni-mpls-static {
    config false;
    description
      "An OpenConfig description of a network-instance";
    container network-instances {
      description
        "Network instances configured on the local system";
      list network-instance {
        key "name";
        description
          "Network instances configured on the local
           system";
        container mpls {
          description
            "Anchor point for mpls configuration and
             operational data";
          container lsps {
            description
              "LSP definitions and configuration";
            container static-lsps {
              description
                "list of defined static LSPs";
              list static-lsp {
                key "name";
                description
                  "list of defined static LSPs";
                leaf name {
                  type string;
                  description
                    "Reference the name list key";
                }
                uses OVERLAY-OCNI-MPLS-STATIC-STATIC-LSP;
              }
            }
          }
        }
        leaf name {
          type string;
          description
            "A unique name identifying the network instance";
        }
      }
    }
  }
}
