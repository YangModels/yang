module control_driver {
  namespace "http://cisco.com/calvados/control_driver";
  prefix control_driver;

  import tailf-common {
    prefix tailf;
  }
  import Cisco-IOS-XR-sysadmin-show-trace {
    prefix show_trace;
  }

  container control_driver {
    config false;
    tailf:callpoint "ctrl_driver-top-level-catchall";
    uses show_trace:traceable;
  }
}
