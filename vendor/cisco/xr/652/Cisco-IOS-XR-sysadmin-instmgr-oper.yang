module Cisco-IOS-XR-sysadmin-instmgr-oper {
  namespace "http://www.cisco.com/ns/yang/Cisco-IOS-XR-sysadmin-instmgr-oper";
  prefix install;
  import tailf-common {
    prefix tailf;
  }
  organization "Cisco Systems Inc.";
  contact
    "Cisco Systems, Inc.
     Customer Service
     
     Postal: 170 West Tasman Drive
     San Jose, CA 95134
     
     Tel: +1 800 553-NETS
     E-mail: cs-yang@cisco.com";

  description 
    "This module contains definitions
     for the Calvados model objects.

    This module contains a collection of YANG
definitions for Cisco IOS-XR sysadmin-instmgr 
operational model

    Copyright (c) 2012-2018 by Cisco Systems, Inc.
     All rights reserved.";
  revision 2017-10-13 {
    description
      "Changed file name's suffix from -cfg.yang to -oper.yang";
  }


  typedef install_add_pkg_type {
    type string {
    }
  }

  typedef install_add_source_type {
    type string {
    }
  }

  typedef install_backup_zipfile {
    type string {
    }
  }

  typedef install_pkg_type {
    type string {
    }
  }

  typedef install_node_type {
    type string {
    }
  }

  typedef install_node_wildcard_type {
    type string {
    }
  }

  typedef install_id_type {
    type uint32 {
    }
  }

  typedef install_log_id_type {
    type uint32 {
    }
  }

  typedef node_location_type {
    type string {
      pattern "((0?[0-9]|1[1-5])/(([rR][pP]|[lL][cC])?\\d{1,2}))(/[cC][pP][uU]0)?|all";
    }
    description
      "A system location in Rack/Slot/Instance";
  }

  typedef install_which_file {
    type string {
    }
  }
  container install {
    config false;
    container version {
      description
        "Gives sysadmin version information";
      leaf-list img_info {
        type string;
      }
    }
    container inactive {
      description
        "Calvados inactive package(s) list for this node";
      container summary {
        description
          "shows summary information of the inactive install software";
        leaf-list si_inactive_summary_output {
          type string;
        }
      }
      leaf-list si_inactive_output {
        type string;
      }
    }
    container prepare {
      description
        "Calvados prepared package(s) list for this node";
      leaf-list si_prepare_output {
        type string;
      }
    }
    container package {
      description
        "Package Name(s) to get info for";
      list pkg_list {
        key "pkg_name";
        leaf pkg_name {
          type string;
        }
        container detail {
          leaf-list si_package_detail_output {
            type string;
          }
        }
        container verbose {
          leaf-list si_package_verbose_output {
            type string;
          }
        }
        leaf-list si_package_output {
          type string;
        }
      }
    }
    container active {
      description
        "Calvados active package(s) list for this node";
      container summary {
        description
          "shows summary information of the active install software";
        leaf-list si_active_summary_output {
          type string;
        }
      }
      leaf-list si_active_output {
        type string;
      }
    }
    container superseded {
      description
        "Calvados superseded package(s) list for this node";
      container summary {
        description
          "shows summary information of the show install superseded";
        leaf-list si_superseded_summary_output {
          type string;
        }
      }
      leaf-list si_superseded_output {
        type string;
      }
    }
    container request {
      description
        "Sysadmin current install operation details";
      leaf-list curr_inst_oper {
        type string;
      }
    }
    container repository {
      description
        "Shows information about the install software repository.";
      container all {
        description
          "shows contents of all the install software repositories";
        leaf-list si_repository_all_output {
          type string;
        }
      }
      leaf-list si_repository_output {
        type string;
      }
    }
    container log {
      list id {
        key "opid";
        leaf opid {
          type install_log_id_type;
        }
        container detail {
          leaf-list si_log_id_detail_output {
            type string;
          }
        }
        leaf-list si_log_id_output {
          type string;
        }
      }
      container reverse {
        container detail {
          leaf-list si_log_reverse_detail_output {
            type string;
          }
        }
        leaf-list si_log_reverse_output {
          type string;
        }
      }
      container detail {
        leaf-list si_log_detail_output {
          type string;
        }
      }
      leaf-list si_log_output {
        type string;
      }
    }
    container which {
      description
        "Filename to get info for";
      list file_list {
        key "file_name";
        leaf file_name {
          type string {
          }
        }
        container detail {
          leaf-list si_which_detail_output {
            type string;
          }
        }
        leaf-list si_which_output {
          type string;
        }
      }
    }
    container committed {
      description
        "Calvados committed package(s) list for this node";
      container summary {
        description
          "shows summary information of the committed install software";
        leaf-list si_committed_summary_output {
          type string;
        }
      }
      leaf-list si_committed_output {
        type string;
      }
    }
    tailf:action "activate-internal-nopackages" {
      description
        "Install activate";
      input {
        choice prompt_choice {
          mandatory false;
          case noprompt_choice {
            leaf noprompt {
              mandatory false;
              type empty;
            }
          }
        }
      }
      output {
        leaf result {
          type string;
        }
      }
    }
    tailf:action "activate-internal-packages" {
      description
        "Install activate";
      input {
        choice prompt_choice {
          mandatory false;
          case noprompt_choice {
            leaf noprompt {
              mandatory false;
              type empty;
            }
          }
        }
        choice activate_choice {
          mandatory true;
          case package_choice {
            leaf-list packages {
              type string;
              description
                "List of packages to activate";
            }
          }
          case location_choice {
            leaf-list locationlist {
              type string;
              description
                "List of nodes where Activate is requested";
            }
          }
          case id_choice {
            leaf-list idlist {
              type uint32;
              description
                "IDs of add operations whose packages are to be activated";
            }
          }
        }
      }
      output {
        leaf result {
          type string;
        }
      }
    }
    tailf:action "add-internal" {
      description
        "Install scp add operation implemenation";
      input {
        leaf addtype {
          type enumeration {
            enum "cp";
            enum "tftp";
            enum "scp";
            enum "sftp";
            enum "ftp";
          }
        }
        leaf src {
          type string;
          mandatory false;
        }
        leaf user {
          type string;
          mandatory false;
        }
        leaf password {
          type string;
          mandatory false;
        }
        leaf server {
          type string;
          mandatory false;
        }
        leaf source_dir {
          type string;
        }
        leaf-list files {
          type string;
        }
      }
      output {
        leaf result {
          type string;
        }
      }
    }
    tailf:action "prepare-internal" {
      description
        "Install prepare";
      input {
        choice prepare_choice {
          mandatory true;
          case package_choice {
            leaf-list packages {
              type string;
              description
                "List of packages to prepare";
            }
          }
          case clean_choice {
            leaf clean {
              type empty;
              mandatory false;
              description
                "clean prepare";
            }
          }
          case id_choice {
            leaf-list idlist {
              type uint32;
              description
                "IDs of add operations whose packages are to be prepared";
            }
          }
        }
      }
      output {
        leaf result {
          type string;
        }
      }
    }
    tailf:action "deactivate-internal" {
      description
        "Install deactivate";
      input {
        choice prompt_choice {
          mandatory false;
          case noprompt_choice {
            leaf noprompt {
              mandatory false;
              type empty;
            }
          }
        }
        choice deactivate_choice {
          mandatory true;
          case package_choice {
            leaf-list packages {
              type string;
              description
                "List of packages to deactivate";
            }
          }
          case id_choice {
            leaf-list idlist {
              type uint32;
              description
                "IDs of add operations whose packages are to be deactivated";
            }
          }
          case superseded_choice {
            leaf superseded {
              type empty;
              description
                "Remove Sysadmin superseded packages";
            }
          }
        }
      }
      output {
        leaf result {
          type string;
        }
      }
    }
    tailf:action "extract-internal" {
      description
        "Install extract";
      input {
        choice remove_choice {
          mandatory true;
          case package_choice {
            leaf-list packages {
              type string;
              description
                "List of packages to extracted";
            }
          }
          case id_choice {
            leaf-list idlist {
              type uint32;
              description
                "IDs of add operations whose packages are to be extracted";
            }
          }
        }
      }
      output {
        leaf result {
          type string;
        }
      }
    }
    tailf:action "remove-internal" {
      description
        "Install remove";
      input {
        choice remove_choice {
          mandatory true;
          case package_choice {
            leaf-list packages {
              type string;
              description
                "List of packages to remove";
            }
          }
          case id_choice {
            leaf-list idlist {
              type uint32;
              description
                "IDs of add operations whose packages are to be removed";
            }
          }
          case inactive_choice {
            leaf inactive {
              type empty;
              description
                "Remove Sysadmin inactive packages";
            }
          }
        }
      }
      output {
        leaf result {
          type string;
        }
      }
    }
    tailf:action "commit-internal" {
      description
        "Install commit";
      output {
        leaf result {
          type string;
        }
      }
    }
    tailf:action "verify-internal-packages" {
      description
        "Install verify";
      input {
        choice location_choice {
          mandatory true;
          case location {
            leaf-list locations {
              type string;
              description
                "locations at which packages are to be verified";
            }
          }
        }
      }
      output {
        leaf result {
          type string;
        }
      }
    }
    tailf:action "verify-internal-nolocation" {
      description
        "Install verify";
      output {
        leaf result {
          type string;
        }
      }
    }
    tailf:action "backup-internal-cli" {
      description
        "Install Backup";
      input {
        choice location_choice {
          mandatory true;
          case location {
            leaf-list locations {
              type string;
              description
                "locations at which recovery image to be updated ";
            }
          }
        }
      }
      output {
        leaf result {
          type string;
        }
      }
    }
  }
}
