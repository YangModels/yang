module Cisco-IOS-XR-sysadmin-dumper {
  namespace "http://www.cisco.com/ns/yang/Cisco-IOS-XR-sysadmin-dumper";
  prefix dumper;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin dumper to
configure file path options to copy the core files to.

Copyright(c) 2015-2017 by Cisco Systems, Inc.
All rights reserved.

    Copyright (c) 2012-2018 by Cisco Systems, Inc.
     All rights reserved.";
  revision 2017-05-09 {
    description
      "Modified module name, namespace and filename 
       to adhere to standard notation";
  }

  container exception {
    list choice {
      key "order";
      leaf order {
        type int32 {
          range "1 .. 3";
        }
      }
      leaf filepath {
        type string;
        mandatory true;
      }
    }
  }
}
