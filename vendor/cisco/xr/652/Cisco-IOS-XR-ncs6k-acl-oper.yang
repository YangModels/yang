module Cisco-IOS-XR-ncs6k-acl-oper {
  namespace "http://cisco.com/ns/yang/Cisco-IOS-XR-ncs6k-acl-oper";
  prefix ncs6k-acl-oper;

  import Cisco-IOS-XR-types {
    prefix xr;
  }
  include Cisco-IOS-XR-ncs6k-acl-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs6k-acl package operational data.
     
     This module contains definitions
     for the following management objects:
       access-list-hardware: Root class of accesslist hardware
     
     Copyright (c) 2013-2018 by Cisco Systems, Inc.
     All rights reserved.";

  revision 2017-09-07 {
    description
      "Fixed type translation error.";
  }
  revision 2017-05-01 {
    description
      "adding PD yang.";
  }
  revision 2015-11-09 {
    description
      "IOS XR 6.0 revision.";
  }

  grouping ACCESS-LIST-TABLE {
    description
      "Common node of ipv4, ipv6";
    container accesses {
      description
        "Table for access lists";
      list access {
        key "access-list-name";
        description
          "List of ACLs";
        container implicit {
          description
            "Implicit ACL information";
          uses SSE-PFILTER-EA-ACE-IMPLICIT;
        }
        container sequence-details {
          description
            "Table of all sequence numbers per ACL";
          list sequence-detail {
            key "sequence-number";
            description
              "Detail ACL information";
            leaf sequence-number {
              type uint32;
              description
                "Detail ACL information for a particular
                 sequence";
            }
            uses SSE-PFILTER-EA-ACE-DETAIL;
          }
        }
        container sequence-briefs {
          description
            "Table of all sequence numbers per ACL";
          list sequence-brief {
            key "sequence-number";
            description
              "Detail ACL information";
            leaf sequence-number {
              type uint32;
              description
                "Brief ACL information for a particular
                 sequence";
            }
            uses SSE-PFILTER-EA-ACE-BRIEF;
          }
        }
        leaf access-list-name {
          type string;
          description
            "Name of the access list";
        }
      }
    }
  }

  grouping IPV4 {
    description
      "Common node of egress, ingress";
    container ipv4 {
      description
        "Accesslist version IPv4";
      uses ACCESS-LIST-TABLE;
    }
  }

  grouping IPV6 {
    description
      "Common node of egress, ingress";
    container ipv6 {
      description
        "Accesslist version IPv6";
      uses ACCESS-LIST-TABLE;
    }
  }

  container access-list-hardware {
    config false;
    description
      "Root class of accesslist hardware";
    container nodes {
      description
        "Accesslist nodes";
      list node {
        key "node-name";
        description
          "Accesslist node";
        container egress {
          description
            "Accesslist direction egress";
          uses IPV4;
          uses IPV6;
        }
        container ingress {
          description
            "Accesslist direction ingress";
          uses IPV4;
          uses IPV6;
        }
        leaf node-name {
          type xr:Node-id;
          description
            "Node name";
        }
      }
    }
  }
}
