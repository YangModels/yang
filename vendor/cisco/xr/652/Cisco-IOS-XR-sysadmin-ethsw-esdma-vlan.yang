module Cisco-IOS-XR-sysadmin-ethsw-esdma-vlan {
  namespace "http://www.cisco.com/ns/yang/Cisco-IOS-XR-sysadmin-ethsw-esdma-vlan";
  prefix esdma_vlan;
  import Cisco-IOS-XR-sysadmin-ethsw-esdma-types {
    prefix esdma_types;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains the YANG definitions
for the Cisco IOS-XR SysAdmin
'show controller switch vlan' commands.

Copyright(c) 2011-2017 by Cisco Systems, Inc.
All rights reserved.

    Copyright (c) 2012-2018 by Cisco Systems, Inc.
     All rights reserved.";
  revision 2017-05-01 {
    description
      "Namespace change to comply with Cisco guidelines on namespace";
  }


  grouping sdr-list-summary {
    list sdr-id {
      key "sdr";
      leaf sdr {
        type esdma_types:esdma-sdr-id;
      }
      leaf esd-sdr-name {
        type string;
      }
      list vlan-id {
        key "vlan";
        leaf vlan {
          type esdma_types:vlan-id-type;
        }
        leaf vlan-hex {
          type leafref {
            path "../vlan";
          }
        }
        leaf vlan-use {
          type string;
        }
      }
    }
  }

  grouping sdr-list {
    list sdr-id {
      key "sdr";
      leaf sdr {
        type esdma_types:esdma-sdr-id;
      }
      leaf esd-sdr-name {
        type string;
      }
      list vlan-id {
        key "vlan";
        leaf vlan {
          type esdma_types:vlan-id-type;
        }
        leaf vlan-hex {
          type leafref {
            path "../vlan";
          }
        }
        leaf vlan-use {
          type string;
        }
      }
    }
  }

  grouping vlan-information-group {
    container information {
      list location {
        key "rack card switch-id";
        leaf rack {
          type esdma_types:esdma-rack-num-enum;
        }
        leaf card {
          type esdma_types:esdma-cpu;
          description
            "Card to list the switch VLAN information for";
        }
        leaf switch-id {
          type esdma_types:esdma-switch-type-enum;
          description
            "Switch type";
        }
        leaf serial-num {
          type string;
          description
            "Rack serial number";
        }
        uses sdr-list;
      }
      container summary {
        uses sdr-list-summary;
      }
    }
  }

  grouping vlan-rule-info {
    list rule-id {
      leaf direction {
        type esdma_types:switch-data-direction-enum;
        description
          "Packet direction this rule applies to";
      }
      leaf match-table {
        type esdma_types:switch-table-type-enum;
      }
      leaf match-type {
        type esdma_types:switch-match-type-enum;
      }
      leaf match-vlan-id {
        type esdma_types:vlan-id-type;
      }
      leaf action {
        type esdma_types:switch-action-type-enum;
      }
      leaf action-vlan-id {
        type esdma_types:vlan-id-type;
      }
    }
  }

  grouping vlan-detail-group {
    container vlan-detail {
      list vlan-id {
        key "vlan";
        leaf vlan {
          type esdma_types:vlan-id-type;
        }
        container rules {
          list location {
            key "rack card switch-id";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              leaf port {
                type esdma_types:esdma-switch-port-type;
                description
                  "Switch port";
              }
              uses vlan-rule-info;
            }
          }
        }
      }
    }
  }

  grouping vlan-summary-group {
    container rules {
      list location {
        key "rack card switch-id";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list port-iter {
          key "port";
          leaf port {
            type esdma_types:esdma-switch-port-type;
            description
              "Switch port";
          }
          list vlan-id {
            key "vlan";
            leaf vlan {
              type esdma_types:vlan-id-type;
              description
                "This VLAN represents a VLAN membership for this switch port. Multiple rules may exist to support this VLAN.";
            }
            uses vlan-rule-info;
          }
        }
      }
    }
  }

  grouping vlan-membership-group {
    container membership {
      list location {
        key "rack card switch-id";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list vlan-id {
          key "vlan";
          leaf vlan {
            type esdma_types:vlan-id-type;
          }
          leaf vlan-hex {
            type leafref {
              path "../vlan";
            }
          }
          leaf-list port {
            type uint8;
          }
        }
      }
    }
  }

  grouping switch-vlan-group {
    container vlan {
      uses vlan-summary-group;
      uses vlan-information-group;
      uses vlan-detail-group;
      uses vlan-membership-group;
    }
  }

  grouping switch-vlan-group-ncs5500 {
    container vlan {
      uses vlan-information-group;
      uses vlan-membership-group;
    }
  }
}
