submodule Cisco-IOS-XR-infra-tc-oper-sub1 {
  belongs-to Cisco-IOS-XR-infra-tc-oper {
    prefix Cisco-IOS-XR-infra-tc-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-tc package operational data.
     
     Copyright (c) 2013-2018 by Cisco Systems, Inc.
     All rights reserved.";

  revision 2015-11-09 {
    description
      "IOS XR 6.0 revision.";
  }

  grouping TC-MGMT-MSG-STAT {
    description
      "TC Server Message Statistics";
    leaf packet-sent {
      type uint64;
      description
        "Number of packets sent";
    }
    leaf byte-sent {
      type uint64;
      units "byte";
      description
        "Number of bytes sent";
    }
    leaf packet-received {
      type uint64;
      description
        "Number of packets received";
    }
    leaf byte-received {
      type uint64;
      units "byte";
      description
        "Number of bytes received";
    }
    leaf maximum-roundtrip-latency {
      type uint32;
      description
        "Maximum roundtrip latency in msec";
    }
    leaf maimum-latency-timestamp {
      type uint64;
      description
        "Timestamp of maximum latency";
    }
  }

  grouping TC-MGMT-VRF-STAT {
    description
      "Statistics on VRF Table and its sub-tables";
    container database-statistics-ipv4 {
      description
        "Database statistics for IPv4 table";
      uses TC-MGMT-DB-STAT;
    }
    container database-statistics-tunnel {
      description
        "Database statistics for Tunnel table";
      uses TC-MGMT-DB-STAT;
    }
    leaf vrf-name {
      type string;
      description
        "VRF name";
    }
  }

  grouping TC-MGMT-DB-STAT {
    description
      "Database statistics";
    leaf number-of-entries {
      type uint32;
      description
        "Number of DB entries";
    }
    leaf number-of-stale-entries {
      type uint32;
      description
        "Number of stale  entries";
    }
    leaf number-of-add-o-perations {
      type uint64;
      description
        "Number of add operations";
    }
    leaf number-of-delete-o-perations {
      type uint64;
      description
        "Number of delete operations";
    }
  }

  grouping TC-MGMT-SUMMARY {
    description
      "TC Server Summary";
    container database-statistics-external-interface {
      description
        "Database statistics for External Interface";
      uses TC-MGMT-DB-STAT;
    }
    leaf collection-interval {
      type uint8;
      units "minute";
      description
        "Statistic collection interval in minutes";
    }
    leaf collection-timer-is-running {
      type boolean;
      description
        "TRUE if collection timer is running";
    }
    leaf timeout-interval {
      type uint16;
      units "hour";
      description
        "Statistic history timeout interval in hours";
    }
    leaf timeout-timer-is-running {
      type boolean;
      description
        "TRUE if history timeout timer is running";
    }
    leaf history-size {
      type uint8;
      description
        "Statistics history size";
    }
    list vrf-statistic {
      description
        "VRF table statistics";
      uses TC-MGMT-VRF-STAT;
    }
    list collection-message-statistic {
      description
        "Statistics per message type for STAT collector";
      uses TC-MGMT-MSG-STAT;
    }
    list checkpoint-message-statistic {
      description
        "Statistics per message type for Chkpt";
      uses TC-MGMT-MSG-STAT;
    }
  }

  grouping TC-MGMT-EXT-IF-DATA {
    description
      "TC Server external interface data";
    leaf interface-name-xr {
      type string;
      description
        "Interface name in Display format";
    }
    leaf interface-handle {
      type uint32;
      description
        "Interface handle";
    }
    leaf vrfid {
      type uint32;
      description
        "Interface VRF ID";
    }
    leaf is-interface-enabled {
      type boolean;
      description
        "Flag to indicate interface enabled or not";
    }
  }

  grouping TC-MGMT-TUNNEL-DATA {
    description
      "TC Server external interface data";
    container base-counter-statistics {
      description
        "Base counter statistics";
      uses TC-MGMT-COUNT-STATS;
    }
    leaf interface-name-xr {
      type string;
      description
        "Interface name in Display format";
    }
    leaf interface-handle {
      type uint32;
      description
        "Interface handle";
    }
    leaf vrfid {
      type uint32;
      description
        "Interface VRF ID";
    }
    leaf is-active {
      type boolean;
      description
        "Interface is Active and collecting new
         Statistics";
    }
  }

  grouping TC-MGMT-COUNT-HISTORY {
    description
      "TC Server counter statistics";
    leaf event-start-timestamp {
      type uint64;
      description
        "Event Start timestamp";
    }
    leaf event-end-timestamp {
      type uint64;
      description
        "Event End timestamp";
    }
    leaf transmit-number-of-packets-switched {
      type uint64;
      description
        "Number of packets switched in this interval";
    }
    leaf transmit-number-of-bytes-switched {
      type uint64;
      units "byte";
      description
        "Number of Bytes switched in this interval";
    }
    leaf is-valid {
      type boolean;
      description
        "Flag to indicate if this history entry is valid";
    }
  }

  grouping TC-MGMT-COUNT-STATS {
    description
      "TC Server counter statistics";
    leaf transmit-packets-per-second-switched {
      type uint64;
      units "packet/s";
      description
        "Average Rate of Packets/second switched";
    }
    leaf transmit-bytes-per-second-switched {
      type uint64;
      units "byte/s";
      description
        "Average Rate of Bytes/second switched";
    }
    list count-history {
      description
        "Counter History";
      uses TC-MGMT-COUNT-HISTORY;
    }
  }

  grouping TC-MGMT-PREFIX-DATA {
    description
      "TC Server Prefix data";
    container base-counter-statistics {
      description
        "Base counter statistics";
      uses TC-MGMT-COUNT-STATS;
    }
    container traffic-matrix-counter-statistics {
      description
        "Traffic Matrix (TM) counter statistics";
      uses TC-MGMT-COUNT-STATS;
    }
    leaf prefix {
      type string;
      description
        "Prefix Address (V4 or V6 Format)";
    }
    leaf label-xr {
      type uint32;
      description
        "SR Label";
    }
    leaf ldp-label {
      type uint32;
      description
        "LDP Label";
    }
    leaf is-active {
      type boolean;
      description
        "Prefix is Active and collecting new Statistics";
    }
  }
}
