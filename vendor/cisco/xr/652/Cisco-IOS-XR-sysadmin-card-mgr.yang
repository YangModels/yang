module Cisco-IOS-XR-sysadmin-card-mgr {
  namespace "http://www.cisco.com/ns/yang/Cisco-IOS-XR-sysadmin-card-mgr";
  prefix card_mgr;
  import Cisco-IOS-XR-sysadmin-show-trace {
    prefix show_trace;
  }
  import Cisco-IOS-XR-sysadmin-types {
    prefix calvados;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    The 'card_mgr' module provides support for access to detail card HW information like power status, card state, inventory info, etc.

    Copyright (c) 2012-2018 by Cisco Systems, Inc.
     All rights reserved.";
  revision 2017-05-01 {
    description
      "Namespace change to comply with Cisco guidelines on namespace";
  }


  typedef startHexOffset {
    type string;
  }

  typedef endHexOffset {
    type string;
  }

  typedef HexOffset {
    type string;
  }

  grouping card_mgr-group {
    container card_mgr {
      uses show_trace:traceable;
      uses inventory-group;
      uses event-hist-group;
      uses notif-hist-group;
      uses oir-hist-group;
      uses iofpga-group;
      uses bootldr-group;
    }
  }

  grouping inventory-group {
    container inventory {
      config false;
      uses inventory-summary-group;
      uses inventory-detail-group;
    }
  }

  grouping inventory-summary-group {
    container summary {
      config false;
      list card_mgr_inv_summary {
        key "location";
        leaf location {
          type string;
          mandatory true;
        }
        leaf card_mgr_inv_PID_string {
          type string;
        }
        leaf card_mgr_inv_slot_number {
          type uint32;
        }
        leaf card_mgr_inv_serial_number {
          type string;
        }
        leaf card_mgr_inv_hw_version {
          type string;
        }
        leaf card_mgr_inv_card_state {
          type string;
        }
      }
    }
  }

  grouping inventory-detail-group {
    container detail {
      config false;
      list card_mgr_inv_detail {
        key "location";
        leaf location {
          type string;
        }
        container card_mgr_inv_detail_list {
          leaf-list card_mgr_inv_detail_values {
            type string;
          }
        }
      }
    }
  }

  grouping event-hist-group {
    container event-history {
      config false;
      container brief {
        config false;
        uses event-hist-group-brief;
      }
      container detail {
        config false;
        uses event-hist-group-detail;
      }
    }
  }

  grouping event-hist-group-brief {
    list location {
      key "location";
      leaf location {
        type string;
      }
      container card_event_hist_brief {
        leaf-list card_event_hist_brief_values {
          type string;
        }
      }
    }
  }

  grouping event-hist-group-detail {
    list location {
      key "location";
      leaf location {
        type string;
      }
      container card_event_hist_detail {
        leaf-list card_event_hist_detail_values {
          type string;
        }
      }
    }
  }

  grouping notif-hist-group {
    container notif-history {
      config false;
      container brief {
        config false;
        uses notif-hist-group-brief;
      }
      container detail {
        config false;
        uses notif-hist-group-detail;
      }
    }
  }

  grouping notif-hist-group-brief {
    list location {
      key "location";
      leaf location {
        type string;
      }
      container card_notif_hist_brief {
        leaf-list card_notif_hist_brief_values {
          type string;
        }
      }
    }
  }

  grouping notif-hist-group-detail {
    list location {
      key "location";
      leaf location {
        type string;
      }
      container card_notif_hist_detail {
        leaf-list card_notif_hist_detail_values {
          type string;
        }
      }
    }
  }

  grouping oir-hist-group {
    container oir-history {
      config false;
      list rack {
        key "rack";
        leaf rack {
          type string;
        }
        container card_oir_hist {
          leaf-list card_oir_events {
            type string;
          }
        }
      }
    }
  }

  grouping iofpga-group {
    container iofpga {
      config false;
      uses iofpga-register-group;
      uses iofpga-flash-group;
    }
  }

  grouping iofpga-register-group {
    container register {
      config false;
      uses cpu-register-group;
      uses mb-register-group;
      uses dc-register-group;
    }
  }

  grouping cpu-register-group {
    container cpu {
      config false;
      list register_location {
        config false;
        key "register_location";
        leaf register_location {
          type string;
        }
        uses iofpga-block-number-group;
        uses iofpga-offset-group;
        uses iofpga-address-group;
      }
    }
  }

  grouping mb-register-group {
    container mb {
      config false;
      list register_location {
        config false;
        key "register_location";
        leaf register_location {
          type string;
        }
        uses iofpga-block-number-group;
        uses iofpga-offset-group;
        uses iofpga-address-group;
      }
    }
  }

  grouping dc-register-group {
    container dc {
      config false;
      list register_location {
        config false;
        key "register_location";
        leaf register_location {
          type string;
        }
        uses iofpga-block-number-group;
        uses iofpga-offset-group;
        uses iofpga-address-group;
      }
    }
  }

  grouping iofpga-block-number-group {
    list iofpga_block_number {
      config false;
      key "iofpga_block_num";
      leaf iofpga_block_num {
        type uint32;
      }
      leaf block_location {
        type string;
      }
      leaf iofpga_block_nm {
        type string;
      }
      list iofpga_register_number {
        key "index";
        leaf index {
          type uint32;
        }
        leaf iofpga_register_name {
          type string;
        }
        list iofpga_data {
          leaf name {
            type string;
          }
          leaf offset {
            type uint32;
          }
          leaf value {
            type uint32;
          }
        }
      }
    }
  }

  grouping iofpga-offset-group {
    list iofpga_offset {
      config false;
      key "hex_offset";
      leaf hex_offset {
        type HexOffset;
      }
      list iofpga_reg_offset_data {
        leaf iofpga_reg_off_addr {
          type uint32;
        }
        leaf reg_off_value {
          type string;
        }
      }
    }
  }

  grouping iofpga-address-group {
    list iofpga_address {
      config false;
      key "start_hex_addr end_hex_addr";
      leaf start_hex_addr {
        type startHexOffset;
      }
      leaf end_hex_addr {
        type endHexOffset;
      }
      list iofpga_reg_range_addr_list {
        key "iofpga_reg_range_addr";
        leaf iofpga_reg_range_addr {
          type uint32;
        }
        list iofpga_reg_data {
          leaf iofpga_reg_addr {
            type uint32;
          }
          leaf reg_value {
            type string;
          }
        }
      }
    }
  }

  grouping iofpga-flash-group {
    container flash {
      config false;
      uses iofpga-flash-info-group;
      uses iofpga-flash-status-group;
    }
  }

  grouping iofpga-flash-info-group {
    container info {
      config false;
      list flash_location {
        key "flash_location";
        leaf flash_location {
          type calvados:location-id;
        }
        container iofpga_flash_info {
          leaf-list iofpga_flash_info_values {
            type string;
          }
        }
      }
    }
  }

  grouping iofpga-flash-status-group {
    container status {
      config false;
      list flash_location {
        key "flash_location";
        leaf flash_location {
          type calvados:location-id;
        }
        container iofpga_flash_status {
          leaf-list iofpga_flash_status_values {
            type string;
          }
        }
      }
    }
  }

  grouping bootldr-group {
    container bootloader {
      config false;
      uses bootldr-flash-group;
    }
  }

  grouping bootldr-flash-group {
    container flash {
      config false;
      uses bootldr-flash-info-group;
      uses bootldr-flash-status-group;
    }
  }

  grouping bootldr-flash-info-group {
    container info {
      config false;
      list flash_location {
        key "flash_location";
        leaf flash_location {
          type calvados:location-id;
        }
        container bootldr_flash_info {
          leaf-list bootldr_flash_info_values {
            type string;
          }
        }
      }
    }
  }

  grouping bootldr-flash-status-group {
    container status {
      config false;
      list flash_location {
        key "flash_location";
        leaf flash_location {
          type calvados:location-id;
        }
        container bootldr_flash_status {
          leaf-list bootldr_flash_status_values {
            type string;
          }
        }
      }
    }
  }
}
