module Cisco-IOS-XR-PRIVATE-ocni-mpls-te-oper {
  namespace "http://cisco.com/ns/yang/Cisco-IOS-XR-PRIVATE-ocni-mpls-te-oper";
  prefix private-ocni-mpls-te-oper;

  include Cisco-IOS-XR-PRIVATE-ocni-mpls-te-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR PRIVATE-ocni-mpls-te package operational data.
     
     This module contains definitions
     for the following management objects:
       ocni-mpls-te: An OpenConfig description of a network-instance
     
     Copyright (c) 2013-2018 by Cisco Systems, Inc.
     All rights reserved.";

  revision 2015-11-09 {
    description
      "IOS XR 6.0 revision.";
  }

  container ocni-mpls-te {
    config false;
    description
      "An OpenConfig description of a network-instance";
    container network-instances {
      description
        "Network instances configured on the local system";
      list network-instance {
        key "name";
        description
          "Network instances configured on the local
           system";
        container mpls {
          description
            "Anchor point for mpls configuration and
             operational data";
          container global {
            description
              "general mpls configuration applicable to any
               type of LSP and signaling protocol - label
               ranges, entropy label supportmay be added
               here";
            uses OVERLAY-OCNI-MPLS-TE-GLOBAL;
          }
          container lsps {
            description
              "LSP definitions and configuration";
            container constrained-path {
              description
                "traffic-engineered LSPs supporting different
                 path computation and signaling methods";
              container named-explicit-paths {
                description
                  "A list of explicit paths";
                list named-explicit-path {
                  key "name";
                  description
                    "A list of explicit paths";
                  container explicit-route-objects {
                    description
                      "List of explicit route objects";
                    list explicit-route-object {
                      key "index";
                      description
                        "List of explicit route objects";
                      leaf index {
                        type uint32;
                        description
                          "Index of this explicit route object, to
                           express the order of hops in path";
                      }
                      uses OVERLAY-OCNI-MPLS-TE-EXPLICIT-ROUTE-OBJECT;
                    }
                  }
                  container named-explicit-paths-state {
                    description
                      "Operational state parameters relating to
                       the named explicit paths";
                    uses OVERLAY-OCNI-MPLS-TE-NAMED-EXPLICIT-PATH-STATE;
                  }
                  leaf name {
                    type string;
                    description
                      "A string name that uniquely identifies an
                       explicit path";
                  }
                }
              }
              container tunnels {
                description
                  "List of TE tunnels";
                list tunnel {
                  key "name";
                  description
                    "List of TE tunnels";
                  container bandwidth {
                    description
                      "Bandwidth configuration for TE LSPs";
                    uses OVERLAY-OCNI-MPLS-TE-BANDWIDTH;
                  }
                  container tunnels-state {
                    description
                      "State parameters related to TE tunnels";
                    uses OVERLAY-OCNI-MPLS-TE-TUNNEL-STATE;
                  }
                  container p2p-tunnel-attributes {
                    description
                      "Parameters related to LSPs of type P2P";
                    container p2p-primary-paths {
                      description
                        "List of p2p primary paths for a tunnel";
                      list p2p-primary-path {
                        key "name";
                        description
                          "List of p2p primary paths for a tunnel";
                        leaf name {
                          type string;
                          description
                            "Path name";
                        }
                        uses OVERLAY-OCNI-MPLS-TE-P2P-PRIMARY-PATH;
                      }
                    }
                    container p2p-tunnel-attributes-state {
                      description
                        "State parameters for P2P LSPs";
                      uses OVERLAY-OCNI-MPLS-TE-P2P-TUNNEL-ATTRIBUTES-STATE;
                    }
                  }
                  leaf name {
                    type string;
                    description
                      "The tunnel name";
                  }
                }
              }
            }
          }
          container te-global-attributes {
            description
              "traffic-engineering global attributes";
            container bandwidth-measurement {
              description
                "Configuration and operational state
                 parameters related to how bandwidth
                 utilisation is measured and flooded into the
                 IGP";
              uses OVERLAY-OCNI-MPLS-TE-BANDWIDTH-MEASUREMENT;
            }
            container mpls-admin-groups {
              description
                "configuration of value to name mapping for
                 mpls affinities/admin-groups";
              list mpls-admin-group {
                key "admin-group-name";
                description
                  "configuration of value to name mapping for
                   mpls affinities/admin-groups";
                leaf admin-group-name {
                  type string;
                  description
                    "name for mpls admin-group";
                }
                uses OVERLAY-OCNI-MPLS-TE-ADMIN-GROUP;
              }
            }
            container te-lsp-timers {
              description
                "Definition for delays associated with setup
                 and cleanup of TE LSPs";
              uses OVERLAY-OCNI-MPLS-TE-TE-LSP-TIMERS;
            }
            container srlgses {
              description
                "List of shared risk link groups";
              list srlgs {
                key "name";
                description
                  "List of shared risk link groups";
                container state {
                  description
                    "State parameters related to the SRLG";
                  uses OVERLAY-OCNI-MPLS-TE-STATE;
                }
                container static-srlg-members {
                  description
                    "List of SRLG members, which are expressed
                     as IP address endpoints of links contained
                     in the SRLG";
                  list static-srlg-member {
                    key "from-address";
                    description
                      "List of SRLG members, which are expressed
                       as IP address endpoints of links
                       contained in the SRLG";
                    leaf from-address {
                      type string;
                      description
                        "The from address of the link in the SRLG";
                    }
                    uses OVERLAY-OCNI-MPLS-TE-MEMBERS-LIST;
                  }
                }
                leaf name {
                  type string;
                  description
                    "The SRLG group identifier";
                }
              }
            }
          }
          container signaling-protocols {
            description
              "top-level signaling protocol configuration";
            container rsvp-te {
              description
                "RSVP-TE global signaling protocol
                 configuration";
              container rsvp-te-global {
                description
                  "Platform wide RSVP configuration and state";
                uses OVERLAY-OCNI-MPLS-TE-RSVP-TE-GLOBAL;
              }
              container interface-attributes {
                description
                  "list of per-interface RSVP configurations";
                list interface-attribute {
                  key "interface-id";
                  description
                    "list of per-interface RSVP configurations";
                  container bandwidth-reservations {
                    description
                      "Available and reserved bandwidth by
                       priority on the interface";
                    list bandwidth-reservation {
                      key "priority";
                      description
                        "Available and reserved bandwidth by
                         priority on the interface";
                      leaf priority {
                        type string;
                        description
                          "Reference to the RSVP priority level";
                      }
                      uses OVERLAY-OCNI-MPLS-TE-BANDWIDTH-RESERVATION;
                    }
                  }
                  container interface-ref {
                    description
                      "Reference to an interface or subinterface";
                    uses OVERLAY-OCNI-MPLS-TE-INTERFACE-REF;
                  }
                  container protection {
                    description
                      "link-protection (NHOP) related
                       configuration";
                    uses OVERLAY-OCNI-MPLS-TE-PROTECTION;
                  }
                  container subscription {
                    description
                      "Bandwidth percentage reservable by RSVP
                       on an interface";
                    uses OVERLAY-OCNI-MPLS-TE-SUBSCRIPTION;
                  }
                  leaf interface-id {
                    type string;
                    description
                      "reference to the interface-id data";
                  }
                }
              }
            }
          }
          container te-interface-attributes {
            description
              "List of TE interfaces";
            list te-interface-attribute {
              key "interface-id";
              description
                "List of TE interfaces";
              leaf interface-id {
                type string;
                description
                  "Reference to the interface id list key";
              }
              uses OVERLAY-OCNI-MPLS-TE-INTERFACE;
            }
          }
        }
        leaf name {
          type string;
          description
            "A unique name identifying the network instance";
        }
      }
    }
  }
}
