submodule Cisco-IOS-XR-ncs6k-acl-oper-sub1 {
  belongs-to Cisco-IOS-XR-ncs6k-acl-oper {
    prefix Cisco-IOS-XR-ncs6k-acl-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs6k-acl package operational data.
     
     Copyright (c) 2013-2018 by Cisco Systems, Inc.
     All rights reserved.";

  revision 2017-09-07 {
    description
      "Fixed type translation error.";
  }
  revision 2017-05-01 {
    description
      "adding PD yang.";
  }
  revision 2015-11-09 {
    description
      "IOS XR 6.0 revision.";
  }

  typedef Sse-ipv6-address {
    type inet:ipv6-address;
    description
      "Sse ipv6 address";
  }

  typedef Sse-ipv4-address {
    type inet:ipv4-address;
    description
      "Sse ipv4 address";
  }

  typedef Sse-pfilter-addr {
    type enumeration {
      enum "ipv4" {
        description
          "IPv4";
      }
      enum "ipv6" {
        description
          "IPv6";
      }
    }
    description
      "Address types";
  }

  typedef Sse-grant {
    type enumeration {
      enum "permit" {
        value 1;
        description
          "Grant permit";
      }
      enum "deny" {
        value 2;
        description
          "Grant deny";
      }
    }
    description
      "ACL grant";
  }

  grouping SSE-PFILTER-EA-ACE-BRIEF {
    description
      "Pfilter ACE Brief information across Slices";
    list common-acl {
      description
        "Common ACL information across Slices";
      uses SSE-PFILTER-EA-ACE-DATA-BRIEF;
    }
    list interface-acl {
      description
        "Interface ACL information across Slices";
      uses SSE-PFILTER-EA-ACE-DATA-BRIEF;
    }
  }

  grouping SSE-PFILTER-EA-ACE-DETAIL {
    description
      "Pfilter ACE detail information across Slices";
    list common-acl-detail {
      description
        "Common ACL detail information across Slices";
      uses SSE-PFILTER-EA-ACE-DATA-DETAIL;
    }
    list interface-acl-detail {
      description
        "Interface ACL detail information across Slices";
      uses SSE-PFILTER-EA-ACE-DATA-DETAIL;
    }
  }

  grouping SSE-PFILTER-IPV6-TCAM {
    description
      "Pfilter ipv6 TCAM entry";
    container tcp-flags {
      description
        "TCP flags";
      uses SSE-PFILTER-TCP-FLAGS;
    }
    leaf acl-id {
      type uint16;
      description
        "ACL ID";
    }
    leaf protocol {
      type uint8;
      description
        "protocol flags";
    }
    leaf layer4-source-port {
      type uint32;
      description
        "Layer 4 source port";
    }
    leaf layer4-destination-port {
      type uint16;
      description
        "Layer 4 destination port";
    }
    leaf source-range-id {
      type uint32;
      description
        "Source range";
    }
    leaf destination-range-id {
      type uint32;
      description
        "Destination range ID";
    }
    leaf destination-header {
      type uint8;
      description
        "Destination header";
    }
    leaf receive-transition-gap-header {
      type uint8;
      description
        "Receive/transmit transition gap header";
    }
    leaf authentication-header {
      type uint8;
      description
        "Authentication header";
    }
    leaf fragment {
      type uint8;
      description
        "Fragment";
    }
    leaf tos {
      type uint8;
      description
        "TOS";
    }
    leaf packet-length-range {
      type uint32;
      description
        "Packet length range ID";
    }
  }

  grouping SSE-PFILTER-TCAM-ENTRY-IPV6 {
    description
      "Pfilter TCAM entry for Pita";
    container value {
      description
        "IPv6 TCAM value";
      uses SSE-PFILTER-IPV6-TCAM;
    }
    container mask {
      description
        "IPv6 TCAM mask";
      uses SSE-PFILTER-IPV6-TCAM;
    }
    container result {
      description
        "IPv6 TCAM result";
      uses SSE-PFILTER-IPV6-TCAM;
    }
    leaf source-address {
      type inet:ipv6-address;
      description
        "Source address";
    }
    leaf source-address-mask {
      type inet:ipv6-address;
      description
        "Source address mask";
    }
    leaf destination-address {
      type inet:ipv6-address;
      description
        "Destination address";
    }
    leaf destination-address-mask {
      type inet:ipv6-address;
      description
        "Destination address mask";
    }
  }

  grouping SSE-IPV6-PFILTER-TCAM {
    description
      "IPv6 pfilter TCAM";
    container tcam-entry {
      description
        "TCAM entries";
      uses SSE-PFILTER-TCAM-ENTRY-IPV6;
    }
  }

  grouping SSE-PFILTER-TCP-FLAGS {
    description
      "TCP flags";
    leaf urgent {
      type uint8;
      description
        "TCP urgent flag";
    }
    leaf acknowledge {
      type uint8;
      description
        "TCP acknowledge flag";
    }
    leaf push {
      type uint8;
      description
        "TCP push flag";
    }
    leaf reset {
      type uint8;
      description
        "TCP reset flag";
    }
    leaf synchronization {
      type uint8;
      description
        "TCP synchronization flag";
    }
    leaf finish {
      type uint8;
      description
        "TCP finish flag";
    }
  }

  grouping SSE-PFILTER-IPV4-TCAM {
    description
      "Pfilter IPv4 TCAM entry";
    container tcp-flags {
      description
        "TCP flag value";
      uses SSE-PFILTER-TCP-FLAGS;
    }
    leaf acl-id {
      type uint16;
      description
        "ACL ID";
    }
    leaf source-range-id {
      type uint16;
      description
        "Source range ID";
    }
    leaf destination-range-id {
      type uint16;
      description
        "Destination range ID";
    }
    leaf source-address {
      type inet:ipv4-address;
      description
        "Source address";
    }
    leaf protocol {
      type uint8;
      description
        "protocol flags";
    }
    leaf fragment {
      type uint16;
      description
        "Fragment";
    }
    leaf dscp {
      type uint8;
      description
        "DSCP";
    }
    leaf ttl {
      type uint32;
      description
        "TTL";
    }
    leaf layer4-source-port {
      type uint16;
      description
        "Layer 4 source port";
    }
    leaf destination-address {
      type inet:ipv4-address;
      description
        "Destination address";
    }
    leaf layer4-destination-port {
      type uint16;
      description
        "Layer 4 destination port";
    }
    leaf packet-length-range {
      type uint8;
      description
        "Packet length range ID";
    }
  }

  grouping SSE-PFILTER-TCAM-ENTRY-IPV4 {
    description
      "Pfilter TCAM entry for Pita";
    container value {
      description
        "Pfilter IPv4 TCAM value";
      uses SSE-PFILTER-IPV4-TCAM;
    }
    container mask {
      description
        "Pfilter IPv4 TCAM mask";
      uses SSE-PFILTER-IPV4-TCAM;
    }
    container result {
      description
        "Pfilter IPv4 TCAM result";
      uses SSE-PFILTER-IPV4-TCAM;
    }
  }

  grouping SSE-IPV4-PFILTER-TCAM {
    description
      "IPv4 pfilter TCAM";
    container tcam-entry {
      description
        "TCAM entries";
      uses SSE-PFILTER-TCAM-ENTRY-IPV4;
    }
  }

  grouping SSE-PFILTER-EA-ACE {
    description
      "Pfilter ACL hardware detail";
    container ipv4tcam {
      description
        "IPv4 TCAM entries";
      uses SSE-IPV4-PFILTER-TCAM;
    }
    container ipv6tcam {
      description
        "IPv6 TCAM entries";
      uses SSE-IPV6-PFILTER-TCAM;
    }
    leaf entry-id {
      type int32;
      description
        "Entry ID";
    }
  }

  grouping SSE-PFILTER-NEXT-HOP-ADDR-TYPE {
    description
      "SSE PFILTER NEXT HOP ADDR TYPE";
    leaf address-type {
      type Sse-pfilter-addr;
      description
        "AddressType";
    }
    leaf ipv4-address {
      when "../address-type = 'ipv4'" {
        description
          "../AddressType = 'IPv4'";
      }
      type Sse-ipv4-address;
      description
        "IPv4 address type";
    }
    leaf ipv6-address {
      when "../address-type = 'ipv6'" {
        description
          "../AddressType = 'IPv6'";
      }
      type Sse-ipv6-address;
      description
        "IPv6 address type";
    }
  }

  grouping SSE-PFILTER-EA-ACE-DATA-BRIEF {
    description
      "Pfilter ACL hardware brief";
    container next-hop-address {
      description
        "Next hop address";
      uses SSE-PFILTER-NEXT-HOP-ADDR-TYPE;
    }
    leaf grant {
      type Sse-grant;
      description
        "Either permit or deny";
    }
    leaf logging-enabled {
      type boolean;
      description
        "Logging enabled/disabled";
    }
    leaf per-ace-icmp-enabled {
      type boolean;
      description
        "Per ACE ICMP enabled/disabled";
    }
    leaf next-hop-enabled {
      type boolean;
      description
        "Next hop enabled/disabled";
    }
    leaf default-next-hop-enabled {
      type boolean;
      description
        "Default next hop enabled/disabled";
    }
    leaf total-tcam-entries {
      type uint32;
      description
        "Number of TCAM entries";
    }
    leaf hits {
      type uint64;
      description
        "Number of TCAM hits";
    }
    leaf npu-id {
      type uint8;
      description
        "NPU Id";
    }
  }

  grouping SSE-PFILTER-EA-ACE-DATA-DETAIL {
    description
      "Pfilter ACL ACE details";
    container ace-brief {
      description
        "ACE brief information";
      uses SSE-PFILTER-EA-ACE-DATA-BRIEF;
    }
    list ace-detail {
      description
        "ACE detail information";
      uses SSE-PFILTER-EA-ACE;
    }
  }

  grouping SSE-PFILTER-EA-ACE-IMPLICIT-INTERNAL {
    description
      "Pfilter ACL implicit info";
    container implicit-ndna-permit {
      description
        "Implicit NDNA permit";
      uses SSE-PFILTER-EA-ACE-DATA-DETAIL;
    }
    container implicit-ndns-permit {
      description
        "Implicit NDNS permit";
      uses SSE-PFILTER-EA-ACE-DATA-DETAIL;
    }
    container implicit-deny {
      description
        "Implicit deny";
      uses SSE-PFILTER-EA-ACE-DATA-DETAIL;
    }
  }

  grouping SSE-PFILTER-EA-ACE-IMPLICIT-DETAIL {
    description
      "Pfilter ACL implicit details for Common/Interface
       ACL";
    container common-acl-implicit {
      description
        "Common ACL Implicit Entries";
      uses SSE-PFILTER-EA-ACE-IMPLICIT-INTERNAL;
    }
    container interface-acl-implicit {
      description
        "Interface ACL Implicit Entries";
      uses SSE-PFILTER-EA-ACE-IMPLICIT-INTERNAL;
    }
  }

  grouping SSE-PFILTER-EA-ACE-IMPLICIT {
    description
      "Pfilter ACL implicit details across Slices";
    list implicit-acl {
      description
        "Implicit ACL Entries across Slices";
      uses SSE-PFILTER-EA-ACE-IMPLICIT-DETAIL;
    }
  }
}
