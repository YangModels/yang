submodule Cisco-IOS-XR-PRIVATE-ocni-mpls-static-oper-sub1 {
  belongs-to Cisco-IOS-XR-PRIVATE-ocni-mpls-static-oper {
    prefix Cisco-IOS-XR-PRIVATE-ocni-mpls-static-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR PRIVATE-ocni-mpls-static package operational data.
     
     Copyright (c) 2013-2018 by Cisco Systems, Inc.
     All rights reserved.";

  revision 2015-11-09 {
    description
      "IOS XR 6.0 revision.";
  }

  typedef Yang2bag-string {
    type string;
    description
      "Yang2bag string";
  }

  grouping EGRESS-STATE {
    description
      "EGRESS STATE";
    leaf next-hop {
      type Yang2bag-string;
      description
        "next hop IP address for the LSP";
    }
    leaf incoming-label {
      type Yang2bag-string;
      description
        "label value on the incoming packet";
    }
    leaf push-label {
      type Yang2bag-string;
      description
        "label value to push at the current hop for the
         LSP";
    }
  }

  grouping EGRESS {
    description
      "EGRESS";
    container state {
      description
        "Operational state data for egress LSPs";
      uses EGRESS-STATE;
    }
  }

  grouping TRANSIT-STATE {
    description
      "TRANSIT STATE";
    leaf next-hop {
      type Yang2bag-string;
      description
        "next hop IP address for the LSP";
    }
    leaf incoming-label {
      type Yang2bag-string;
      description
        "label value on the incoming packet";
    }
    leaf push-label {
      type Yang2bag-string;
      description
        "label value to push at the current hop for the
         LSP";
    }
  }

  grouping TRANSIT {
    description
      "TRANSIT";
    container state {
      description
        "Operational state data for transit LSPs";
      uses TRANSIT-STATE;
    }
  }

  grouping INGRESS-STATE {
    description
      "INGRESS STATE";
    leaf next-hop {
      type Yang2bag-string;
      description
        "next hop IP address for the LSP";
    }
    leaf incoming-label {
      type Yang2bag-string;
      description
        "label value on the incoming packet";
    }
    leaf push-label {
      type Yang2bag-string;
      description
        "label value to push at the current hop for the
         LSP";
    }
  }

  grouping INGRESS {
    description
      "INGRESS";
    container state {
      description
        "Operational state data for ingress LSPs";
      uses INGRESS-STATE;
    }
  }

  grouping STATE {
    description
      "STATE";
    leaf name {
      type Yang2bag-string;
      description
        "name to identify the LSP";
    }
  }

  grouping OVERLAY-OCNI-MPLS-STATIC-STATIC-LSP {
    description
      "list of defined static LSPs";
    container state {
      description
        "Operational state data for the static lsp";
      uses STATE;
    }
    container ingress {
      description
        "Static LSPs for which the router is an  ingress
         node";
      uses INGRESS;
    }
    container transit {
      description
        "Static LSPs for which the router is an  transit
         node";
      uses TRANSIT;
    }
    container egress {
      description
        "Static LSPs for which the router is an  egress
         node";
      uses EGRESS;
    }
  }
}
