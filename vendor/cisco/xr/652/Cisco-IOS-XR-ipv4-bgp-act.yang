module Cisco-IOS-XR-ipv4-bgp-act {

  namespace "http://cisco.com/ns/yang/Cisco-IOS-XR-ipv4-bgp-act";

  prefix "bgp-act";

  import Cisco-IOS-XR-types { prefix "csc"; }
  import ietf-inet-types { prefix "inet"; }

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR action package configuration.

     Copyright (c) 2016-2018 by Cisco Systems, Inc.
     All rights reserved.";

  revision "2016-10-12" {
    description
      "IOS XR 6.2.1 revision.";
  }

  typedef update-group-id {
    type string {
      pattern '(([0-9]|1[0-5])\.\d+)';
    }
  }

  typedef refresh-sub-group-id {
    type string {
      pattern '(([0-9]|1[0-5])\.\d+)(:\d+)';
    }
  }

  typedef ip-netmask {
    type inet:ip-address;
  }

  typedef ipv4-netmask {
    type inet:ipv4-address;
  }

  typedef ipv6-netmask {
    type inet:ipv6-address;
  }

  typedef two-byte {
    type uint16 {
      range "1..65535";
    }
  }

  typedef as-number {
    description "AS number";
    type union {
      type two-byte-as;
      type four-byte-as;
    }
  }

  typedef two-byte-as {
    type uint16 {
      range "1..65535";
    }
  }

  typedef four-byte-as {
    type union {
      type as-four-byte;
      type as-plain;
    }
  }

  typedef as-four-byte {
    type string {
      pattern '(\d+\.\d+)';
    }
  }

  typedef as-plain {
    type uint32 {
      range "65536..4294967295";
    }
  }

  typedef rd {
    description "Route distinguisher";
    type union {
      type rd-four-byte-as;
      type rd-two-byte-as;
      type rd-plain-as;
      type rd-ipv4-address;
    }
  }

  typedef rd-four-byte-as {
    type string {
      pattern '(\d+\.\d+:\d+)';
    }
  }

  typedef rd-two-byte-as {
    type string {
      pattern '(\d+:\d+)';
    }
  }

  typedef rd-plain-as {
    type string {
      pattern '(\d+:\d+)';
    }
  }

  typedef rd-ipv4-address {
    type string {
      pattern
         '(([0-9]|[1-9][0-9]|1[0-9][0-9]|2[0-4][0-9]|25[0-5])\.){3}'
      +  '([0-9]|[1-9][0-9]|1[0-9][0-9]|2[0-4][0-9]|25[0-5])'
      + '(:\d+)';
    }
  }

  typedef afi-safi-type {
    type enumeration {
      enum all-all {
        description "Both unicast and multicast address family modifiers
                     of ipv4 and ipv6 address family";
      }
      enum all-evpn;
      enum all-flowspec;
      enum all-labeled-unicast;
      enum all-mdt;
      enum all-mspw;
      enum all-multicast;
      enum all-mvpn;
      enum all-rt-filter;
      enum all-sr-policy;
      enum all-tunnel;
      enum all-unicast;
      enum all-vpls;
      enum all-vpws;
      enum ipv4-all {
        description "Both unicast and multicast address family modifiers";
      }
      enum ipv4-flowspec;
      enum ipv4-labeled-unicast;
      enum ipv4-mdt;
      enum ipv4-multicast;
      enum ipv4-mvpn;
      enum ipv4-rt-filter;
      enum ipv4-sr-policy;
      enum ipv4-tunnel;
      enum ipv4-unicast;
      enum ipv6-all {
        description "Both unicast and multicast address family modifiers";
      }
      enum ipv6-flowspec;
      enum ipv6-labeled-unicast;
      enum ipv6-multicast;
      enum ipv6-mvpn;
      enum ipv6-sr-policy;
      enum ipv6-unicast;
      enum l2vpn-evpn;
      enum l2vpn-mspw;
      enum l2vpn-vpls;
      enum l2vpn-vpws;
      enum link-state;
      enum vpnv4-flowspec;
      enum vpnv4-multicast;
      enum vpnv4-unicast;
      enum vpnv6-flowspec;
      enum vpnv6-multicast;
      enum vpnv6-unicast;
    }
  }

  typedef afi {
    type enumeration {
      enum all {
        description "Both ipv4 and ipv6 address families";
      }
      enum ipv4;
      enum ipv6;
      enum l2vpn;
      enum link-state;
      enum vpnv4;
      enum vpnv6;
    }
  }

  typedef safi {
    type union {
      type ipv4-safi;
      type ipv6-safi;
      type l2vpn-safi;
      type link-state-safi;
      type vpnv4-safi;
      type vpnv6-safi;
    }
  }

  typedef ipv4-safi {
    type enumeration {
      enum all {
        description "Both unicast and multicast address family modifiers";
      }
      enum flowspec;
      enum labeled-unicast;
      enum mdt;
      enum multicast;
      enum mvpn;
      enum rt-filter;
      enum sr-policy;
      enum tunnel;
      enum unicast;
    }
  }

  typedef ipv6-safi {
    type enumeration {
      enum all {
        description "Both unicast and multicast address family modifiers";
      }
      enum flowspec;
      enum labeled-unicast;
      enum multicast;
      enum mvpn;
      enum sr-policy;
      enum unicast;
    }
  }

  typedef l2vpn-safi {
    type enumeration {
      enum evpn;
      enum mspw;
      enum vpls;
      enum vpws;
    }
  }

  typedef link-state-safi {
    type enumeration {
      enum link-state;
    }
  }

  typedef vpnv4-safi {
    type enumeration {
      enum flowspec;
      enum multicast;
      enum unicast;
    }
  }

  typedef vpnv6-safi {
    type enumeration {
      enum flowspec;
      enum multicast;
      enum unicast;
    }
  }

  typedef instance-name {
    type union {
      type enumeration {
        enum all;
      }
      type string;
    }
  }

  typedef vrf-name {
    type union {
      type enumeration {
        enum all;
      }
      type string;
    }
  }

  rpc clear-bgp-all-graceful {
    csc:xr-task "bgp";
    csc:cli-command "clear bgp * graceful";
    description
      "Clear all peers and all routes from the BGP table.
       Clear with a hard reset and a graceful restart.
      ";
  }

  rpc clear-bgp-all {
    csc:xr-task "bgp";
    csc:cli-command "clear bgp *";
    description
      "Clear all peers and all routes from the BGP table.
      ";
  }

  rpc clear-bgp-ip-addr-graceful {
    csc:xr-task "bgp";
    csc:cli-command "clear bgp <ip-addr> graceful";
    description
      "BGP neighbor address to clear.
       Clear with a hard reset and a graceful restart.
      ";
    input {
      leaf ip-addr {
        mandatory true;
        type inet:ip-address;
        description "BGP neighbor address to clear";
      }
    }
  }

  rpc clear-bgp-ip-addr-long-lived-stale {
    csc:xr-task "bgp";
    csc:cli-command "clear bgp <ip-addr> long-lived-stale";
    description
      "BGP neighbor address to clear.
       Clear long-lived-stale routes.
      ";
    input {
      leaf ip-addr {
        mandatory true;
        type inet:ip-address;
        description "BGP neighbor address to clear";
      }
    }
  }

  rpc clear-bgp-ip-addr {
    csc:xr-task "bgp";
    csc:cli-command "clear bgp <ip-addr>";
    description
      "BGP neighbor address to clear.
      ";
    input {
      leaf ip-addr {
        mandatory true;
        type inet:ip-address;
        description "BGP neighbor address to clear";
      }
    }
  }

  rpc clear-bgp-afi-safi-all-soft-in-prefix-filter {
    csc:xr-task "bgp";
    csc:cli-command "clear bgp <afi-safi-name> * soft in prefix-filter";
    description
      "Clear all peers and all routes from the BGP table.
       Soft reconfig.
       Soft reconfig inbound update.
       Push out prefix ORF and do inbound soft reconfig.
      ";
    input {
      leaf afi-safi-name {
        mandatory true;
        type afi-safi-type;
        description "AFI and SAFI";
      }
    }
  }

  rpc clear-bgp-afi-safi-all-soft-in {
    csc:xr-task "bgp";
    csc:cli-command "clear bgp <afi-safi-name> * soft in";
    description
      "Clear all peers and all routes from the BGP table.
       Soft reconfig.
       Soft reconfig inbound update.
      ";
    input {
      leaf afi-safi-name {
        mandatory true;
        type afi-safi-type;
        description "AFI and SAFI";
      }
    }
  }

  rpc clear-bgp-afi-safi-all-soft-out {
    csc:xr-task "bgp";
    csc:cli-command "clear bgp <afi-safi-name> * soft out";
    description
      "Clear all peers and all routes from the BGP table.
       Soft reconfig.
       Soft reconfig outbound update.
      ";
    input {
      leaf afi-safi-name {
        mandatory true;
        type afi-safi-type;
        description "AFI and SAFI";
      }
    }
  }

  rpc clear-bgp-afi-safi-all-soft {
    csc:xr-task "bgp";
    csc:cli-command "clear bgp <afi-safi-name> * soft";
    description
      "Clear all peers and all routes from the BGP table.
       Soft reconfig.
      ";
    input {
      leaf afi-safi-name {
        mandatory true;
        type afi-safi-type;
        description "AFI and SAFI";
      }
    }
  }

  rpc clear-bgp-afi-safi-ip-addr-long-lived-stale {
    csc:xr-task "bgp";
    csc:cli-command "clear bgp <afi-safi-name> <ip-addr> long-lived-stale";
    description
      "Clear long-lived-stale routes.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-ip-addr-soft-in-prefix-filter {
    csc:xr-task "bgp";
    csc:cli-command "clear bgp <afi-safi-name> <ip-addr> soft in prefix-filter";
    description
      "Soft reconfig.
       Soft reconfig inbound update.
       Push out prefix ORF and do inbound soft reconfig.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-ip-addr-soft-in {
    csc:xr-task "bgp";
    csc:cli-command "clear bgp <afi-safi-name> <ip-addr> soft in";
    description
      "Soft reconfig.
       Soft reconfig inbound update.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-ip-addr-soft-out {
    csc:xr-task "bgp";
    csc:cli-command "clear bgp <afi-safi-name> <ip-addr> soft out";
    description
      "Soft reconfig.
       Soft reconfig outbound update.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-ip-addr-soft {
    csc:xr-task "bgp";
    csc:cli-command "clear bgp <afi-safi-name> <ip-addr> soft";
    description
      "Soft reconfig.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-as-soft-in-prefix-filter {
    csc:xr-task "bgp";
    csc:cli-command "clear bgp <afi-safi-name> as <as-number> soft in prefix-filter";
    description
      "Clear peers in a specific AS.
       Soft reconfig.
       Soft reconfig inbound update.
       Push out prefix ORF and do inbound soft reconfig.
      ";
    input {
      leaf afi-safi-name {
        mandatory true;
        type afi-safi-type;
        description "AFI and SAFI";
      }
      leaf as-number {
        mandatory true;
        type as-number;
        description "AS number";
      }
    }
  }

  rpc clear-bgp-afi-safi-as-soft-in {
    csc:xr-task "bgp";
    csc:cli-command "clear bgp <afi-safi-name> as <as-number> soft in";
    description
      "Clear peers in a specific AS.
       Soft reconfig.
       Soft reconfig inbound update.
      ";
    input {
      leaf afi-safi-name {
        mandatory true;
        type afi-safi-type;
        description "AFI and SAFI";
      }
      leaf as-number {
        mandatory true;
        type as-number;
        description "AS number";
      }
    }
  }

  rpc clear-bgp-afi-safi-as-soft-out {
    csc:xr-task "bgp";
    csc:cli-command "clear bgp <afi-safi-name> as <as-number> soft out";
    description
      "Clear peers in a specific AS.
       Soft reconfig.
       Soft reconfig outbound update.
      ";
    input {
      leaf afi-safi-name {
        mandatory true;
        type afi-safi-type;
        description "AFI and SAFI";
      }
      leaf as-number {
        mandatory true;
        type as-number;
        description "AS number";
      }
    }
  }

  rpc clear-bgp-afi-safi-as-soft {
    csc:xr-task "bgp";
    csc:cli-command "clear bgp <afi-safi-name> as <as-number> soft";
    description
      "Clear peers in a specific AS.
       Soft reconfig.
      ";
    input {
      leaf afi-safi-name {
        mandatory true;
        type afi-safi-type;
        description "AFI and SAFI";
      }
      leaf as-number {
        mandatory true;
        type as-number;
        description "AS number";
      }
    }
  }

  rpc clear-bgp-afi-safi-dampening-ip-prefix {
    csc:xr-task "bgp";
    csc:cli-command "clear bgp <afi-safi-name> dampening <ip-prefix>";
    description
      "Clear route flap dampening information.
      ";
    input {
      leaf afi-safi-name {
        mandatory true;
        type afi-safi-type;
        description "AFI and SAFI";
      }
      leaf ip-prefix {
        mandatory true;
        type inet:ip-prefix;
        description "Network and mask or masklength to clear dampening information";
      }
    }
  }

  rpc clear-bgp-afi-safi-dampening {
    csc:xr-task "bgp";
    csc:cli-command "clear bgp <afi-safi-name> dampening";
    description
      "Clear route flap dampening information.
      ";
    input {
      leaf afi-safi-name {
        mandatory true;
        type afi-safi-type;
        description "AFI and SAFI";
      }
    }
  }

  rpc clear-bgp-afi-safi-external-soft-in-prefix-filter {
    csc:xr-task "bgp";
    csc:cli-command "clear bgp <afi-safi-name> external soft in prefix-filter";
    description
      "Clear all external peers.
       Soft reconfig.
       Soft reconfig inbound update.
       Push out prefix ORF and do inbound soft reconfig.
      ";
    input {
      leaf afi-safi-name {
        mandatory true;
        type afi-safi-type;
        description "AFI and SAFI";
      }
    }
  }

  rpc clear-bgp-afi-safi-external-soft-in {
    csc:xr-task "bgp";
    csc:cli-command "clear bgp <afi-safi-name> external soft in";
    description
      "Clear all external peers.
       Soft reconfig.
       Soft reconfig inbound update.
      ";
    input {
      leaf afi-safi-name {
        mandatory true;
        type afi-safi-type;
        description "AFI and SAFI";
      }
    }
  }

  rpc clear-bgp-afi-safi-external-soft-out {
    csc:xr-task "bgp";
    csc:cli-command "clear bgp <afi-safi-name> external soft out";
    description
      "Clear all external peers.
       Soft reconfig.
       Soft reconfig outbound update.
      ";
    input {
      leaf afi-safi-name {
        mandatory true;
        type afi-safi-type;
        description "AFI and SAFI";
      }
    }
  }

  rpc clear-bgp-afi-safi-external-soft {
    csc:xr-task "bgp";
    csc:cli-command "clear bgp <afi-safi-name> external soft";
    description
      "Clear all external peers.
       Soft reconfig.
      ";
    input {
      leaf afi-safi-name {
        mandatory true;
        type afi-safi-type;
        description "AFI and SAFI";
      }
    }
  }

  rpc clear-bgp-afi-safi-flap-statistics-ip-addr-ipv4-mask {
    csc:xr-task "bgp";
    csc:cli-command "clear bgp <afi-safi-name> flap-statistics <ip-addr> <ipv4-mask>";
    description
      "Clear flap statistics.
      ";
    input {
      leaf afi-safi-name {
        mandatory true;
        type afi-safi-type;
        description "AFI and SAFI";
      }
      leaf ip-addr {
        mandatory true;
        type inet:ip-address;
        description "BGP neighbor address to clear";
      }
      leaf ipv4-mask {
        mandatory true;
        type ipv4-netmask;
        description "Network and mask or masklength to clear flap statistics";
      }
    }
  }

  rpc clear-bgp-afi-safi-flap-statistics-ip-addr {
    csc:xr-task "bgp";
    csc:cli-command "clear bgp <afi-safi-name> flap-statistics <ip-addr>";
    description
      "Clear flap statistics.
      ";
    input {
      leaf afi-safi-name {
        mandatory true;
        type afi-safi-type;
        description "AFI and SAFI";
      }
      leaf ip-addr {
        mandatory true;
        type inet:ip-address;
        description "BGP neighbor address to clear";
      }
    }
  }

  rpc clear-bgp-afi-safi-flap-statistics-ip-prefix {
    csc:xr-task "bgp";
    csc:cli-command "clear bgp <afi-safi-name> flap-statistics <ip-prefix>";
    description
      "Clear flap statistics.
      ";
    input {
      leaf afi-safi-name {
        mandatory true;
        type afi-safi-type;
        description "AFI and SAFI";
      }
      leaf ip-prefix {
        mandatory true;
        type inet:ip-prefix;
        description "Network and mask or masklength to clear flap statistics";
      }
    }
  }

  rpc clear-bgp-afi-safi-flap-statistics-regexp {
    csc:xr-task "bgp";
    csc:cli-command "clear bgp <afi-safi-name> flap-statistics regexp <regexp-pattern>";
    description
      "Clear flap statistics.
       Clear flap statistics for routes matching the regular expression.
      ";
    input {
      leaf afi-safi-name {
        mandatory true;
        type afi-safi-type;
        description "AFI and SAFI";
      }
      leaf regexp-pattern {
        mandatory true;
        type string;
        description "A regular expression to match the BGP AS paths.  Use 'ctrl-v ?' to enter '?'";
      }
    }
  }

  rpc clear-bgp-afi-safi-flap-statistics-route-policy {
    csc:xr-task "bgp";
    csc:cli-command "clear bgp <afi-safi-name> flap-statistics route-policy <route-policy-name>";
    description
      "Clear flap statistics.
       Clear flap statistics for routes matching the route policy.
      ";
    input {
      leaf afi-safi-name {
        mandatory true;
        type afi-safi-type;
        description "AFI and SAFI";
      }
      leaf route-policy-name {
        mandatory true;
        type string;
        description "Route Policy name";
      }
    }
  }

  rpc clear-bgp-afi-safi-flap-statistics {
    csc:xr-task "bgp";
    csc:cli-command "clear bgp <afi-safi-name> flap-statistics";
    description
      "Clear flap statistics.
      ";
    input {
      leaf afi-safi-name {
        mandatory true;
        type afi-safi-type;
        description "AFI and SAFI";
      }
    }
  }

  rpc clear-bgp-afi-safi-nexthop-performance-statistics {
    csc:xr-task "bgp";
    csc:cli-command "clear bgp <afi-safi-name> nexthop performance-statistics";
    description
      "Clear nexthop.
       Performance statistics information related to processing.
      ";
    input {
      leaf afi-safi-name {
        mandatory true;
        type afi-safi-type;
        description "AFI and SAFI";
      }
    }
  }

  rpc clear-bgp-afi-safi-nexthop-registration-ip-addr {
    csc:xr-task "bgp";
    csc:cli-command "clear bgp <afi-safi-name> nexthop registration <ip-addr>";
    description
      "Clear nexthop.
       Registration with RIB and reregister.
      ";
    input {
      leaf afi-safi-name {
        mandatory true;
        type afi-safi-type;
        description "AFI and SAFI";
      }
      leaf ip-addr {
        mandatory true;
        type inet:ip-address;
        description "Nexthop address";
      }
    }
  }

  rpc clear-bgp-afi-safi-self-originated {
    csc:xr-task "bgp";
    csc:cli-command "clear bgp <afi-safi-name> self-originated";
    description
      "Clear redistributed, network and aggregate routes originated here.
      ";
    input {
      leaf afi-safi-name {
        mandatory true;
        type afi-safi-type;
        description "AFI and SAFI";
      }
    }
  }

  rpc clear-bgp-afi-safi-shutdown {
    csc:xr-task "bgp";
    csc:cli-command "clear bgp <afi-safi-name> shutdown";
    description
      "Clear all peers which were shut down due to low memory.
      ";
    input {
      leaf afi-safi-name {
        mandatory true;
        type afi-safi-type;
        description "AFI and SAFI";
      }
    }
  }

  rpc clear-bgp-afi-safi-update-outq-address-family-update-parent {
    csc:xr-task "bgp";
    csc:cli-command "clear bgp <afi-safi-name> update outq address-family update-parent";
    description
      "Clear Update information (Do NOT execute without cisco support)(cisco-support).
       Clear Update generation OutQ counters (Do NOT execute without cisco support)(cisco-support).
       Address-family.
       Update parents' OutQ counters too.
      ";
    input {
      leaf afi-safi-name {
        mandatory true;
        type afi-safi-type;
        description "AFI and SAFI";
      }
    }
  }

  rpc clear-bgp-afi-safi-update-outq-address-family {
    csc:xr-task "bgp";
    csc:cli-command "clear bgp <afi-safi-name> update outq address-family";
    description
      "Clear Update information (Do NOT execute without cisco support)(cisco-support).
       Clear Update generation OutQ counters (Do NOT execute without cisco support)(cisco-support).
       Address-family.
      ";
    input {
      leaf afi-safi-name {
        mandatory true;
        type afi-safi-type;
        description "AFI and SAFI";
      }
    }
  }

  rpc clear-bgp-afi-safi-update-outq-neighbor-ip-addr-refresh-update-parent {
    csc:xr-task "bgp";
    csc:cli-command "clear bgp <afi-safi-name> update outq neighbor <ip-addr> refresh update-parent";
    description
      "Clear Update information (Do NOT execute without cisco support)(cisco-support).
       Clear Update generation OutQ counters (Do NOT execute without cisco support)(cisco-support).
       Neighbor.
       Refresh OutQ.
       Update parents' OutQ counters too.
      ";
    input {
      leaf afi-safi-name {
        mandatory true;
        type afi-safi-type;
        description "AFI and SAFI";
      }
      leaf ip-addr {
        mandatory true;
        type inet:ip-address;
        description "Neighbor address";
      }
    }
  }

  rpc clear-bgp-afi-safi-update-outq-neighbor-ip-addr-refresh {
    csc:xr-task "bgp";
    csc:cli-command "clear bgp <afi-safi-name> update outq neighbor <ip-addr> refresh";
    description
      "Clear Update information (Do NOT execute without cisco support)(cisco-support).
       Clear Update generation OutQ counters (Do NOT execute without cisco support)(cisco-support).
       Neighbor.
       Refresh OutQ.
      ";
    input {
      leaf afi-safi-name {
        mandatory true;
        type afi-safi-type;
        description "AFI and SAFI";
      }
      leaf ip-addr {
        mandatory true;
        type inet:ip-address;
        description "Neighbor address";
      }
    }
  }

  rpc clear-bgp-afi-safi-update-outq-neighbor-ip-addr-update-parent {
    csc:xr-task "bgp";
    csc:cli-command "clear bgp <afi-safi-name> update outq neighbor <ip-addr> update-parent";
    description
      "Clear Update information (Do NOT execute without cisco support)(cisco-support).
       Clear Update generation OutQ counters (Do NOT execute without cisco support)(cisco-support).
       Neighbor.
       Update parents' OutQ counters too.
      ";
    input {
      leaf afi-safi-name {
        mandatory true;
        type afi-safi-type;
        description "AFI and SAFI";
      }
      leaf ip-addr {
        mandatory true;
        type inet:ip-address;
        description "Neighbor address";
      }
    }
  }

  rpc clear-bgp-afi-safi-update-outq-neighbor-ip-addr {
    csc:xr-task "bgp";
    csc:cli-command "clear bgp <afi-safi-name> update outq neighbor <ip-addr>";
    description
      "Clear Update information (Do NOT execute without cisco support)(cisco-support).
       Clear Update generation OutQ counters (Do NOT execute without cisco support)(cisco-support).
       Neighbor.
      ";
    input {
      leaf afi-safi-name {
        mandatory true;
        type afi-safi-type;
        description "AFI and SAFI";
      }
      leaf ip-addr {
        mandatory true;
        type inet:ip-address;
        description "Neighbor address";
      }
    }
  }

  rpc clear-bgp-afi-safi-update-outq-update-group-sub-group-update-parent {
    csc:xr-task "bgp";
    csc:cli-command "clear bgp <afi-safi-name> update outq update-group <update-group> sub-group <sub-group> update-parent";
    description
      "Clear Update information (Do NOT execute without cisco support)(cisco-support).
       Clear Update generation OutQ counters (Do NOT execute without cisco support)(cisco-support).
       Update-group.
       Sub-group.
       Update parents' OutQ counters too.
      ";
    input {
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-afi-safi-update-outq-update-group-sub-group {
    csc:xr-task "bgp";
    csc:cli-command "clear bgp <afi-safi-name> update outq update-group <update-group> sub-group <sub-group>";
    description
      "Clear Update information (Do NOT execute without cisco support)(cisco-support).
       Clear Update generation OutQ counters (Do NOT execute without cisco support)(cisco-support).
       Update-group.
       Sub-group.
      ";
    input {
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-afi-safi-update-outq-update-group-sub-group-refresh-sub-group-update-parent {
    csc:xr-task "bgp";
    csc:cli-command "clear bgp <afi-safi-name> update outq update-group <update-group> sub-group <refresh-sub-group> update-parent";
    description
      "Clear Update information (Do NOT execute without cisco support)(cisco-support).
       Clear Update generation OutQ counters (Do NOT execute without cisco support)(cisco-support).
       Update-group.
       Sub-group.
       Update parents' OutQ counters too.
      ";
    input {
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-afi-safi-update-outq-update-group-sub-group-refresh-sub-group {
    csc:xr-task "bgp";
    csc:cli-command "clear bgp <afi-safi-name> update outq update-group <update-group> sub-group <refresh-sub-group>";
    description
      "Clear Update information (Do NOT execute without cisco support)(cisco-support).
       Clear Update generation OutQ counters (Do NOT execute without cisco support)(cisco-support).
       Update-group.
       Sub-group.
      ";
    input {
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-afi-safi-update-outq-update-group-update-parent {
    csc:xr-task "bgp";
    csc:cli-command "clear bgp <afi-safi-name> update outq update-group <update-group> update-parent";
    description
      "Clear Update information (Do NOT execute without cisco support)(cisco-support).
       Clear Update generation OutQ counters (Do NOT execute without cisco support)(cisco-support).
       Update-group.
       Update parents' OutQ counters too.
      ";
    input {
      leaf afi-safi-name {
        mandatory true;
        type afi-safi-type;
        description "AFI and SAFI";
      }
      leaf update-group {
        mandatory true;
        type update-group-id;
        description "Update-group process ID <x.y>";
      }
    }
  }

  rpc clear-bgp-afi-safi-update-outq-update-group {
    csc:xr-task "bgp";
    csc:cli-command "clear bgp <afi-safi-name> update outq update-group <update-group>";
    description
      "Clear Update information (Do NOT execute without cisco support)(cisco-support).
       Clear Update generation OutQ counters (Do NOT execute without cisco support)(cisco-support).
       Update-group.
      ";
    input {
      leaf afi-safi-name {
        mandatory true;
        type afi-safi-type;
        description "AFI and SAFI";
      }
      leaf update-group {
        mandatory true;
        type update-group-id;
        description "Update-group process ID <x.y>";
      }
    }
  }

  rpc clear-bgp-as-graceful {
    csc:xr-task "bgp";
    csc:cli-command "clear bgp as <as-number> graceful";
    description
      "Clear peers in a specific AS.
       Clear with a hard reset and a graceful restart.
      ";
    input {
      leaf as-number {
        mandatory true;
        type as-number;
        description "AS number";
      }
    }
  }

  rpc clear-bgp-as {
    csc:xr-task "bgp";
    csc:cli-command "clear bgp as <as-number>";
    description
      "Clear peers in a specific AS.
      ";
    input {
      leaf as-number {
        mandatory true;
        type as-number;
        description "AS number";
      }
    }
  }

  rpc clear-bgp-bestpath-ip-addr-ip-netmask {
    csc:xr-task "bgp";
    csc:cli-command "clear bgp bestpath <ip-addr> <ip-netmask>";
    description
      "re-run BGP bestpath selection.
      ";
    input {
      leaf ip-addr {
        mandatory true;
        type inet:ip-address;
        description "Network";
      }
      leaf ip-netmask {
        mandatory true;
        type ip-netmask;
        description "Mask";
      }
    }
  }

  rpc clear-bgp-bestpath-ip-addr {
    csc:xr-task "bgp";
    csc:cli-command "clear bgp bestpath <ip-addr>";
    description
      "re-run BGP bestpath selection.
      ";
    input {
      leaf ip-addr {
        mandatory true;
        type inet:ip-address;
        description "Network";
      }
    }
  }

  rpc clear-bgp-bestpath-ip-prefix {
    csc:xr-task "bgp";
    csc:cli-command "clear bgp bestpath <ip-prefix>";
    description
      "re-run BGP bestpath selection.
      ";
    input {
      leaf ip-prefix {
        mandatory true;
        type inet:ip-prefix;
        description "Network and masklength";
      }
    }
  }

  rpc clear-bgp-bestpath-afi-safi-ip-addr-ip-netmask {
    csc:xr-task "bgp";
    csc:cli-command "clear bgp bestpath <afi-safi-name> <ip-addr> <ip-netmask>";
    description
      "re-run BGP bestpath selection.
      ";
    input {
      leaf afi-safi-name {
        mandatory true;
        type afi-safi-type;
        description "AFI and SAFI";
      }
      leaf ip-addr {
        mandatory true;
        type inet:ip-address;
        description "Network";
      }
      leaf ip-netmask {
        mandatory true;
        type ip-netmask;
        description "Mask";
      }
    }
  }

  rpc clear-bgp-bestpath-afi-safi-ip-addr {
    csc:xr-task "bgp";
    csc:cli-command "clear bgp bestpath <afi-safi-name> <ip-addr>";
    description
      "re-run BGP bestpath selection.
      ";
    input {
      leaf afi-safi-name {
        mandatory true;
        type afi-safi-type;
        description "AFI and SAFI";
      }
      leaf ip-addr {
        mandatory true;
        type inet:ip-address;
        description "Network";
      }
    }
  }

  rpc clear-bgp-bestpath-afi-safi-ip-prefix {
    csc:xr-task "bgp";
    csc:cli-command "clear bgp bestpath <afi-safi-name> <ip-prefix>";
    description
      "re-run BGP bestpath selection.
      ";
    input {
      leaf afi-safi-name {
        mandatory true;
        type afi-safi-type;
        description "AFI and SAFI";
      }
      leaf ip-prefix {
        mandatory true;
        type inet:ip-prefix;
        description "Network and masklength";
      }
    }
  }

  rpc clear-bgp-bestpath-afi-safi-bridge-domain-ip-addr-ip-netmask {
    csc:xr-task "bgp";
    csc:cli-command "clear bgp bestpath <afi-safi-name> bridge-domain <bridge-domain-name> <ip-addr> <ip-netmask>";
    description
      "re-run BGP bestpath selection.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
      leaf ip-netmask {
        mandatory true;
        type ip-netmask;
        description "Mask";
      }
    }
  }

  rpc clear-bgp-bestpath-afi-safi-bridge-domain-ip-addr {
    csc:xr-task "bgp";
    csc:cli-command "clear bgp bestpath <afi-safi-name> bridge-domain <bridge-domain-name> <ip-addr>";
    description
      "re-run BGP bestpath selection.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
    }
  }

  rpc clear-bgp-bestpath-afi-safi-bridge-domain-ip-prefix {
    csc:xr-task "bgp";
    csc:cli-command "clear bgp bestpath <afi-safi-name> bridge-domain <bridge-domain-name> <ip-prefix>";
    description
      "re-run BGP bestpath selection.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-prefix {
        mandatory true;
        type inet:ip-prefix;
        description "Network and masklength";
      }
    }
  }

  rpc clear-bgp-bestpath-afi-safi-rd-ip-addr-ip-netmask {
    csc:xr-task "bgp";
    csc:cli-command "clear bgp bestpath <afi-safi-name> rd <rd> <ip-addr> <ip-netmask>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
      leaf ip-netmask {
        mandatory true;
        type ip-netmask;
        description "Mask";
      }
    }
  }

  rpc clear-bgp-bestpath-afi-safi-rd-ip-addr {
    csc:xr-task "bgp";
    csc:cli-command "clear bgp bestpath <afi-safi-name> rd <rd> <ip-addr>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
    }
  }

  rpc clear-bgp-bestpath-afi-safi-rd-ip-prefix {
    csc:xr-task "bgp";
    csc:cli-command "clear bgp bestpath <afi-safi-name> rd <rd> <ip-prefix>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ip-prefix {
        mandatory true;
        type inet:ip-prefix;
        description "Network and masklength";
      }
    }
  }

  rpc clear-bgp-bestpath-afi-safi-ipv4-addr-ipv4-mask {
    csc:xr-task "bgp";
    csc:cli-command "clear bgp bestpath <afi-safi-name> <ipv4-addr> <ipv4-mask>";
    description
      "re-run BGP bestpath selection.
      ";
    input {
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-bestpath-afi-safi-ipv4-addr {
    csc:xr-task "bgp";
    csc:cli-command "clear bgp bestpath <afi-safi-name> <ipv4-addr>";
    description
      "re-run BGP bestpath selection.
      ";
    input {
      leaf afi-safi-name {
        mandatory true;
        type afi-safi-type;
        description "AFI and SAFI";
      }
      leaf ipv4-addr {
        mandatory true;
        type inet:ipv4-address;
        description "IPv4 network";
      }
    }
  }

  rpc clear-bgp-bestpath-afi-safi-ipv4-prefix {
    csc:xr-task "bgp";
    csc:cli-command "clear bgp bestpath <afi-safi-name> <ipv4-prefix>";
    description
      "re-run BGP bestpath selection.
      ";
    input {
      leaf afi-safi-name {
        mandatory true;
        type afi-safi-type;
        description "AFI and SAFI";
      }
      leaf ipv4-prefix {
        mandatory true;
        type inet:ipv4-prefix;
        description "IPv4 network and masklength";
      }
    }
  }

  rpc clear-bgp-bestpath-afi-safi-rd-ipv4-addr {
    csc:xr-task "bgp";
    csc:cli-command "clear bgp bestpath <afi-safi-name> rd <rd> <ipv4-addr>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 MDT network";
      }
    }
  }

  rpc clear-bgp-bestpath-afi-safi-vrf-ipv4-addr {
    csc:xr-task "bgp";
    csc:cli-command "clear bgp bestpath <afi-safi-name> vrf <vrf-name> <ipv4-addr>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 MDT network";
      }
    }
  }

  rpc clear-bgp-bestpath-afi-safi-network {
    csc:xr-task "bgp";
    csc:cli-command "clear bgp bestpath <afi-safi-name> <network>";
    description
      "re-run BGP bestpath selection.
      ";
    input {
      leaf afi-safi-name {
        mandatory true;
        type afi-safi-type;
        description "AFI and SAFI";
      }
      leaf network {
        mandatory true;
        type string;
        description "Address family modifier specific network";
      }
    }
  }

  rpc clear-bgp-bestpath-afi-safi-rd-network {
    csc:xr-task "bgp";
    csc:cli-command "clear bgp bestpath <afi-safi-name> rd <rd> <network>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-bestpath-afi-safi-vrf-network {
    csc:xr-task "bgp";
    csc:cli-command "clear bgp bestpath <afi-safi-name> vrf <vrf-name> <network>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-bestpath-afi-safi-rt-constraint-network {
    csc:xr-task "bgp";
    csc:cli-command "clear bgp bestpath <afi-safi-name> <rt-constraint-network>";
    description
      "re-run BGP bestpath selection.
      ";
    input {
      leaf afi-safi-name {
        mandatory true;
        type afi-safi-type;
        description "AFI and SAFI";
      }
      leaf rt-constraint-network {
        mandatory true;
        type string;
        description "RT-Constraint network";
      }
    }
  }

  rpc clear-bgp-bestpath-afi-safi-ipv4-tunnel-network {
    csc:xr-task "bgp";
    csc:cli-command "clear bgp bestpath <afi-safi-name> <ipv4-tunnel-network>";
    description
      "re-run BGP bestpath selection.
      ";
    input {
      leaf afi-safi-name {
        mandatory true;
        type afi-safi-type;
        description "AFI and SAFI";
      }
      leaf ipv4-tunnel-network {
        mandatory true;
        type string;
        description "IPv4 Tunnel network <Tunnel-ID>:<IPv4 Address>";
      }
    }
  }

  rpc clear-bgp-bestpath-afi-safi-ipv6-addr-ipv6-netmask {
    csc:xr-task "bgp";
    csc:cli-command "clear bgp bestpath <afi-safi-name> <ipv6-addr> <ipv6-netmask>";
    description
      "re-run BGP bestpath selection.
      ";
    input {
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-bestpath-afi-safi-ipv6-addr {
    csc:xr-task "bgp";
    csc:cli-command "clear bgp bestpath <afi-safi-name> <ipv6-addr>";
    description
      "re-run BGP bestpath selection.
      ";
    input {
      leaf afi-safi-name {
        mandatory true;
        type afi-safi-type;
        description "AFI and SAFI";
      }
      leaf ipv6-addr {
        mandatory true;
        type inet:ipv6-address;
        description "IPv6 network";
      }
    }
  }

  rpc clear-bgp-bestpath-afi-safi-ipv6-prefix {
    csc:xr-task "bgp";
    csc:cli-command "clear bgp bestpath <afi-safi-name> <ipv6-prefix>";
    description
      "re-run BGP bestpath selection.
      ";
    input {
      leaf afi-safi-name {
        mandatory true;
        type afi-safi-type;
        description "AFI and SAFI";
      }
      leaf ipv6-prefix {
        mandatory true;
        type inet:ipv6-prefix;
        description "IPv6 network and masklength";
      }
    }
  }

  rpc clear-bgp-bestpath-afi-safi-rd {
    csc:xr-task "bgp";
    csc:cli-command "clear bgp bestpath <afi-safi-name> rd <rd>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
    }
  }

  rpc clear-bgp-bestpath-afi-safi-vrf {
    csc:xr-task "bgp";
    csc:cli-command "clear bgp bestpath <afi-safi-name> vrf <vrf-name>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
    }
  }

  rpc clear-bgp-bestpath-afi-safi {
    csc:xr-task "bgp";
    csc:cli-command "clear bgp bestpath <afi-safi-name>";
    description
      "re-run BGP bestpath selection.
      ";
    input {
      leaf afi-safi-name {
        mandatory true;
        type afi-safi-type;
        description "AFI and SAFI";
      }
    }
  }

  rpc clear-bgp-bestpath-afi-safi-sr-policy-prefix {
    csc:xr-task "bgp";
    csc:cli-command "clear bgp bestpath <afi-safi-name> <sr-policy-prefix>";
    description
      "re-run BGP bestpath selection.
      ";
    input {
      leaf afi-safi-name {
        mandatory true;
        type afi-safi-type;
        description "AFI and SAFI";
      }
      leaf sr-policy-prefix {
        mandatory true;
        type string;
        description "SR Policy prefix";
      }
    }
  }

  rpc clear-bgp-bestpath-afi-safi-bridge-domain-ipv4-prefix {
    csc:xr-task "bgp";
    csc:cli-command "clear bgp bestpath <afi-safi-name> bridge-domain <bridge-domain-name> <ipv4-prefix>";
    description
      "re-run BGP bestpath selection.
       Display routes for a specified Bridge Domain.
      ";
    input {
      leaf afi-safi-name {
        mandatory true;
        type afi-safi-type;
        description "AFI and SAFI";
      }
      leaf bridge-domain-name {
        mandatory true;
        type string;
        description "Bridge Domain";
      }
      leaf ipv4-prefix {
        mandatory true;
        type inet:ipv4-prefix;
        description "L2VPN EVPN Prefix";
      }
    }
  }

  rpc clear-bgp-bestpath-afi-safi-rd-ipv4-prefix {
    csc:xr-task "bgp";
    csc:cli-command "clear bgp bestpath <afi-safi-name> rd <rd> <ipv4-prefix>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv4-prefix {
        mandatory true;
        type inet:ipv4-prefix;
        description "L2VPN EVPN Prefix";
      }
    }
  }

  rpc clear-bgp-bestpath-afi-safi-mp2mp-ipv4-prefix {
    csc:xr-task "bgp";
    csc:cli-command "clear bgp bestpath <afi-safi-name> mp2mp <mp2mp> <ipv4-prefix>";
    description
      "re-run BGP bestpath selection.
       Display routes for a specified Xconnect group:MP2MP.
      ";
    input {
      leaf afi-safi-name {
        mandatory true;
        type afi-safi-type;
        description "AFI and SAFI";
      }
      leaf mp2mp {
        mandatory true;
        type string;
        description "Xconnect Group:mp2mp";
      }
      leaf ipv4-prefix {
        mandatory true;
        type inet:ipv4-prefix;
        description "L2VPN VPWS Prefix";
      }
    }
  }

  rpc clear-bgp-bestpath-afi-safi-vrf-ipv4-prefix {
    csc:xr-task "bgp";
    csc:cli-command "clear bgp bestpath <afi-safi-name> vrf <vrf-name> <ipv4-prefix>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv4-prefix {
        mandatory true;
        type inet:ipv4-prefix;
        description "VPN Fspec Prefix";
      }
    }
  }

  rpc clear-bgp-bestpath-afi-safi-rd-ipv4-addr-ipv4-mask {
    csc:xr-task "bgp";
    csc:cli-command "clear bgp bestpath <afi-safi-name> rd <rd> <ipv4-addr> <ipv4-mask>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 network";
      }
      leaf ipv4-mask {
        mandatory true;
        type ipv4-netmask;
        description "IPv4 mask";
      }
    }
  }

  rpc clear-bgp-bestpath-afi-safi-vrf-ipv4-addr-ipv4-mask {
    csc:xr-task "bgp";
    csc:cli-command "clear bgp bestpath <afi-safi-name> vrf <vrf-name> <ipv4-addr> <ipv4-mask>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 network";
      }
      leaf ipv4-mask {
        mandatory true;
        type ipv4-netmask;
        description "IPv4 mask";
      }
    }
  }

  rpc clear-bgp-bestpath-afi-safi-rd-ipv6-addr-ipv6-netmask {
    csc:xr-task "bgp";
    csc:cli-command "clear bgp bestpath <afi-safi-name> rd <rd> <ipv6-addr> <ipv6-netmask>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
      leaf ipv6-netmask {
        mandatory true;
        type ipv6-netmask;
        description "IPv6 mask";
      }
    }
  }

  rpc clear-bgp-bestpath-afi-safi-rd-ipv6-addr {
    csc:xr-task "bgp";
    csc:cli-command "clear bgp bestpath <afi-safi-name> rd <rd> <ipv6-addr>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
    }
  }

  rpc clear-bgp-bestpath-afi-safi-rd-ipv6-prefix {
    csc:xr-task "bgp";
    csc:cli-command "clear bgp bestpath <afi-safi-name> rd <rd> <ipv6-prefix>";
    description
      "re-run BGP bestpath selection.
       Display routes with a specific route distinguisher.
      ";
    input {
      leaf afi-safi-name {
        mandatory true;
        type afi-safi-type;
        description "AFI and SAFI";
      }
      leaf rd {
        mandatory true;
        type rd;
        description "Route distinguisher";
      }
      leaf ipv6-prefix {
        mandatory true;
        type inet:ipv6-prefix;
        description "IPv6 network and masklength";
      }
    }
  }

  rpc clear-bgp-bestpath-afi-safi-vrf-ipv6-addr-ipv6-netmask {
    csc:xr-task "bgp";
    csc:cli-command "clear bgp bestpath <afi-safi-name> vrf <vrf-name> <ipv6-addr> <ipv6-netmask>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
      leaf ipv6-netmask {
        mandatory true;
        type ipv6-netmask;
        description "IPv6 mask";
      }
    }
  }

  rpc clear-bgp-bestpath-afi-safi-vrf-ipv6-addr {
    csc:xr-task "bgp";
    csc:cli-command "clear bgp bestpath <afi-safi-name> vrf <vrf-name> <ipv6-addr>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
    }
  }

  rpc clear-bgp-bestpath-afi-safi-vrf-ipv6-prefix {
    csc:xr-task "bgp";
    csc:cli-command "clear bgp bestpath <afi-safi-name> vrf <vrf-name> <ipv6-prefix>";
    description
      "re-run BGP bestpath selection.
       Display routes for a specified VRF.
      ";
    input {
      leaf afi-safi-name {
        mandatory true;
        type afi-safi-type;
        description "AFI and SAFI";
      }
      leaf vrf-name {
        mandatory true;
        type string;
        description "VRF name";
      }
      leaf ipv6-prefix {
        mandatory true;
        type inet:ipv6-prefix;
        description "IPv6 network and masklength";
      }
    }
  }

  rpc clear-bgp-bestpath-vrf-ip-addr-ip-netmask {
    csc:xr-task "bgp";
    csc:cli-command "clear bgp bestpath vrf <vrf-all> <ip-addr> <ip-netmask>";
    description
      "re-run BGP bestpath selection.
       Specify a VRF.
      ";
    input {
      leaf vrf-all {
        mandatory true;
        type vrf-name;
        description "VRF name or all";
      }
      leaf ip-addr {
        mandatory true;
        type inet:ip-address;
        description "Network";
      }
      leaf ip-netmask {
        mandatory true;
        type ip-netmask;
        description "Mask";
      }
    }
  }

  rpc clear-bgp-bestpath-vrf-ip-addr {
    csc:xr-task "bgp";
    csc:cli-command "clear bgp bestpath vrf <vrf-all> <ip-addr>";
    description
      "re-run BGP bestpath selection.
       Specify a VRF.
      ";
    input {
      leaf vrf-all {
        mandatory true;
        type vrf-name;
        description "VRF name or all";
      }
      leaf ip-addr {
        mandatory true;
        type inet:ip-address;
        description "Network";
      }
    }
  }

  rpc clear-bgp-bestpath-vrf-ip-prefix {
    csc:xr-task "bgp";
    csc:cli-command "clear bgp bestpath vrf <vrf-all> <ip-prefix>";
    description
      "re-run BGP bestpath selection.
       Specify a VRF.
      ";
    input {
      leaf vrf-all {
        mandatory true;
        type vrf-name;
        description "VRF name or all";
      }
      leaf ip-prefix {
        mandatory true;
        type inet:ip-prefix;
        description "Network and masklength";
      }
    }
  }

  rpc clear-bgp-bestpath-vrf-afi-safi-ipv4-prefix {
    csc:xr-task "bgp";
    csc:cli-command "clear bgp bestpath vrf <vrf-all> <afi-safi-name> <ipv4-prefix>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "Fspec IPv4 Prefix";
      }
    }
  }

  rpc clear-bgp-bestpath-vrf-afi-safi-ipv4-addr-ipv4-mask {
    csc:xr-task "bgp";
    csc:cli-command "clear bgp bestpath vrf <vrf-all> <afi-safi-name> <ipv4-addr> <ipv4-mask>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-bestpath-vrf-afi-safi-ipv4-addr {
    csc:xr-task "bgp";
    csc:cli-command "clear bgp bestpath vrf <vrf-all> <afi-safi-name> <ipv4-addr>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
    }
  }

  rpc clear-bgp-bestpath-vrf-afi-safi-network {
    csc:xr-task "bgp";
    csc:cli-command "clear bgp bestpath vrf <vrf-all> <afi-safi-name> <network>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf network {
        mandatory true;
        type string;
        description "Address family modifier specific network";
      }
    }
  }

  rpc clear-bgp-bestpath-vrf-afi-safi-rd-network {
    csc:xr-task "bgp";
    csc:cli-command "clear bgp bestpath vrf <vrf-all> <afi-safi-name> rd <rd> <network>";
    description
      "re-run BGP bestpath selection.
       Specify a VRF.
       Display routes with a specific route distinguisher.
      ";
    input {
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-bestpath-vrf-afi-safi-vrf-network {
    csc:xr-task "bgp";
    csc:cli-command "clear bgp bestpath vrf <vrf-all> <afi-safi-name> vrf <vrf-name> <network>";
    description
      "re-run BGP bestpath selection.
       Specify a VRF.
       Display routes for a specified VRF.
      ";
    input {
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-bestpath-vrf-afi-safi-ipv6-addr-ipv6-netmask {
    csc:xr-task "bgp";
    csc:cli-command "clear bgp bestpath vrf <vrf-all> <afi-safi-name> <ipv6-addr> <ipv6-netmask>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-bestpath-vrf-afi-safi-ipv6-addr {
    csc:xr-task "bgp";
    csc:cli-command "clear bgp bestpath vrf <vrf-all> <afi-safi-name> <ipv6-addr>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
    }
  }

  rpc clear-bgp-bestpath-vrf-afi-safi-ipv6-prefix {
    csc:xr-task "bgp";
    csc:cli-command "clear bgp bestpath vrf <vrf-all> <afi-safi-name> <ipv6-prefix>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-bestpath-vrf-afi-safi-rd {
    csc:xr-task "bgp";
    csc:cli-command "clear bgp bestpath vrf <vrf-all> <afi-safi-name> rd <rd>";
    description
      "re-run BGP bestpath selection.
       Specify a VRF.
       Display routes with a specific route distinguisher.
      ";
    input {
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
    }
  }

  rpc clear-bgp-bestpath-vrf-afi-safi-vrf {
    csc:xr-task "bgp";
    csc:cli-command "clear bgp bestpath vrf <vrf-all> <afi-safi-name> vrf <vrf-name>";
    description
      "re-run BGP bestpath selection.
       Specify a VRF.
       Display routes for a specified VRF.
      ";
    input {
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
    }
  }

  rpc clear-bgp-bestpath-vrf-afi-safi {
    csc:xr-task "bgp";
    csc:cli-command "clear bgp bestpath vrf <vrf-all> <afi-safi-name>";
    description
      "re-run BGP bestpath selection.
       Specify a VRF.
      ";
    input {
      leaf vrf-all {
        mandatory true;
        type vrf-name;
        description "VRF name or all";
      }
      leaf afi-safi-name {
        mandatory true;
        type afi-safi-type;
        description "AFI and SAFI";
      }
    }
  }

  rpc clear-bgp-external-graceful {
    csc:xr-task "bgp";
    csc:cli-command "clear bgp external graceful";
    description
      "Clear all external peers.
       Clear with a hard reset and a graceful restart.
      ";
  }

  rpc clear-bgp-external {
    csc:xr-task "bgp";
    csc:cli-command "clear bgp external";
    description
      "Clear all external peers.
      ";
  }

  rpc clear-bgp-instance-all-graceful {
    csc:xr-task "bgp";
    csc:cli-command "clear bgp instance <instance-name> * graceful";
    description
      "Choose a particular BGP instance.
       Clear all peers and all routes from the BGP table.
       Clear with a hard reset and a graceful restart.
      ";
    input {
      leaf instance-name {
        mandatory true;
        type instance-name;
        description "instance name or all";
      }
    }
  }

  rpc clear-bgp-instance-all {
    csc:xr-task "bgp";
    csc:cli-command "clear bgp instance <instance-name> *";
    description
      "Choose a particular BGP instance.
       Clear all peers and all routes from the BGP table.
      ";
    input {
      leaf instance-name {
        mandatory true;
        type instance-name;
        description "instance name or all";
      }
    }
  }

  rpc clear-bgp-instance-ip-addr-graceful {
    csc:xr-task "bgp";
    csc:cli-command "clear bgp instance <instance-name> <ip-addr> graceful";
    description
      "Choose a particular BGP instance.
       Clear with a hard reset and a graceful restart.
      ";
    input {
      leaf instance-name {
        mandatory true;
        type instance-name;
        description "instance name or all";
      }
      leaf ip-addr {
        mandatory true;
        type inet:ip-address;
        description "BGP neighbor address to clear";
      }
    }
  }

  rpc clear-bgp-instance-ip-addr-long-lived-stale {
    csc:xr-task "bgp";
    csc:cli-command "clear bgp instance <instance-name> <ip-addr> long-lived-stale";
    description
      "Choose a particular BGP instance.
       Clear long-lived-stale routes.
      ";
    input {
      leaf instance-name {
        mandatory true;
        type instance-name;
        description "instance name or all";
      }
      leaf ip-addr {
        mandatory true;
        type inet:ip-address;
        description "BGP neighbor address to clear";
      }
    }
  }

  rpc clear-bgp-instance-ip-addr {
    csc:xr-task "bgp";
    csc:cli-command "clear bgp instance <instance-name> <ip-addr>";
    description
      "Choose a particular BGP instance.
      ";
    input {
      leaf instance-name {
        mandatory true;
        type instance-name;
        description "instance name or all";
      }
      leaf ip-addr {
        mandatory true;
        type inet:ip-address;
        description "BGP neighbor address to clear";
      }
    }
  }

  rpc clear-bgp-instance-afi-safi-all-soft-in-prefix-filter {
    csc:xr-task "bgp";
    csc:cli-command "clear bgp instance <instance-name> <afi-safi-name> * soft in prefix-filter";
    description
      "Choose a particular BGP instance.
       Clear all peers and all routes from the BGP table.
       Soft reconfig.
       Soft reconfig inbound update.
       Push out prefix ORF and do inbound soft reconfig.
      ";
    input {
      leaf instance-name {
        mandatory true;
        type instance-name;
        description "instance name or all";
      }
      leaf afi-safi-name {
        mandatory true;
        type afi-safi-type;
        description "AFI and SAFI";
      }
    }
  }

  rpc clear-bgp-instance-afi-safi-all-soft-in {
    csc:xr-task "bgp";
    csc:cli-command "clear bgp instance <instance-name> <afi-safi-name> * soft in";
    description
      "Choose a particular BGP instance.
       Clear all peers and all routes from the BGP table.
       Soft reconfig.
       Soft reconfig inbound update.
      ";
    input {
      leaf instance-name {
        mandatory true;
        type instance-name;
        description "instance name or all";
      }
      leaf afi-safi-name {
        mandatory true;
        type afi-safi-type;
        description "AFI and SAFI";
      }
    }
  }

  rpc clear-bgp-instance-afi-safi-all-soft-out {
    csc:xr-task "bgp";
    csc:cli-command "clear bgp instance <instance-name> <afi-safi-name> * soft out";
    description
      "Choose a particular BGP instance.
       Clear all peers and all routes from the BGP table.
       Soft reconfig.
       Soft reconfig outbound update.
      ";
    input {
      leaf instance-name {
        mandatory true;
        type instance-name;
        description "instance name or all";
      }
      leaf afi-safi-name {
        mandatory true;
        type afi-safi-type;
        description "AFI and SAFI";
      }
    }
  }

  rpc clear-bgp-instance-afi-safi-all-soft {
    csc:xr-task "bgp";
    csc:cli-command "clear bgp instance <instance-name> <afi-safi-name> * soft";
    description
      "Choose a particular BGP instance.
       Clear all peers and all routes from the BGP table.
       Soft reconfig.
      ";
    input {
      leaf instance-name {
        mandatory true;
        type instance-name;
        description "instance name or all";
      }
      leaf afi-safi-name {
        mandatory true;
        type afi-safi-type;
        description "AFI and SAFI";
      }
    }
  }

  rpc clear-bgp-instance-afi-safi-ip-addr-long-lived-stale {
    csc:xr-task "bgp";
    csc:cli-command "clear bgp instance <instance-name> <afi-safi-name> <ip-addr> long-lived-stale";
    description
      "Choose a particular BGP instance.
       Clear long-lived-stale routes.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-ip-addr-soft-in-prefix-filter {
    csc:xr-task "bgp";
    csc:cli-command "clear bgp instance <instance-name> <afi-safi-name> <ip-addr> soft in prefix-filter";
    description
      "Choose a particular BGP instance.
       Soft reconfig.
       Soft reconfig inbound update.
       Push out prefix ORF and do inbound soft reconfig.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-ip-addr-soft-in {
    csc:xr-task "bgp";
    csc:cli-command "clear bgp instance <instance-name> <afi-safi-name> <ip-addr> soft in";
    description
      "Choose a particular BGP instance.
       Soft reconfig.
       Soft reconfig inbound update.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-ip-addr-soft-out {
    csc:xr-task "bgp";
    csc:cli-command "clear bgp instance <instance-name> <afi-safi-name> <ip-addr> soft out";
    description
      "Choose a particular BGP instance.
       Soft reconfig.
       Soft reconfig outbound update.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-ip-addr-soft {
    csc:xr-task "bgp";
    csc:cli-command "clear bgp instance <instance-name> <afi-safi-name> <ip-addr> soft";
    description
      "Choose a particular BGP instance.
       Soft reconfig.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-as-soft-in-prefix-filter {
    csc:xr-task "bgp";
    csc:cli-command "clear bgp instance <instance-name> <afi-safi-name> as <as-number> soft in prefix-filter";
    description
      "Choose a particular BGP instance.
       Clear peers in a specific AS.
       Soft reconfig.
       Soft reconfig inbound update.
       Push out prefix ORF and do inbound soft reconfig.
      ";
    input {
      leaf instance-name {
        mandatory true;
        type instance-name;
        description "instance name or all";
      }
      leaf afi-safi-name {
        mandatory true;
        type afi-safi-type;
        description "AFI and SAFI";
      }
      leaf as-number {
        mandatory true;
        type as-number;
        description "AS number";
      }
    }
  }

  rpc clear-bgp-instance-afi-safi-as-soft-in {
    csc:xr-task "bgp";
    csc:cli-command "clear bgp instance <instance-name> <afi-safi-name> as <as-number> soft in";
    description
      "Choose a particular BGP instance.
       Clear peers in a specific AS.
       Soft reconfig.
       Soft reconfig inbound update.
      ";
    input {
      leaf instance-name {
        mandatory true;
        type instance-name;
        description "instance name or all";
      }
      leaf afi-safi-name {
        mandatory true;
        type afi-safi-type;
        description "AFI and SAFI";
      }
      leaf as-number {
        mandatory true;
        type as-number;
        description "AS number";
      }
    }
  }

  rpc clear-bgp-instance-afi-safi-as-soft-out {
    csc:xr-task "bgp";
    csc:cli-command "clear bgp instance <instance-name> <afi-safi-name> as <as-number> soft out";
    description
      "Choose a particular BGP instance.
       Clear peers in a specific AS.
       Soft reconfig.
       Soft reconfig outbound update.
      ";
    input {
      leaf instance-name {
        mandatory true;
        type instance-name;
        description "instance name or all";
      }
      leaf afi-safi-name {
        mandatory true;
        type afi-safi-type;
        description "AFI and SAFI";
      }
      leaf as-number {
        mandatory true;
        type as-number;
        description "AS number";
      }
    }
  }

  rpc clear-bgp-instance-afi-safi-as-soft {
    csc:xr-task "bgp";
    csc:cli-command "clear bgp instance <instance-name> <afi-safi-name> as <as-number> soft";
    description
      "Choose a particular BGP instance.
       Clear peers in a specific AS.
       Soft reconfig.
      ";
    input {
      leaf instance-name {
        mandatory true;
        type instance-name;
        description "instance name or all";
      }
      leaf afi-safi-name {
        mandatory true;
        type afi-safi-type;
        description "AFI and SAFI";
      }
      leaf as-number {
        mandatory true;
        type as-number;
        description "AS number";
      }
    }
  }

  rpc clear-bgp-instance-afi-safi-dampening-ip-prefix {
    csc:xr-task "bgp";
    csc:cli-command "clear bgp instance <instance-name> <afi-safi-name> dampening <ip-prefix>";
    description
      "Choose a particular BGP instance.
       Clear route flap dampening information.
      ";
    input {
      leaf instance-name {
        mandatory true;
        type instance-name;
        description "instance name or all";
      }
      leaf afi-safi-name {
        mandatory true;
        type afi-safi-type;
        description "AFI and SAFI";
      }
      leaf ip-prefix {
        mandatory true;
        type inet:ip-prefix;
        description "Network and mask or masklength to clear dampening information";
      }
    }
  }

  rpc clear-bgp-instance-afi-safi-dampening {
    csc:xr-task "bgp";
    csc:cli-command "clear bgp instance <instance-name> <afi-safi-name> dampening";
    description
      "Choose a particular BGP instance.
       Clear route flap dampening information.
      ";
    input {
      leaf instance-name {
        mandatory true;
        type instance-name;
        description "instance name or all";
      }
      leaf afi-safi-name {
        mandatory true;
        type afi-safi-type;
        description "AFI and SAFI";
      }
    }
  }

  rpc clear-bgp-instance-afi-safi-external-soft-in-prefix-filter {
    csc:xr-task "bgp";
    csc:cli-command "clear bgp instance <instance-name> <afi-safi-name> external soft in prefix-filter";
    description
      "Choose a particular BGP instance.
       Clear all external peers.
       Soft reconfig.
       Soft reconfig inbound update.
       Push out prefix ORF and do inbound soft reconfig.
      ";
    input {
      leaf instance-name {
        mandatory true;
        type instance-name;
        description "instance name or all";
      }
      leaf afi-safi-name {
        mandatory true;
        type afi-safi-type;
        description "AFI and SAFI";
      }
    }
  }

  rpc clear-bgp-instance-afi-safi-external-soft-in {
    csc:xr-task "bgp";
    csc:cli-command "clear bgp instance <instance-name> <afi-safi-name> external soft in";
    description
      "Choose a particular BGP instance.
       Clear all external peers.
       Soft reconfig.
       Soft reconfig inbound update.
      ";
    input {
      leaf instance-name {
        mandatory true;
        type instance-name;
        description "instance name or all";
      }
      leaf afi-safi-name {
        mandatory true;
        type afi-safi-type;
        description "AFI and SAFI";
      }
    }
  }

  rpc clear-bgp-instance-afi-safi-external-soft-out {
    csc:xr-task "bgp";
    csc:cli-command "clear bgp instance <instance-name> <afi-safi-name> external soft out";
    description
      "Choose a particular BGP instance.
       Clear all external peers.
       Soft reconfig.
       Soft reconfig outbound update.
      ";
    input {
      leaf instance-name {
        mandatory true;
        type instance-name;
        description "instance name or all";
      }
      leaf afi-safi-name {
        mandatory true;
        type afi-safi-type;
        description "AFI and SAFI";
      }
    }
  }

  rpc clear-bgp-instance-afi-safi-external-soft {
    csc:xr-task "bgp";
    csc:cli-command "clear bgp instance <instance-name> <afi-safi-name> external soft";
    description
      "Choose a particular BGP instance.
       Clear all external peers.
       Soft reconfig.
      ";
    input {
      leaf instance-name {
        mandatory true;
        type instance-name;
        description "instance name or all";
      }
      leaf afi-safi-name {
        mandatory true;
        type afi-safi-type;
        description "AFI and SAFI";
      }
    }
  }

  rpc clear-bgp-instance-afi-safi-flap-statistics-ip-addr-ipv4-mask {
    csc:xr-task "bgp";
    csc:cli-command "clear bgp instance <instance-name> <afi-safi-name> flap-statistics <ip-addr> <ipv4-mask>";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
      leaf ipv4-mask {
        mandatory true;
        type ipv4-netmask;
        description "Network and mask or masklength to clear flap statistics";
      }
    }
  }

  rpc clear-bgp-instance-afi-safi-flap-statistics-ip-addr {
    csc:xr-task "bgp";
    csc:cli-command "clear bgp instance <instance-name> <afi-safi-name> flap-statistics <ip-addr>";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-afi-safi-flap-statistics-ip-prefix {
    csc:xr-task "bgp";
    csc:cli-command "clear bgp instance <instance-name> <afi-safi-name> flap-statistics <ip-prefix>";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
      leaf ip-prefix {
        mandatory true;
        type inet:ip-prefix;
        description "Network and mask or masklength to clear flap statistics";
      }
    }
  }

  rpc clear-bgp-instance-afi-safi-flap-statistics-regexp {
    csc:xr-task "bgp";
    csc:cli-command "clear bgp instance <instance-name> <afi-safi-name> flap-statistics regexp <regexp-pattern>";
    description
      "Choose a particular BGP instance.
       Clear flap statistics.
       Clear flap statistics for routes matching the regular expression.
      ";
    input {
      leaf instance-name {
        mandatory true;
        type instance-name;
        description "instance name or all";
      }
      leaf afi-safi-name {
        mandatory true;
        type afi-safi-type;
        description "AFI and SAFI";
      }
      leaf regexp-pattern {
        mandatory true;
        type string;
        description "A regular expression to match the BGP AS paths.  Use 'ctrl-v ?' to enter '?'";
      }
    }
  }

  rpc clear-bgp-instance-afi-safi-flap-statistics-route-policy {
    csc:xr-task "bgp";
    csc:cli-command "clear bgp instance <instance-name> <afi-safi-name> flap-statistics route-policy <route-policy-name>";
    description
      "Choose a particular BGP instance.
       Clear flap statistics.
       Clear flap statistics for routes matching the route policy.
      ";
    input {
      leaf instance-name {
        mandatory true;
        type instance-name;
        description "instance name or all";
      }
      leaf afi-safi-name {
        mandatory true;
        type afi-safi-type;
        description "AFI and SAFI";
      }
      leaf route-policy-name {
        mandatory true;
        type string;
        description "Route Policy name";
      }
    }
  }

  rpc clear-bgp-instance-afi-safi-flap-statistics {
    csc:xr-task "bgp";
    csc:cli-command "clear bgp instance <instance-name> <afi-safi-name> flap-statistics";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
    }
  }

  rpc clear-bgp-instance-afi-safi-nexthop-performance-statistics {
    csc:xr-task "bgp";
    csc:cli-command "clear bgp instance <instance-name> <afi-safi-name> nexthop performance-statistics";
    description
      "Choose a particular BGP instance.
       Clear nexthop.
       Performance statistics information related to processing.
      ";
    input {
      leaf instance-name {
        mandatory true;
        type instance-name;
        description "instance name or all";
      }
      leaf afi-safi-name {
        mandatory true;
        type afi-safi-type;
        description "AFI and SAFI";
      }
    }
  }

  rpc clear-bgp-instance-afi-safi-nexthop-registration-ip-addr {
    csc:xr-task "bgp";
    csc:cli-command "clear bgp instance <instance-name> <afi-safi-name> nexthop registration <ip-addr>";
    description
      "Choose a particular BGP instance.
       Clear nexthop.
       Registration with RIB and reregister.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Nexthop address";
      }
    }
  }

  rpc clear-bgp-instance-afi-safi-self-originated {
    csc:xr-task "bgp";
    csc:cli-command "clear bgp instance <instance-name> <afi-safi-name> self-originated";
    description
      "Choose a particular BGP instance.
       Clear redistributed, network and aggregate routes originated here.
      ";
    input {
      leaf instance-name {
        mandatory true;
        type instance-name;
        description "instance name or all";
      }
      leaf afi-safi-name {
        mandatory true;
        type afi-safi-type;
        description "AFI and SAFI";
      }
    }
  }

  rpc clear-bgp-instance-afi-safi-shutdown {
    csc:xr-task "bgp";
    csc:cli-command "clear bgp instance <instance-name> <afi-safi-name> shutdown";
    description
      "Choose a particular BGP instance.
       Clear all peers which were shut down due to low memory.
      ";
    input {
      leaf instance-name {
        mandatory true;
        type instance-name;
        description "instance name or all";
      }
      leaf afi-safi-name {
        mandatory true;
        type afi-safi-type;
        description "AFI and SAFI";
      }
    }
  }

  rpc clear-bgp-instance-afi-safi-update-outq-address-family-update-parent {
    csc:xr-task "bgp";
    csc:cli-command "clear bgp instance <instance-name> <afi-safi-name> update outq address-family update-parent";
    description
      "Choose a particular BGP instance.
       Clear Update information (Do NOT execute without cisco support)(cisco-support).
       Clear Update generation OutQ counters (Do NOT execute without cisco support)(cisco-support).
       Address-family.
       Update parents' OutQ counters too.
      ";
    input {
      leaf instance-name {
        mandatory true;
        type instance-name;
        description "instance name or all";
      }
      leaf afi-safi-name {
        mandatory true;
        type afi-safi-type;
        description "AFI and SAFI";
      }
    }
  }

  rpc clear-bgp-instance-afi-safi-update-outq-address-family {
    csc:xr-task "bgp";
    csc:cli-command "clear bgp instance <instance-name> <afi-safi-name> update outq address-family";
    description
      "Choose a particular BGP instance.
       Clear Update information (Do NOT execute without cisco support)(cisco-support).
       Clear Update generation OutQ counters (Do NOT execute without cisco support)(cisco-support).
       Address-family.
      ";
    input {
      leaf instance-name {
        mandatory true;
        type instance-name;
        description "instance name or all";
      }
      leaf afi-safi-name {
        mandatory true;
        type afi-safi-type;
        description "AFI and SAFI";
      }
    }
  }

  rpc clear-bgp-instance-afi-safi-update-outq-neighbor-ip-addr-refresh-update-parent {
    csc:xr-task "bgp";
    csc:cli-command "clear bgp instance <instance-name> <afi-safi-name> update outq neighbor <ip-addr> refresh update-parent";
    description
      "Choose a particular BGP instance.
       Clear Update information (Do NOT execute without cisco support)(cisco-support).
       Clear Update generation OutQ counters (Do NOT execute without cisco support)(cisco-support).
       Neighbor.
       Refresh OutQ.
       Update parents' OutQ counters too.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Neighbor address";
      }
    }
  }

  rpc clear-bgp-instance-afi-safi-update-outq-neighbor-ip-addr-refresh {
    csc:xr-task "bgp";
    csc:cli-command "clear bgp instance <instance-name> <afi-safi-name> update outq neighbor <ip-addr> refresh";
    description
      "Choose a particular BGP instance.
       Clear Update information (Do NOT execute without cisco support)(cisco-support).
       Clear Update generation OutQ counters (Do NOT execute without cisco support)(cisco-support).
       Neighbor.
       Refresh OutQ.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Neighbor address";
      }
    }
  }

  rpc clear-bgp-instance-afi-safi-update-outq-neighbor-ip-addr-update-parent {
    csc:xr-task "bgp";
    csc:cli-command "clear bgp instance <instance-name> <afi-safi-name> update outq neighbor <ip-addr> update-parent";
    description
      "Choose a particular BGP instance.
       Clear Update information (Do NOT execute without cisco support)(cisco-support).
       Clear Update generation OutQ counters (Do NOT execute without cisco support)(cisco-support).
       Neighbor.
       Update parents' OutQ counters too.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Neighbor address";
      }
    }
  }

  rpc clear-bgp-instance-afi-safi-update-outq-neighbor-ip-addr {
    csc:xr-task "bgp";
    csc:cli-command "clear bgp instance <instance-name> <afi-safi-name> update outq neighbor <ip-addr>";
    description
      "Choose a particular BGP instance.
       Clear Update information (Do NOT execute without cisco support)(cisco-support).
       Clear Update generation OutQ counters (Do NOT execute without cisco support)(cisco-support).
       Neighbor.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Neighbor address";
      }
    }
  }

  rpc clear-bgp-instance-afi-safi-update-outq-update-group-sub-group-update-parent {
    csc:xr-task "bgp";
    csc:cli-command "clear bgp instance <instance-name> <afi-safi-name> update outq update-group <update-group> sub-group <sub-group> update-parent";
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-instance-afi-safi-update-outq-update-group-sub-group {
    csc:xr-task "bgp";
    csc:cli-command "clear bgp instance <instance-name> <afi-safi-name> update outq update-group <update-group> sub-group <sub-group>";
    description
      "Choose a particular BGP instance.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-instance-afi-safi-update-outq-update-group-sub-group-refresh-sub-group-update-parent {
    csc:xr-task "bgp";
    csc:cli-command "clear bgp instance <instance-name> <afi-safi-name> update outq update-group <update-group> sub-group <refresh-sub-group> update-parent";
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-afi-safi-update-outq-update-group-sub-group-refresh-sub-group {
    csc:xr-task "bgp";
    csc:cli-command "clear bgp instance <instance-name> <afi-safi-name> update outq update-group <update-group> sub-group <refresh-sub-group>";
    description
      "Choose a particular BGP instance.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-afi-safi-update-outq-update-group-update-parent {
    csc:xr-task "bgp";
    csc:cli-command "clear bgp instance <instance-name> <afi-safi-name> update outq update-group <update-group> update-parent";
    description
      "Choose a particular BGP instance.
       Clear Update information (Do NOT execute without cisco support)(cisco-support).
       Clear Update generation OutQ counters (Do NOT execute without cisco support)(cisco-support).
       Update-group.
       Update parents' OutQ counters too.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
    }
  }

  rpc clear-bgp-instance-afi-safi-update-outq-update-group {
    csc:xr-task "bgp";
    csc:cli-command "clear bgp instance <instance-name> <afi-safi-name> update outq update-group <update-group>";
    description
      "Choose a particular BGP instance.
       Clear Update information (Do NOT execute without cisco support)(cisco-support).
       Clear Update generation OutQ counters (Do NOT execute without cisco support)(cisco-support).
       Update-group.
      ";
    input {
      leaf instance-name {
        mandatory true;
        type instance-name;
        description "instance name or all";
      }
      leaf afi-safi-name {
        mandatory true;
        type afi-safi-type;
        description "AFI and SAFI";
      }
      leaf update-group {
        mandatory true;
        type update-group-id;
        description "Update-group process ID <x.y>";
      }
    }
  }

  rpc clear-bgp-instance-as-graceful {
    csc:xr-task "bgp";
    csc:cli-command "clear bgp instance <instance-name> as <as-number> graceful";
    description
      "Choose a particular BGP instance.
       Clear peers in a specific AS.
       Clear with a hard reset and a graceful restart.
      ";
    input {
      leaf instance-name {
        mandatory true;
        type instance-name;
        description "instance name or all";
      }
      leaf as-number {
        mandatory true;
        type as-number;
        description "AS number";
      }
    }
  }

  rpc clear-bgp-instance-as {
    csc:xr-task "bgp";
    csc:cli-command "clear bgp instance <instance-name> as <as-number>";
    description
      "Choose a particular BGP instance.
       Clear peers in a specific AS.
      ";
    input {
      leaf instance-name {
        mandatory true;
        type instance-name;
        description "instance name or all";
      }
      leaf as-number {
        mandatory true;
        type as-number;
        description "AS number";
      }
    }
  }

  rpc clear-bgp-instance-bestpath-ip-addr-ip-netmask {
    csc:xr-task "bgp";
    csc:cli-command "clear bgp instance <instance-name> bestpath <ip-addr> <ip-netmask>";
    description
      "Choose a particular BGP instance.
       re-run BGP bestpath selection.
      ";
    input {
      leaf instance-name {
        mandatory true;
        type instance-name;
        description "instance name or all";
      }
      leaf ip-addr {
        mandatory true;
        type inet:ip-address;
        description "Network";
      }
      leaf ip-netmask {
        mandatory true;
        type ip-netmask;
        description "Mask";
      }
    }
  }

  rpc clear-bgp-instance-bestpath-ip-addr {
    csc:xr-task "bgp";
    csc:cli-command "clear bgp instance <instance-name> bestpath <ip-addr>";
    description
      "Choose a particular BGP instance.
       re-run BGP bestpath selection.
      ";
    input {
      leaf instance-name {
        mandatory true;
        type instance-name;
        description "instance name or all";
      }
      leaf ip-addr {
        mandatory true;
        type inet:ip-address;
        description "Network";
      }
    }
  }

  rpc clear-bgp-instance-bestpath-ip-prefix {
    csc:xr-task "bgp";
    csc:cli-command "clear bgp instance <instance-name> bestpath <ip-prefix>";
    description
      "Choose a particular BGP instance.
       re-run BGP bestpath selection.
      ";
    input {
      leaf instance-name {
        mandatory true;
        type instance-name;
        description "instance name or all";
      }
      leaf ip-prefix {
        mandatory true;
        type inet:ip-prefix;
        description "Network and masklength";
      }
    }
  }

  rpc clear-bgp-instance-bestpath-afi-safi-ip-addr-ip-netmask {
    csc:xr-task "bgp";
    csc:cli-command "clear bgp instance <instance-name> bestpath <afi-safi-name> <ip-addr> <ip-netmask>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Network";
      }
      leaf ip-netmask {
        mandatory true;
        type ip-netmask;
        description "Mask";
      }
    }
  }

  rpc clear-bgp-instance-bestpath-afi-safi-ip-addr {
    csc:xr-task "bgp";
    csc:cli-command "clear bgp instance <instance-name> bestpath <afi-safi-name> <ip-addr>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Network";
      }
    }
  }

  rpc clear-bgp-instance-bestpath-afi-safi-ip-prefix {
    csc:xr-task "bgp";
    csc:cli-command "clear bgp instance <instance-name> bestpath <afi-safi-name> <ip-prefix>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ip-prefix {
        mandatory true;
        type inet:ip-prefix;
        description "Network and masklength";
      }
    }
  }

  rpc clear-bgp-instance-bestpath-afi-safi-bridge-domain-ip-addr-ip-netmask {
    csc:xr-task "bgp";
    csc:cli-command "clear bgp instance <instance-name> bestpath <afi-safi-name> bridge-domain <bridge-domain-name> <ip-addr> <ip-netmask>";
    description
      "Choose a particular BGP instance.
       re-run BGP bestpath selection.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
      leaf ip-netmask {
        mandatory true;
        type ip-netmask;
        description "Mask";
      }
    }
  }

  rpc clear-bgp-instance-bestpath-afi-safi-bridge-domain-ip-addr {
    csc:xr-task "bgp";
    csc:cli-command "clear bgp instance <instance-name> bestpath <afi-safi-name> bridge-domain <bridge-domain-name> <ip-addr>";
    description
      "Choose a particular BGP instance.
       re-run BGP bestpath selection.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
    }
  }

  rpc clear-bgp-instance-bestpath-afi-safi-bridge-domain-ip-prefix {
    csc:xr-task "bgp";
    csc:cli-command "clear bgp instance <instance-name> bestpath <afi-safi-name> bridge-domain <bridge-domain-name> <ip-prefix>";
    description
      "Choose a particular BGP instance.
       re-run BGP bestpath selection.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-prefix {
        mandatory true;
        type inet:ip-prefix;
        description "Network and masklength";
      }
    }
  }

  rpc clear-bgp-instance-bestpath-afi-safi-rd-ip-addr-ip-netmask {
    csc:xr-task "bgp";
    csc:cli-command "clear bgp instance <instance-name> bestpath <afi-safi-name> rd <rd> <ip-addr> <ip-netmask>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
      leaf ip-netmask {
        mandatory true;
        type ip-netmask;
        description "Mask";
      }
    }
  }

  rpc clear-bgp-instance-bestpath-afi-safi-rd-ip-addr {
    csc:xr-task "bgp";
    csc:cli-command "clear bgp instance <instance-name> bestpath <afi-safi-name> rd <rd> <ip-addr>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
    }
  }

  rpc clear-bgp-instance-bestpath-afi-safi-rd-ip-prefix {
    csc:xr-task "bgp";
    csc:cli-command "clear bgp instance <instance-name> bestpath <afi-safi-name> rd <rd> <ip-prefix>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-prefix {
        mandatory true;
        type inet:ip-prefix;
        description "Network and masklength";
      }
    }
  }

  rpc clear-bgp-instance-bestpath-afi-safi-ipv4-addr-ipv4-mask {
    csc:xr-task "bgp";
    csc:cli-command "clear bgp instance <instance-name> bestpath <afi-safi-name> <ipv4-addr> <ipv4-mask>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-instance-bestpath-afi-safi-ipv4-addr {
    csc:xr-task "bgp";
    csc:cli-command "clear bgp instance <instance-name> bestpath <afi-safi-name> <ipv4-addr>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv4-addr {
        mandatory true;
        type inet:ipv4-address;
        description "IPv4 network";
      }
    }
  }

  rpc clear-bgp-instance-bestpath-afi-safi-ipv4-prefix {
    csc:xr-task "bgp";
    csc:cli-command "clear bgp instance <instance-name> bestpath <afi-safi-name> <ipv4-prefix>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv4-prefix {
        mandatory true;
        type inet:ipv4-prefix;
        description "IPv4 network and masklength";
      }
    }
  }

  rpc clear-bgp-instance-bestpath-afi-safi-rd-ipv4-addr {
    csc:xr-task "bgp";
    csc:cli-command "clear bgp instance <instance-name> bestpath <afi-safi-name> rd <rd> <ipv4-addr>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 MDT network";
      }
    }
  }

  rpc clear-bgp-instance-bestpath-afi-safi-vrf-ipv4-addr {
    csc:xr-task "bgp";
    csc:cli-command "clear bgp instance <instance-name> bestpath <afi-safi-name> vrf <vrf-name> <ipv4-addr>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 MDT network";
      }
    }
  }

  rpc clear-bgp-instance-bestpath-afi-safi-network {
    csc:xr-task "bgp";
    csc:cli-command "clear bgp instance <instance-name> bestpath <afi-safi-name> <network>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf network {
        mandatory true;
        type string;
        description "Address family modifier specific network";
      }
    }
  }

  rpc clear-bgp-instance-bestpath-afi-safi-rd-network {
    csc:xr-task "bgp";
    csc:cli-command "clear bgp instance <instance-name> bestpath <afi-safi-name> rd <rd> <network>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-instance-bestpath-afi-safi-vrf-network {
    csc:xr-task "bgp";
    csc:cli-command "clear bgp instance <instance-name> bestpath <afi-safi-name> vrf <vrf-name> <network>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-instance-bestpath-afi-safi-rt-constraint-network {
    csc:xr-task "bgp";
    csc:cli-command "clear bgp instance <instance-name> bestpath <afi-safi-name> <rt-constraint-network>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf rt-constraint-network {
        mandatory true;
        type string;
        description "RT-Constraint network";
      }
    }
  }

  rpc clear-bgp-instance-bestpath-afi-safi-ipv4-tunnel-network {
    csc:xr-task "bgp";
    csc:cli-command "clear bgp instance <instance-name> bestpath <afi-safi-name> <ipv4-tunnel-network>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv4-tunnel-network {
        mandatory true;
        type string;
        description "IPv4 Tunnel network <Tunnel-ID>:<IPv4 Address>";
      }
    }
  }

  rpc clear-bgp-instance-bestpath-afi-safi-ipv6-addr-ipv6-netmask {
    csc:xr-task "bgp";
    csc:cli-command "clear bgp instance <instance-name> bestpath <afi-safi-name> <ipv6-addr> <ipv6-netmask>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-instance-bestpath-afi-safi-ipv6-addr {
    csc:xr-task "bgp";
    csc:cli-command "clear bgp instance <instance-name> bestpath <afi-safi-name> <ipv6-addr>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv6-addr {
        mandatory true;
        type inet:ipv6-address;
        description "IPv6 network";
      }
    }
  }

  rpc clear-bgp-instance-bestpath-afi-safi-ipv6-prefix {
    csc:xr-task "bgp";
    csc:cli-command "clear bgp instance <instance-name> bestpath <afi-safi-name> <ipv6-prefix>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-instance-bestpath-afi-safi-rd {
    csc:xr-task "bgp";
    csc:cli-command "clear bgp instance <instance-name> bestpath <afi-safi-name> rd <rd>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
    }
  }

  rpc clear-bgp-instance-bestpath-afi-safi-vrf {
    csc:xr-task "bgp";
    csc:cli-command "clear bgp instance <instance-name> bestpath <afi-safi-name> vrf <vrf-name>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
    }
  }

  rpc clear-bgp-instance-bestpath-afi-safi {
    csc:xr-task "bgp";
    csc:cli-command "clear bgp instance <instance-name> bestpath <afi-safi-name>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
    }
  }

  rpc clear-bgp-instance-bestpath-afi-safi-sr-policy-prefix {
    csc:xr-task "bgp";
    csc:cli-command "clear bgp instance <instance-name> bestpath <afi-safi-name> <sr-policy-prefix>";
    description
      "Choose a particular BGP instance.
       re-run BGP bestpath selection.
      ";
    input {
      leaf instance-name {
        mandatory true;
        type instance-name;
        description "instance name or all";
      }
      leaf afi-safi-name {
        mandatory true;
        type afi-safi-type;
        description "AFI and SAFI";
      }
      leaf sr-policy-prefix {
        mandatory true;
        type string;
        description "SR Policy prefix";
      }
    }
  }

  rpc clear-bgp-instance-bestpath-afi-safi-bridge-domain-ipv4-prefix {
    csc:xr-task "bgp";
    csc:cli-command "clear bgp instance <instance-name> bestpath <afi-safi-name> bridge-domain <bridge-domain-name> <ipv4-prefix>";
    description
      "Choose a particular BGP instance.
       re-run BGP bestpath selection.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ipv4-prefix {
        mandatory true;
        type inet:ipv4-prefix;
        description "L2VPN EVPN Prefix";
      }
    }
  }

  rpc clear-bgp-instance-bestpath-afi-safi-rd-ipv4-prefix {
    csc:xr-task "bgp";
    csc:cli-command "clear bgp instance <instance-name> bestpath <afi-safi-name> rd <rd> <ipv4-prefix>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-prefix {
        mandatory true;
        type inet:ipv4-prefix;
        description "L2VPN EVPN Prefix";
      }
    }
  }

  rpc clear-bgp-instance-bestpath-afi-safi-mp2mp-ipv4-prefix {
    csc:xr-task "bgp";
    csc:cli-command "clear bgp instance <instance-name> bestpath <afi-safi-name> mp2mp <mp2mp> <ipv4-prefix>";
    description
      "Choose a particular BGP instance.
       re-run BGP bestpath selection.
       Display routes for a specified Xconnect group:MP2MP.
      ";
    input {
      leaf instance-name {
        mandatory true;
        type instance-name;
        description "instance name or all";
      }
      leaf afi-safi-name {
        mandatory true;
        type afi-safi-type;
        description "AFI and SAFI";
      }
      leaf mp2mp {
        mandatory true;
        type string;
        description "Xconnect Group:mp2mp";
      }
      leaf ipv4-prefix {
        mandatory true;
        type inet:ipv4-prefix;
        description "L2VPN VPWS Prefix";
      }
    }
  }

  rpc clear-bgp-instance-bestpath-afi-safi-vrf-ipv4-prefix {
    csc:xr-task "bgp";
    csc:cli-command "clear bgp instance <instance-name> bestpath <afi-safi-name> vrf <vrf-name> <ipv4-prefix>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-prefix {
        mandatory true;
        type inet:ipv4-prefix;
        description "VPN Fspec Prefix";
      }
    }
  }

  rpc clear-bgp-instance-bestpath-afi-safi-rd-ipv4-addr-ipv4-mask {
    csc:xr-task "bgp";
    csc:cli-command "clear bgp instance <instance-name> bestpath <afi-safi-name> rd <rd> <ipv4-addr> <ipv4-mask>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 network";
      }
      leaf ipv4-mask {
        mandatory true;
        type ipv4-netmask;
        description "IPv4 mask";
      }
    }
  }

  rpc clear-bgp-instance-bestpath-afi-safi-vrf-ipv4-addr-ipv4-mask {
    csc:xr-task "bgp";
    csc:cli-command "clear bgp instance <instance-name> bestpath <afi-safi-name> vrf <vrf-name> <ipv4-addr> <ipv4-mask>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 network";
      }
      leaf ipv4-mask {
        mandatory true;
        type ipv4-netmask;
        description "IPv4 mask";
      }
    }
  }

  rpc clear-bgp-instance-bestpath-afi-safi-rd-ipv6-addr-ipv6-netmask {
    csc:xr-task "bgp";
    csc:cli-command "clear bgp instance <instance-name> bestpath <afi-safi-name> rd <rd> <ipv6-addr> <ipv6-netmask>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
      leaf ipv6-netmask {
        mandatory true;
        type ipv6-netmask;
        description "IPv6 mask";
      }
    }
  }

  rpc clear-bgp-instance-bestpath-afi-safi-rd-ipv6-addr {
    csc:xr-task "bgp";
    csc:cli-command "clear bgp instance <instance-name> bestpath <afi-safi-name> rd <rd> <ipv6-addr>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
    }
  }

  rpc clear-bgp-instance-bestpath-afi-safi-rd-ipv6-prefix {
    csc:xr-task "bgp";
    csc:cli-command "clear bgp instance <instance-name> bestpath <afi-safi-name> rd <rd> <ipv6-prefix>";
    description
      "Choose a particular BGP instance.
       re-run BGP bestpath selection.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-prefix {
        mandatory true;
        type inet:ipv6-prefix;
        description "IPv6 network and masklength";
      }
    }
  }

  rpc clear-bgp-instance-bestpath-afi-safi-vrf-ipv6-addr-ipv6-netmask {
    csc:xr-task "bgp";
    csc:cli-command "clear bgp instance <instance-name> bestpath <afi-safi-name> vrf <vrf-name> <ipv6-addr> <ipv6-netmask>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
      leaf ipv6-netmask {
        mandatory true;
        type ipv6-netmask;
        description "IPv6 mask";
      }
    }
  }

  rpc clear-bgp-instance-bestpath-afi-safi-vrf-ipv6-addr {
    csc:xr-task "bgp";
    csc:cli-command "clear bgp instance <instance-name> bestpath <afi-safi-name> vrf <vrf-name> <ipv6-addr>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
    }
  }

  rpc clear-bgp-instance-bestpath-afi-safi-vrf-ipv6-prefix {
    csc:xr-task "bgp";
    csc:cli-command "clear bgp instance <instance-name> bestpath <afi-safi-name> vrf <vrf-name> <ipv6-prefix>";
    description
      "Choose a particular BGP instance.
       re-run BGP bestpath selection.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-prefix {
        mandatory true;
        type inet:ipv6-prefix;
        description "IPv6 network and masklength";
      }
    }
  }

  rpc clear-bgp-instance-bestpath-vrf-ip-addr-ip-netmask {
    csc:xr-task "bgp";
    csc:cli-command "clear bgp instance <instance-name> bestpath vrf <vrf-all> <ip-addr> <ip-netmask>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Network";
      }
      leaf ip-netmask {
        mandatory true;
        type ip-netmask;
        description "Mask";
      }
    }
  }

  rpc clear-bgp-instance-bestpath-vrf-ip-addr {
    csc:xr-task "bgp";
    csc:cli-command "clear bgp instance <instance-name> bestpath vrf <vrf-all> <ip-addr>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Network";
      }
    }
  }

  rpc clear-bgp-instance-bestpath-vrf-ip-prefix {
    csc:xr-task "bgp";
    csc:cli-command "clear bgp instance <instance-name> bestpath vrf <vrf-all> <ip-prefix>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf ip-prefix {
        mandatory true;
        type inet:ip-prefix;
        description "Network and masklength";
      }
    }
  }

  rpc clear-bgp-instance-bestpath-vrf-afi-safi-ipv4-prefix {
    csc:xr-task "bgp";
    csc:cli-command "clear bgp instance <instance-name> bestpath vrf <vrf-all> <afi-safi-name> <ipv4-prefix>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "Fspec IPv4 Prefix";
      }
    }
  }

  rpc clear-bgp-instance-bestpath-vrf-afi-safi-ipv4-addr-ipv4-mask {
    csc:xr-task "bgp";
    csc:cli-command "clear bgp instance <instance-name> bestpath vrf <vrf-all> <afi-safi-name> <ipv4-addr> <ipv4-mask>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-instance-bestpath-vrf-afi-safi-ipv4-addr {
    csc:xr-task "bgp";
    csc:cli-command "clear bgp instance <instance-name> bestpath vrf <vrf-all> <afi-safi-name> <ipv4-addr>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
    }
  }

  rpc clear-bgp-instance-bestpath-vrf-afi-safi-network {
    csc:xr-task "bgp";
    csc:cli-command "clear bgp instance <instance-name> bestpath vrf <vrf-all> <afi-safi-name> <network>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf network {
        mandatory true;
        type string;
        description "Address family modifier specific network";
      }
    }
  }

  rpc clear-bgp-instance-bestpath-vrf-afi-safi-rd-network {
    csc:xr-task "bgp";
    csc:cli-command "clear bgp instance <instance-name> bestpath vrf <vrf-all> <afi-safi-name> rd <rd> <network>";
    description
      "Choose a particular BGP instance.
       re-run BGP bestpath selection.
       Specify a VRF.
       Display routes with a specific route distinguisher.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-instance-bestpath-vrf-afi-safi-vrf-network {
    csc:xr-task "bgp";
    csc:cli-command "clear bgp instance <instance-name> bestpath vrf <vrf-all> <afi-safi-name> vrf <vrf-name> <network>";
    description
      "Choose a particular BGP instance.
       re-run BGP bestpath selection.
       Specify a VRF.
       Display routes for a specified VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-instance-bestpath-vrf-afi-safi-ipv6-addr-ipv6-netmask {
    csc:xr-task "bgp";
    csc:cli-command "clear bgp instance <instance-name> bestpath vrf <vrf-all> <afi-safi-name> <ipv6-addr> <ipv6-netmask>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-instance-bestpath-vrf-afi-safi-ipv6-addr {
    csc:xr-task "bgp";
    csc:cli-command "clear bgp instance <instance-name> bestpath vrf <vrf-all> <afi-safi-name> <ipv6-addr>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
    }
  }

  rpc clear-bgp-instance-bestpath-vrf-afi-safi-ipv6-prefix {
    csc:xr-task "bgp";
    csc:cli-command "clear bgp instance <instance-name> bestpath vrf <vrf-all> <afi-safi-name> <ipv6-prefix>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-instance-bestpath-vrf-afi-safi-rd {
    csc:xr-task "bgp";
    csc:cli-command "clear bgp instance <instance-name> bestpath vrf <vrf-all> <afi-safi-name> rd <rd>";
    description
      "Choose a particular BGP instance.
       re-run BGP bestpath selection.
       Specify a VRF.
       Display routes with a specific route distinguisher.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
    }
  }

  rpc clear-bgp-instance-bestpath-vrf-afi-safi-vrf {
    csc:xr-task "bgp";
    csc:cli-command "clear bgp instance <instance-name> bestpath vrf <vrf-all> <afi-safi-name> vrf <vrf-name>";
    description
      "Choose a particular BGP instance.
       re-run BGP bestpath selection.
       Specify a VRF.
       Display routes for a specified VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
    }
  }

  rpc clear-bgp-instance-bestpath-vrf-afi-safi {
    csc:xr-task "bgp";
    csc:cli-command "clear bgp instance <instance-name> bestpath vrf <vrf-all> <afi-safi-name>";
    description
      "Choose a particular BGP instance.
       re-run BGP bestpath selection.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-external-graceful {
    csc:xr-task "bgp";
    csc:cli-command "clear bgp instance <instance-name> external graceful";
    description
      "Choose a particular BGP instance.
       Clear all external peers.
       Clear with a hard reset and a graceful restart.
      ";
    input {
      leaf instance-name {
        mandatory true;
        type instance-name;
        description "instance name or all";
      }
    }
  }

  rpc clear-bgp-instance-external {
    csc:xr-task "bgp";
    csc:cli-command "clear bgp instance <instance-name> external";
    description
      "Choose a particular BGP instance.
       Clear all external peers.
      ";
    input {
      leaf instance-name {
        mandatory true;
        type instance-name;
        description "instance name or all";
      }
    }
  }

  rpc clear-bgp-instance-afi-safi-dampening-ipv4-prefix {
    csc:xr-task "bgp";
    csc:cli-command "clear bgp instance <instance-name> <afi-safi-name> dampening <ipv4-prefix>";
    description
      "Choose a particular BGP instance.
       Clear route flap dampening information.
      ";
    input {
      leaf instance-name {
        mandatory true;
        type instance-name;
        description "instance name or all";
      }
      leaf afi-safi-name {
        mandatory true;
        type afi-safi-type;
        description "AFI and SAFI";
      }
      leaf ipv4-prefix {
        mandatory true;
        type inet:ipv4-prefix;
        description "IPv4 Network and mask or masklength to clear dampening information";
      }
    }
  }

  rpc clear-bgp-instance-afi-safi-flap-statistics-ipv4-prefix {
    csc:xr-task "bgp";
    csc:cli-command "clear bgp instance <instance-name> <afi-safi-name> flap-statistics <ipv4-prefix>";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
      leaf ipv4-prefix {
        mandatory true;
        type inet:ipv4-prefix;
        description "IPv4 Network and mask or masklength to clear flap statistics";
      }
    }
  }

  rpc clear-bgp-instance-afi-safi-dampening-ipv6-prefix {
    csc:xr-task "bgp";
    csc:cli-command "clear bgp instance <instance-name> <afi-safi-name> dampening <ipv6-prefix>";
    description
      "Choose a particular BGP instance.
       Clear route flap dampening information.
      ";
    input {
      leaf instance-name {
        mandatory true;
        type instance-name;
        description "instance name or all";
      }
      leaf afi-safi-name {
        mandatory true;
        type afi-safi-type;
        description "AFI and SAFI";
      }
      leaf ipv6-prefix {
        mandatory true;
        type inet:ipv6-prefix;
        description "IPv6 Network and mask or masklength to clear dampening information";
      }
    }
  }

  rpc clear-bgp-instance-afi-safi-flap-statistics-ipv6-prefix {
    csc:xr-task "bgp";
    csc:cli-command "clear bgp instance <instance-name> <afi-safi-name> flap-statistics <ipv6-prefix>";
    description
      "Choose a particular BGP instance.
       Clear flap statistics.
      ";
    input {
      leaf instance-name {
        mandatory true;
        type instance-name;
        description "instance name or all";
      }
      leaf afi-safi-name {
        mandatory true;
        type afi-safi-type;
        description "AFI and SAFI";
      }
      leaf ipv6-prefix {
        mandatory true;
        type inet:ipv6-prefix;
        description "IPv6 Network and mask or masklength to clear flap statistics";
      }
    }
  }

  rpc clear-bgp-instance-nexthop-performance-statistics {
    csc:xr-task "bgp";
    csc:cli-command "clear bgp instance <instance-name> nexthop performance-statistics";
    description
      "Choose a particular BGP instance.
       Clear nexthop.
       Performance statistics information related to processing.
      ";
    input {
      leaf instance-name {
        mandatory true;
        type instance-name;
        description "instance name or all";
      }
    }
  }

  rpc clear-bgp-instance-nexthop-registration-ip-addr {
    csc:xr-task "bgp";
    csc:cli-command "clear bgp instance <instance-name> nexthop registration <ip-addr>";
    description
      "Choose a particular BGP instance.
       Clear nexthop.
       Registration with RIB and reregister.
      ";
    input {
      leaf instance-name {
        mandatory true;
        type instance-name;
        description "instance name or all";
      }
      leaf ip-addr {
        mandatory true;
        type inet:ip-address;
        description "Nexthop address";
      }
    }
  }

  rpc clear-bgp-instance-peer-drops-all {
    csc:xr-task "bgp";
    csc:cli-command "clear bgp instance <instance-name> peer-drops *";
    description
      "Choose a particular BGP instance.
       Clear established/dropped counters for a peer.
       All Neighbors.
      ";
    input {
      leaf instance-name {
        mandatory true;
        type instance-name;
        description "instance name or all";
      }
    }
  }

  rpc clear-bgp-instance-peer-drops-ip-addr {
    csc:xr-task "bgp";
    csc:cli-command "clear bgp instance <instance-name> peer-drops <ip-addr>";
    description
      "Choose a particular BGP instance.
       Clear established/dropped counters for a peer.
      ";
    input {
      leaf instance-name {
        mandatory true;
        type instance-name;
        description "instance name or all";
      }
      leaf ip-addr {
        mandatory true;
        type inet:ip-address;
        description "BGP neighbor IP address";
      }
    }
  }

  rpc clear-bgp-instance-performance-statistics {
    csc:xr-task "bgp";
    csc:cli-command "clear bgp instance <instance-name> performance-statistics";
    description
      "Choose a particular BGP instance.
       Clear performance statistics.
      ";
    input {
      leaf instance-name {
        mandatory true;
        type instance-name;
        description "instance name or all";
      }
    }
  }

  rpc clear-bgp-instance-rpki-server-all-serial-query {
    csc:xr-task "bgp";
    csc:cli-command "clear bgp instance <instance-name> rpki server * serial-query";
    description
      "Choose a particular BGP instance.
       RPKI clear command.
       clear RPKI cache-server.
       clear all RPKI cache-servers.
       send serial-queries to all cache-servers (with latest serial numbers).
      ";
    input {
      leaf instance-name {
        mandatory true;
        type instance-name;
        description "instance name or all";
      }
    }
  }

  rpc clear-bgp-instance-rpki-server-all {
    csc:xr-task "bgp";
    csc:cli-command "clear bgp instance <instance-name> rpki server *";
    description
      "Choose a particular BGP instance.
       RPKI clear command.
       clear RPKI cache-server.
       clear all RPKI cache-servers.
      ";
    input {
      leaf instance-name {
        mandatory true;
        type instance-name;
        description "instance name or all";
      }
    }
  }

  rpc clear-bgp-instance-rpki-server-rpki-server {
    csc:xr-task "bgp";
    csc:cli-command "clear bgp instance <instance-name> rpki server <rpki-server>";
    description
      "Choose a particular BGP instance.
       RPKI clear command.
       clear RPKI cache-server.
      ";
    input {
      leaf instance-name {
        mandatory true;
        type instance-name;
        description "instance name or all";
      }
      leaf rpki-server {
        mandatory true;
        type string;
        description "clear a specific RPKI cache-server (hostname or IP address)";
      }
    }
  }

  rpc clear-bgp-instance-rpki-validation-ipv4 {
    csc:xr-task "bgp";
    csc:cli-command "clear bgp instance <instance-name> rpki validation ipv4";
    description
      "Choose a particular BGP instance.
       RPKI clear command.
       clear RPKI origin-validation (trigger origin validation).
       trigger origin validation walk for the IPv4 table.
      ";
    input {
      leaf instance-name {
        mandatory true;
        type instance-name;
        description "instance name or all";
      }
    }
  }

  rpc clear-bgp-instance-rpki-validation-ipv6 {
    csc:xr-task "bgp";
    csc:cli-command "clear bgp instance <instance-name> rpki validation ipv6";
    description
      "Choose a particular BGP instance.
       RPKI clear command.
       clear RPKI origin-validation (trigger origin validation).
       trigger origin validation walk for the IPv6 table.
      ";
    input {
      leaf instance-name {
        mandatory true;
        type instance-name;
        description "instance name or all";
      }
    }
  }

  rpc clear-bgp-instance-rpki-validation {
    csc:xr-task "bgp";
    csc:cli-command "clear bgp instance <instance-name> rpki validation";
    description
      "Choose a particular BGP instance.
       RPKI clear command.
       clear RPKI origin-validation (trigger origin validation).
      ";
    input {
      leaf instance-name {
        mandatory true;
        type instance-name;
        description "instance name or all";
      }
    }
  }

  rpc clear-bgp-instance-shutdown {
    csc:xr-task "bgp";
    csc:cli-command "clear bgp instance <instance-name> shutdown";
    description
      "Choose a particular BGP instance.
       Clear all peers which were shut down due to low memory.
      ";
    input {
      leaf instance-name {
        mandatory true;
        type instance-name;
        description "instance name or all";
      }
    }
  }

  rpc clear-bgp-instance-update-outq-address-family-update-parent {
    csc:xr-task "bgp";
    csc:cli-command "clear bgp instance <instance-name> update outq address-family update-parent";
    description
      "Choose a particular BGP instance.
       Clear Update information (Do NOT execute without cisco support)(cisco-support).
       Clear Update generation OutQ counters (Do NOT execute without cisco support)(cisco-support).
       Address-family.
       Update parents' OutQ counters too.
      ";
    input {
      leaf instance-name {
        mandatory true;
        type instance-name;
        description "instance name or all";
      }
    }
  }

  rpc clear-bgp-instance-update-outq-address-family {
    csc:xr-task "bgp";
    csc:cli-command "clear bgp instance <instance-name> update outq address-family";
    description
      "Choose a particular BGP instance.
       Clear Update information (Do NOT execute without cisco support)(cisco-support).
       Clear Update generation OutQ counters (Do NOT execute without cisco support)(cisco-support).
       Address-family.
      ";
    input {
      leaf instance-name {
        mandatory true;
        type instance-name;
        description "instance name or all";
      }
    }
  }

  rpc clear-bgp-instance-update-outq-neighbor-ip-addr-refresh-update-parent {
    csc:xr-task "bgp";
    csc:cli-command "clear bgp instance <instance-name> update outq neighbor <ip-addr> refresh update-parent";
    description
      "Choose a particular BGP instance.
       Clear Update information (Do NOT execute without cisco support)(cisco-support).
       Clear Update generation OutQ counters (Do NOT execute without cisco support)(cisco-support).
       Neighbor.
       Refresh OutQ.
       Update parents' OutQ counters too.
      ";
    input {
      leaf instance-name {
        mandatory true;
        type instance-name;
        description "instance name or all";
      }
      leaf ip-addr {
        mandatory true;
        type inet:ip-address;
        description "Neighbor address";
      }
    }
  }

  rpc clear-bgp-instance-update-outq-neighbor-ip-addr-refresh {
    csc:xr-task "bgp";
    csc:cli-command "clear bgp instance <instance-name> update outq neighbor <ip-addr> refresh";
    description
      "Choose a particular BGP instance.
       Clear Update information (Do NOT execute without cisco support)(cisco-support).
       Clear Update generation OutQ counters (Do NOT execute without cisco support)(cisco-support).
       Neighbor.
       Refresh OutQ.
      ";
    input {
      leaf instance-name {
        mandatory true;
        type instance-name;
        description "instance name or all";
      }
      leaf ip-addr {
        mandatory true;
        type inet:ip-address;
        description "Neighbor address";
      }
    }
  }

  rpc clear-bgp-instance-update-outq-neighbor-ip-addr-update-parent {
    csc:xr-task "bgp";
    csc:cli-command "clear bgp instance <instance-name> update outq neighbor <ip-addr> update-parent";
    description
      "Choose a particular BGP instance.
       Clear Update information (Do NOT execute without cisco support)(cisco-support).
       Clear Update generation OutQ counters (Do NOT execute without cisco support)(cisco-support).
       Neighbor.
       Update parents' OutQ counters too.
      ";
    input {
      leaf instance-name {
        mandatory true;
        type instance-name;
        description "instance name or all";
      }
      leaf ip-addr {
        mandatory true;
        type inet:ip-address;
        description "Neighbor address";
      }
    }
  }

  rpc clear-bgp-instance-update-outq-neighbor-ip-addr {
    csc:xr-task "bgp";
    csc:cli-command "clear bgp instance <instance-name> update outq neighbor <ip-addr>";
    description
      "Choose a particular BGP instance.
       Clear Update information (Do NOT execute without cisco support)(cisco-support).
       Clear Update generation OutQ counters (Do NOT execute without cisco support)(cisco-support).
       Neighbor.
      ";
    input {
      leaf instance-name {
        mandatory true;
        type instance-name;
        description "instance name or all";
      }
      leaf ip-addr {
        mandatory true;
        type inet:ip-address;
        description "Neighbor address";
      }
    }
  }

  rpc clear-bgp-instance-update-outq-process {
    csc:xr-task "bgp";
    csc:cli-command "clear bgp instance <instance-name> update outq process";
    description
      "Choose a particular BGP instance.
       Clear Update information (Do NOT execute without cisco support)(cisco-support).
       Clear Update generation OutQ counters (Do NOT execute without cisco support)(cisco-support).
       Process.
      ";
    input {
      leaf instance-name {
        mandatory true;
        type instance-name;
        description "instance name or all";
      }
    }
  }

  rpc clear-bgp-instance-update-outq-update-group-sub-group-update-parent {
    csc:xr-task "bgp";
    csc:cli-command "clear bgp instance <instance-name> update outq update-group <update-group> sub-group <sub-group> update-parent";
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf update-group {
        mandatory true;
        type update-group-id;
        description "Update-group process ID <x.y>";
      }
      leaf sub-group {
        mandatory true;
        type update-group-id;
        description "Sub-group process ID <x.y>";
      }
    }
  }

  rpc clear-bgp-instance-update-outq-update-group-sub-group {
    csc:xr-task "bgp";
    csc:cli-command "clear bgp instance <instance-name> update outq update-group <update-group> sub-group <sub-group>";
    description
      "Choose a particular BGP instance.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf update-group {
        mandatory true;
        type update-group-id;
        description "Update-group process ID <x.y>";
      }
      leaf sub-group {
        mandatory true;
        type update-group-id;
        description "Sub-group process ID <x.y>";
      }
    }
  }

  rpc clear-bgp-instance-update-outq-update-group-sub-group-refresh-sub-group-update-parent {
    csc:xr-task "bgp";
    csc:cli-command "clear bgp instance <instance-name> update outq update-group <update-group> sub-group <refresh-sub-group> update-parent";
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-update-outq-update-group-sub-group-refresh-sub-group {
    csc:xr-task "bgp";
    csc:cli-command "clear bgp instance <instance-name> update outq update-group <update-group> sub-group <refresh-sub-group>";
    description
      "Choose a particular BGP instance.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-update-outq-update-group-update-parent {
    csc:xr-task "bgp";
    csc:cli-command "clear bgp instance <instance-name> update outq update-group <update-group> update-parent";
    description
      "Choose a particular BGP instance.
       Clear Update information (Do NOT execute without cisco support)(cisco-support).
       Clear Update generation OutQ counters (Do NOT execute without cisco support)(cisco-support).
       Update-group.
       Update parents' OutQ counters too.
      ";
    input {
      leaf instance-name {
        mandatory true;
        type instance-name;
        description "instance name or all";
      }
      leaf update-group {
        mandatory true;
        type update-group-id;
        description "Update-group process ID <x.y>";
      }
    }
  }

  rpc clear-bgp-instance-update-outq-update-group {
    csc:xr-task "bgp";
    csc:cli-command "clear bgp instance <instance-name> update outq update-group <update-group>";
    description
      "Choose a particular BGP instance.
       Clear Update information (Do NOT execute without cisco support)(cisco-support).
       Clear Update generation OutQ counters (Do NOT execute without cisco support)(cisco-support).
       Update-group.
      ";
    input {
      leaf instance-name {
        mandatory true;
        type instance-name;
        description "instance name or all";
      }
      leaf update-group {
        mandatory true;
        type update-group-id;
        description "Update-group process ID <x.y>";
      }
    }
  }

  rpc clear-bgp-instance-version-ip-addr-ip-netmask {
    csc:xr-task "bgp";
    csc:cli-command "clear bgp instance <instance-name> version <ip-addr> <ip-netmask>";
    description
      "Choose a particular BGP instance.
       clear BGP prefix version.
      ";
    input {
      leaf instance-name {
        mandatory true;
        type instance-name;
        description "instance name or all";
      }
      leaf ip-addr {
        mandatory true;
        type inet:ip-address;
        description "Network";
      }
      leaf ip-netmask {
        mandatory true;
        type ip-netmask;
        description "Mask";
      }
    }
  }

  rpc clear-bgp-instance-version-ip-addr {
    csc:xr-task "bgp";
    csc:cli-command "clear bgp instance <instance-name> version <ip-addr>";
    description
      "Choose a particular BGP instance.
       clear BGP prefix version.
      ";
    input {
      leaf instance-name {
        mandatory true;
        type instance-name;
        description "instance name or all";
      }
      leaf ip-addr {
        mandatory true;
        type inet:ip-address;
        description "Network";
      }
    }
  }

  rpc clear-bgp-instance-version-ip-prefix {
    csc:xr-task "bgp";
    csc:cli-command "clear bgp instance <instance-name> version <ip-prefix>";
    description
      "Choose a particular BGP instance.
       clear BGP prefix version.
      ";
    input {
      leaf instance-name {
        mandatory true;
        type instance-name;
        description "instance name or all";
      }
      leaf ip-prefix {
        mandatory true;
        type inet:ip-prefix;
        description "Network and masklength";
      }
    }
  }

  rpc clear-bgp-instance-version-afi-safi-ip-addr-ip-netmask {
    csc:xr-task "bgp";
    csc:cli-command "clear bgp instance <instance-name> version <afi-safi-name> <ip-addr> <ip-netmask>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Network";
      }
      leaf ip-netmask {
        mandatory true;
        type ip-netmask;
        description "Mask";
      }
    }
  }

  rpc clear-bgp-instance-version-afi-safi-ip-addr {
    csc:xr-task "bgp";
    csc:cli-command "clear bgp instance <instance-name> version <afi-safi-name> <ip-addr>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ip-addr {
        mandatory true;
        type inet:ip-address;
        description "Network";
      }
    }
  }

  rpc clear-bgp-instance-version-afi-safi-ip-prefix {
    csc:xr-task "bgp";
    csc:cli-command "clear bgp instance <instance-name> version <afi-safi-name> <ip-prefix>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ip-prefix {
        mandatory true;
        type inet:ip-prefix;
        description "Network and masklength";
      }
    }
  }

  rpc clear-bgp-instance-version-afi-safi-bridge-domain-ip-addr-ip-netmask {
    csc:xr-task "bgp";
    csc:cli-command "clear bgp instance <instance-name> version <afi-safi-name> bridge-domain <bridge-domain-name> <ip-addr> <ip-netmask>";
    description
      "Choose a particular BGP instance.
       clear BGP prefix version.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
      leaf ip-netmask {
        mandatory true;
        type ip-netmask;
        description "Mask";
      }
    }
  }

  rpc clear-bgp-instance-version-afi-safi-bridge-domain-ip-addr {
    csc:xr-task "bgp";
    csc:cli-command "clear bgp instance <instance-name> version <afi-safi-name> bridge-domain <bridge-domain-name> <ip-addr>";
    description
      "Choose a particular BGP instance.
       clear BGP prefix version.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
    }
  }

  rpc clear-bgp-instance-version-afi-safi-bridge-domain-ip-prefix {
    csc:xr-task "bgp";
    csc:cli-command "clear bgp instance <instance-name> version <afi-safi-name> bridge-domain <bridge-domain-name> <ip-prefix>";
    description
      "Choose a particular BGP instance.
       clear BGP prefix version.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ip-prefix {
        mandatory true;
        type inet:ip-prefix;
        description "Network and masklength";
      }
    }
  }

  rpc clear-bgp-instance-version-afi-safi-rd-ip-addr-ip-netmask {
    csc:xr-task "bgp";
    csc:cli-command "clear bgp instance <instance-name> version <afi-safi-name> rd <rd> <ip-addr> <ip-netmask>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
      leaf ip-netmask {
        mandatory true;
        type ip-netmask;
        description "Mask";
      }
    }
  }

  rpc clear-bgp-instance-version-afi-safi-rd-ip-addr {
    csc:xr-task "bgp";
    csc:cli-command "clear bgp instance <instance-name> version <afi-safi-name> rd <rd> <ip-addr>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
    }
  }

  rpc clear-bgp-instance-version-afi-safi-rd-ip-prefix {
    csc:xr-task "bgp";
    csc:cli-command "clear bgp instance <instance-name> version <afi-safi-name> rd <rd> <ip-prefix>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ip-prefix {
        mandatory true;
        type inet:ip-prefix;
        description "Network and masklength";
      }
    }
  }

  rpc clear-bgp-instance-version-afi-safi-ipv4-addr-ipv4-mask {
    csc:xr-task "bgp";
    csc:cli-command "clear bgp instance <instance-name> version <afi-safi-name> <ipv4-addr> <ipv4-mask>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-instance-version-afi-safi-ipv4-addr {
    csc:xr-task "bgp";
    csc:cli-command "clear bgp instance <instance-name> version <afi-safi-name> <ipv4-addr>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv4-addr {
        mandatory true;
        type inet:ipv4-address;
        description "IPv4 network";
      }
    }
  }

  rpc clear-bgp-instance-version-afi-safi-ipv4-prefix {
    csc:xr-task "bgp";
    csc:cli-command "clear bgp instance <instance-name> version <afi-safi-name> <ipv4-prefix>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv4-prefix {
        mandatory true;
        type inet:ipv4-prefix;
        description "IPv4 network and masklength";
      }
    }
  }

  rpc clear-bgp-instance-version-afi-safi-rd-ipv4-addr {
    csc:xr-task "bgp";
    csc:cli-command "clear bgp instance <instance-name> version <afi-safi-name> rd <rd> <ipv4-addr>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 MDT network";
      }
    }
  }

  rpc clear-bgp-instance-version-afi-safi-vrf-ipv4-addr {
    csc:xr-task "bgp";
    csc:cli-command "clear bgp instance <instance-name> version <afi-safi-name> vrf <vrf-name> <ipv4-addr>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 MDT network";
      }
    }
  }

  rpc clear-bgp-instance-version-afi-safi-network {
    csc:xr-task "bgp";
    csc:cli-command "clear bgp instance <instance-name> version <afi-safi-name> <network>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf network {
        mandatory true;
        type string;
        description "Address family modifier specific network";
      }
    }
  }

  rpc clear-bgp-instance-version-afi-safi-rd-network {
    csc:xr-task "bgp";
    csc:cli-command "clear bgp instance <instance-name> version <afi-safi-name> rd <rd> <network>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-instance-version-afi-safi-vrf-network {
    csc:xr-task "bgp";
    csc:cli-command "clear bgp instance <instance-name> version <afi-safi-name> vrf <vrf-name> <network>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-instance-version-afi-safi-rt-constraint-network {
    csc:xr-task "bgp";
    csc:cli-command "clear bgp instance <instance-name> version <afi-safi-name> <rt-constraint-network>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf rt-constraint-network {
        mandatory true;
        type string;
        description "RT-Constraint network";
      }
    }
  }

  rpc clear-bgp-instance-version-afi-safi-ipv4-tunnel-network {
    csc:xr-task "bgp";
    csc:cli-command "clear bgp instance <instance-name> version <afi-safi-name> <ipv4-tunnel-network>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv4-tunnel-network {
        mandatory true;
        type string;
        description "IPv4 Tunnel network <Tunnel-ID>:<IPv4 Address>";
      }
    }
  }

  rpc clear-bgp-instance-version-afi-safi-ipv6-addr-ipv6-netmask {
    csc:xr-task "bgp";
    csc:cli-command "clear bgp instance <instance-name> version <afi-safi-name> <ipv6-addr> <ipv6-netmask>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-instance-version-afi-safi-ipv6-addr {
    csc:xr-task "bgp";
    csc:cli-command "clear bgp instance <instance-name> version <afi-safi-name> <ipv6-addr>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv6-addr {
        mandatory true;
        type inet:ipv6-address;
        description "IPv6 network";
      }
    }
  }

  rpc clear-bgp-instance-version-afi-safi-ipv6-prefix {
    csc:xr-task "bgp";
    csc:cli-command "clear bgp instance <instance-name> version <afi-safi-name> <ipv6-prefix>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-instance-version-afi-safi-rd {
    csc:xr-task "bgp";
    csc:cli-command "clear bgp instance <instance-name> version <afi-safi-name> rd <rd>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
    }
  }

  rpc clear-bgp-instance-version-afi-safi-vrf {
    csc:xr-task "bgp";
    csc:cli-command "clear bgp instance <instance-name> version <afi-safi-name> vrf <vrf-name>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
    }
  }

  rpc clear-bgp-instance-version-afi-safi {
    csc:xr-task "bgp";
    csc:cli-command "clear bgp instance <instance-name> version <afi-safi-name>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
    }
  }

  rpc clear-bgp-instance-version-afi-safi-sr-policy-prefix {
    csc:xr-task "bgp";
    csc:cli-command "clear bgp instance <instance-name> version <afi-safi-name> <sr-policy-prefix>";
    description
      "Choose a particular BGP instance.
       clear BGP prefix version.
      ";
    input {
      leaf instance-name {
        mandatory true;
        type instance-name;
        description "instance name or all";
      }
      leaf afi-safi-name {
        mandatory true;
        type afi-safi-type;
        description "AFI and SAFI";
      }
      leaf sr-policy-prefix {
        mandatory true;
        type string;
        description "SR Policy prefix";
      }
    }
  }

  rpc clear-bgp-instance-version-afi-safi-bridge-domain-ipv4-prefix {
    csc:xr-task "bgp";
    csc:cli-command "clear bgp instance <instance-name> version <afi-safi-name> bridge-domain <bridge-domain-name> <ipv4-prefix>";
    description
      "Choose a particular BGP instance.
       clear BGP prefix version.
       Display routes for a specified Bridge Domain.
      ";
    input {
      leaf instance-name {
        mandatory true;
        type instance-name;
        description "instance name or all";
      }
      leaf afi-safi-name {
        mandatory true;
        type afi-safi-type;
        description "AFI and SAFI";
      }
      leaf bridge-domain-name {
        mandatory true;
        type string;
        description "Bridge Domain";
      }
      leaf ipv4-prefix {
        mandatory true;
        type inet:ipv4-prefix;
        description "L2VPN EVPN Prefix";
      }
    }
  }

  rpc clear-bgp-instance-version-afi-safi-rd-ipv4-prefix {
    csc:xr-task "bgp";
    csc:cli-command "clear bgp instance <instance-name> version <afi-safi-name> rd <rd> <ipv4-prefix>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-prefix {
        mandatory true;
        type inet:ipv4-prefix;
        description "L2VPN EVPN Prefix";
      }
    }
  }

  rpc clear-bgp-instance-version-afi-safi-mp2mp-ipv4-prefix {
    csc:xr-task "bgp";
    csc:cli-command "clear bgp instance <instance-name> version <afi-safi-name> mp2mp <mp2mp> <ipv4-prefix>";
    description
      "Choose a particular BGP instance.
       clear BGP prefix version.
       Display routes for a specified Xconnect group:MP2MP.
      ";
    input {
      leaf instance-name {
        mandatory true;
        type instance-name;
        description "instance name or all";
      }
      leaf afi-safi-name {
        mandatory true;
        type afi-safi-type;
        description "AFI and SAFI";
      }
      leaf mp2mp {
        mandatory true;
        type string;
        description "Xconnect Group:mp2mp";
      }
      leaf ipv4-prefix {
        mandatory true;
        type inet:ipv4-prefix;
        description "L2VPN VPWS Prefix";
      }
    }
  }

  rpc clear-bgp-instance-version-afi-safi-vrf-ipv4-prefix {
    csc:xr-task "bgp";
    csc:cli-command "clear bgp instance <instance-name> version <afi-safi-name> vrf <vrf-name> <ipv4-prefix>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-prefix {
        mandatory true;
        type inet:ipv4-prefix;
        description "VPN Fspec Prefix";
      }
    }
  }

  rpc clear-bgp-instance-version-afi-safi-rd-ipv4-addr-ipv4-mask {
    csc:xr-task "bgp";
    csc:cli-command "clear bgp instance <instance-name> version <afi-safi-name> rd <rd> <ipv4-addr> <ipv4-mask>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 network";
      }
      leaf ipv4-mask {
        mandatory true;
        type ipv4-netmask;
        description "IPv4 mask";
      }
    }
  }

  rpc clear-bgp-instance-version-afi-safi-vrf-ipv4-addr-ipv4-mask {
    csc:xr-task "bgp";
    csc:cli-command "clear bgp instance <instance-name> version <afi-safi-name> vrf <vrf-name> <ipv4-addr> <ipv4-mask>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 network";
      }
      leaf ipv4-mask {
        mandatory true;
        type ipv4-netmask;
        description "IPv4 mask";
      }
    }
  }

  rpc clear-bgp-instance-version-afi-safi-rd-ipv6-addr-ipv6-netmask {
    csc:xr-task "bgp";
    csc:cli-command "clear bgp instance <instance-name> version <afi-safi-name> rd <rd> <ipv6-addr> <ipv6-netmask>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
      leaf ipv6-netmask {
        mandatory true;
        type ipv6-netmask;
        description "IPv6 mask";
      }
    }
  }

  rpc clear-bgp-instance-version-afi-safi-rd-ipv6-addr {
    csc:xr-task "bgp";
    csc:cli-command "clear bgp instance <instance-name> version <afi-safi-name> rd <rd> <ipv6-addr>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
    }
  }

  rpc clear-bgp-instance-version-afi-safi-rd-ipv6-prefix {
    csc:xr-task "bgp";
    csc:cli-command "clear bgp instance <instance-name> version <afi-safi-name> rd <rd> <ipv6-prefix>";
    description
      "Choose a particular BGP instance.
       clear BGP prefix version.
       Display routes with a specific route distinguisher.
      ";
    input {
      leaf instance-name {
        mandatory true;
        type instance-name;
        description "instance name or all";
      }
      leaf afi-safi-name {
        mandatory true;
        type afi-safi-type;
        description "AFI and SAFI";
      }
      leaf rd {
        mandatory true;
        type rd;
        description "Route distinguisher";
      }
      leaf ipv6-prefix {
        mandatory true;
        type inet:ipv6-prefix;
        description "IPv6 network and masklength";
      }
    }
  }

  rpc clear-bgp-instance-version-afi-safi-vrf-ipv6-addr-ipv6-netmask {
    csc:xr-task "bgp";
    csc:cli-command "clear bgp instance <instance-name> version <afi-safi-name> vrf <vrf-name> <ipv6-addr> <ipv6-netmask>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
      leaf ipv6-netmask {
        mandatory true;
        type ipv6-netmask;
        description "IPv6 mask";
      }
    }
  }

  rpc clear-bgp-instance-version-afi-safi-vrf-ipv6-addr {
    csc:xr-task "bgp";
    csc:cli-command "clear bgp instance <instance-name> version <afi-safi-name> vrf <vrf-name> <ipv6-addr>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
    }
  }

  rpc clear-bgp-instance-version-afi-safi-vrf-ipv6-prefix {
    csc:xr-task "bgp";
    csc:cli-command "clear bgp instance <instance-name> version <afi-safi-name> vrf <vrf-name> <ipv6-prefix>";
    description
      "Choose a particular BGP instance.
       clear BGP prefix version.
       Display routes for a specified VRF.
      ";
    input {
      leaf instance-name {
        mandatory true;
        type instance-name;
        description "instance name or all";
      }
      leaf afi-safi-name {
        mandatory true;
        type afi-safi-type;
        description "AFI and SAFI";
      }
      leaf vrf-name {
        mandatory true;
        type string;
        description "VRF name";
      }
      leaf ipv6-prefix {
        mandatory true;
        type inet:ipv6-prefix;
        description "IPv6 network and masklength";
      }
    }
  }

  rpc clear-bgp-instance-version-vrf-ip-addr-ip-netmask {
    csc:xr-task "bgp";
    csc:cli-command "clear bgp instance <instance-name> version vrf <vrf-all> <ip-addr> <ip-netmask>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Network";
      }
      leaf ip-netmask {
        mandatory true;
        type ip-netmask;
        description "Mask";
      }
    }
  }

  rpc clear-bgp-instance-version-vrf-ip-addr {
    csc:xr-task "bgp";
    csc:cli-command "clear bgp instance <instance-name> version vrf <vrf-all> <ip-addr>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Network";
      }
    }
  }

  rpc clear-bgp-instance-version-vrf-ip-prefix {
    csc:xr-task "bgp";
    csc:cli-command "clear bgp instance <instance-name> version vrf <vrf-all> <ip-prefix>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf ip-prefix {
        mandatory true;
        type inet:ip-prefix;
        description "Network and masklength";
      }
    }
  }

  rpc clear-bgp-instance-version-vrf-afi-safi-ipv4-prefix {
    csc:xr-task "bgp";
    csc:cli-command "clear bgp instance <instance-name> version vrf <vrf-all> <afi-safi-name> <ipv4-prefix>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "Fspec IPv4 Prefix";
      }
    }
  }

  rpc clear-bgp-instance-version-vrf-afi-safi-ipv4-addr-ipv4-mask {
    csc:xr-task "bgp";
    csc:cli-command "clear bgp instance <instance-name> version vrf <vrf-all> <afi-safi-name> <ipv4-addr> <ipv4-mask>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-instance-version-vrf-afi-safi-ipv4-addr {
    csc:xr-task "bgp";
    csc:cli-command "clear bgp instance <instance-name> version vrf <vrf-all> <afi-safi-name> <ipv4-addr>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
    }
  }

  rpc clear-bgp-instance-version-vrf-afi-safi-network {
    csc:xr-task "bgp";
    csc:cli-command "clear bgp instance <instance-name> version vrf <vrf-all> <afi-safi-name> <network>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf network {
        mandatory true;
        type string;
        description "Address family modifier specific network";
      }
    }
  }

  rpc clear-bgp-instance-version-vrf-afi-safi-rd-network {
    csc:xr-task "bgp";
    csc:cli-command "clear bgp instance <instance-name> version vrf <vrf-all> <afi-safi-name> rd <rd> <network>";
    description
      "Choose a particular BGP instance.
       clear BGP prefix version.
       Specify a VRF.
       Display routes with a specific route distinguisher.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-instance-version-vrf-afi-safi-vrf-network {
    csc:xr-task "bgp";
    csc:cli-command "clear bgp instance <instance-name> version vrf <vrf-all> <afi-safi-name> vrf <vrf-name> <network>";
    description
      "Choose a particular BGP instance.
       clear BGP prefix version.
       Specify a VRF.
       Display routes for a specified VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-instance-version-vrf-afi-safi-ipv6-addr-ipv6-netmask {
    csc:xr-task "bgp";
    csc:cli-command "clear bgp instance <instance-name> version vrf <vrf-all> <afi-safi-name> <ipv6-addr> <ipv6-netmask>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-instance-version-vrf-afi-safi-ipv6-addr {
    csc:xr-task "bgp";
    csc:cli-command "clear bgp instance <instance-name> version vrf <vrf-all> <afi-safi-name> <ipv6-addr>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
    }
  }

  rpc clear-bgp-instance-version-vrf-afi-safi-ipv6-prefix {
    csc:xr-task "bgp";
    csc:cli-command "clear bgp instance <instance-name> version vrf <vrf-all> <afi-safi-name> <ipv6-prefix>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-instance-version-vrf-afi-safi-rd {
    csc:xr-task "bgp";
    csc:cli-command "clear bgp instance <instance-name> version vrf <vrf-all> <afi-safi-name> rd <rd>";
    description
      "Choose a particular BGP instance.
       clear BGP prefix version.
       Specify a VRF.
       Display routes with a specific route distinguisher.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
    }
  }

  rpc clear-bgp-instance-version-vrf-afi-safi-vrf {
    csc:xr-task "bgp";
    csc:cli-command "clear bgp instance <instance-name> version vrf <vrf-all> <afi-safi-name> vrf <vrf-name>";
    description
      "Choose a particular BGP instance.
       clear BGP prefix version.
       Specify a VRF.
       Display routes for a specified VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
    }
  }

  rpc clear-bgp-instance-version-vrf-afi-safi {
    csc:xr-task "bgp";
    csc:cli-command "clear bgp instance <instance-name> version vrf <vrf-all> <afi-safi-name>";
    description
      "Choose a particular BGP instance.
       clear BGP prefix version.
       Specify a VRF.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-all-graceful {
    csc:xr-task "bgp";
    csc:cli-command "clear bgp instance <instance-name> vrf <vrf-all> * graceful";
    description
      "Choose a particular BGP instance.
       Specify a VRF.
       Clear all peers and all routes from the BGP table.
       Clear with a hard reset and a graceful restart.
      ";
    input {
      leaf instance-name {
        mandatory true;
        type instance-name;
        description "instance name or all";
      }
      leaf vrf-all {
        mandatory true;
        type vrf-name;
        description "VRF name or all";
      }
    }
  }

  rpc clear-bgp-instance-vrf-all {
    csc:xr-task "bgp";
    csc:cli-command "clear bgp instance <instance-name> vrf <vrf-all> *";
    description
      "Choose a particular BGP instance.
       Specify a VRF.
       Clear all peers and all routes from the BGP table.
      ";
    input {
      leaf instance-name {
        mandatory true;
        type instance-name;
        description "instance name or all";
      }
      leaf vrf-all {
        mandatory true;
        type vrf-name;
        description "VRF name or all";
      }
    }
  }

  rpc clear-bgp-instance-vrf-ip-addr-graceful {
    csc:xr-task "bgp";
    csc:cli-command "clear bgp instance <instance-name> vrf <vrf-all> <ip-addr> graceful";
    description
      "Choose a particular BGP instance.
       Specify a VRF.
       Clear with a hard reset and a graceful restart.
      ";
    input {
      leaf instance-name {
        mandatory true;
        type instance-name;
        description "instance name or all";
      }
      leaf vrf-all {
        mandatory true;
        type vrf-name;
        description "VRF name or all";
      }
      leaf ip-addr {
        mandatory true;
        type inet:ip-address;
        description "BGP neighbor address to clear";
      }
    }
  }

  rpc clear-bgp-instance-vrf-ip-addr-long-lived-stale {
    csc:xr-task "bgp";
    csc:cli-command "clear bgp instance <instance-name> vrf <vrf-all> <ip-addr> long-lived-stale";
    description
      "Choose a particular BGP instance.
       Specify a VRF.
       Clear long-lived-stale routes.
      ";
    input {
      leaf instance-name {
        mandatory true;
        type instance-name;
        description "instance name or all";
      }
      leaf vrf-all {
        mandatory true;
        type vrf-name;
        description "VRF name or all";
      }
      leaf ip-addr {
        mandatory true;
        type inet:ip-address;
        description "BGP neighbor address to clear";
      }
    }
  }

  rpc clear-bgp-instance-vrf-ip-addr {
    csc:xr-task "bgp";
    csc:cli-command "clear bgp instance <instance-name> vrf <vrf-all> <ip-addr>";
    description
      "Choose a particular BGP instance.
       Specify a VRF.
      ";
    input {
      leaf instance-name {
        mandatory true;
        type instance-name;
        description "instance name or all";
      }
      leaf vrf-all {
        mandatory true;
        type vrf-name;
        description "VRF name or all";
      }
      leaf ip-addr {
        mandatory true;
        type inet:ip-address;
        description "BGP neighbor address to clear";
      }
    }
  }

  rpc clear-bgp-instance-vrf-as-graceful {
    csc:xr-task "bgp";
    csc:cli-command "clear bgp instance <instance-name> vrf <vrf-all> as <as-number> graceful";
    description
      "Choose a particular BGP instance.
       Specify a VRF.
       Clear peers in a specific AS.
       Clear with a hard reset and a graceful restart.
      ";
    input {
      leaf instance-name {
        mandatory true;
        type instance-name;
        description "instance name or all";
      }
      leaf vrf-all {
        mandatory true;
        type vrf-name;
        description "VRF name or all";
      }
      leaf as-number {
        mandatory true;
        type as-number;
        description "AS number";
      }
    }
  }

  rpc clear-bgp-instance-vrf-as {
    csc:xr-task "bgp";
    csc:cli-command "clear bgp instance <instance-name> vrf <vrf-all> as <as-number>";
    description
      "Choose a particular BGP instance.
       Specify a VRF.
       Clear peers in a specific AS.
      ";
    input {
      leaf instance-name {
        mandatory true;
        type instance-name;
        description "instance name or all";
      }
      leaf vrf-all {
        mandatory true;
        type vrf-name;
        description "VRF name or all";
      }
      leaf as-number {
        mandatory true;
        type as-number;
        description "AS number";
      }
    }
  }

  rpc clear-bgp-instance-vrf-external-graceful {
    csc:xr-task "bgp";
    csc:cli-command "clear bgp instance <instance-name> vrf <vrf-all> external graceful";
    description
      "Choose a particular BGP instance.
       Specify a VRF.
       Clear all external peers.
       Clear with a hard reset and a graceful restart.
      ";
    input {
      leaf instance-name {
        mandatory true;
        type instance-name;
        description "instance name or all";
      }
      leaf vrf-all {
        mandatory true;
        type vrf-name;
        description "VRF name or all";
      }
    }
  }

  rpc clear-bgp-instance-vrf-external {
    csc:xr-task "bgp";
    csc:cli-command "clear bgp instance <instance-name> vrf <vrf-all> external";
    description
      "Choose a particular BGP instance.
       Specify a VRF.
       Clear all external peers.
      ";
    input {
      leaf instance-name {
        mandatory true;
        type instance-name;
        description "instance name or all";
      }
      leaf vrf-all {
        mandatory true;
        type vrf-name;
        description "VRF name or all";
      }
    }
  }

  rpc clear-bgp-instance-vrf-afi-safi-all-soft-in-prefix-filter {
    csc:xr-task "bgp";
    csc:cli-command "clear bgp instance <instance-name> vrf <vrf-all> <afi-safi-name> * soft in prefix-filter";
    description
      "Choose a particular BGP instance.
       Specify a VRF.
       Clear all peers and all routes from the BGP table.
       Soft reconfig.
       Soft reconfig inbound update.
       Push out prefix ORF and do inbound soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-all-soft-in {
    csc:xr-task "bgp";
    csc:cli-command "clear bgp instance <instance-name> vrf <vrf-all> <afi-safi-name> * soft in";
    description
      "Choose a particular BGP instance.
       Specify a VRF.
       Clear all peers and all routes from the BGP table.
       Soft reconfig.
       Soft reconfig inbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-all-soft-out {
    csc:xr-task "bgp";
    csc:cli-command "clear bgp instance <instance-name> vrf <vrf-all> <afi-safi-name> * soft out";
    description
      "Choose a particular BGP instance.
       Specify a VRF.
       Clear all peers and all routes from the BGP table.
       Soft reconfig.
       Soft reconfig outbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-all-soft {
    csc:xr-task "bgp";
    csc:cli-command "clear bgp instance <instance-name> vrf <vrf-all> <afi-safi-name> * soft";
    description
      "Choose a particular BGP instance.
       Specify a VRF.
       Clear all peers and all routes from the BGP table.
       Soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-ip-addr-long-lived-stale {
    csc:xr-task "bgp";
    csc:cli-command "clear bgp instance <instance-name> vrf <vrf-all> <afi-safi-name> <ip-addr> long-lived-stale";
    description
      "Choose a particular BGP instance.
       Specify a VRF.
       Clear long-lived-stale routes.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-ip-addr-soft-in-prefix-filter {
    csc:xr-task "bgp";
    csc:cli-command "clear bgp instance <instance-name> vrf <vrf-all> <afi-safi-name> <ip-addr> soft in prefix-filter";
    description
      "Choose a particular BGP instance.
       Specify a VRF.
       Soft reconfig.
       Soft reconfig inbound update.
       Push out prefix ORF and do inbound soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-ip-addr-soft-in {
    csc:xr-task "bgp";
    csc:cli-command "clear bgp instance <instance-name> vrf <vrf-all> <afi-safi-name> <ip-addr> soft in";
    description
      "Choose a particular BGP instance.
       Specify a VRF.
       Soft reconfig.
       Soft reconfig inbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-ip-addr-soft-out {
    csc:xr-task "bgp";
    csc:cli-command "clear bgp instance <instance-name> vrf <vrf-all> <afi-safi-name> <ip-addr> soft out";
    description
      "Choose a particular BGP instance.
       Specify a VRF.
       Soft reconfig.
       Soft reconfig outbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-ip-addr-soft {
    csc:xr-task "bgp";
    csc:cli-command "clear bgp instance <instance-name> vrf <vrf-all> <afi-safi-name> <ip-addr> soft";
    description
      "Choose a particular BGP instance.
       Specify a VRF.
       Soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-as-soft-in-prefix-filter {
    csc:xr-task "bgp";
    csc:cli-command "clear bgp instance <instance-name> vrf <vrf-all> <afi-safi-name> as <as-number> soft in prefix-filter";
    description
      "Choose a particular BGP instance.
       Specify a VRF.
       Clear peers in a specific AS.
       Soft reconfig.
       Soft reconfig inbound update.
       Push out prefix ORF and do inbound soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-instance-vrf-afi-safi-as-soft-in {
    csc:xr-task "bgp";
    csc:cli-command "clear bgp instance <instance-name> vrf <vrf-all> <afi-safi-name> as <as-number> soft in";
    description
      "Choose a particular BGP instance.
       Specify a VRF.
       Clear peers in a specific AS.
       Soft reconfig.
       Soft reconfig inbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-instance-vrf-afi-safi-as-soft-out {
    csc:xr-task "bgp";
    csc:cli-command "clear bgp instance <instance-name> vrf <vrf-all> <afi-safi-name> as <as-number> soft out";
    description
      "Choose a particular BGP instance.
       Specify a VRF.
       Clear peers in a specific AS.
       Soft reconfig.
       Soft reconfig outbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-instance-vrf-afi-safi-as-soft {
    csc:xr-task "bgp";
    csc:cli-command "clear bgp instance <instance-name> vrf <vrf-all> <afi-safi-name> as <as-number> soft";
    description
      "Choose a particular BGP instance.
       Specify a VRF.
       Clear peers in a specific AS.
       Soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-instance-vrf-afi-safi-dampening-ipv4-prefix {
    csc:xr-task "bgp";
    csc:cli-command "clear bgp instance <instance-name> vrf <vrf-all> <afi-safi-name> dampening <ipv4-prefix>";
    description
      "Choose a particular BGP instance.
       Specify a VRF.
       Clear route flap dampening information.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "IPv4 Network and mask or masklength to clear dampening information";
      }
    }
  }

  rpc clear-bgp-instance-vrf-afi-safi-dampening {
    csc:xr-task "bgp";
    csc:cli-command "clear bgp instance <instance-name> vrf <vrf-all> <afi-safi-name> dampening";
    description
      "Choose a particular BGP instance.
       Specify a VRF.
       Clear route flap dampening information.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-external-soft-in-prefix-filter {
    csc:xr-task "bgp";
    csc:cli-command "clear bgp instance <instance-name> vrf <vrf-all> <afi-safi-name> external soft in prefix-filter";
    description
      "Choose a particular BGP instance.
       Specify a VRF.
       Clear all external peers.
       Soft reconfig.
       Soft reconfig inbound update.
       Push out prefix ORF and do inbound soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-external-soft-in {
    csc:xr-task "bgp";
    csc:cli-command "clear bgp instance <instance-name> vrf <vrf-all> <afi-safi-name> external soft in";
    description
      "Choose a particular BGP instance.
       Specify a VRF.
       Clear all external peers.
       Soft reconfig.
       Soft reconfig inbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-external-soft-out {
    csc:xr-task "bgp";
    csc:cli-command "clear bgp instance <instance-name> vrf <vrf-all> <afi-safi-name> external soft out";
    description
      "Choose a particular BGP instance.
       Specify a VRF.
       Clear all external peers.
       Soft reconfig.
       Soft reconfig outbound update.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-external-soft {
    csc:xr-task "bgp";
    csc:cli-command "clear bgp instance <instance-name> vrf <vrf-all> <afi-safi-name> external soft";
    description
      "Choose a particular BGP instance.
       Specify a VRF.
       Clear all external peers.
       Soft reconfig.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-flap-statistics-ip-addr-ipv4-mask {
    csc:xr-task "bgp";
    csc:cli-command "clear bgp instance <instance-name> vrf <vrf-all> <afi-safi-name> flap-statistics <ip-addr> <ipv4-mask>";
    description
      "Choose a particular BGP instance.
       Specify a VRF.
       Clear flap statistics.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
      leaf ipv4-mask {
        mandatory true;
        type ipv4-netmask;
        description "IPv4 Network and mask or masklength to clear flap statistics";
      }
    }
  }

  rpc clear-bgp-instance-vrf-afi-safi-flap-statistics-ip-addr {
    csc:xr-task "bgp";
    csc:cli-command "clear bgp instance <instance-name> vrf <vrf-all> <afi-safi-name> flap-statistics <ip-addr>";
    description
      "Choose a particular BGP instance.
       Specify a VRF.
       Clear flap statistics.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-instance-vrf-afi-safi-flap-statistics-ipv4-prefix {
    csc:xr-task "bgp";
    csc:cli-command "clear bgp instance <instance-name> vrf <vrf-all> <afi-safi-name> flap-statistics <ipv4-prefix>";
    description
      "Choose a particular BGP instance.
       Specify a VRF.
       Clear flap statistics.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "IPv4 Network and mask or masklength to clear flap statistics";
      }
    }
  }

  rpc clear-bgp-instance-vrf-afi-safi-flap-statistics-regexp {
    csc:xr-task "bgp";
    csc:cli-command "clear bgp instance <instance-name> vrf <vrf-all> <afi-safi-name> flap-statistics regexp <regexp-pattern>";
    description
      "Choose a particular BGP instance.
       Specify a VRF.
       Clear flap statistics.
       Clear flap statistics for routes matching the regular expression.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf regexp-pattern {
        mandatory true;
        type string;
        description "A regular expression to match the BGP AS paths.  Use 'ctrl-v ?' to enter '?'";
      }
    }
  }

  rpc clear-bgp-instance-vrf-afi-safi-flap-statistics-route-policy {
    csc:xr-task "bgp";
    csc:cli-command "clear bgp instance <instance-name> vrf <vrf-all> <afi-safi-name> flap-statistics route-policy <route-policy-name>";
    description
      "Choose a particular BGP instance.
       Specify a VRF.
       Clear flap statistics.
       Clear flap statistics for routes matching the route policy.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf route-policy-name {
        mandatory true;
        type string;
        description "Route Policy name";
      }
    }
  }

  rpc clear-bgp-instance-vrf-afi-safi-flap-statistics {
    csc:xr-task "bgp";
    csc:cli-command "clear bgp instance <instance-name> vrf <vrf-all> <afi-safi-name> flap-statistics";
    description
      "Choose a particular BGP instance.
       Specify a VRF.
       Clear flap statistics.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-nexthop-performance-statistics {
    csc:xr-task "bgp";
    csc:cli-command "clear bgp instance <instance-name> vrf <vrf-all> <afi-safi-name> nexthop performance-statistics";
    description
      "Choose a particular BGP instance.
       Specify a VRF.
       Clear nexthop.
       Performance statistics information related to processing.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-nexthop-registration-ip-addr {
    csc:xr-task "bgp";
    csc:cli-command "clear bgp instance <instance-name> vrf <vrf-all> <afi-safi-name> nexthop registration <ip-addr>";
    description
      "Choose a particular BGP instance.
       Specify a VRF.
       Clear nexthop.
       Registration with RIB and reregister.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Nexthop address";
      }
    }
  }

  rpc clear-bgp-instance-vrf-afi-safi-self-originated {
    csc:xr-task "bgp";
    csc:cli-command "clear bgp instance <instance-name> vrf <vrf-all> <afi-safi-name> self-originated";
    description
      "Choose a particular BGP instance.
       Specify a VRF.
       Clear redistributed, network and aggregate routes originated here.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-shutdown {
    csc:xr-task "bgp";
    csc:cli-command "clear bgp instance <instance-name> vrf <vrf-all> <afi-safi-name> shutdown";
    description
      "Choose a particular BGP instance.
       Specify a VRF.
       Clear all peers which were shut down due to low memory.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-update-outq-address-family-update-parent {
    csc:xr-task "bgp";
    csc:cli-command "clear bgp instance <instance-name> vrf <vrf-all> <afi-safi-name> update outq address-family update-parent";
    description
      "Choose a particular BGP instance.
       Specify a VRF.
       Clear Update information (Do NOT execute without cisco support)(cisco-support).
       Clear Update generation OutQ counters (Do NOT execute without cisco support)(cisco-support).
       Address-family.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-update-outq-address-family {
    csc:xr-task "bgp";
    csc:cli-command "clear bgp instance <instance-name> vrf <vrf-all> <afi-safi-name> update outq address-family";
    description
      "Choose a particular BGP instance.
       Specify a VRF.
       Clear Update information (Do NOT execute without cisco support)(cisco-support).
       Clear Update generation OutQ counters (Do NOT execute without cisco support)(cisco-support).
       Address-family.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
    }
  }

  rpc clear-bgp-instance-vrf-afi-safi-update-outq-neighbor-ip-addr-refresh-update-parent {
    csc:xr-task "bgp";
    csc:cli-command "clear bgp instance <instance-name> vrf <vrf-all> <afi-safi-name> update outq neighbor <ip-addr> refresh update-parent";
    description
      "Choose a particular BGP instance.
       Specify a VRF.
       Clear Update information (Do NOT execute without cisco support)(cisco-support).
       Clear Update generation OutQ counters (Do NOT execute without cisco support)(cisco-support).
       Neighbor.
       Refresh OutQ.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-instance-vrf-afi-safi-update-outq-neighbor-ip-addr-refresh {
    csc:xr-task "bgp";
    csc:cli-command "clear bgp instance <instance-name> vrf <vrf-all> <afi-safi-name> update outq neighbor <ip-addr> refresh";
    description
      "Choose a particular BGP instance.
       Specify a VRF.
       Clear Update information (Do NOT execute without cisco support)(cisco-support).
       Clear Update generation OutQ counters (Do NOT execute without cisco support)(cisco-support).
       Neighbor.
       Refresh OutQ.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-instance-vrf-afi-safi-update-outq-neighbor-ip-addr-update-parent {
    csc:xr-task "bgp";
    csc:cli-command "clear bgp instance <instance-name> vrf <vrf-all> <afi-safi-name> update outq neighbor <ip-addr> update-parent";
    description
      "Choose a particular BGP instance.
       Specify a VRF.
       Clear Update information (Do NOT execute without cisco support)(cisco-support).
       Clear Update generation OutQ counters (Do NOT execute without cisco support)(cisco-support).
       Neighbor.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-instance-vrf-afi-safi-update-outq-neighbor-ip-addr {
    csc:xr-task "bgp";
    csc:cli-command "clear bgp instance <instance-name> vrf <vrf-all> <afi-safi-name> update outq neighbor <ip-addr>";
    description
      "Choose a particular BGP instance.
       Specify a VRF.
       Clear Update information (Do NOT execute without cisco support)(cisco-support).
       Clear Update generation OutQ counters (Do NOT execute without cisco support)(cisco-support).
       Neighbor.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-instance-vrf-afi-safi-update-outq-update-group-sub-group-update-parent {
    csc:xr-task "bgp";
    csc:cli-command "clear bgp instance <instance-name> vrf <vrf-all> <afi-safi-name> update outq update-group <update-group> sub-group <sub-group> update-parent";
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-instance-vrf-afi-safi-update-outq-update-group-sub-group {
    csc:xr-task "bgp";
    csc:cli-command "clear bgp instance <instance-name> vrf <vrf-all> <afi-safi-name> update outq update-group <update-group> sub-group <sub-group>";
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-instance-vrf-afi-safi-update-outq-update-group-sub-group-refresh-sub-group-update-parent {
    csc:xr-task "bgp";
    csc:cli-command "clear bgp instance <instance-name> vrf <vrf-all> <afi-safi-name> update outq update-group <update-group> sub-group <refresh-sub-group> update-parent";
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-vrf-afi-safi-update-outq-update-group-sub-group-refresh-sub-group {
    csc:xr-task "bgp";
    csc:cli-command "clear bgp instance <instance-name> vrf <vrf-all> <afi-safi-name> update outq update-group <update-group> sub-group <refresh-sub-group>";
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-vrf-afi-safi-update-outq-update-group-update-parent {
    csc:xr-task "bgp";
    csc:cli-command "clear bgp instance <instance-name> vrf <vrf-all> <afi-safi-name> update outq update-group <update-group> update-parent";
    description
      "Choose a particular BGP instance.
       Specify a VRF.
       Clear Update information (Do NOT execute without cisco support)(cisco-support).
       Clear Update generation OutQ counters (Do NOT execute without cisco support)(cisco-support).
       Update-group.
       Update parents' OutQ counters too.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
    }
  }

  rpc clear-bgp-instance-vrf-afi-safi-update-outq-update-group {
    csc:xr-task "bgp";
    csc:cli-command "clear bgp instance <instance-name> vrf <vrf-all> <afi-safi-name> update outq update-group <update-group>";
    description
      "Choose a particular BGP instance.
       Specify a VRF.
       Clear Update information (Do NOT execute without cisco support)(cisco-support).
       Clear Update generation OutQ counters (Do NOT execute without cisco support)(cisco-support).
       Update-group.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
    }
  }

  rpc clear-bgp-instance-vrf-afi-safi-dampening-ipv6-prefix {
    csc:xr-task "bgp";
    csc:cli-command "clear bgp instance <instance-name> vrf <vrf-all> <afi-safi-name> dampening <ipv6-prefix>";
    description
      "Choose a particular BGP instance.
       Specify a VRF.
       Clear route flap dampening information.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 Network and mask or masklength to clear dampening information";
      }
    }
  }

  rpc clear-bgp-instance-vrf-afi-safi-flap-statistics-ipv6-prefix {
    csc:xr-task "bgp";
    csc:cli-command "clear bgp instance <instance-name> vrf <vrf-all> <afi-safi-name> flap-statistics <ipv6-prefix>";
    description
      "Choose a particular BGP instance.
       Specify a VRF.
       Clear flap statistics.
      ";
    input {
      leaf instance-name {
        mandatory true;
        type instance-name;
        description "instance name or all";
      }
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 Network and mask or masklength to clear flap statistics";
      }
    }
  }

  rpc clear-bgp-instance-vrf-nexthop-performance-statistics {
    csc:xr-task "bgp";
    csc:cli-command "clear bgp instance <instance-name> vrf <vrf-all> nexthop performance-statistics";
    description
      "Choose a particular BGP instance.
       Specify a VRF.
       Clear nexthop.
       Performance statistics information related to processing.
      ";
    input {
      leaf instance-name {
        mandatory true;
        type instance-name;
        description "instance name or all";
      }
      leaf vrf-all {
        mandatory true;
        type vrf-name;
        description "VRF name or all";
      }
    }
  }

  rpc clear-bgp-instance-vrf-nexthop-registration-ip-addr {
    csc:xr-task "bgp";
    csc:cli-command "clear bgp instance <instance-name> vrf <vrf-all> nexthop registration <ip-addr>";
    description
      "Choose a particular BGP instance.
       Specify a VRF.
       Clear nexthop.
       Registration with RIB and reregister.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Nexthop address";
      }
    }
  }

  rpc clear-bgp-instance-vrf-peer-drops-all {
    csc:xr-task "bgp";
    csc:cli-command "clear bgp instance <instance-name> vrf <vrf-all> peer-drops *";
    description
      "Choose a particular BGP instance.
       Specify a VRF.
       Clear established/dropped counters for a peer.
       All Neighbors.
      ";
    input {
      leaf instance-name {
        mandatory true;
        type instance-name;
        description "instance name or all";
      }
      leaf vrf-all {
        mandatory true;
        type vrf-name;
        description "VRF name or all";
      }
    }
  }

  rpc clear-bgp-instance-vrf-peer-drops-ip-addr {
    csc:xr-task "bgp";
    csc:cli-command "clear bgp instance <instance-name> vrf <vrf-all> peer-drops <ip-addr>";
    description
      "Choose a particular BGP instance.
       Specify a VRF.
       Clear established/dropped counters for a peer.
      ";
    input {
      leaf instance-name {
        mandatory true;
        type instance-name;
        description "instance name or all";
      }
      leaf vrf-all {
        mandatory true;
        type vrf-name;
        description "VRF name or all";
      }
      leaf ip-addr {
        mandatory true;
        type inet:ip-address;
        description "BGP neighbor IP address";
      }
    }
  }

  rpc clear-bgp-instance-vrf-performance-statistics {
    csc:xr-task "bgp";
    csc:cli-command "clear bgp instance <instance-name> vrf <vrf-all> performance-statistics";
    description
      "Choose a particular BGP instance.
       Specify a VRF.
       Clear performance statistics.
      ";
    input {
      leaf instance-name {
        mandatory true;
        type instance-name;
        description "instance name or all";
      }
      leaf vrf-all {
        mandatory true;
        type vrf-name;
        description "VRF name or all";
      }
    }
  }

  rpc clear-bgp-instance-vrf-shutdown {
    csc:xr-task "bgp";
    csc:cli-command "clear bgp instance <instance-name> vrf <vrf-all> shutdown";
    description
      "Choose a particular BGP instance.
       Specify a VRF.
       Clear all peers which were shut down due to low memory.
      ";
    input {
      leaf instance-name {
        mandatory true;
        type instance-name;
        description "instance name or all";
      }
      leaf vrf-all {
        mandatory true;
        type vrf-name;
        description "VRF name or all";
      }
    }
  }

  rpc clear-bgp-instance-vrf-update-outq-address-family-update-parent {
    csc:xr-task "bgp";
    csc:cli-command "clear bgp instance <instance-name> vrf <vrf-all> update outq address-family update-parent";
    description
      "Choose a particular BGP instance.
       Specify a VRF.
       Clear Update information (Do NOT execute without cisco support)(cisco-support).
       Clear Update generation OutQ counters (Do NOT execute without cisco support)(cisco-support).
       Address-family.
       Update parents' OutQ counters too.
      ";
    input {
      leaf instance-name {
        mandatory true;
        type instance-name;
        description "instance name or all";
      }
      leaf vrf-all {
        mandatory true;
        type vrf-name;
        description "VRF name or all";
      }
    }
  }

  rpc clear-bgp-instance-vrf-update-outq-address-family {
    csc:xr-task "bgp";
    csc:cli-command "clear bgp instance <instance-name> vrf <vrf-all> update outq address-family";
    description
      "Choose a particular BGP instance.
       Specify a VRF.
       Clear Update information (Do NOT execute without cisco support)(cisco-support).
       Clear Update generation OutQ counters (Do NOT execute without cisco support)(cisco-support).
       Address-family.
      ";
    input {
      leaf instance-name {
        mandatory true;
        type instance-name;
        description "instance name or all";
      }
      leaf vrf-all {
        mandatory true;
        type vrf-name;
        description "VRF name or all";
      }
    }
  }

  rpc clear-bgp-instance-vrf-update-outq-neighbor-ip-addr-refresh-update-parent {
    csc:xr-task "bgp";
    csc:cli-command "clear bgp instance <instance-name> vrf <vrf-all> update outq neighbor <ip-addr> refresh update-parent";
    description
      "Choose a particular BGP instance.
       Specify a VRF.
       Clear Update information (Do NOT execute without cisco support)(cisco-support).
       Clear Update generation OutQ counters (Do NOT execute without cisco support)(cisco-support).
       Neighbor.
       Refresh OutQ.
       Update parents' OutQ counters too.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Neighbor address";
      }
    }
  }

  rpc clear-bgp-instance-vrf-update-outq-neighbor-ip-addr-refresh {
    csc:xr-task "bgp";
    csc:cli-command "clear bgp instance <instance-name> vrf <vrf-all> update outq neighbor <ip-addr> refresh";
    description
      "Choose a particular BGP instance.
       Specify a VRF.
       Clear Update information (Do NOT execute without cisco support)(cisco-support).
       Clear Update generation OutQ counters (Do NOT execute without cisco support)(cisco-support).
       Neighbor.
       Refresh OutQ.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Neighbor address";
      }
    }
  }

  rpc clear-bgp-instance-vrf-update-outq-neighbor-ip-addr-update-parent {
    csc:xr-task "bgp";
    csc:cli-command "clear bgp instance <instance-name> vrf <vrf-all> update outq neighbor <ip-addr> update-parent";
    description
      "Choose a particular BGP instance.
       Specify a VRF.
       Clear Update information (Do NOT execute without cisco support)(cisco-support).
       Clear Update generation OutQ counters (Do NOT execute without cisco support)(cisco-support).
       Neighbor.
       Update parents' OutQ counters too.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Neighbor address";
      }
    }
  }

  rpc clear-bgp-instance-vrf-update-outq-neighbor-ip-addr {
    csc:xr-task "bgp";
    csc:cli-command "clear bgp instance <instance-name> vrf <vrf-all> update outq neighbor <ip-addr>";
    description
      "Choose a particular BGP instance.
       Specify a VRF.
       Clear Update information (Do NOT execute without cisco support)(cisco-support).
       Clear Update generation OutQ counters (Do NOT execute without cisco support)(cisco-support).
       Neighbor.
      ";
    input {
      leaf instance-name {
        mandatory true;
        type instance-name;
        description "instance name or all";
      }
      leaf vrf-all {
        mandatory true;
        type vrf-name;
        description "VRF name or all";
      }
      leaf ip-addr {
        mandatory true;
        type inet:ip-address;
        description "Neighbor address";
      }
    }
  }

  rpc clear-bgp-instance-vrf-update-outq-update-group-sub-group-update-parent {
    csc:xr-task "bgp";
    csc:cli-command "clear bgp instance <instance-name> vrf <vrf-all> update outq update-group <update-group> sub-group <sub-group> update-parent";
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
      leaf sub-group {
        mandatory true;
        type update-group-id;
        description "Sub-group process ID <x.y>";
      }
    }
  }

  rpc clear-bgp-instance-vrf-update-outq-update-group-sub-group {
    csc:xr-task "bgp";
    csc:cli-command "clear bgp instance <instance-name> vrf <vrf-all> update outq update-group <update-group> sub-group <sub-group>";
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
      leaf sub-group {
        mandatory true;
        type update-group-id;
        description "Sub-group process ID <x.y>";
      }
    }
  }

  rpc clear-bgp-instance-vrf-update-outq-update-group-sub-group-refresh-sub-group-update-parent {
    csc:xr-task "bgp";
    csc:cli-command "clear bgp instance <instance-name> vrf <vrf-all> update outq update-group <update-group> sub-group <refresh-sub-group> update-parent";
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-vrf-update-outq-update-group-sub-group-refresh-sub-group {
    csc:xr-task "bgp";
    csc:cli-command "clear bgp instance <instance-name> vrf <vrf-all> update outq update-group <update-group> sub-group <refresh-sub-group>";
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-instance-vrf-update-outq-update-group-update-parent {
    csc:xr-task "bgp";
    csc:cli-command "clear bgp instance <instance-name> vrf <vrf-all> update outq update-group <update-group> update-parent";
    description
      "Choose a particular BGP instance.
       Specify a VRF.
       Clear Update information (Do NOT execute without cisco support)(cisco-support).
       Clear Update generation OutQ counters (Do NOT execute without cisco support)(cisco-support).
       Update-group.
       Update parents' OutQ counters too.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
    }
  }

  rpc clear-bgp-instance-vrf-update-outq-update-group {
    csc:xr-task "bgp";
    csc:cli-command "clear bgp instance <instance-name> vrf <vrf-all> update outq update-group <update-group>";
    description
      "Choose a particular BGP instance.
       Specify a VRF.
       Clear Update information (Do NOT execute without cisco support)(cisco-support).
       Clear Update generation OutQ counters (Do NOT execute without cisco support)(cisco-support).
       Update-group.
      ";
    input {
      leaf instance-name {
        mandatory true;
        type instance-name;
        description "instance name or all";
      }
      leaf vrf-all {
        mandatory true;
        type vrf-name;
        description "VRF name or all";
      }
      leaf update-group {
        mandatory true;
        type update-group-id;
        description "Update-group process ID <x.y>";
      }
    }
  }

  rpc clear-bgp-afi-safi-dampening-ipv4-prefix {
    csc:xr-task "bgp";
    csc:cli-command "clear bgp <afi-safi-name> dampening <ipv4-prefix>";
    description
      "Clear route flap dampening information.
      ";
    input {
      leaf afi-safi-name {
        mandatory true;
        type afi-safi-type;
        description "AFI and SAFI";
      }
      leaf ipv4-prefix {
        mandatory true;
        type inet:ipv4-prefix;
        description "IPv4 Network and mask or masklength to clear dampening information";
      }
    }
  }

  rpc clear-bgp-afi-safi-flap-statistics-ipv4-prefix {
    csc:xr-task "bgp";
    csc:cli-command "clear bgp <afi-safi-name> flap-statistics <ipv4-prefix>";
    description
      "Clear flap statistics.
      ";
    input {
      leaf afi-safi-name {
        mandatory true;
        type afi-safi-type;
        description "AFI and SAFI";
      }
      leaf ipv4-prefix {
        mandatory true;
        type inet:ipv4-prefix;
        description "IPv4 Network and mask or masklength to clear flap statistics";
      }
    }
  }

  rpc clear-bgp-afi-safi-dampening-ipv6-prefix {
    csc:xr-task "bgp";
    csc:cli-command "clear bgp <afi-safi-name> dampening <ipv6-prefix>";
    description
      "Clear route flap dampening information.
      ";
    input {
      leaf afi-safi-name {
        mandatory true;
        type afi-safi-type;
        description "AFI and SAFI";
      }
      leaf ipv6-prefix {
        mandatory true;
        type inet:ipv6-prefix;
        description "IPv6 Network and mask or masklength to clear dampening information";
      }
    }
  }

  rpc clear-bgp-afi-safi-flap-statistics-ipv6-prefix {
    csc:xr-task "bgp";
    csc:cli-command "clear bgp <afi-safi-name> flap-statistics <ipv6-prefix>";
    description
      "Clear flap statistics.
      ";
    input {
      leaf afi-safi-name {
        mandatory true;
        type afi-safi-type;
        description "AFI and SAFI";
      }
      leaf ipv6-prefix {
        mandatory true;
        type inet:ipv6-prefix;
        description "IPv6 Network and mask or masklength to clear flap statistics";
      }
    }
  }

  rpc clear-bgp-nexthop-performance-statistics {
    csc:xr-task "bgp";
    csc:cli-command "clear bgp nexthop performance-statistics";
    description
      "Clear nexthop.
       Performance statistics information related to processing.
      ";
  }

  rpc clear-bgp-nexthop-registration-ip-addr {
    csc:xr-task "bgp";
    csc:cli-command "clear bgp nexthop registration <ip-addr>";
    description
      "Clear nexthop.
       Registration with RIB and reregister.
      ";
    input {
      leaf ip-addr {
        mandatory true;
        type inet:ip-address;
        description "Nexthop address";
      }
    }
  }

  rpc clear-bgp-peer-drops-all {
    csc:xr-task "bgp";
    csc:cli-command "clear bgp peer-drops *";
    description
      "Clear established/dropped counters for a peer.
       All Neighbors.
      ";
  }

  rpc clear-bgp-peer-drops-ip-addr {
    csc:xr-task "bgp";
    csc:cli-command "clear bgp peer-drops <ip-addr>";
    description
      "Clear established/dropped counters for a peer.
      ";
    input {
      leaf ip-addr {
        mandatory true;
        type inet:ip-address;
        description "BGP neighbor IP address";
      }
    }
  }

  rpc clear-bgp-performance-statistics {
    csc:xr-task "bgp";
    csc:cli-command "clear bgp performance-statistics";
    description
      "Clear performance statistics.
      ";
  }

  rpc clear-bgp-rpki-server-all-serial-query {
    csc:xr-task "bgp";
    csc:cli-command "clear bgp rpki server * serial-query";
    description
      "RPKI clear command.
       clear RPKI cache-server.
       clear all RPKI cache-servers.
       send serial-queries to all cache-servers (with latest serial numbers).
      ";
  }

  rpc clear-bgp-rpki-server-all {
    csc:xr-task "bgp";
    csc:cli-command "clear bgp rpki server *";
    description
      "RPKI clear command.
       clear RPKI cache-server.
       clear all RPKI cache-servers.
      ";
  }

  rpc clear-bgp-rpki-server-rpki-server {
    csc:xr-task "bgp";
    csc:cli-command "clear bgp rpki server <rpki-server>";
    description
      "RPKI clear command.
       clear RPKI cache-server.
      ";
    input {
      leaf rpki-server {
        mandatory true;
        type string;
        description "clear a specific RPKI cache-server (hostname or IP address)";
      }
    }
  }

  rpc clear-bgp-rpki-validation-ipv4 {
    csc:xr-task "bgp";
    csc:cli-command "clear bgp rpki validation ipv4";
    description
      "RPKI clear command.
       clear RPKI origin-validation (trigger origin validation).
       trigger origin validation walk for the IPv4 table.
      ";
  }

  rpc clear-bgp-rpki-validation-ipv6 {
    csc:xr-task "bgp";
    csc:cli-command "clear bgp rpki validation ipv6";
    description
      "RPKI clear command.
       clear RPKI origin-validation (trigger origin validation).
       trigger origin validation walk for the IPv6 table.
      ";
  }

  rpc clear-bgp-rpki-validation {
    csc:xr-task "bgp";
    csc:cli-command "clear bgp rpki validation";
    description
      "RPKI clear command.
       clear RPKI origin-validation (trigger origin validation).
      ";
  }

  rpc clear-bgp-shutdown {
    csc:xr-task "bgp";
    csc:cli-command "clear bgp shutdown";
    description
      "Clear all peers which were shut down due to low memory.
      ";
  }

  rpc clear-bgp-update-outq-address-family-update-parent {
    csc:xr-task "bgp";
    csc:cli-command "clear bgp update outq address-family update-parent";
    description
      "Clear Update information (Do NOT execute without cisco support)(cisco-support).
       Clear Update generation OutQ counters (Do NOT execute without cisco support)(cisco-support).
       Address-family.
       Update parents' OutQ counters too.
      ";
  }

  rpc clear-bgp-update-outq-address-family {
    csc:xr-task "bgp";
    csc:cli-command "clear bgp update outq address-family";
    description
      "Clear Update information (Do NOT execute without cisco support)(cisco-support).
       Clear Update generation OutQ counters (Do NOT execute without cisco support)(cisco-support).
       Address-family.
      ";
  }

  rpc clear-bgp-update-outq-neighbor-ip-addr-refresh-update-parent {
    csc:xr-task "bgp";
    csc:cli-command "clear bgp update outq neighbor <ip-addr> refresh update-parent";
    description
      "Clear Update information (Do NOT execute without cisco support)(cisco-support).
       Clear Update generation OutQ counters (Do NOT execute without cisco support)(cisco-support).
       Neighbor.
       Refresh OutQ.
       Update parents' OutQ counters too.
      ";
    input {
      leaf ip-addr {
        mandatory true;
        type inet:ip-address;
        description "Neighbor address";
      }
    }
  }

  rpc clear-bgp-update-outq-neighbor-ip-addr-refresh {
    csc:xr-task "bgp";
    csc:cli-command "clear bgp update outq neighbor <ip-addr> refresh";
    description
      "Clear Update information (Do NOT execute without cisco support)(cisco-support).
       Clear Update generation OutQ counters (Do NOT execute without cisco support)(cisco-support).
       Neighbor.
       Refresh OutQ.
      ";
    input {
      leaf ip-addr {
        mandatory true;
        type inet:ip-address;
        description "Neighbor address";
      }
    }
  }

  rpc clear-bgp-update-outq-neighbor-ip-addr-update-parent {
    csc:xr-task "bgp";
    csc:cli-command "clear bgp update outq neighbor <ip-addr> update-parent";
    description
      "Clear Update information (Do NOT execute without cisco support)(cisco-support).
       Clear Update generation OutQ counters (Do NOT execute without cisco support)(cisco-support).
       Neighbor.
       Update parents' OutQ counters too.
      ";
    input {
      leaf ip-addr {
        mandatory true;
        type inet:ip-address;
        description "Neighbor address";
      }
    }
  }

  rpc clear-bgp-update-outq-neighbor-ip-addr {
    csc:xr-task "bgp";
    csc:cli-command "clear bgp update outq neighbor <ip-addr>";
    description
      "Clear Update information (Do NOT execute without cisco support)(cisco-support).
       Clear Update generation OutQ counters (Do NOT execute without cisco support)(cisco-support).
       Neighbor.
      ";
    input {
      leaf ip-addr {
        mandatory true;
        type inet:ip-address;
        description "Neighbor address";
      }
    }
  }

  rpc clear-bgp-update-outq-process {
    csc:xr-task "bgp";
    csc:cli-command "clear bgp update outq process";
    description
      "Clear Update information (Do NOT execute without cisco support)(cisco-support).
       Clear Update generation OutQ counters (Do NOT execute without cisco support)(cisco-support).
       Process.
      ";
  }

  rpc clear-bgp-update-outq-update-group-sub-group-update-parent {
    csc:xr-task "bgp";
    csc:cli-command "clear bgp update outq update-group <update-group> sub-group <sub-group> update-parent";
    description
      "Clear Update information (Do NOT execute without cisco support)(cisco-support).
       Clear Update generation OutQ counters (Do NOT execute without cisco support)(cisco-support).
       Update-group.
       Sub-group.
       Update parents' OutQ counters too.
      ";
    input {
      leaf update-group {
        mandatory true;
        type update-group-id;
        description "Update-group process ID <x.y>";
      }
      leaf sub-group {
        mandatory true;
        type update-group-id;
        description "Sub-group process ID <x.y>";
      }
    }
  }

  rpc clear-bgp-update-outq-update-group-sub-group {
    csc:xr-task "bgp";
    csc:cli-command "clear bgp update outq update-group <update-group> sub-group <sub-group>";
    description
      "Clear Update information (Do NOT execute without cisco support)(cisco-support).
       Clear Update generation OutQ counters (Do NOT execute without cisco support)(cisco-support).
       Update-group.
       Sub-group.
      ";
    input {
      leaf update-group {
        mandatory true;
        type update-group-id;
        description "Update-group process ID <x.y>";
      }
      leaf sub-group {
        mandatory true;
        type update-group-id;
        description "Sub-group process ID <x.y>";
      }
    }
  }

  rpc clear-bgp-update-outq-update-group-sub-group-refresh-sub-group-update-parent {
    csc:xr-task "bgp";
    csc:cli-command "clear bgp update outq update-group <update-group> sub-group <refresh-sub-group> update-parent";
    description
      "Clear Update information (Do NOT execute without cisco support)(cisco-support).
       Clear Update generation OutQ counters (Do NOT execute without cisco support)(cisco-support).
       Update-group.
       Sub-group.
       Update parents' OutQ counters too.
      ";
    input {
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-update-outq-update-group-sub-group-refresh-sub-group {
    csc:xr-task "bgp";
    csc:cli-command "clear bgp update outq update-group <update-group> sub-group <refresh-sub-group>";
    description
      "Clear Update information (Do NOT execute without cisco support)(cisco-support).
       Clear Update generation OutQ counters (Do NOT execute without cisco support)(cisco-support).
       Update-group.
       Sub-group.
      ";
    input {
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-update-outq-update-group-update-parent {
    csc:xr-task "bgp";
    csc:cli-command "clear bgp update outq update-group <update-group> update-parent";
    description
      "Clear Update information (Do NOT execute without cisco support)(cisco-support).
       Clear Update generation OutQ counters (Do NOT execute without cisco support)(cisco-support).
       Update-group.
       Update parents' OutQ counters too.
      ";
    input {
      leaf update-group {
        mandatory true;
        type update-group-id;
        description "Update-group process ID <x.y>";
      }
    }
  }

  rpc clear-bgp-update-outq-update-group {
    csc:xr-task "bgp";
    csc:cli-command "clear bgp update outq update-group <update-group>";
    description
      "Clear Update information (Do NOT execute without cisco support)(cisco-support).
       Clear Update generation OutQ counters (Do NOT execute without cisco support)(cisco-support).
       Update-group.
      ";
    input {
      leaf update-group {
        mandatory true;
        type update-group-id;
        description "Update-group process ID <x.y>";
      }
    }
  }

  rpc clear-bgp-version-ip-addr-ip-netmask {
    csc:xr-task "bgp";
    csc:cli-command "clear bgp version <ip-addr> <ip-netmask>";
    description
      "clear BGP prefix version.
      ";
    input {
      leaf ip-addr {
        mandatory true;
        type inet:ip-address;
        description "Network";
      }
      leaf ip-netmask {
        mandatory true;
        type ip-netmask;
        description "Mask";
      }
    }
  }

  rpc clear-bgp-version-ip-addr {
    csc:xr-task "bgp";
    csc:cli-command "clear bgp version <ip-addr>";
    description
      "clear BGP prefix version.
      ";
    input {
      leaf ip-addr {
        mandatory true;
        type inet:ip-address;
        description "Network";
      }
    }
  }

  rpc clear-bgp-version-ip-prefix {
    csc:xr-task "bgp";
    csc:cli-command "clear bgp version <ip-prefix>";
    description
      "clear BGP prefix version.
      ";
    input {
      leaf ip-prefix {
        mandatory true;
        type inet:ip-prefix;
        description "Network and masklength";
      }
    }
  }

  rpc clear-bgp-version-afi-safi-ip-addr-ip-netmask {
    csc:xr-task "bgp";
    csc:cli-command "clear bgp version <afi-safi-name> <ip-addr> <ip-netmask>";
    description
      "clear BGP prefix version.
      ";
    input {
      leaf afi-safi-name {
        mandatory true;
        type afi-safi-type;
        description "AFI and SAFI";
      }
      leaf ip-addr {
        mandatory true;
        type inet:ip-address;
        description "Network";
      }
      leaf ip-netmask {
        mandatory true;
        type ip-netmask;
        description "Mask";
      }
    }
  }

  rpc clear-bgp-version-afi-safi-ip-addr {
    csc:xr-task "bgp";
    csc:cli-command "clear bgp version <afi-safi-name> <ip-addr>";
    description
      "clear BGP prefix version.
      ";
    input {
      leaf afi-safi-name {
        mandatory true;
        type afi-safi-type;
        description "AFI and SAFI";
      }
      leaf ip-addr {
        mandatory true;
        type inet:ip-address;
        description "Network";
      }
    }
  }

  rpc clear-bgp-version-afi-safi-ip-prefix {
    csc:xr-task "bgp";
    csc:cli-command "clear bgp version <afi-safi-name> <ip-prefix>";
    description
      "clear BGP prefix version.
      ";
    input {
      leaf afi-safi-name {
        mandatory true;
        type afi-safi-type;
        description "AFI and SAFI";
      }
      leaf ip-prefix {
        mandatory true;
        type inet:ip-prefix;
        description "Network and masklength";
      }
    }
  }

  rpc clear-bgp-version-afi-safi-bridge-domain-ip-addr-ip-netmask {
    csc:xr-task "bgp";
    csc:cli-command "clear bgp version <afi-safi-name> bridge-domain <bridge-domain-name> <ip-addr> <ip-netmask>";
    description
      "clear BGP prefix version.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
      leaf ip-netmask {
        mandatory true;
        type ip-netmask;
        description "Mask";
      }
    }
  }

  rpc clear-bgp-version-afi-safi-bridge-domain-ip-addr {
    csc:xr-task "bgp";
    csc:cli-command "clear bgp version <afi-safi-name> bridge-domain <bridge-domain-name> <ip-addr>";
    description
      "clear BGP prefix version.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-addr {
        mandatory true;
        type inet:ip-address;
        description "Network";
      }
    }
  }

  rpc clear-bgp-version-afi-safi-bridge-domain-ip-prefix {
    csc:xr-task "bgp";
    csc:cli-command "clear bgp version <afi-safi-name> bridge-domain <bridge-domain-name> <ip-prefix>";
    description
      "clear BGP prefix version.
       Display routes for a specified Bridge Domain.
      ";
    input {
      leaf afi-safi-name {
        mandatory true;
        type afi-safi-type;
        description "AFI and SAFI";
      }
      leaf bridge-domain-name {
        mandatory true;
        type string;
        description "Bridge Domain";
      }
      leaf ip-prefix {
        mandatory true;
        type inet:ip-prefix;
        description "Network and masklength";
      }
    }
  }

  rpc clear-bgp-version-afi-safi-rd-ip-addr-ip-netmask {
    csc:xr-task "bgp";
    csc:cli-command "clear bgp version <afi-safi-name> rd <rd> <ip-addr> <ip-netmask>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
      leaf ip-netmask {
        mandatory true;
        type ip-netmask;
        description "Mask";
      }
    }
  }

  rpc clear-bgp-version-afi-safi-rd-ip-addr {
    csc:xr-task "bgp";
    csc:cli-command "clear bgp version <afi-safi-name> rd <rd> <ip-addr>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ip-addr {
        mandatory true;
        type inet:ip-address;
        description "Network";
      }
    }
  }

  rpc clear-bgp-version-afi-safi-rd-ip-prefix {
    csc:xr-task "bgp";
    csc:cli-command "clear bgp version <afi-safi-name> rd <rd> <ip-prefix>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ip-prefix {
        mandatory true;
        type inet:ip-prefix;
        description "Network and masklength";
      }
    }
  }

  rpc clear-bgp-version-afi-safi-ipv4-addr-ipv4-mask {
    csc:xr-task "bgp";
    csc:cli-command "clear bgp version <afi-safi-name> <ipv4-addr> <ipv4-mask>";
    description
      "clear BGP prefix version.
      ";
    input {
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-version-afi-safi-ipv4-addr {
    csc:xr-task "bgp";
    csc:cli-command "clear bgp version <afi-safi-name> <ipv4-addr>";
    description
      "clear BGP prefix version.
      ";
    input {
      leaf afi-safi-name {
        mandatory true;
        type afi-safi-type;
        description "AFI and SAFI";
      }
      leaf ipv4-addr {
        mandatory true;
        type inet:ipv4-address;
        description "IPv4 network";
      }
    }
  }

  rpc clear-bgp-version-afi-safi-ipv4-prefix {
    csc:xr-task "bgp";
    csc:cli-command "clear bgp version <afi-safi-name> <ipv4-prefix>";
    description
      "clear BGP prefix version.
      ";
    input {
      leaf afi-safi-name {
        mandatory true;
        type afi-safi-type;
        description "AFI and SAFI";
      }
      leaf ipv4-prefix {
        mandatory true;
        type inet:ipv4-prefix;
        description "IPv4 network and masklength";
      }
    }
  }

  rpc clear-bgp-version-afi-safi-rd-ipv4-addr {
    csc:xr-task "bgp";
    csc:cli-command "clear bgp version <afi-safi-name> rd <rd> <ipv4-addr>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 MDT network";
      }
    }
  }

  rpc clear-bgp-version-afi-safi-vrf-ipv4-addr {
    csc:xr-task "bgp";
    csc:cli-command "clear bgp version <afi-safi-name> vrf <vrf-name> <ipv4-addr>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 MDT network";
      }
    }
  }

  rpc clear-bgp-version-afi-safi-network {
    csc:xr-task "bgp";
    csc:cli-command "clear bgp version <afi-safi-name> <network>";
    description
      "clear BGP prefix version.
      ";
    input {
      leaf afi-safi-name {
        mandatory true;
        type afi-safi-type;
        description "AFI and SAFI";
      }
      leaf network {
        mandatory true;
        type string;
        description "Address family modifier specific network";
      }
    }
  }

  rpc clear-bgp-version-afi-safi-rd-network {
    csc:xr-task "bgp";
    csc:cli-command "clear bgp version <afi-safi-name> rd <rd> <network>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-version-afi-safi-vrf-network {
    csc:xr-task "bgp";
    csc:cli-command "clear bgp version <afi-safi-name> vrf <vrf-name> <network>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-version-afi-safi-rt-constraint-network {
    csc:xr-task "bgp";
    csc:cli-command "clear bgp version <afi-safi-name> <rt-constraint-network>";
    description
      "clear BGP prefix version.
      ";
    input {
      leaf afi-safi-name {
        mandatory true;
        type afi-safi-type;
        description "AFI and SAFI";
      }
      leaf rt-constraint-network {
        mandatory true;
        type string;
        description "RT-Constraint network";
      }
    }
  }

  rpc clear-bgp-version-afi-safi-ipv4-tunnel-network {
    csc:xr-task "bgp";
    csc:cli-command "clear bgp version <afi-safi-name> <ipv4-tunnel-network>";
    description
      "clear BGP prefix version.
      ";
    input {
      leaf afi-safi-name {
        mandatory true;
        type afi-safi-type;
        description "AFI and SAFI";
      }
      leaf ipv4-tunnel-network {
        mandatory true;
        type string;
        description "IPv4 Tunnel network <Tunnel-ID>:<IPv4 Address>";
      }
    }
  }

  rpc clear-bgp-version-afi-safi-ipv6-addr-ipv6-netmask {
    csc:xr-task "bgp";
    csc:cli-command "clear bgp version <afi-safi-name> <ipv6-addr> <ipv6-netmask>";
    description
      "clear BGP prefix version.
      ";
    input {
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-version-afi-safi-ipv6-addr {
    csc:xr-task "bgp";
    csc:cli-command "clear bgp version <afi-safi-name> <ipv6-addr>";
    description
      "clear BGP prefix version.
      ";
    input {
      leaf afi-safi-name {
        mandatory true;
        type afi-safi-type;
        description "AFI and SAFI";
      }
      leaf ipv6-addr {
        mandatory true;
        type inet:ipv6-address;
        description "IPv6 network";
      }
    }
  }

  rpc clear-bgp-version-afi-safi-ipv6-prefix {
    csc:xr-task "bgp";
    csc:cli-command "clear bgp version <afi-safi-name> <ipv6-prefix>";
    description
      "clear BGP prefix version.
      ";
    input {
      leaf afi-safi-name {
        mandatory true;
        type afi-safi-type;
        description "AFI and SAFI";
      }
      leaf ipv6-prefix {
        mandatory true;
        type inet:ipv6-prefix;
        description "IPv6 network and masklength";
      }
    }
  }

  rpc clear-bgp-version-afi-safi-rd {
    csc:xr-task "bgp";
    csc:cli-command "clear bgp version <afi-safi-name> rd <rd>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
    }
  }

  rpc clear-bgp-version-afi-safi-vrf {
    csc:xr-task "bgp";
    csc:cli-command "clear bgp version <afi-safi-name> vrf <vrf-name>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
    }
  }

  rpc clear-bgp-version-afi-safi {
    csc:xr-task "bgp";
    csc:cli-command "clear bgp version <afi-safi-name>";
    description
      "clear BGP prefix version.
      ";
    input {
      leaf afi-safi-name {
        mandatory true;
        type afi-safi-type;
        description "AFI and SAFI";
      }
    }
  }

  rpc clear-bgp-version-afi-safi-sr-policy-prefix {
    csc:xr-task "bgp";
    csc:cli-command "clear bgp version <afi-safi-name> <sr-policy-prefix>";
    description
      "clear BGP prefix version.
      ";
    input {
      leaf afi-safi-name {
        mandatory true;
        type afi-safi-type;
        description "AFI and SAFI";
      }
      leaf sr-policy-prefix {
        mandatory true;
        type string;
        description "SR Policy prefix";
      }
    }
  }

  rpc clear-bgp-version-afi-safi-bridge-domain-ipv4-prefix {
    csc:xr-task "bgp";
    csc:cli-command "clear bgp version <afi-safi-name> bridge-domain <bridge-domain-name> <ipv4-prefix>";
    description
      "clear BGP prefix version.
       Display routes for a specified Bridge Domain.
      ";
    input {
      leaf afi-safi-name {
        mandatory true;
        type afi-safi-type;
        description "AFI and SAFI";
      }
      leaf bridge-domain-name {
        mandatory true;
        type string;
        description "Bridge Domain";
      }
      leaf ipv4-prefix {
        mandatory true;
        type inet:ipv4-prefix;
        description "L2VPN EVPN Prefix";
      }
    }
  }

  rpc clear-bgp-version-afi-safi-rd-ipv4-prefix {
    csc:xr-task "bgp";
    csc:cli-command "clear bgp version <afi-safi-name> rd <rd> <ipv4-prefix>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv4-prefix {
        mandatory true;
        type inet:ipv4-prefix;
        description "L2VPN EVPN Prefix";
      }
    }
  }

  rpc clear-bgp-version-afi-safi-mp2mp-ipv4-prefix {
    csc:xr-task "bgp";
    csc:cli-command "clear bgp version <afi-safi-name> mp2mp <mp2mp> <ipv4-prefix>";
    description
      "clear BGP prefix version.
       Display routes for a specified Xconnect group:MP2MP.
      ";
    input {
      leaf afi-safi-name {
        mandatory true;
        type afi-safi-type;
        description "AFI and SAFI";
      }
      leaf mp2mp {
        mandatory true;
        type string;
        description "Xconnect Group:mp2mp";
      }
      leaf ipv4-prefix {
        mandatory true;
        type inet:ipv4-prefix;
        description "L2VPN VPWS Prefix";
      }
    }
  }

  rpc clear-bgp-version-afi-safi-vrf-ipv4-prefix {
    csc:xr-task "bgp";
    csc:cli-command "clear bgp version <afi-safi-name> vrf <vrf-name> <ipv4-prefix>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv4-prefix {
        mandatory true;
        type inet:ipv4-prefix;
        description "VPN Fspec Prefix";
      }
    }
  }

  rpc clear-bgp-version-afi-safi-rd-ipv4-addr-ipv4-mask {
    csc:xr-task "bgp";
    csc:cli-command "clear bgp version <afi-safi-name> rd <rd> <ipv4-addr> <ipv4-mask>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv4-addr {
        mandatory true;
        type inet:ipv4-address;
        description "IPv4 network";
      }
      leaf ipv4-mask {
        mandatory true;
        type ipv4-netmask;
        description "IPv4 mask";
      }
    }
  }

  rpc clear-bgp-version-afi-safi-vrf-ipv4-addr-ipv4-mask {
    csc:xr-task "bgp";
    csc:cli-command "clear bgp version <afi-safi-name> vrf <vrf-name> <ipv4-addr> <ipv4-mask>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv4-addr {
        mandatory true;
        type inet:ipv4-address;
        description "IPv4 network";
      }
      leaf ipv4-mask {
        mandatory true;
        type ipv4-netmask;
        description "IPv4 mask";
      }
    }
  }

  rpc clear-bgp-version-afi-safi-rd-ipv6-addr-ipv6-netmask {
    csc:xr-task "bgp";
    csc:cli-command "clear bgp version <afi-safi-name> rd <rd> <ipv6-addr> <ipv6-netmask>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
      leaf ipv6-netmask {
        mandatory true;
        type ipv6-netmask;
        description "IPv6 mask";
      }
    }
  }

  rpc clear-bgp-version-afi-safi-rd-ipv6-addr {
    csc:xr-task "bgp";
    csc:cli-command "clear bgp version <afi-safi-name> rd <rd> <ipv6-addr>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv6-addr {
        mandatory true;
        type inet:ipv6-address;
        description "IPv6 network";
      }
    }
  }

  rpc clear-bgp-version-afi-safi-rd-ipv6-prefix {
    csc:xr-task "bgp";
    csc:cli-command "clear bgp version <afi-safi-name> rd <rd> <ipv6-prefix>";
    description
      "clear BGP prefix version.
       Display routes with a specific route distinguisher.
      ";
    input {
      leaf afi-safi-name {
        mandatory true;
        type afi-safi-type;
        description "AFI and SAFI";
      }
      leaf rd {
        mandatory true;
        type rd;
        description "Route distinguisher";
      }
      leaf ipv6-prefix {
        mandatory true;
        type inet:ipv6-prefix;
        description "IPv6 network and masklength";
      }
    }
  }

  rpc clear-bgp-version-afi-safi-vrf-ipv6-addr-ipv6-netmask {
    csc:xr-task "bgp";
    csc:cli-command "clear bgp version <afi-safi-name> vrf <vrf-name> <ipv6-addr> <ipv6-netmask>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
      leaf ipv6-netmask {
        mandatory true;
        type ipv6-netmask;
        description "IPv6 mask";
      }
    }
  }

  rpc clear-bgp-version-afi-safi-vrf-ipv6-addr {
    csc:xr-task "bgp";
    csc:cli-command "clear bgp version <afi-safi-name> vrf <vrf-name> <ipv6-addr>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv6-addr {
        mandatory true;
        type inet:ipv6-address;
        description "IPv6 network";
      }
    }
  }

  rpc clear-bgp-version-afi-safi-vrf-ipv6-prefix {
    csc:xr-task "bgp";
    csc:cli-command "clear bgp version <afi-safi-name> vrf <vrf-name> <ipv6-prefix>";
    description
      "clear BGP prefix version.
       Display routes for a specified VRF.
      ";
    input {
      leaf afi-safi-name {
        mandatory true;
        type afi-safi-type;
        description "AFI and SAFI";
      }
      leaf vrf-name {
        mandatory true;
        type string;
        description "VRF name";
      }
      leaf ipv6-prefix {
        mandatory true;
        type inet:ipv6-prefix;
        description "IPv6 network and masklength";
      }
    }
  }

  rpc clear-bgp-version-vrf-ip-addr-ip-netmask {
    csc:xr-task "bgp";
    csc:cli-command "clear bgp version vrf <vrf-all> <ip-addr> <ip-netmask>";
    description
      "clear BGP prefix version.
       Specify a VRF.
      ";
    input {
      leaf vrf-all {
        mandatory true;
        type vrf-name;
        description "VRF name or all";
      }
      leaf ip-addr {
        mandatory true;
        type inet:ip-address;
        description "Network";
      }
      leaf ip-netmask {
        mandatory true;
        type ip-netmask;
        description "Mask";
      }
    }
  }

  rpc clear-bgp-version-vrf-ip-addr {
    csc:xr-task "bgp";
    csc:cli-command "clear bgp version vrf <vrf-all> <ip-addr>";
    description
      "clear BGP prefix version.
       Specify a VRF.
      ";
    input {
      leaf vrf-all {
        mandatory true;
        type vrf-name;
        description "VRF name or all";
      }
      leaf ip-addr {
        mandatory true;
        type inet:ip-address;
        description "Network";
      }
    }
  }

  rpc clear-bgp-version-vrf-ip-prefix {
    csc:xr-task "bgp";
    csc:cli-command "clear bgp version vrf <vrf-all> <ip-prefix>";
    description
      "clear BGP prefix version.
       Specify a VRF.
      ";
    input {
      leaf vrf-all {
        mandatory true;
        type vrf-name;
        description "VRF name or all";
      }
      leaf ip-prefix {
        mandatory true;
        type inet:ip-prefix;
        description "Network and masklength";
      }
    }
  }

  rpc clear-bgp-version-vrf-afi-safi-ipv4-prefix {
    csc:xr-task "bgp";
    csc:cli-command "clear bgp version vrf <vrf-all> <afi-safi-name> <ipv4-prefix>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "Fspec IPv4 Prefix";
      }
    }
  }

  rpc clear-bgp-version-vrf-afi-safi-ipv4-addr-ipv4-mask {
    csc:xr-task "bgp";
    csc:cli-command "clear bgp version vrf <vrf-all> <afi-safi-name> <ipv4-addr> <ipv4-mask>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
      leaf ipv4-mask {
        mandatory true;
        type ipv4-netmask;
        description "IPv4 mask";
      }
    }
  }

  rpc clear-bgp-version-vrf-afi-safi-ipv4-addr {
    csc:xr-task "bgp";
    csc:cli-command "clear bgp version vrf <vrf-all> <afi-safi-name> <ipv4-addr>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv4-addr {
        mandatory true;
        type inet:ipv4-address;
        description "IPv4 network";
      }
    }
  }

  rpc clear-bgp-version-vrf-afi-safi-network {
    csc:xr-task "bgp";
    csc:cli-command "clear bgp version vrf <vrf-all> <afi-safi-name> <network>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf network {
        mandatory true;
        type string;
        description "Address family modifier specific network";
      }
    }
  }

  rpc clear-bgp-version-vrf-afi-safi-rd-network {
    csc:xr-task "bgp";
    csc:cli-command "clear bgp version vrf <vrf-all> <afi-safi-name> rd <rd> <network>";
    description
      "clear BGP prefix version.
       Specify a VRF.
       Display routes with a specific route distinguisher.
      ";
    input {
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
      leaf network {
        mandatory true;
        type string;
        description "Address family modifier specific network";
      }
    }
  }

  rpc clear-bgp-version-vrf-afi-safi-vrf-network {
    csc:xr-task "bgp";
    csc:cli-command "clear bgp version vrf <vrf-all> <afi-safi-name> vrf <vrf-name> <network>";
    description
      "clear BGP prefix version.
       Specify a VRF.
       Display routes for a specified VRF.
      ";
    input {
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
      leaf network {
        mandatory true;
        type string;
        description "Address family modifier specific network";
      }
    }
  }

  rpc clear-bgp-version-vrf-afi-safi-ipv6-addr-ipv6-netmask {
    csc:xr-task "bgp";
    csc:cli-command "clear bgp version vrf <vrf-all> <afi-safi-name> <ipv6-addr> <ipv6-netmask>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
      leaf ipv6-netmask {
        mandatory true;
        type ipv6-netmask;
        description "IPv6 mask";
      }
    }
  }

  rpc clear-bgp-version-vrf-afi-safi-ipv6-addr {
    csc:xr-task "bgp";
    csc:cli-command "clear bgp version vrf <vrf-all> <afi-safi-name> <ipv6-addr>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv6-addr {
        mandatory true;
        type inet:ipv6-address;
        description "IPv6 network";
      }
    }
  }

  rpc clear-bgp-version-vrf-afi-safi-ipv6-prefix {
    csc:xr-task "bgp";
    csc:cli-command "clear bgp version vrf <vrf-all> <afi-safi-name> <ipv6-prefix>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 network and masklength";
      }
    }
  }

  rpc clear-bgp-version-vrf-afi-safi-rd {
    csc:xr-task "bgp";
    csc:cli-command "clear bgp version vrf <vrf-all> <afi-safi-name> rd <rd>";
    description
      "clear BGP prefix version.
       Specify a VRF.
       Display routes with a specific route distinguisher.
      ";
    input {
      leaf vrf-all {
        mandatory true;
        type vrf-name;
        description "VRF name or all";
      }
      leaf afi-safi-name {
        mandatory true;
        type afi-safi-type;
        description "AFI and SAFI";
      }
      leaf rd {
        mandatory true;
        type rd;
        description "Route distinguisher";
      }
    }
  }

  rpc clear-bgp-version-vrf-afi-safi-vrf {
    csc:xr-task "bgp";
    csc:cli-command "clear bgp version vrf <vrf-all> <afi-safi-name> vrf <vrf-name>";
    description
      "clear BGP prefix version.
       Specify a VRF.
       Display routes for a specified VRF.
      ";
    input {
      leaf vrf-all {
        mandatory true;
        type vrf-name;
        description "VRF name or all";
      }
      leaf afi-safi-name {
        mandatory true;
        type afi-safi-type;
        description "AFI and SAFI";
      }
      leaf vrf-name {
        mandatory true;
        type string;
        description "VRF name";
      }
    }
  }

  rpc clear-bgp-version-vrf-afi-safi {
    csc:xr-task "bgp";
    csc:cli-command "clear bgp version vrf <vrf-all> <afi-safi-name>";
    description
      "clear BGP prefix version.
       Specify a VRF.
      ";
    input {
      leaf vrf-all {
        mandatory true;
        type vrf-name;
        description "VRF name or all";
      }
      leaf afi-safi-name {
        mandatory true;
        type afi-safi-type;
        description "AFI and SAFI";
      }
    }
  }

  rpc clear-bgp-vrf-all-graceful {
    csc:xr-task "bgp";
    csc:cli-command "clear bgp vrf <vrf-all> * graceful";
    description
      "Specify a VRF.
       Clear all peers and all routes from the BGP table.
       Clear with a hard reset and a graceful restart.
      ";
    input {
      leaf vrf-all {
        mandatory true;
        type vrf-name;
        description "VRF name or all";
      }
    }
  }

  rpc clear-bgp-instance-vrf-rpki-validation-ipv4 {
    csc:xr-task "bgp";
    csc:cli-command "clear bgp instance <instance-name> vrf <vrf-all> rpki validation ipv4";
    description
      "Choose a particular BGP instance and VRF.
       RPKI clear command.
       clear RPKI origin-validation (trigger origin validation).
       trigger origin validation walk for the IPv4 table.
      ";
    input {
      leaf instance-name {
        mandatory true;
        type instance-name;
        description "instance name or all";
      }
      leaf vrf-all {
        mandatory true;
        type vrf-name;
        description "VRF name or all";
      }
    }
  }

  rpc clear-bgp-instance-vrf-rpki-validation-ipv6 {
    csc:xr-task "bgp";
    csc:cli-command "clear bgp instance <instance-name> vrf <vrf-all> rpki validation ipv6";
    description
      "Choose a particular BGP instance and VRF.
       RPKI clear command.
       clear RPKI origin-validation (trigger origin validation).
       trigger origin validation walk for the IPv6 table.
      ";
    input {
      leaf instance-name {
        mandatory true;
        type instance-name;
        description "instance name or all";
      }
      leaf vrf-all {
        mandatory true;
        type vrf-name;
        description "VRF name or all";
      }
    }
  }

  rpc clear-bgp-instance-vrf-rpki-validation {
    csc:xr-task "bgp";
    csc:cli-command "clear bgp instance <instance-name> vrf <vrf-all> rpki validation";
    description
      "Choose a particular BGP instance and VRF.
       RPKI clear command.
       clear RPKI origin-validation (trigger origin validation).
      ";
    input {
      leaf instance-name {
        mandatory true;
        type instance-name;
        description "instance name or all";
      }
      leaf vrf-all {
        mandatory true;
        type vrf-name;
        description "VRF name or all";
      }
    }
  }

  rpc clear-bgp-vrf-rpki-validation-ipv4 {
    csc:xr-task "bgp";
    csc:cli-command "clear bgp vrf <vrf-all> rpki validation ipv4";
    description
      "RPKI clear command.
       clear RPKI origin-validation (trigger origin validation).
       trigger origin validation walk for the IPv4 table.
      ";
    input {
      leaf vrf-all {
        mandatory true;
        type vrf-name;
        description "VRF name or all";
      }
    }
  }

  rpc clear-bgp-vrf-rpki-validation-ipv6 {
    csc:xr-task "bgp";
    csc:cli-command "clear bgp vrf <vrf-all> rpki validation ipv6";
    description
      "RPKI clear command.
       clear RPKI origin-validation (trigger origin validation).
       trigger origin validation walk for the IPv6 table.
      ";
    input {
      leaf vrf-all {
        mandatory true;
        type vrf-name;
        description "VRF name or all";
      }
    }
  }

  rpc clear-bgp-vrf-rpki-validation {
    csc:xr-task "bgp";
    csc:cli-command "clear bgp vrf <vrf-all> rpki validation";
    description
      "RPKI clear command.
       clear RPKI origin-validation (trigger origin validation).
      ";
    input {
      leaf vrf-all {
        mandatory true;
        type vrf-name;
        description "VRF name or all";
      }
    }
  }

  rpc clear-bgp-vrf-all {
    csc:xr-task "bgp";
    csc:cli-command "clear bgp vrf <vrf-all> *";
    description
      "Specify a VRF.
       Clear all peers and all routes from the BGP table.
      ";
    input {
      leaf vrf-all {
        mandatory true;
        type vrf-name;
        description "VRF name or all";
      }
    }
  }

  rpc clear-bgp-vrf-ip-addr-graceful {
    csc:xr-task "bgp";
    csc:cli-command "clear bgp vrf <vrf-all> <ip-addr> graceful";
    description
      "Specify a VRF.
       Clear with a hard reset and a graceful restart.
      ";
    input {
      leaf vrf-all {
        mandatory true;
        type vrf-name;
        description "VRF name or all";
      }
      leaf ip-addr {
        mandatory true;
        type inet:ip-address;
        description "BGP neighbor address to clear";
      }
    }
  }

  rpc clear-bgp-vrf-ip-addr-long-lived-stale {
    csc:xr-task "bgp";
    csc:cli-command "clear bgp vrf <vrf-all> <ip-addr> long-lived-stale";
    description
      "Specify a VRF.
       Clear long-lived-stale routes.
      ";
    input {
      leaf vrf-all {
        mandatory true;
        type vrf-name;
        description "VRF name or all";
      }
      leaf ip-addr {
        mandatory true;
        type inet:ip-address;
        description "BGP neighbor address to clear";
      }
    }
  }

  rpc clear-bgp-vrf-ip-addr {
    csc:xr-task "bgp";
    csc:cli-command "clear bgp vrf <vrf-all> <ip-addr>";
    description
      "Specify a VRF.
      ";
    input {
      leaf vrf-all {
        mandatory true;
        type vrf-name;
        description "VRF name or all";
      }
      leaf ip-addr {
        mandatory true;
        type inet:ip-address;
        description "BGP neighbor address to clear";
      }
    }
  }

  rpc clear-bgp-vrf-as-graceful {
    csc:xr-task "bgp";
    csc:cli-command "clear bgp vrf <vrf-all> as <as-number> graceful";
    description
      "Specify a VRF.
       Clear peers in a specific AS.
       Clear with a hard reset and a graceful restart.
      ";
    input {
      leaf vrf-all {
        mandatory true;
        type vrf-name;
        description "VRF name or all";
      }
      leaf as-number {
        mandatory true;
        type as-number;
        description "AS number";
      }
    }
  }

  rpc clear-bgp-vrf-as {
    csc:xr-task "bgp";
    csc:cli-command "clear bgp vrf <vrf-all> as <as-number>";
    description
      "Specify a VRF.
       Clear peers in a specific AS.
      ";
    input {
      leaf vrf-all {
        mandatory true;
        type vrf-name;
        description "VRF name or all";
      }
      leaf as-number {
        mandatory true;
        type as-number;
        description "AS number";
      }
    }
  }

  rpc clear-bgp-vrf-external-graceful {
    csc:xr-task "bgp";
    csc:cli-command "clear bgp vrf <vrf-all> external graceful";
    description
      "Specify a VRF.
       Clear all external peers.
       Clear with a hard reset and a graceful restart.
      ";
    input {
      leaf vrf-all {
        mandatory true;
        type vrf-name;
        description "VRF name or all";
      }
    }
  }

  rpc clear-bgp-vrf-external {
    csc:xr-task "bgp";
    csc:cli-command "clear bgp vrf <vrf-all> external";
    description
      "Specify a VRF.
       Clear all external peers.
      ";
    input {
      leaf vrf-all {
        mandatory true;
        type vrf-name;
        description "VRF name or all";
      }
    }
  }

  rpc clear-bgp-vrf-afi-safi-all-soft-in-prefix-filter {
    csc:xr-task "bgp";
    csc:cli-command "clear bgp vrf <vrf-all> <afi-safi-name> * soft in prefix-filter";
    description
      "Specify a VRF.
       Clear all peers and all routes from the BGP table.
       Soft reconfig.
       Soft reconfig inbound update.
       Push out prefix ORF and do inbound soft reconfig.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-all-soft-in {
    csc:xr-task "bgp";
    csc:cli-command "clear bgp vrf <vrf-all> <afi-safi-name> * soft in";
    description
      "Specify a VRF.
       Clear all peers and all routes from the BGP table.
       Soft reconfig.
       Soft reconfig inbound update.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-all-soft-out {
    csc:xr-task "bgp";
    csc:cli-command "clear bgp vrf <vrf-all> <afi-safi-name> * soft out";
    description
      "Specify a VRF.
       Clear all peers and all routes from the BGP table.
       Soft reconfig.
       Soft reconfig outbound update.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-all-soft {
    csc:xr-task "bgp";
    csc:cli-command "clear bgp vrf <vrf-all> <afi-safi-name> * soft";
    description
      "Specify a VRF.
       Clear all peers and all routes from the BGP table.
       Soft reconfig.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-ip-addr-long-lived-stale {
    csc:xr-task "bgp";
    csc:cli-command "clear bgp vrf <vrf-all> <afi-safi-name> <ip-addr> long-lived-stale";
    description
      "Specify a VRF.
       Clear long-lived-stale routes.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-ip-addr-soft-in-prefix-filter {
    csc:xr-task "bgp";
    csc:cli-command "clear bgp vrf <vrf-all> <afi-safi-name> <ip-addr> soft in prefix-filter";
    description
      "Specify a VRF.
       Soft reconfig.
       Soft reconfig inbound update.
       Push out prefix ORF and do inbound soft reconfig.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-ip-addr-soft-in {
    csc:xr-task "bgp";
    csc:cli-command "clear bgp vrf <vrf-all> <afi-safi-name> <ip-addr> soft in";
    description
      "Specify a VRF.
       Soft reconfig.
       Soft reconfig inbound update.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-ip-addr-soft-out {
    csc:xr-task "bgp";
    csc:cli-command "clear bgp vrf <vrf-all> <afi-safi-name> <ip-addr> soft out";
    description
      "Specify a VRF.
       Soft reconfig.
       Soft reconfig outbound update.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-ip-addr-soft {
    csc:xr-task "bgp";
    csc:cli-command "clear bgp vrf <vrf-all> <afi-safi-name> <ip-addr> soft";
    description
      "Specify a VRF.
       Soft reconfig.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-as-soft-in-prefix-filter {
    csc:xr-task "bgp";
    csc:cli-command "clear bgp vrf <vrf-all> <afi-safi-name> as <as-number> soft in prefix-filter";
    description
      "Specify a VRF.
       Clear peers in a specific AS.
       Soft reconfig.
       Soft reconfig inbound update.
       Push out prefix ORF and do inbound soft reconfig.
      ";
    input {
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-vrf-afi-safi-as-soft-in {
    csc:xr-task "bgp";
    csc:cli-command "clear bgp vrf <vrf-all> <afi-safi-name> as <as-number> soft in";
    description
      "Specify a VRF.
       Clear peers in a specific AS.
       Soft reconfig.
       Soft reconfig inbound update.
      ";
    input {
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-vrf-afi-safi-as-soft-out {
    csc:xr-task "bgp";
    csc:cli-command "clear bgp vrf <vrf-all> <afi-safi-name> as <as-number> soft out";
    description
      "Specify a VRF.
       Clear peers in a specific AS.
       Soft reconfig.
       Soft reconfig outbound update.
      ";
    input {
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-vrf-afi-safi-as-soft {
    csc:xr-task "bgp";
    csc:cli-command "clear bgp vrf <vrf-all> <afi-safi-name> as <as-number> soft";
    description
      "Specify a VRF.
       Clear peers in a specific AS.
       Soft reconfig.
      ";
    input {
      leaf vrf-all {
        mandatory true;
        type vrf-name;
        description "VRF name or all";
      }
      leaf afi-safi-name {
        mandatory true;
        type afi-safi-type;
        description "AFI and SAFI";
      }
      leaf as-number {
        mandatory true;
        type as-number;
        description "AS number";
      }
    }
  }

  rpc clear-bgp-vrf-afi-safi-dampening-ipv4-prefix {
    csc:xr-task "bgp";
    csc:cli-command "clear bgp vrf <vrf-all> <afi-safi-name> dampening <ipv4-prefix>";
    description
      "Specify a VRF.
       Clear route flap dampening information.
      ";
    input {
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "IPv4 Network and mask or masklength to clear dampening information";
      }
    }
  }

  rpc clear-bgp-vrf-afi-safi-dampening {
    csc:xr-task "bgp";
    csc:cli-command "clear bgp vrf <vrf-all> <afi-safi-name> dampening";
    description
      "Specify a VRF.
       Clear route flap dampening information.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-external-soft-in-prefix-filter {
    csc:xr-task "bgp";
    csc:cli-command "clear bgp vrf <vrf-all> <afi-safi-name> external soft in prefix-filter";
    description
      "Specify a VRF.
       Clear all external peers.
       Soft reconfig.
       Soft reconfig inbound update.
       Push out prefix ORF and do inbound soft reconfig.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-external-soft-in {
    csc:xr-task "bgp";
    csc:cli-command "clear bgp vrf <vrf-all> <afi-safi-name> external soft in";
    description
      "Specify a VRF.
       Clear all external peers.
       Soft reconfig.
       Soft reconfig inbound update.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-external-soft-out {
    csc:xr-task "bgp";
    csc:cli-command "clear bgp vrf <vrf-all> <afi-safi-name> external soft out";
    description
      "Specify a VRF.
       Clear all external peers.
       Soft reconfig.
       Soft reconfig outbound update.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-external-soft {
    csc:xr-task "bgp";
    csc:cli-command "clear bgp vrf <vrf-all> <afi-safi-name> external soft";
    description
      "Specify a VRF.
       Clear all external peers.
       Soft reconfig.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-flap-statistics-ip-addr-ipv4-mask {
    csc:xr-task "bgp";
    csc:cli-command "clear bgp vrf <vrf-all> <afi-safi-name> flap-statistics <ip-addr> <ipv4-mask>";
    description
      "Specify a VRF.
       Clear flap statistics.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
      leaf ipv4-mask {
        mandatory true;
        type ipv4-netmask;
        description "IPv4 Network and mask or masklength to clear flap statistics";
      }
    }
  }

  rpc clear-bgp-vrf-afi-safi-flap-statistics-ip-addr {
    csc:xr-task "bgp";
    csc:cli-command "clear bgp vrf <vrf-all> <afi-safi-name> flap-statistics <ip-addr>";
    description
      "Specify a VRF.
       Clear flap statistics.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "BGP neighbor address to clear";
      }
    }
  }

  rpc clear-bgp-vrf-afi-safi-flap-statistics-ipv4-prefix {
    csc:xr-task "bgp";
    csc:cli-command "clear bgp vrf <vrf-all> <afi-safi-name> flap-statistics <ipv4-prefix>";
    description
      "Specify a VRF.
       Clear flap statistics.
      ";
    input {
      leaf vrf-all {
        mandatory true;
        type vrf-name;
        description "VRF name or all";
      }
      leaf afi-safi-name {
        mandatory true;
        type afi-safi-type;
        description "AFI and SAFI";
      }
      leaf ipv4-prefix {
        mandatory true;
        type inet:ipv4-prefix;
        description "IPv4 Network and mask or masklength to clear flap statistics";
      }
    }
  }

  rpc clear-bgp-vrf-afi-safi-flap-statistics-regexp {
    csc:xr-task "bgp";
    csc:cli-command "clear bgp vrf <vrf-all> <afi-safi-name> flap-statistics regexp <regexp-pattern>";
    description
      "Specify a VRF.
       Clear flap statistics.
       Clear flap statistics for routes matching the regular expression.
      ";
    input {
      leaf vrf-all {
        mandatory true;
        type vrf-name;
        description "VRF name or all";
      }
      leaf afi-safi-name {
        mandatory true;
        type afi-safi-type;
        description "AFI and SAFI";
      }
      leaf regexp-pattern {
        mandatory true;
        type string;
        description "A regular expression to match the BGP AS paths.  Use 'ctrl-v ?' to enter '?'";
      }
    }
  }

  rpc clear-bgp-vrf-afi-safi-flap-statistics-route-policy {
    csc:xr-task "bgp";
    csc:cli-command "clear bgp vrf <vrf-all> <afi-safi-name> flap-statistics route-policy <route-policy-name>";
    description
      "Specify a VRF.
       Clear flap statistics.
       Clear flap statistics for routes matching the route policy.
      ";
    input {
      leaf vrf-all {
        mandatory true;
        type vrf-name;
        description "VRF name or all";
      }
      leaf afi-safi-name {
        mandatory true;
        type afi-safi-type;
        description "AFI and SAFI";
      }
      leaf route-policy-name {
        mandatory true;
        type string;
        description "Route Policy name";
      }
    }
  }

  rpc clear-bgp-vrf-afi-safi-flap-statistics {
    csc:xr-task "bgp";
    csc:cli-command "clear bgp vrf <vrf-all> <afi-safi-name> flap-statistics";
    description
      "Specify a VRF.
       Clear flap statistics.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-nexthop-performance-statistics {
    csc:xr-task "bgp";
    csc:cli-command "clear bgp vrf <vrf-all> <afi-safi-name> nexthop performance-statistics";
    description
      "Specify a VRF.
       Clear nexthop.
       Performance statistics information related to processing.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-nexthop-registration-ip-addr {
    csc:xr-task "bgp";
    csc:cli-command "clear bgp vrf <vrf-all> <afi-safi-name> nexthop registration <ip-addr>";
    description
      "Specify a VRF.
       Clear nexthop.
       Registration with RIB and reregister.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Nexthop address";
      }
    }
  }

  rpc clear-bgp-vrf-afi-safi-self-originated {
    csc:xr-task "bgp";
    csc:cli-command "clear bgp vrf <vrf-all> <afi-safi-name> self-originated";
    description
      "Specify a VRF.
       Clear redistributed, network and aggregate routes originated here.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-shutdown {
    csc:xr-task "bgp";
    csc:cli-command "clear bgp vrf <vrf-all> <afi-safi-name> shutdown";
    description
      "Specify a VRF.
       Clear all peers which were shut down due to low memory.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-update-outq-address-family-update-parent {
    csc:xr-task "bgp";
    csc:cli-command "clear bgp vrf <vrf-all> <afi-safi-name> update outq address-family update-parent";
    description
      "Specify a VRF.
       Clear Update information (Do NOT execute without cisco support)(cisco-support).
       Clear Update generation OutQ counters (Do NOT execute without cisco support)(cisco-support).
       Address-family.
       Update parents' OutQ counters too.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-update-outq-address-family {
    csc:xr-task "bgp";
    csc:cli-command "clear bgp vrf <vrf-all> <afi-safi-name> update outq address-family";
    description
      "Specify a VRF.
       Clear Update information (Do NOT execute without cisco support)(cisco-support).
       Clear Update generation OutQ counters (Do NOT execute without cisco support)(cisco-support).
       Address-family.
      ";
    input {
      leaf vrf-all {
        mandatory true;
        type vrf-name;
        description "VRF name or all";
      }
      leaf afi-safi-name {
        mandatory true;
        type afi-safi-type;
        description "AFI and SAFI";
      }
    }
  }

  rpc clear-bgp-vrf-afi-safi-update-outq-neighbor-ip-addr-refresh-update-parent {
    csc:xr-task "bgp";
    csc:cli-command "clear bgp vrf <vrf-all> <afi-safi-name> update outq neighbor <ip-addr> refresh update-parent";
    description
      "Specify a VRF.
       Clear Update information (Do NOT execute without cisco support)(cisco-support).
       Clear Update generation OutQ counters (Do NOT execute without cisco support)(cisco-support).
       Neighbor.
       Refresh OutQ.
       Update parents' OutQ counters too.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-vrf-afi-safi-update-outq-neighbor-ip-addr-refresh {
    csc:xr-task "bgp";
    csc:cli-command "clear bgp vrf <vrf-all> <afi-safi-name> update outq neighbor <ip-addr> refresh";
    description
      "Specify a VRF.
       Clear Update information (Do NOT execute without cisco support)(cisco-support).
       Clear Update generation OutQ counters (Do NOT execute without cisco support)(cisco-support).
       Neighbor.
       Refresh OutQ.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-vrf-afi-safi-update-outq-neighbor-ip-addr-update-parent {
    csc:xr-task "bgp";
    csc:cli-command "clear bgp vrf <vrf-all> <afi-safi-name> update outq neighbor <ip-addr> update-parent";
    description
      "Specify a VRF.
       Clear Update information (Do NOT execute without cisco support)(cisco-support).
       Clear Update generation OutQ counters (Do NOT execute without cisco support)(cisco-support).
       Neighbor.
       Update parents' OutQ counters too.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-vrf-afi-safi-update-outq-neighbor-ip-addr {
    csc:xr-task "bgp";
    csc:cli-command "clear bgp vrf <vrf-all> <afi-safi-name> update outq neighbor <ip-addr>";
    description
      "Specify a VRF.
       Clear Update information (Do NOT execute without cisco support)(cisco-support).
       Clear Update generation OutQ counters (Do NOT execute without cisco support)(cisco-support).
       Neighbor.
      ";
    input {
      leaf vrf-all {
        mandatory true;
        type vrf-name;
        description "VRF name or all";
      }
      leaf afi-safi-name {
        mandatory true;
        type afi-safi-type;
        description "AFI and SAFI";
      }
      leaf ip-addr {
        mandatory true;
        type inet:ip-address;
        description "Neighbor address";
      }
    }
  }

  rpc clear-bgp-vrf-afi-safi-update-outq-update-group-sub-group-update-parent {
    csc:xr-task "bgp";
    csc:cli-command "clear bgp vrf <vrf-all> <afi-safi-name> update outq update-group <update-group> sub-group <sub-group> update-parent";
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-vrf-afi-safi-update-outq-update-group-sub-group {
    csc:xr-task "bgp";
    csc:cli-command "clear bgp vrf <vrf-all> <afi-safi-name> update outq update-group <update-group> sub-group <sub-group>";
    description
      "Specify a VRF.
       Clear Update information (Do NOT execute without cisco support)(cisco-support).
       Clear Update generation OutQ counters (Do NOT execute without cisco support)(cisco-support).
       Update-group.
       Sub-group.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf sub-group {
        mandatory true;
        type update-group-id;
        description "Sub-group process ID <x.y>";
      }
    }
  }

  rpc clear-bgp-vrf-afi-safi-update-outq-update-group-sub-group-refresh-sub-group-update-parent {
    csc:xr-task "bgp";
    csc:cli-command "clear bgp vrf <vrf-all> <afi-safi-name> update outq update-group <update-group> sub-group <refresh-sub-group> update-parent";
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-vrf-afi-safi-update-outq-update-group-sub-group-refresh-sub-group {
    csc:xr-task "bgp";
    csc:cli-command "clear bgp vrf <vrf-all> <afi-safi-name> update outq update-group <update-group> sub-group <refresh-sub-group>";
    description
      "Specify a VRF.
       Clear Update information (Do NOT execute without cisco support)(cisco-support).
       Clear Update generation OutQ counters (Do NOT execute without cisco support)(cisco-support).
       Update-group.
       Sub-group.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-vrf-afi-safi-update-outq-update-group-update-parent {
    csc:xr-task "bgp";
    csc:cli-command "clear bgp vrf <vrf-all> <afi-safi-name> update outq update-group <update-group> update-parent";
    description
      "Specify a VRF.
       Clear Update information (Do NOT execute without cisco support)(cisco-support).
       Clear Update generation OutQ counters (Do NOT execute without cisco support)(cisco-support).
       Update-group.
       Update parents' OutQ counters too.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
    }
  }

  rpc clear-bgp-vrf-afi-safi-update-outq-update-group {
    csc:xr-task "bgp";
    csc:cli-command "clear bgp vrf <vrf-all> <afi-safi-name> update outq update-group <update-group>";
    description
      "Specify a VRF.
       Clear Update information (Do NOT execute without cisco support)(cisco-support).
       Clear Update generation OutQ counters (Do NOT execute without cisco support)(cisco-support).
       Update-group.
      ";
    input {
      leaf vrf-all {
        mandatory true;
        type vrf-name;
        description "VRF name or all";
      }
      leaf afi-safi-name {
        mandatory true;
        type afi-safi-type;
        description "AFI and SAFI";
      }
      leaf update-group {
        mandatory true;
        type update-group-id;
        description "Update-group process ID <x.y>";
      }
    }
  }

  rpc clear-bgp-vrf-afi-safi-dampening-ipv6-prefix {
    csc:xr-task "bgp";
    csc:cli-command "clear bgp vrf <vrf-all> <afi-safi-name> dampening <ipv6-prefix>";
    description
      "Specify a VRF.
       Clear route flap dampening information.
      ";
    input {
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 Network and mask or masklength to clear dampening information";
      }
    }
  }

  rpc clear-bgp-vrf-afi-safi-flap-statistics-ipv6-prefix {
    csc:xr-task "bgp";
    csc:cli-command "clear bgp vrf <vrf-all> <afi-safi-name> flap-statistics <ipv6-prefix>";
    description
      "Specify a VRF.
       Clear flap statistics.
      ";
    input {
      leaf vrf-all {
        mandatory true;
        type vrf-name;
        description "VRF name or all";
      }
      leaf afi-safi-name {
        mandatory true;
        type afi-safi-type;
        description "AFI and SAFI";
      }
      leaf ipv6-prefix {
        mandatory true;
        type inet:ipv6-prefix;
        description "IPv6 Network and mask or masklength to clear flap statistics";
      }
    }
  }

  rpc clear-bgp-vrf-nexthop-performance-statistics {
    csc:xr-task "bgp";
    csc:cli-command "clear bgp vrf <vrf-all> nexthop performance-statistics";
    description
      "Specify a VRF.
       Clear nexthop.
       Performance statistics information related to processing.
      ";
    input {
      leaf vrf-all {
        mandatory true;
        type vrf-name;
        description "VRF name or all";
      }
    }
  }

  rpc clear-bgp-vrf-nexthop-registration-ip-addr {
    csc:xr-task "bgp";
    csc:cli-command "clear bgp vrf <vrf-all> nexthop registration <ip-addr>";
    description
      "Specify a VRF.
       Clear nexthop.
       Registration with RIB and reregister.
      ";
    input {
      leaf vrf-all {
        mandatory true;
        type vrf-name;
        description "VRF name or all";
      }
      leaf ip-addr {
        mandatory true;
        type inet:ip-address;
        description "Nexthop address";
      }
    }
  }

  rpc clear-bgp-vrf-peer-drops-all {
    csc:xr-task "bgp";
    csc:cli-command "clear bgp vrf <vrf-all> peer-drops *";
    description
      "Specify a VRF.
       Clear established/dropped counters for a peer.
       All Neighbors.
      ";
    input {
      leaf vrf-all {
        mandatory true;
        type vrf-name;
        description "VRF name or all";
      }
    }
  }

  rpc clear-bgp-vrf-peer-drops-ip-addr {
    csc:xr-task "bgp";
    csc:cli-command "clear bgp vrf <vrf-all> peer-drops <ip-addr>";
    description
      "Specify a VRF.
       Clear established/dropped counters for a peer.
      ";
    input {
      leaf vrf-all {
        mandatory true;
        type vrf-name;
        description "VRF name or all";
      }
      leaf ip-addr {
        mandatory true;
        type inet:ip-address;
        description "BGP neighbor IP address";
      }
    }
  }

  rpc clear-bgp-vrf-performance-statistics {
    csc:xr-task "bgp";
    csc:cli-command "clear bgp vrf <vrf-all> performance-statistics";
    description
      "Specify a VRF.
       Clear performance statistics.
      ";
    input {
      leaf vrf-all {
        mandatory true;
        type vrf-name;
        description "VRF name or all";
      }
    }
  }

  rpc clear-bgp-vrf-shutdown {
    csc:xr-task "bgp";
    csc:cli-command "clear bgp vrf <vrf-all> shutdown";
    description
      "Specify a VRF.
       Clear all peers which were shut down due to low memory.
      ";
    input {
      leaf vrf-all {
        mandatory true;
        type vrf-name;
        description "VRF name or all";
      }
    }
  }

  rpc clear-bgp-vrf-update-outq-address-family-update-parent {
    csc:xr-task "bgp";
    csc:cli-command "clear bgp vrf <vrf-all> update outq address-family update-parent";
    description
      "Specify a VRF.
       Clear Update information (Do NOT execute without cisco support)(cisco-support).
       Clear Update generation OutQ counters (Do NOT execute without cisco support)(cisco-support).
       Address-family.
       Update parents' OutQ counters too.
      ";
    input {
      leaf vrf-all {
        mandatory true;
        type vrf-name;
        description "VRF name or all";
      }
    }
  }

  rpc clear-bgp-vrf-update-outq-address-family {
    csc:xr-task "bgp";
    csc:cli-command "clear bgp vrf <vrf-all> update outq address-family";
    description
      "Specify a VRF.
       Clear Update information (Do NOT execute without cisco support)(cisco-support).
       Clear Update generation OutQ counters (Do NOT execute without cisco support)(cisco-support).
       Address-family.
      ";
    input {
      leaf vrf-all {
        mandatory true;
        type vrf-name;
        description "VRF name or all";
      }
    }
  }

  rpc clear-bgp-vrf-update-outq-neighbor-ip-addr-refresh-update-parent {
    csc:xr-task "bgp";
    csc:cli-command "clear bgp vrf <vrf-all> update outq neighbor <ip-addr> refresh update-parent";
    description
      "Specify a VRF.
       Clear Update information (Do NOT execute without cisco support)(cisco-support).
       Clear Update generation OutQ counters (Do NOT execute without cisco support)(cisco-support).
       Neighbor.
       Refresh OutQ.
       Update parents' OutQ counters too.
      ";
    input {
      leaf vrf-all {
        mandatory true;
        type vrf-name;
        description "VRF name or all";
      }
      leaf ip-addr {
        mandatory true;
        type inet:ip-address;
        description "Neighbor address";
      }
    }
  }

  rpc clear-bgp-vrf-update-outq-neighbor-ip-addr-refresh {
    csc:xr-task "bgp";
    csc:cli-command "clear bgp vrf <vrf-all> update outq neighbor <ip-addr> refresh";
    description
      "Specify a VRF.
       Clear Update information (Do NOT execute without cisco support)(cisco-support).
       Clear Update generation OutQ counters (Do NOT execute without cisco support)(cisco-support).
       Neighbor.
       Refresh OutQ.
      ";
    input {
      leaf vrf-all {
        mandatory true;
        type vrf-name;
        description "VRF name or all";
      }
      leaf ip-addr {
        mandatory true;
        type inet:ip-address;
        description "Neighbor address";
      }
    }
  }

  rpc clear-bgp-vrf-update-outq-neighbor-ip-addr-update-parent {
    csc:xr-task "bgp";
    csc:cli-command "clear bgp vrf <vrf-all> update outq neighbor <ip-addr> update-parent";
    description
      "Specify a VRF.
       Clear Update information (Do NOT execute without cisco support)(cisco-support).
       Clear Update generation OutQ counters (Do NOT execute without cisco support)(cisco-support).
       Neighbor.
       Update parents' OutQ counters too.
      ";
    input {
      leaf vrf-all {
        mandatory true;
        type vrf-name;
        description "VRF name or all";
      }
      leaf ip-addr {
        mandatory true;
        type inet:ip-address;
        description "Neighbor address";
      }
    }
  }

  rpc clear-bgp-vrf-update-outq-neighbor-ip-addr {
    csc:xr-task "bgp";
    csc:cli-command "clear bgp vrf <vrf-all> update outq neighbor <ip-addr>";
    description
      "Specify a VRF.
       Clear Update information (Do NOT execute without cisco support)(cisco-support).
       Clear Update generation OutQ counters (Do NOT execute without cisco support)(cisco-support).
       Neighbor.
      ";
    input {
      leaf vrf-all {
        mandatory true;
        type vrf-name;
        description "VRF name or all";
      }
      leaf ip-addr {
        mandatory true;
        type inet:ip-address;
        description "Neighbor address";
      }
    }
  }

  rpc clear-bgp-vrf-update-outq-update-group-sub-group-update-parent {
    csc:xr-task "bgp";
    csc:cli-command "clear bgp vrf <vrf-all> update outq update-group <update-group> sub-group <sub-group> update-parent";
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        mandatory true;
        type vrf-name;
        description "VRF name or all";
      }
      leaf update-group {
        mandatory true;
        type update-group-id;
        description "Update-group process ID <x.y>";
      }
      leaf sub-group {
        mandatory true;
        type update-group-id;
        description "Sub-group process ID <x.y>";
      }
    }
  }

  rpc clear-bgp-vrf-update-outq-update-group-sub-group {
    csc:xr-task "bgp";
    csc:cli-command "clear bgp vrf <vrf-all> update outq update-group <update-group> sub-group <sub-group>";
    description
      "Specify a VRF.
       Clear Update information (Do NOT execute without cisco support)(cisco-support).
       Clear Update generation OutQ counters (Do NOT execute without cisco support)(cisco-support).
       Update-group.
       Sub-group.
      ";
    input {
      leaf vrf-all {
        mandatory true;
        type vrf-name;
        description "VRF name or all";
      }
      leaf update-group {
        mandatory true;
        type update-group-id;
        description "Update-group process ID <x.y>";
      }
      leaf sub-group {
        mandatory true;
        type update-group-id;
        description "Sub-group process ID <x.y>";
      }
    }
  }

  rpc clear-bgp-vrf-update-outq-update-group-sub-group-refresh-sub-group-update-parent {
    csc:xr-task "bgp";
    csc:cli-command "clear bgp vrf <vrf-all> update outq update-group <update-group> sub-group <refresh-sub-group> update-parent";
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        mandatory true;
        type vrf-name;
        description "VRF name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-vrf-update-outq-update-group-sub-group-refresh-sub-group {
    csc:xr-task "bgp";
    csc:cli-command "clear bgp vrf <vrf-all> update outq update-group <update-group> sub-group <refresh-sub-group>";
    description
      "Specify a VRF.
       Clear Update information (Do NOT execute without cisco support)(cisco-support).
       Clear Update generation OutQ counters (Do NOT execute without cisco support)(cisco-support).
       Update-group.
       Sub-group.
      ";
    input {
      leaf vrf-all {
        mandatory true;
        type vrf-name;
        description "VRF name or all";
      }
      leaf update-group {
        mandatory true;
        type update-group-id;
        description "Update-group process ID <x.y>";
      }
      leaf refresh-sub-group {
        mandatory true;
        type refresh-sub-group-id;
        description "Refresh Sub-group process ID <x.y:z>";
      }
    }
  }

  rpc clear-bgp-vrf-update-outq-update-group-update-parent {
    csc:xr-task "bgp";
    csc:cli-command "clear bgp vrf <vrf-all> update outq update-group <update-group> update-parent";
    description
      "Specify a VRF.
       Clear Update information (Do NOT execute without cisco support)(cisco-support).
       Clear Update generation OutQ counters (Do NOT execute without cisco support)(cisco-support).
       Update-group.
       Update parents' OutQ counters too.
      ";
    input {
      leaf vrf-all {
        mandatory true;
        type vrf-name;
        description "VRF name or all";
      }
      leaf update-group {
        mandatory true;
        type update-group-id;
        description "Update-group process ID <x.y>";
      }
    }
  }

  rpc clear-bgp-vrf-update-outq-update-group {
    csc:xr-task "bgp";
    csc:cli-command "clear bgp vrf <vrf-all> update outq update-group <update-group>";
    description
      "Specify a VRF.
       Clear Update information (Do NOT execute without cisco support)(cisco-support).
       Clear Update generation OutQ counters (Do NOT execute without cisco support)(cisco-support).
       Update-group.
      ";
    input {
      leaf vrf-all {
        mandatory true;
        type vrf-name;
        description "VRF name or all";
      }
      leaf update-group {
        mandatory true;
        type update-group-id;
        description "Update-group process ID <x.y>";
      }
    }
  }

}
