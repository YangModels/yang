module Cisco-IOS-XR-PRIVATE-ocacl-ipv4-oper {
  namespace "http://cisco.com/ns/yang/Cisco-IOS-XR-PRIVATE-ocacl-ipv4-oper";
  prefix private-ocacl-ipv4-oper;

  include Cisco-IOS-XR-PRIVATE-ocacl-ipv4-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR PRIVATE-ocacl-ipv4 package operational data.
     
     This module contains definitions
     for the following management objects:
       ocacl-ipv4: This module defines configuration and operational
         state data for network access control lists (i
     
     Copyright (c) 2013-2018 by Cisco Systems, Inc.
     All rights reserved.";

  revision 2015-11-09 {
    description
      "IOS XR 6.0 revision.";
  }

  container ocacl-ipv4 {
    config false;
    description
      "This module defines configuration and operational
       state data for network access control lists (i";
    container acl {
      description
        "Top level enclosing container for ACL model
         config and operational state data";
      container acl-sets {
        description
          "List of ACL sets, each comprising of a list of
           ACL entries";
        list acl-set {
          key "name type";
          description
            "List of ACL sets, each comprising of a list of
             ACL entries";
          container acl-entries {
            description
              "List of ACL entries comprising an ACL set";
            list acl-entry {
              key "sequence-id";
              description
                "List of ACL entries comprising an ACL set";
              leaf sequence-id {
                type uint32;
                description
                  "references the list key";
              }
              uses OVERLAY-OCACL-IPV4-ACL-ENTRY;
            }
          }
          container acl-sets-state {
            description
              "Access list state information";
            uses OVERLAY-OCACL-IPV4-ACL-SET-STATE;
          }
          leaf name {
            type string;
            description
              "Reference to the name list key";
          }
          leaf type {
            type string;
            description
              "Reference to the type list key";
          }
        }
      }
      container state {
        description
          "Global operational state data for ACLs";
        uses OVERLAY-OCACL-IPV4-STATE;
      }
    }
  }
}
