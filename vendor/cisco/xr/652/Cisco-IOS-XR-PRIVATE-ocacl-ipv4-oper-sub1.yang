submodule Cisco-IOS-XR-PRIVATE-ocacl-ipv4-oper-sub1 {
  belongs-to Cisco-IOS-XR-PRIVATE-ocacl-ipv4-oper {
    prefix Cisco-IOS-XR-PRIVATE-ocacl-ipv4-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR PRIVATE-ocacl-ipv4 package operational data.
     
     Copyright (c) 2013-2018 by Cisco Systems, Inc.
     All rights reserved.";

  revision 2015-11-09 {
    description
      "IOS XR 6.0 revision.";
  }

  typedef Yang2bag-string {
    type string;
    description
      "Yang2bag string";
  }

  grouping OVERLAY-OCACL-IPV4-STATE {
    description
      "Global operational state data for ACLs";
    leaf counter-capability {
      type Yang2bag-string;
      description
        "System reported indication of how ACL counters
         are reported by the target";
    }
  }

  grouping OVERLAY-OCACL-IPV4-ACL-SET-STATE {
    description
      "Access list state information";
    leaf name {
      type Yang2bag-string;
      description
        "The name of the access-list set";
    }
    leaf type {
      type Yang2bag-string;
      description
        "The type determines the fields allowed in the
         ACL entries belonging to the ACL set (e";
    }
  }

  grouping ACTIONS-STATE {
    description
      "ACTIONS STATE";
    leaf forwarding-action {
      type Yang2bag-string;
      description
        "Specifies the forwarding action";
    }
    leaf log-action {
      type Yang2bag-string;
      description
        "Specifies the log action and destination for
         matched packets";
    }
  }

  grouping ACTIONS {
    description
      "ACTIONS";
    container state {
      description
        "State information for ACL actions";
      uses ACTIONS-STATE;
    }
  }

  grouping TRANSPORT-STATE {
    description
      "TRANSPORT STATE";
    leaf source-port {
      type Yang2bag-string;
      description
        "Source port or range";
    }
    leaf destination-port {
      type Yang2bag-string;
      description
        "Destination port or range";
    }
    leaf-list tcp-flag {
      type Yang2bag-string;
      description
        "List of TCP flags to match";
    }
  }

  grouping TRANSPORT {
    description
      "TRANSPORT";
    container state {
      description
        "State data";
      uses TRANSPORT-STATE;
    }
  }

  grouping IPV4-STATE {
    description
      "IPV4 STATE";
    leaf source-address {
      type Yang2bag-string;
      description
        "Source IPv4 address prefix";
    }
    leaf destination-address {
      type Yang2bag-string;
      description
        "Destination IPv4 address prefix";
    }
    leaf dscp {
      type uint8;
      description
        "Value of diffserv codepoint";
    }
    leaf protocol {
      type Yang2bag-string;
      description
        "The protocol carried in the IP packet, expressed
         either as its IP protocol number, or by a
         defined identity";
    }
    leaf hop-limit {
      type uint8;
      description
        "The IP packet's hop limit -- known as TTL (in
         hops) in IPv4 packets, and hop limit in IPv6";
    }
  }

  grouping IPV4 {
    description
      "IPV4";
    container state {
      description
        "State information for IPv4 match fields";
      uses IPV4-STATE;
    }
  }

  grouping STATE {
    description
      "STATE";
    leaf sequence-id {
      type uint32;
      description
        "The sequence id determines the order in which
         ACL entries are applied";
    }
    leaf matched-packets {
      type uint64;
      description
        "Count of the number of packets matching the
         current ACL entry";
    }
    leaf matched-octets {
      type uint64;
      units "byte";
      description
        "Count of the number of octets (bytes) matching
         the current ACL entry";
    }
  }

  grouping OVERLAY-OCACL-IPV4-ACL-ENTRY {
    description
      "List of ACL entries comprising an ACL set";
    container state {
      description
        "State information for ACL entries";
      uses STATE;
    }
    container ipv4 {
      description
        "Top level container for IPv4 match field data";
      uses IPV4;
    }
    container transport {
      description
        "Transport fields container";
      uses TRANSPORT;
    }
    container actions {
      description
        "Enclosing container for list of ACL actions
         associated with an entry";
      uses ACTIONS;
    }
  }
}
