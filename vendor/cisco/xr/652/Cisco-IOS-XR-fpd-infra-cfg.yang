module Cisco-IOS-XR-fpd-infra-cfg {
  namespace "http://cisco.com/ns/yang/Cisco-IOS-XR-fpd-infra-cfg";
  prefix fpd-infra-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fpd-infra package configuration.
     
     This module contains definitions
     for the following management objects:
       fpd: Configuration for fpd auto-upgrade enable/disable
     
     Copyright (c) 2013-2018 by Cisco Systems, Inc.
     All rights reserved.";

  revision 2015-11-09 {
    description
      "IOS XR 6.0 revision.";
  }

  typedef Auto-reload {
    type enumeration {
      enum "disable" {
        value 0;
        description
          "fpd auto-reload disable";
      }
      enum "enable" {
        value 1;
        description
          "fpd auto-reload enable";
      }
    }
    description
      "Auto reload";
  }

  typedef Auto-upgrade {
    type enumeration {
      enum "disable" {
        value 0;
        description
          "fpd auto-upgrade disable";
      }
      enum "enable" {
        value 1;
        description
          "fpd auto-upgrade enable";
      }
    }
    description
      "Auto upgrade";
  }

  container fpd {
    description
      "Configuration for fpd auto-upgrade enable/disable";
    leaf auto-reload {
      type Auto-reload;
      description
        "Variable for fpd auto-reload enable/disable";
    }
    leaf auto-upgrade {
      type Auto-upgrade;
      description
        "Variable for fpd auto-upgrade enable/disable";
    }
  }
}
