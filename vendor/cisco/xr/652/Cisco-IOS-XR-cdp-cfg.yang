module Cisco-IOS-XR-cdp-cfg {
  namespace "http://cisco.com/ns/yang/Cisco-IOS-XR-cdp-cfg";
  prefix cdp-cfg;

  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cdp package configuration.
     
     This module contains definitions
     for the following management objects:
       cdp: Global CDP configuration data
     
     This YANG module augments the
       Cisco-IOS-XR-ifmgr-cfg
     module with configuration data.
     
     Copyright (c) 2013-2018 by Cisco Systems, Inc.
     All rights reserved.";

  revision 2017-08-16 {
    description
      "Descriptions updated.";
  }
  revision 2015-01-07 {
    description
      "IOS XR 5.3.1 revision.";
  }

  augment "/a1:interface-configurations/a1:interface-configuration" {
    description
      "This augment extends the configuration data of
       'Cisco-IOS-XR-ifmgr-cfg'";
    container cdp {
      description
        "Interface specific CDP configuration";
      leaf enable {
        type empty;
        description
          "Enable or disable CDP on an interface";
      }
    }
  }
  container cdp {
    description
      "Global CDP configuration data";
    leaf timer {
      type uint32 {
        range "5..254";
      }
      default "60";
      description
        "Specify the rate at which CDP packets are sent";
    }
    leaf advertise-v1-only {
      type empty;
      description
        "Enable CDPv1 only advertisements";
    }
    leaf enable {
      type boolean;
      default "true";
      description
        "Enable or disable CDP globally";
    }
    leaf hold-time {
      type uint32 {
        range "10..255";
      }
      default "180";
      description
        "Length of time (in sec) that the receiver must
         keep a CDP packet";
    }
    leaf log-adjacency {
      type empty;
      description
        "Enable logging of adjacency changes";
    }
  }
}
