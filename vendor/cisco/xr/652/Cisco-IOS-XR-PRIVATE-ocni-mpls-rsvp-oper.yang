module Cisco-IOS-XR-PRIVATE-ocni-mpls-rsvp-oper {
  namespace "http://cisco.com/ns/yang/Cisco-IOS-XR-PRIVATE-ocni-mpls-rsvp-oper";
  prefix private-ocni-mpls-rsvp-oper;

  include Cisco-IOS-XR-PRIVATE-ocni-mpls-rsvp-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR PRIVATE-ocni-mpls-rsvp package operational data.
     
     This module contains definitions
     for the following management objects:
       ocni-mpls-rsvp: An OpenConfig description of a
         network-instance
     
     Copyright (c) 2013-2018 by Cisco Systems, Inc.
     All rights reserved.";

  revision 2015-11-09 {
    description
      "IOS XR 6.0 revision.";
  }

  typedef Oc-netinst-integer64 {
    type string;
    description
      "Oc netinst integer64";
  }

  container ocni-mpls-rsvp {
    config false;
    description
      "An OpenConfig description of a network-instance";
    container network-instances {
      description
        "Network instances configured on the local system";
      list network-instance {
        key "name";
        description
          "Network instances configured on the local
           system";
        container mpls {
          description
            "Anchor point for mpls configuration and
             operational data";
          container signaling-protocols {
            description
              "top-level signaling protocol configuration";
            container rsvp-te {
              description
                "RSVP-TE global signaling protocol
                 configuration";
              container global {
                description
                  "Platform wide RSVP configuration and state";
                uses OVERLAY-OCNI-MPLS-RSVP-GLOBAL;
              }
              container sessions {
                description
                  "List of RSVP sessions";
                list session {
                  key "local-index";
                  description
                    "List of RSVP sessions";
                  container state {
                    description
                      "Operational state parameters relating to
                       the RSVP session";
                    uses OVERLAY-OCNI-MPLS-RSVP-STATE;
                  }
                  container record-route-objects {
                    description
                      "Read-only list of record route objects
                       associated with the traffic engineered
                       tunnel";
                    list record-route-object {
                      key "index";
                      description
                        "Read-only list of record route objects
                         associated with the traffic engineered
                         tunnel";
                      leaf index {
                        type uint32;
                        description
                          "Reference to the index of the record
                           route object";
                      }
                      uses OVERLAY-OCNI-MPLS-RSVP-RECORD-ROUTE-OBJECT;
                    }
                  }
                  leaf local-index {
                    type Oc-netinst-integer64;
                    description
                      "Reference to the local index for the RSVP
                       session";
                  }
                }
              }
              container interface-attributes {
                description
                  "list of per-interface RSVP configurations";
                list interface-attribute {
                  key "interface-id";
                  description
                    "list of per-interface RSVP configurations";
                  leaf interface-id {
                    type string;
                    description
                      "reference to the interface-id data";
                  }
                  uses OVERLAY-OCNI-MPLS-RSVP-INTERFACE;
                }
              }
              container neighbors {
                description
                  "List of RSVP neighbors of the local system";
                list neighbor {
                  key "address";
                  description
                    "List of RSVP neighbors of the local system";
                  leaf address {
                    type string;
                    description
                      "Reference to the address of the RSVP
                       neighbor";
                  }
                  uses OVERLAY-OCNI-MPLS-RSVP-NEIGHBOR;
                }
              }
            }
          }
        }
        leaf name {
          type string;
          description
            "A unique name identifying the network instance";
        }
      }
    }
  }
}
