module Cisco-IOS-XR-ip-iarm-datatypes {
  namespace "http://cisco.com/ns/yang/Cisco-IOS-XR-ip-iarm-datatypes";
  prefix ip-iarm-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2018 by Cisco Systems, Inc.
     All rights reserved.";

  revision 2015-01-07 {
    description
      "IOS XR 5.3.1 revision.";
  }

  typedef Ipv6arm-prefix-length {
    type uint32 {
      range "0..128";
    }
    description
      "Ipv6arm prefix length";
  }
}
