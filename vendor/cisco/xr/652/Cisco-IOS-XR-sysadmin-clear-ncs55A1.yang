module Cisco-IOS-XR-sysadmin-clear-ncs55A1 {
  namespace "http://www.cisco.com/ns/yang/Cisco-IOS-XR-sysadmin-clear-NCS55A1";
  prefix calvados_clear;
  import tailf-common {
    prefix tailf;
  }
  import Cisco-IOS-XR-sysadmin-asic-errors-ael {
    prefix aelclear;
  }
  import Cisco-IOS-XR-sysadmin-fabric-ncs5502 {
    prefix fabric;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

This module defines the top level container for
all 'clear' commands for Sysadmin.

Copyright(c) 2015-2016 by Cisco Systems, Inc.
All rights reserved.

    Copyright (c) 2012-2018 by Cisco Systems, Inc.
     All rights reserved.";
  revision 2017-10-11 {
    description
      "Changed the namespace to unique namespace per unique model";
  }


  grouping asic_clear {
    tailf:action "statistics" {
    }
  }
  container clear {
    container controller {
      uses fabric:fabric_clear;
    }
    uses aelclear:ael-clear-asic-errors-grp;
  }
}
