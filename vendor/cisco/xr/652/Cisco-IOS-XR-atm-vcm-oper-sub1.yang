submodule Cisco-IOS-XR-atm-vcm-oper-sub1 {
  belongs-to Cisco-IOS-XR-atm-vcm-oper {
    prefix Cisco-IOS-XR-atm-vcm-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR atm-vcm package operational data.
     
     Copyright (c) 2013-2018 by Cisco Systems, Inc.
     All rights reserved.";

  revision 2017-09-07 {
    description
      "Fixed type translation error.";
  }
  revision 2015-11-09 {
    description
      "IOS XR 6.0 revision.";
  }

  typedef Vp-state {
    type enumeration {
      enum "vp-initialized" {
        value 0;
        description
          "VP-Tunnel State: Initialized";
      }
      enum "vp-modifying" {
        value 1;
        description
          "VP-Tunnel State: Modifying";
      }
      enum "vp-ready" {
        value 2;
        description
          "VP-Tunnel State: Ready";
      }
      enum "vp-mgd-down" {
        value 3;
        description
          "VP-Tunnel State: Managed Down";
      }
      enum "vp-deleting" {
        value 4;
        description
          "VP-Tunnel State: Deleting";
      }
      enum "vp-deleted" {
        value 5;
        description
          "VP-Tunnel State: Deleted";
      }
      enum "vp-state-unknown" {
        value 6;
        description
          "VP-Tunnel State: Unknown";
      }
    }
    description
      "VP-Tunnel State";
  }

  typedef Vp-traf-shaping {
    type enumeration {
      enum "vp-cbr" {
        value 1;
        description
          "VP-Tunnel traffic shaping type CBR";
      }
      enum "vp-vbr-nrt" {
        value 2;
        description
          "VP-Tunnel traffic shaping type VBR-NR";
      }
      enum "vp-vbr-rt" {
        value 3;
        description
          "VP-Tunnel traffic shaping type VBR-RT";
      }
      enum "vp-abr" {
        value 4;
        description
          "VP-Tunnel traffic shaping type ABR";
      }
      enum "vp-ubr-plus" {
        value 5;
        description
          "VP-Tunnel traffic shaping type UBR+";
      }
      enum "vp-ubr" {
        value 6;
        description
          "VP-Tunnel traffic shaping type UBR";
      }
      enum "vp-traf-shaping-unknown" {
        value 7;
        description
          "VP-Tunnel traffic shaping type Unknown
           (invalid)";
      }
    }
    description
      "VP-Tunnel traffic shaping type";
  }

  grouping ATM-VCM-VP {
    description
      "ATM VP-Tunnel data";
    leaf main-interface {
      type xr:Interface-name;
      description
        "Main Interface handle";
    }
    leaf vp-interface {
      type xr:Interface-name;
      description
        "VP Interfcace handle";
    }
    leaf vpi-xr {
      type uint16;
      description
        "VP-Tunnel VPI value";
    }
    leaf shape {
      type Vp-traf-shaping;
      description
        "ATM VP traffic shaping type";
    }
    leaf peak-cell-rate {
      type uint32;
      units "kbit/s";
      description
        "Peak cell rate in Kbps";
    }
    leaf sustained-cell-rate {
      type uint32;
      units "kbit/s";
      description
        "Sustained cell rate in Kbps";
    }
    leaf burst-rate {
      type uint32;
      description
        "Burst size in cells";
    }
    leaf f4oam-enabled {
      type boolean;
      description
        "F4OAM Enabled flag";
    }
    leaf data-vc-count {
      type uint32;
      description
        "Number of Data PVCs under this VP-tunnel";
    }
    leaf oper-status {
      type boolean;
      description
        "TRUE value indicates that the VP is
         operationally UP";
    }
    leaf amin-status {
      type boolean;
      description
        "TRUE value indicates that the VP is
         administratively UP";
    }
    leaf internal-state {
      type Vp-state;
      description
        "Internal state";
    }
    leaf last-vp-state-change-time {
      type uint32;
      description
        "Time when VP-Tunnel state was last changed";
    }
  }
}
