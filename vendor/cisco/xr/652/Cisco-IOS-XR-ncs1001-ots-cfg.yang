module Cisco-IOS-XR-ncs1001-ots-cfg {
  namespace "http://cisco.com/ns/yang/Cisco-IOS-XR-ncs1001-ots-cfg";
  prefix ncs1001-ots-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots package configuration.
     
     This module contains definitions
     for the following management objects:
       hardware-module: NCS1k HW module config
     
     Copyright (c) 2013-2018 by Cisco Systems, Inc.
     All rights reserved.";

  revision 2018-03-20 {
    description
      "added Otdr management.";
  }
  revision 2015-11-09 {
    description
      "IOS XR 6.0 revision.";
  }

  typedef Ots-amplifier-node {
    type enumeration {
      enum "term" {
        value 0;
        description
          "Nodetype TERM";
      }
      enum "ila" {
        value 1;
        description
          "Nodetype InLine Amplifier";
      }
      enum "roadm" {
        value 2;
        description
          "Nodetype ROADM";
      }
    }
    description
      "Ots amplifier node";
  }

  typedef Ots-amplifier-grid-mode {
    type enumeration {
      enum "100g-hz" {
        value 0;
        description
          "100GHz mode";
      }
      enum "50g-hz" {
        value 1;
        description
          "50GHz mode";
      }
      enum "gr-idle-ss" {
        value 2;
        description
          "Gridless mode";
      }
    }
    description
      "Ots amplifier grid mode";
  }

  typedef Ots-otdr-direction {
    type enumeration {
      enum "tx" {
        value 0;
        description
          "Tx";
      }
      enum "rx" {
        value 1;
        description
          "Rx";
      }
    }
    description
      "Ots otdr direction";
  }

  typedef Ots-psm-lockout-from {
    type enumeration {
      enum "working" {
        value 1;
        description
          "Working port";
      }
      enum "protected" {
        value 2;
        description
          "Protected port";
      }
    }
    description
      "Ots psm lockout from";
  }

  container hardware-module {
    description
      "NCS1k HW module config";
    list node {
      key "location";
      description
        "Node";
      leaf location {
        type xr:Cisco-ios-xr-string;
        description
          "Fully qualified line card specification";
      }
      list slot {
        key "slot-id";
        description
          "Slot Id";
        container otdrs {
          description
            "OTDR Configs";
          list otdr {
            key "port direction";
            description
              "Otdr Id";
            container mode-auto {
              description
                "Mode Auto";
              leaf loss-sensitivity {
                type uint32 {
                  range "4..50";
                }
                description
                  "Otdr Loss Sensitivity, supported values [4
                   ,50] in units of 0.1dB";
              }
              leaf reflection-sensitivity {
                type int32 {
                  range "-400..-140";
                }
                description
                  "Otdr Reflection Sensitivity, supported
                   values [-400,-140] in units of 0.1dB";
              }
            }
            container mode-expert {
              description
                "Mode Expert";
              leaf fiber-resolution {
                type uint32 {
                  range "0..100";
                }
                description
                  "Fiber Resolution in meters, supported
                   values [0,100]";
              }
              leaf capture-length {
                type uint32 {
                  range "1..150";
                }
                description
                  "Capture Length in Km, supported values [1
                   ,150]";
              }
              leaf pulse-width {
                type uint32 {
                  range "8..100000";
                }
                units "nanosecond";
                description
                  "Pulse Width in nanoseconds, supported
                   values [8,100000]";
              }
              leaf measure-time {
                type uint32 {
                  range "1..360";
                }
                units "second";
                description
                  "Measure time in seconds, supported values
                   [1,360]";
              }
              leaf loss-sensitivity {
                type uint32 {
                  range "4..50";
                }
                description
                  "Otdr Loss Sensitivity, supported values [4
                   ,50] in units of 0.1dB";
              }
              leaf capture-offset {
                type uint32 {
                  range "0..150";
                }
                description
                  "Capture Offset in Km, supported values [0
                   ,150]";
              }
              leaf span-length {
                type uint32 {
                  range "1..150";
                }
                description
                  "Span Length in Km, supported values [1,150]";
              }
              leaf reflection-sensitivity {
                type int32 {
                  range "-400..-140";
                }
                description
                  "Otdr Reflection Sensitivity, supported
                   values [-400,-140] in units of 0.1dB";
              }
            }
            leaf total-loss {
              type uint32 {
                range "0..500";
              }
              description
                "Otdr Insertion Loss, supported values [0
                 ,500] in units of 0.1dB";
            }
            leaf port {
              type uint32 {
                range "1..2";
              }
              description
                "Port Id";
            }
            leaf direction {
              type Ots-otdr-direction;
              description
                "Direction Id";
            }
          }
        }
        container otdr-thresholds {
          description
            "Otdr Threshold";
          list otdr-threshold {
            key "port";
            description
              "Otdr Threshold";
            leaf loss-abs-threshold {
              type uint32 {
                range "1..300";
              }
              description
                "Absolute Loss Threshold, supported values [1
                 ,300] in units of 0.1dB";
            }
            leaf reflection-abs-threshold {
              type int32 {
                range "-500..0";
              }
              description
                "Absolute Reflection Threshold, supported
                 values [-500,0] in units of 0.1dB";
            }
            leaf orl-abs-threshold {
              type uint32 {
                range "140..400";
              }
              description
                "Absolute Orl Threshold, supported values
                 [140,400] in units of 0.1dB";
            }
            leaf port {
              type uint32;
              description
                "Port Id";
            }
          }
        }
        container amplifier {
          description
            "Amplifier Configs";
          container remote-node {
            description
              "RemoteNode Configuration";
            leaf local-ip-address {
              type inet:ip-address-no-zone;
              description
                "IP address of local host";
            }
            leaf remote-ip-address {
              type inet:ip-address-no-zone;
              description
                "IP address of remote host";
            }
            leaf remote-slot-id {
              type uint32 {
                range "1..3";
              }
              description
                "Set remote Slot";
            }
          }
          leaf node-type {
            type Ots-amplifier-node;
            description
              "Define the type of node in which the
               amplifier is set to work";
          }
          leaf grid-mode {
            type Ots-amplifier-grid-mode;
            description
              "Define the working mode for the optical
               module";
          }
          leaf udc-vlan {
            type uint32 {
              range "2..4080";
            }
            description
              "Define the VLAN ID in range <2-4080>";
          }
          leaf span-loss {
            type boolean;
            description
              "SpanLoss configuration";
          }
        }
        container psm {
          description
            "PSM Configs";
          leaf mono-dir {
            type boolean;
            description
              "Psm Uni directional configuration";
          }
          leaf auto-threshold {
            type boolean;
            description
              "Psm Automatic Threshold Setting";
          }
          leaf path-protection {
            type boolean;
            description
              "Psm path protection configuration";
          }
          leaf section-protection {
            type boolean;
            description
              "Psm section protection configuration";
          }
          leaf lockout-from {
            type Ots-psm-lockout-from;
            description
              "Exclude selected port from protection";
          }
        }
        leaf slot-id {
          type uint32 {
            range "1..3";
          }
          description
            "Set Slot";
        }
      }
    }
  }
}
