module Cisco-IOS-XR-fretta-bcm-dpa-resources-oper {
  namespace "http://cisco.com/ns/yang/Cisco-IOS-XR-fretta-bcm-dpa-resources-oper";
  prefix fretta-bcm-dpa-resources-oper;

  import Cisco-IOS-XR-types {
    prefix xr;
  }
  include Cisco-IOS-XR-fretta-bcm-dpa-resources-oper-sub2 {
    revision-date 2015-11-09;
  }
  include Cisco-IOS-XR-fretta-bcm-dpa-resources-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-bcm-dpa-resources package operational data.
     
     This module contains definitions
     for the following management objects:
       dpa: Stats Data
     
     Copyright (c) 2013-2018 by Cisco Systems, Inc.
     All rights reserved.";

  revision 2015-11-09 {
    description
      "IOS XR 6.0 revision.";
  }

  typedef Max-trap-s {
    type uint32 {
      range "0..4294967295";
    }
    description
      "Max trap s";
  }

  typedef Max-lc-intf-hand-les {
    type uint32 {
      range "0..4294967295";
    }
    description
      "Max lc intf hand les";
  }

  typedef Dpa-table {
    type enumeration {
      enum "test-if" {
        value 0;
        description
          "test if";
      }
      enum "test-nhg" {
        value 1;
        description
          "test nhg";
      }
      enum "test-nh" {
        value 2;
        description
          "test nh";
      }
      enum "test-rt" {
        value 3;
        description
          "test rt";
      }
      enum "test-dynhg" {
        value 4;
        description
          "testdynhg";
      }
      enum "test-ip-punt-policy" {
        value 5;
        description
          "test ippuntpolicy";
      }
      enum "test-punt" {
        value 6;
        description
          "test punt";
      }
      enum "test-punt-policy-stats" {
        value 7;
        description
          "testpuntpolicystats";
      }
      enum "test-async-update" {
        value 8;
        description
          "testasyncupdate";
      }
      enum "test-ddel-q" {
        value 9;
        description
          "test ddel q";
      }
      enum "bdbvi" {
        value 10;
        description
          "bdbvi";
      }
      enum "sys" {
        value 11;
        description
          "sys";
      }
      enum "npu" {
        value 12;
        description
          "npu";
      }
      enum "npuhwid" {
        value 13;
        description
          "npuhwid";
      }
      enum "l1-port" {
        value 14;
        description
          "l1port";
      }
      enum "l2-port" {
        value 15;
        description
          "l2port";
      }
      enum "l2intf" {
        value 16;
        description
          "l2intf";
      }
      enum "mplspwe-port-o-list" {
        value 17;
        description
          "mplspweport olist";
      }
      enum "mplspwe-port" {
        value 18;
        description
          "mplspweport";
      }
      enum "mhpwe-port" {
        value 19;
        description
          "mhpweport";
      }
      enum "l2xc" {
        value 20;
        description
          "l2xc";
      }
      enum "l2vpnstats" {
        value 21;
        description
          "l2vpnstats";
      }
      enum "l1-ports-tats" {
        value 22;
        description
          "l1portstats";
      }
      enum "l3intf" {
        value 23;
        description
          "l3intf";
      }
      enum "l3intfrxstats" {
        value 24;
        description
          "l3intfrxstats";
      }
      enum "ip-route" {
        value 25;
        description
          "iproute";
      }
      enum "ip6-route" {
        value 26;
        description
          "ip6route";
      }
      enum "punt-policy-stats" {
        value 27;
        description
          "puntpolicystats";
      }
      enum "tep" {
        value 28;
        description
          "tep";
      }
      enum "ip-punt-policy" {
        value 29;
        description
          "ippuntpolicy";
      }
      enum "ip6-punt-policy" {
        value 30;
        description
          "ip6puntpolicy";
      }
      enum "isis-punt-policy" {
        value 31;
        description
          "isispuntpolicy";
      }
      enum "ipnh-group" {
        value 32;
        description
          "ipnhgroup";
      }
      enum "ip6nh-group" {
        value 33;
        description
          "ip6nhgroup";
      }
      enum "ipnh" {
        value 34;
        description
          "ipnh";
      }
      enum "ip6nh" {
        value 35;
        description
          "ip6nh";
      }
      enum "ipvrf" {
        value 36;
        description
          "ipvrf";
      }
      enum "mplsnh" {
        value 37;
        description
          "mplsnh";
      }
      enum "mpls-label" {
        value 38;
        description
          "mplslabel";
      }
      enum "dnx-trap" {
        value 39;
        description
          "dnx trap";
      }
      enum "punt" {
        value 40;
        description
          "punt";
      }
      enum "punt-police-r" {
        value 41;
        description
          "puntpolicer";
      }
      enum "punt-lpts-police-r" {
        value 42;
        description
          "puntlptspolicer";
      }
      enum "punt-stats" {
        value 43;
        description
          "puntstats";
      }
      enum "tm-port" {
        value 44;
        description
          "tmport";
      }
      enum "span-session" {
        value 45;
        description
          "spansession";
      }
      enum "police-rstats" {
        value 46;
        description
          "policerstats";
      }
      enum "tm-ports-tats" {
        value 47;
        description
          "tmportstats";
      }
      enum "l3intftxstats" {
        value 48;
        description
          "l3intftxstats";
      }
      enum "mplstetxstats" {
        value 49;
        description
          "mplstetxstats";
      }
      enum "mplslblstats" {
        value 50;
        description
          "mplslblstats";
      }
      enum "police-r" {
        value 51;
        description
          "policer";
      }
      enum "l2intfrxstats" {
        value 52;
        description
          "l2intfrxstats";
      }
      enum "l2intftxstats" {
        value 53;
        description
          "l2intftxstats";
      }
      enum "dnx-pbr-tt-ipv4" {
        value 54;
        description
          "dnx pbr tt ipv4";
      }
      enum "dnx-pbr-tt-ipv6" {
        value 55;
        description
          "dnx pbr tt ipv6";
      }
      enum "bfdhwoff" {
        value 56;
        description
          "bfdhwoff";
      }
      enum "global" {
        value 57;
        description
          "global";
      }
      enum "lag-port" {
        value 58;
        description
          "lagport";
      }
      enum "qos-profile" {
        value 59;
        description
          "qosprofile";
      }
      enum "tmrate-profile" {
        value 60;
        description
          "tmrateprofile";
      }
      enum "dnx-port-range" {
        value 61;
        description
          "dnx port range";
      }
      enum "ipacl" {
        value 62;
        description
          "ipacl";
      }
      enum "ip6acl" {
        value 63;
        description
          "ip6acl";
      }
      enum "sched-tree" {
        value 64;
        description
          "schedtree";
      }
      enum "tmcos" {
        value 65;
        description
          "tmcos";
      }
      enum "statsagg" {
        value 66;
        description
          "statsagg";
      }
      enum "nhprotect" {
        value 67;
        description
          "nhprotect";
      }
      enum "sampler" {
        value 68;
        description
          "sampler";
      }
      enum "l2qos" {
        value 69;
        description
          "l2qos";
      }
      enum "peer-qos" {
        value 70;
        description
          "peerqos";
      }
      enum "ipqos" {
        value 71;
        description
          "ipqos";
      }
      enum "ip6qos" {
        value 72;
        description
          "ip6qos";
      }
      enum "mplsqos" {
        value 73;
        description
          "mplsqos";
      }
      enum "qosid" {
        value 74;
        description
          "qosid";
      }
      enum "extlif" {
        value 75;
        description
          "extlif";
      }
      enum "elif" {
        value 76;
        description
          "elif";
      }
      enum "ingaclstats" {
        value 77;
        description
          "ingaclstats";
      }
      enum "egraclstats" {
        value 78;
        description
          "egraclstats";
      }
      enum "edpl" {
        value 79;
        description
          "edpl";
      }
      enum "erp" {
        value 80;
        description
          "erp";
      }
      enum "cfmmaid" {
        value 81;
        description
          "cfmmaid";
      }
      enum "cfmdefmps" {
        value 82;
        description
          "cfmdefmps";
      }
      enum "cfmofflmep" {
        value 83;
        description
          "cfmofflmep";
      }
      enum "cfmoffrmep" {
        value 84;
        description
          "cfmoffrmep";
      }
      enum "cfmnonoff" {
        value 85;
        description
          "cfmnonoff";
      }
      enum "cfmhwoffrxstats" {
        value 86;
        description
          "cfmhwoffrxstats";
      }
      enum "ipmc-route" {
        value 87;
        description
          "ipmcroute";
      }
      enum "l2ipmc-route" {
        value 88;
        description
          "l2ipmcroute";
      }
      enum "ipmco-list" {
        value 89;
        description
          "ipmcolist";
      }
      enum "l2mco-list" {
        value 90;
        description
          "l2mcolist";
      }
      enum "ipmc-merge-do-list" {
        value 91;
        description
          "ipmcmergedolist";
      }
      enum "sgfgid-list" {
        value 92;
        description
          "sgfgidlist";
      }
      enum "meshmc" {
        value 93;
        description
          "meshmc";
      }
      enum "l2-bridge" {
        value 94;
        description
          "l2bridge";
      }
      enum "l2-bridge-port" {
        value 95;
        description
          "l2bridgeport";
      }
      enum "l2-bridge-vni" {
        value 96;
        description
          "l2bridgevni";
      }
      enum "l2-bridge-vnidecap" {
        value 97;
        description
          "l2bridgevnidecap";
      }
      enum "l2-bridge-mac" {
        value 98;
        description
          "l2bridgemac";
      }
      enum "l2brmac" {
        value 99;
        description
          "l2brmac";
      }
      enum "ip-tunnel-decap" {
        value 100;
        description
          "iptunneldecap";
      }
      enum "l2vlan-range" {
        value 101;
        description
          "l2vlanrange";
      }
      enum "ip-tunnel-encap" {
        value 102;
        description
          "iptunnelencap";
      }
      enum "rawget" {
        value 103;
        description
          "rawget";
      }
      enum "ip6mc-route" {
        value 104;
        description
          "ip6mcroute";
      }
      enum "l2evpnact-remote-peer-id" {
        value 105;
        description
          "l2evpnactremotepeerid";
      }
      enum "l2evpnact-local-shl" {
        value 106;
        description
          "l2evpnactlocalshl";
      }
      enum "l2evpnact-remote-shl" {
        value 107;
        description
          "l2evpnactremoteshl";
      }
      enum "evpn-iml-range" {
        value 108;
        description
          "evpn imlrange";
      }
      enum "l2-bridge-o-list" {
        value 109;
        description
          "l2bridgeolist";
      }
      enum "l2-bridge-vnio-list" {
        value 110;
        description
          "l2bridgevniolist";
      }
      enum "l2acl" {
        value 111;
        description
          "l2acl";
      }
      enum "l2evpn-nh" {
        value 112;
        description
          "l2evpn nh";
      }
      enum "l2-bridge-port-sc" {
        value 113;
        description
          "l2bridgeport sc";
      }
      enum "l3intfmctxstats" {
        value 114;
        description
          "l3intfmctxstats";
      }
      enum "tidl-sample" {
        value 115;
        description
          "tidl sample";
      }
      enum "tidl-ref-sample" {
        value 116;
        description
          "tidl ref sample";
      }
      enum "ipacl-prefix" {
        value 117;
        description
          "ipaclprefix";
      }
      enum "ip6acl-prefix" {
        value 118;
        description
          "ip6aclprefix";
      }
      enum "ipacl-port" {
        value 119;
        description
          "ipaclport";
      }
      enum "scaleacl" {
        value 120;
        description
          "scaleacl";
      }
      enum "ipmcf-hop" {
        value 121;
        description
          "ipmcfhop";
      }
      enum "bundle-swoff" {
        value 122;
        description
          "bundle swoff";
      }
      enum "mcidswoff" {
        value 123;
        description
          "mcidswoff";
      }
      enum "dest-map" {
        value 124;
        description
          "destmap";
      }
      enum "l2-bridge-port-pw" {
        value 125;
        description
          "l2bridgeport pw";
      }
      enum "l2evpnact-local-shlstats" {
        value 126;
        description
          "l2evpnactlocalshlstats";
      }
      enum "test-hidden" {
        value 127;
        description
          "testhidden";
      }
      enum "test-local" {
        value 128;
        description
          "testlocal";
      }
      enum "test-repeated" {
        value 129;
        description
          "testrepeated";
      }
      enum "limd" {
        value 130;
        description
          "limd";
      }
      enum "litap" {
        value 131;
        description
          "litap";
      }
      enum "l3intf-proto-stats" {
        value 132;
        description
          "l3intfprotostats";
      }
      enum "srv6sid" {
        value 133;
        description
          "srv6sid";
      }
      enum "srv6nh" {
        value 134;
        description
          "srv6nh";
      }
      enum "redirect-vrf" {
        value 135;
        description
          "redirectvrf";
      }
      enum "test-xtf" {
        value 136;
        description
          "test xtf";
      }
      enum "ippbr" {
        value 137;
        description
          "ippbr";
      }
      enum "ippbrstats" {
        value 138;
        description
          "ippbrstats";
      }
      enum "l2-bridge-port-remote-lc" {
        value 139;
        description
          "l2bridgeport remote lc";
      }
      enum "mpls-mdt-bud" {
        value 140;
        description
          "mplsmdtbud";
      }
      enum "l2mac-static" {
        value 141;
        description
          "l2macstatic";
      }
      enum "sr-label-rxstats" {
        value 142;
        description
          "srlabelrxstats";
      }
      enum "l2vpnxid" {
        value 143;
        description
          "l2vpnxid";
      }
      enum "rpfif" {
        value 144;
        description
          "rpfif";
      }
    }
    description
      "Dpa table";
  }

  container dpa {
    config false;
    description
      "Stats Data";
    container stats {
      description
        "Voq or Trap Data";
      container nodes {
        description
          "DPA data for available nodes";
        list node {
          key "node-name";
          description
            "DPA operational data for a particular node";
          container asic-statistics {
            description
              "ASIC statistics table";
            container asic-statistics-detail-for-npu-ids {
              description
                "Detailed ASIC statistics";
              list asic-statistics-detail-for-npu-id {
                key "npu-id";
                description
                  "Detailed ASIC statistics for a particular
                   NPU";
                leaf npu-id {
                  type uint32;
                  description
                    "NPU number";
                }
                uses FIA-EDM-STATS-INFO;
              }
            }
            container asic-statistics-for-npu-ids {
              description
                "ASIC statistics";
              list asic-statistics-for-npu-id {
                key "npu-id";
                description
                  "ASIC statistics for a particular NPU";
                leaf npu-id {
                  type uint32;
                  description
                    "NPU number";
                }
                uses FIA-EDM-STATS-BRIEF-INFO;
              }
            }
          }
          container npu-numbers {
            description
              "Ingress Stats";
            list npu-number {
              key "npu-id";
              description
                "Stats for a particular npu";
              container display {
                description
                  "show npu specific voq or trap stats";
                container trap-ids {
                  description
                    "Trap stats for a particular npu";
                  list trap-id {
                    key "trap-id";
                    description
                      "Filter by specific trap id";
                    leaf trap-id {
                      type Max-trap-s;
                      description
                        "Trap ID";
                    }
                    uses DPA-TRAP-STATS;
                  }
                }
                container interface-handles {
                  description
                    "Voq stats grouped by interface handle";
                  list interface-handle {
                    key "interface-handle";
                    description
                      "Voq stats for a particular interface
                       handle";
                    leaf interface-handle {
                      type Max-lc-intf-hand-les;
                      description
                        "Interface Handle";
                    }
                    uses DPA-VOQ-INTF-PORT;
                  }
                }
                container base-numbers {
                  description
                    "Voq stats grouped by voq base numbers";
                  list base-number {
                    key "base-number";
                    description
                      "Voq Base Number for a particular voq";
                    leaf base-number {
                      type Max-lc-intf-hand-les;
                      description
                        "Interface handle";
                    }
                    uses DPA-VOQ-INTF-PORT;
                  }
                }
              }
              leaf npu-id {
                type uint32;
                description
                  "Npu number";
              }
            }
          }
          leaf node-name {
            type xr:Node-id;
            description
              "Node ID";
          }
        }
      }
    }
    container resources {
      description
        "OFA Resources Data";
      container nodes {
        description
          "OFA data for available nodes";
        list node {
          key "node-name";
          description
            "OFA operational data for a particular node";
          container table-datas {
            description
              "OFA Resources table";
            list table-data {
              key "resource";
              description
                "DPA Resources table";
              leaf resource {
                type Dpa-table;
                description
                  "Resource type";
              }
              uses DPA-SYSDB-TABLE-RESOURCE;
            }
          }
          leaf node-name {
            type xr:Node-id;
            description
              "Node ID";
          }
        }
      }
    }
  }
}
