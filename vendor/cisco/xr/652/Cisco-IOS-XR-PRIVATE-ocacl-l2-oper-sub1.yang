submodule Cisco-IOS-XR-PRIVATE-ocacl-l2-oper-sub1 {
  belongs-to Cisco-IOS-XR-PRIVATE-ocacl-l2-oper {
    prefix Cisco-IOS-XR-PRIVATE-ocacl-l2-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR PRIVATE-ocacl-l2 package operational data.
     
     Copyright (c) 2013-2018 by Cisco Systems, Inc.
     All rights reserved.";

  revision 2015-11-09 {
    description
      "IOS XR 6.0 revision.";
  }

  typedef Yang2bag-string {
    type string;
    description
      "Yang2bag string";
  }

  grouping ACTIONS-STATE {
    description
      "ACTIONS STATE";
    leaf forwarding-action {
      type Yang2bag-string;
      description
        "Specifies the forwarding action";
    }
    leaf log-action {
      type Yang2bag-string;
      description
        "Specifies the log action and destination for
         matched packets";
    }
  }

  grouping ACTIONS {
    description
      "ACTIONS";
    container state {
      description
        "State information for ACL actions";
      uses ACTIONS-STATE;
    }
  }

  grouping L2-STATE {
    description
      "L2 STATE";
    leaf source-mac {
      type Yang2bag-string;
      description
        "Source IEEE 802 MAC address";
    }
    leaf source-mac-mask {
      type Yang2bag-string;
      description
        "Source IEEE 802 MAC address mask";
    }
    leaf destination-mac {
      type Yang2bag-string;
      description
        "Destination IEEE 802 MAC address";
    }
    leaf destination-mac-mask {
      type Yang2bag-string;
      description
        "Destination IEEE 802 MAC address mask";
    }
    leaf ethertype {
      type Yang2bag-string;
      description
        "Ethertype field to match in Ethernet packets";
    }
  }

  grouping L2 {
    description
      "L2";
    container state {
      description
        "State Information";
      uses L2-STATE;
    }
  }

  grouping STATE {
    description
      "STATE";
    leaf sequence-id {
      type uint32;
      description
        "The sequence id determines the order in which
         ACL entries are applied";
    }
    leaf matched-packets {
      type uint64;
      description
        "Count of the number of packets matching the
         current ACL entry";
    }
    leaf matched-octets {
      type uint64;
      units "byte";
      description
        "Count of the number of octets (bytes) matching
         the current ACL entry";
    }
  }

  grouping OVERLAY-OCACL-L2-ACL-ENTRY {
    description
      "List of ACL entries comprising an ACL set";
    container state {
      description
        "State information for ACL entries";
      uses STATE;
    }
    container l2 {
      description
        "Ethernet header fields";
      uses L2;
    }
    container actions {
      description
        "Enclosing container for list of ACL actions
         associated with an entry";
      uses ACTIONS;
    }
  }

  grouping OVERLAY-OCACL-L2-STATE {
    description
      "Access list state information";
    leaf name {
      type Yang2bag-string;
      description
        "The name of the access-list set";
    }
    leaf type {
      type Yang2bag-string;
      description
        "The type determines the fields allowed in the
         ACL entries belonging to the ACL set (e";
    }
  }
}
