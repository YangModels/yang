submodule Cisco-IOS-XR-clns-isis-oper-sub3 {
  belongs-to Cisco-IOS-XR-clns-isis-oper {
    prefix Cisco-IOS-XR-clns-isis-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR clns-isis package operational data.
     
     Copyright (c) 2013-2018 by Cisco Systems, Inc.
     All rights reserved.";

  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  typedef Openconfig-isis-lsp-attributes-enum {
    type enumeration {
      enum "overload" {
        value 0;
        description
          "When set, node is overloaded, still part of the
           topology but cannot be used for transit.";
      }
      enum "attached" {
        value 1;
        description
          "When set, node is attached to another area
           using the referred metric and can be used as
           default gateway.";
      }
    }
    description
      "Openconfig isis lsp attributes enum";
  }

  typedef Openconfig-isis-lsp-nlpid-enum {
    type enumeration {
      enum "ipv4" {
        value 0;
        description
          "IPv4 Address family.";
      }
      enum "ipv6" {
        value 1;
        description
          "IPv6 Address family.";
      }
    }
    description
      "Openconfig isis lsp nlpid enum";
  }

  typedef Openconfig-isis-lsp-state-flags-enum {
    type enumeration {
      enum "numbered" {
        value 0;
        description
          "When set, the interface is numbered, whereas if
           unset indicates that the interface is
           unnumbered.";
      }
    }
    description
      "Openconfig isis lsp state flags enum";
  }

  typedef Openconfig-isis-lsp-isis-metric-flags-enum {
    type enumeration {
      enum "internal" {
        value 0;
        description
          "When this flag is not set, internal metrics are
           in use.";
      }
      enum "unsupported" {
        value 1;
        description
          "When this flag (referred to as the S-bit) is
           set, then the metric is unsupported.";
      }
    }
    description
      "Openconfig isis lsp isis metric flags enum";
  }

  typedef Openconfig-isis-lsp-default-metric-state-flags-enum {
    type enumeration {
      enum "internal" {
        value 0;
        description
          "When set to zero, indicates internal metrics.";
      }
    }
    description
      "Openconfig isis lsp default metric state flags
       enum";
  }

  typedef Openconfig-isis-lsp-ipv6-srlg-state-flags-enum {
    type enumeration {
      enum "na" {
        value 0;
        description
          "When set, the IPv6 neighbour address is
           included, whereas if unset, it is omitted";
      }
    }
    description
      "Openconfig isis lsp ipv6 srlg state flags enum";
  }

  typedef Openconfig-isis-lsp-lan-adjacency-sid-state-flags-enum {
    type enumeration {
      enum "address-family" {
        value 0;
        description
          "Address-family flag. When unset, the Adj-SID
           refers to an adjacency with outgoing IPv4
           encapsulation. If set then the Adj-SID refers
           to an adjacency with outgoing IPv6
           encapsulation.";
      }
      enum "backup" {
        value 1;
        description
          "Backup flag. When set, the Adj-SID refers to an
           adjacency being protected (e.g.: using IPFRR or
           MPLS-FRR).";
      }
      enum "value" {
        value 2;
        description
          "Value flag. When set, the SID carries a value
           (instead of an index). By default the flag is
           SET.";
      }
      enum "local" {
        value 3;
        description
          "Local flag. When set, the value/index carried
           by the SID has local significance. By default
           the flag is SET.";
      }
      enum "set" {
        value 4;
        description
          "Set flag. When set, the S-Flag indicates that
           the Adj-SID refers to a set of adjacencies.";
      }
    }
    description
      "Openconfig isis lsp lan adjacency sid state flags
       enum";
  }

  typedef Openconfig-isis-lsp-adjacency-sid-state-flags-enum {
    type enumeration {
      enum "address-family" {
        value 0;
        description
          "Address-family flag. When unset, the Adj-SID
           refers to an adjacency with outgoing IPv4
           encapsulation. If set then the Adj-SID refers
           to an adjacency with outgoing IPv6
           encapsulation.";
      }
      enum "backup" {
        value 1;
        description
          "Backup flag. When set, the Adj-SID refers to an
           adjacency being protected (e.g.: using IPFRR or
           MPLS-FRR).";
      }
      enum "value" {
        value 2;
        description
          "Value flag. When set, the SID carries a value
           (instead of an index). By default the flag is
           SET.";
      }
      enum "local" {
        value 3;
        description
          "Local flag. When set, the value/index carried
           by the SID has local significance. By default
           the flag is SET.";
      }
      enum "set" {
        value 4;
        description
          "Set flag. When set, the S-Flag indicates that
           the Adj-SID refers to a set of adjacencies.";
      }
    }
    description
      "Openconfig isis lsp adjacency sid state flags
       enum";
  }

  typedef Openconfig-isis-lsp-flags-state-flags-enum {
    type enumeration {
      enum "external-flag" {
        value 0;
        description
          "External prefix flag. Set if the prefix has
           been redistributed from another protocol. This
           includes the case where multiple virtual
           routers are supported and the source of the
           redistributed prefix is another IS-IS instance.";
      }
      enum "readvertisement-flag" {
        value 1;
        description
          "Readvertisement flag. Set when the prefix has
           been leaked from one level to another (upwards
           or downwards).";
      }
      enum "node-flag" {
        value 2;
        description
          "Node flag. Set when the prefix identifies the
           advertising router, i.e., the prefix is a host
           prefix advertising  a globally reachable
           address typically associated with a loopback
           address.";
      }
    }
    description
      "Openconfig isis lsp flags state flags enum";
  }

  typedef Openconfig-isis-lsp-prefix-sid-state-flags-enum {
    type enumeration {
      enum "readvertisement" {
        value 0;
        description
          "Readvertisment flag. When set, the prefix to
           which this Prefix-SID is attached, has been
           propagated by the router either from another
           level or from redistribution.";
      }
      enum "node" {
        value 1;
        description
          "Node flag. When set, the Prefix-SID refers to
           the router identified by the prefix. Typically,
           the N-Flag is set on Prefix-SIDs attached to a
           router loopback address.";
      }
      enum "php" {
        value 2;
        description
          "Penultimate-Hop-Popping flag. When set, then
           the penultimate hop MUST NOT pop the Prefix-SID
           before delivering the packet to the node that
           advertised the Prefix-SID.";
      }
      enum "explicit-null" {
        value 3;
        description
          "Explicit-Null flag. When set, any upstream
           neighbor of the Prefix-SID originator MUST
           replace the Prefix-SID with a Prefix-SID having
           an Explicit-NULL value (0 for IPv4 and 2 for
           IPv6) before forwarding the packet.";
      }
      enum "value" {
        value 4;
        description
          "Value flag. When set, the Prefix-SID carries a
           value (instead of an index). By default the
           flag is UNSET.";
      }
      enum "local" {
        value 5;
        description
          "Local flag. When set, the value/index carried
           by the Prefix-SID has local significance. By
           default the flag is UNSET.";
      }
    }
    description
      "Openconfig isis lsp prefix sid state flags enum";
  }

  typedef Openconfig-isis-lsp-segment-routing-capability-state-flags-enum {
    type enumeration {
      enum "ipv4-mpls" {
        value 0;
        description
          "When set, the router is capable of processing
           SR MPLS encapsulated IPv4 packets on all
           interfaces.";
      }
      enum "ipv6-mpls" {
        value 1;
        description
          "When set, the router is capable of processing
           SR MPLS encapsulated IPv6 packets on all
           interfaces.";
      }
      enum "ipv6-sr" {
        value 2;
        description
          "When set, the router is capable of processing
           the IPv6 Segment Routing Header on all
           interfaces.";
      }
    }
    description
      "Openconfig isis lsp segment routing capability
       state flags enum";
  }

  typedef Openconfig-isis-lsp-algorithm-enum {
    type enumeration {
      enum "spf" {
        value 0;
        description
          "Shortest Path First (SPF) algorithm based on
           link metric.  This is the well-known shortest
           path algorithm as computed by the IS-IS
           Decision process.  Consistent with the deployed
           practice for link- state protocols, algorithm 0
           permits any node to overwrite the SPF path with
           a different path based on local policy.";
      }
      enum "strict-spf" {
        value 1;
        description
          "Strict Shortest Path First (SPF) algorithm
           based on link metric. The algorithm is
           identical to algorithm 0 but algorithm 1
           requires that all nodes along the path will
           honor the SPF routing decision. Local policy
           MUST NOT alter the forwarding decision computed
           by algorithm 1 at the node claiming to support
           algorithm 1.";
      }
    }
    description
      "Openconfig isis lsp algorithm enum";
  }

  typedef Openconfig-isis-lsp-router-capability-state-flags-enum {
    type enumeration {
      enum "flood" {
        value 0;
        description
          "When the S bit is set(1), the IS - IS Router
           CAPABILITY TLV MUST be flooded across the
           entire routing domain. When the S bit is not
           set(0), the TLV MUST NOT be leaked between
           levels . This bit MUST NOT be altered during
           the TLV leaking.";
      }
      enum "down" {
        value 1;
        description
          "When the IS-IS Router CAPABILITY TLV is leaked
           from level - 2 to level-1, the Down bit MUST be
           set. Otherwise, this bit MUST be clear. IS - IS
           Router capability TLVs with the Down bit set
           MUST NOT be leaked from level - 1 to level-2.
           This is to prevent TLV looping.";
      }
    }
    description
      "Openconfig isis lsp router capability state flags
       enum";
  }

  typedef Openconfig-isis-lsp-crypto-type-enum {
    type enumeration {
      enum "hmac-md5" {
        value 0;
        description
          "HMAC-MD5 Authentication type.";
      }
      enum "cleartext" {
        value 1;
        description
          "Cleartext Authentication type.";
      }
    }
    description
      "Openconfig isis lsp crypto type enum";
  }

  typedef Openconfig-isis-lsp-flags-enum {
    type enumeration {
      enum "partition-repair" {
        value 0;
        description
          "When set, the originator supports partition
           repair.";
      }
      enum "attached-error" {
        value 1;
        description
          "When set, the originator is attached to another
           area using the referred metric.";
      }
      enum "attached-expense" {
        value 2;
        description
          "When set, the originator is attached to another
           area using the referred metric.";
      }
      enum "attached-delay" {
        value 3;
        description
          "When set, the originator is attached to another
           area using the referred metric.";
      }
      enum "attached-default" {
        value 4;
        description
          "When set, the originator is attached to another
           area using the referred metric.";
      }
      enum "overload" {
        value 5;
        description
          "When set, the originator is overloaded, and
           must be avoided in path calculation.";
      }
    }
    description
      "Openconfig isis lsp flags enum";
  }

  typedef Openconfig-isis-lsp-pdu-type-enum {
    type enumeration {
      enum "level1" {
        value 0;
        description
          "This enum describes ISIS level 1 PDU.";
      }
      enum "level2" {
        value 1;
        description
          "This enum describes ISIS level 2 PDU.";
      }
    }
    description
      "Openconfig isis lsp pdu type enum";
  }

  typedef Openconfig-isis-types-metric-style-enum {
    type enumeration {
      enum "narrow-metric" {
        value 0;
        description
          "This enum describes narrow metric style";
      }
      enum "wide-metric" {
        value 1;
        description
          "This enum describes wide metric style";
      }
    }
    description
      "Openconfig isis types metric style enum";
  }

  typedef Openconfig-isis-types-adaptive-timer-type-enum {
    type enumeration {
      enum "linear" {
        value 0;
        description
          "This enum describes linear algorithm timer";
      }
      enum "exponential" {
        value 1;
        description
          "This enum describes exponential algorithm timer";
      }
    }
    description
      "Openconfig isis types adaptive timer type enum";
  }

  typedef Openconfig-segment-routing-label-options-enum {
    type enumeration {
      enum "no-php" {
        value 0;
        description
          "When this value is specified, the penultimate
           hop must not pop the Prefix-SID label before
           forwarding it to the local system.";
      }
      enum "explicit-null" {
        value 1;
        description
          "When set, the penultimate hop must swap the
           prefix SID for the relevant explicit null label
           before forwarding the packet.";
      }
    }
    description
      "Openconfig segment routing label options enum";
  }

  typedef Openconfig-isis-adjacency-state-nlpid-enum {
    type enumeration {
      enum "ipv4" {
        value 0;
        description
          "IPv4 Address family.";
      }
      enum "ipv6" {
        value 1;
        description
          "IPv6 Address family.";
      }
    }
    description
      "Openconfig isis adjacency state nlpid enum";
  }

  typedef Openconfig-isis-types-isis-interface-adj-state-enum {
    type enumeration {
      enum "up" {
        value 0;
        description
          "This state describes that adjacency is
           established.";
      }
      enum "down" {
        value 1;
        description
          "This state describes that adjacency is NOT
           established.";
      }
      enum "init" {
        value 2;
        description
          "This state describes that adjacency is
           establishing.";
      }
      enum "failed" {
        value 3;
        description
          "This state describes that adjacency is failed.";
      }
    }
    description
      "Openconfig isis types isis interface adj state
       enum";
  }

  typedef Openconfig-isis-types-level-type-enum {
    type enumeration {
      enum "level1" {
        value 0;
        description
          "This enum describes ISIS level 1";
      }
      enum "level2" {
        value 1;
        description
          "This enum describes ISIS level 2";
      }
      enum "level12" {
        value 2;
        description
          "This enum describes ISIS level 1-2";
      }
    }
    description
      "Openconfig isis types level type enum";
  }

  typedef Yang2bag-ipv6-addr {
    type inet:ipv6-address;
    description
      "Yang2bag ipv6 addr";
  }

  typedef Yang2bag-ipv4-addr {
    type inet:ipv4-address;
    description
      "Yang2bag ipv4 addr";
  }

  typedef Openconfig-isis-types-circuit-type-enum {
    type enumeration {
      enum "point-to-point" {
        value 0;
        description
          "This enum describes a point-to-point interface";
      }
      enum "broadcast" {
        value 1;
        description
          "This enum describes a broadcast interface";
      }
    }
    description
      "Openconfig isis types circuit type enum";
  }

  typedef Openconfig-isis-types-hello-padding-type-enum {
    type enumeration {
      enum "strict" {
        value 0;
        description
          "This enum describes strict padding";
      }
      enum "loose" {
        value 1;
        description
          "This enum describes loose padding";
      }
      enum "adaptive" {
        value 2;
        description
          "This enum describes adaptive padding";
      }
      enum "disable" {
        value 3;
        description
          "This enum disables padding";
      }
    }
    description
      "Openconfig isis types hello padding type enum";
  }

  typedef Yang2bag-string {
    type string;
    description
      "Yang2bag string";
  }

  grouping OVERLAY-OCNI-ISIS-STATE {
    description
      "Operational state parameters relating to a
       network instance";
    leaf name {
      type Yang2bag-string;
      description
        "An operator-assigned unique name for the
         forwarding instance";
    }
    leaf type {
      type Yang2bag-string;
      description
        "The type of network instance";
    }
    leaf enabled {
      type boolean;
      description
        "Whether the network instance should be
         configured to be active on the network element";
    }
    leaf description {
      type Yang2bag-string;
      description
        "A free-form string to be used by the network
         operator to describe the function of this
         network instance";
    }
  }

  grouping MT-IPV6-REACHABILITY-PREFIXES-PREFIX-UNDEFINED-SUBTLVS-UNDEFINED-SUBTLV-STATE {
    description
      "MT IPV6 REACHABILITY PREFIXES PREFIX UNDEFINED
       SUBTLVS UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-MT-IPV6-REACHABILITY-PREFIXES-PREFIX-UNDEFINED-SUBTLVS-UNDEFINED-SUBTLV {
    description
      "Sub-TLVs that are not defined in the model or not
       recognised by system";
    container state {
      description
        "State parameters of the undefined sub-TLV";
      uses MT-IPV6-REACHABILITY-PREFIXES-PREFIX-UNDEFINED-SUBTLVS-UNDEFINED-SUBTLV-STATE;
    }
  }

  grouping OVERLAY-OCNI-ISIS-PREFIXES-PREFIX-SUBTLVS-SUBTLV-STATE {
    description
      "State parameters for a prefix";
    leaf type {
      type Yang2bag-string;
      description
        "The type of subTLV being described";
    }
  }

  grouping PREFIX-SUBTLVS-SUBTLV-TAG-STATE {
    description
      "PREFIX SUBTLVS SUBTLV TAG STATE";
    leaf-list tag32 {
      type uint32;
      description
        "List of 32-bit tags associated with the prefix";
    }
  }

  grouping OVERLAY-OCNI-ISIS-PREFIX-SUBTLVS-SUBTLV-TAG {
    description
      "This container defines sub-TLV 1";
    container state {
      description
        "State parameters of sub-TLV 1";
      uses PREFIX-SUBTLVS-SUBTLV-TAG-STATE;
    }
  }

  grouping PREFIX-SUBTLVS-SUBTLV-IPV6-SOURCE-ROUTER-ID-STATE {
    description
      "PREFIX SUBTLVS SUBTLV IPV6 SOURCE ROUTER ID STATE";
    leaf type {
      type Yang2bag-string;
      description
        "The type of subTLV being described";
    }
    leaf ipv6-source-router-id {
      type Yang2bag-string;
      description
        "IPv6 Source router ID address";
    }
  }

  grouping OVERLAY-OCNI-ISIS-PREFIX-SUBTLVS-SUBTLV-IPV6-SOURCE-ROUTER-ID {
    description
      "This container defines sub-TLV 12";
    container state {
      description
        "State parameters of sub-TLV 12";
      uses PREFIX-SUBTLVS-SUBTLV-IPV6-SOURCE-ROUTER-ID-STATE;
    }
  }

  grouping PREFIX-SUBTLVS-SUBTLV-TAG64-STATE {
    description
      "PREFIX SUBTLVS SUBTLV TAG64 STATE";
    leaf-list tag64 {
      type uint64;
      description
        "List of 64-bit tags associated with the prefix";
    }
  }

  grouping OVERLAY-OCNI-ISIS-PREFIX-SUBTLVS-SUBTLV-TAG64 {
    description
      "This container defines sub-TLV 2";
    container state {
      description
        "State parameters of sub-TLV 2";
      uses PREFIX-SUBTLVS-SUBTLV-TAG64-STATE;
    }
  }

  grouping PREFIX-SUBTLVS-SUBTLV-IPV4-SOURCE-ROUTER-ID-STATE {
    description
      "PREFIX SUBTLVS SUBTLV IPV4 SOURCE ROUTER ID STATE";
    leaf type {
      type Yang2bag-string;
      description
        "The type of subTLV being described";
    }
    leaf ipv4-source-router-id {
      type Yang2bag-string;
      description
        "IPv4 Source router ID address";
    }
  }

  grouping OVERLAY-OCNI-ISIS-PREFIX-SUBTLVS-SUBTLV-IPV4-SOURCE-ROUTER-ID {
    description
      "This container defines sub-TLV 11";
    container state {
      description
        "State parameters of sub-TLV 11";
      uses PREFIX-SUBTLVS-SUBTLV-IPV4-SOURCE-ROUTER-ID-STATE;
    }
  }

  grouping PREFIX-SUBTLVS-SUBTLV-FLAGS-STATE {
    description
      "PREFIX SUBTLVS SUBTLV FLAGS STATE";
    leaf type {
      type Yang2bag-string;
      description
        "The type of subTLV being described";
    }
    leaf-list flags {
      type Openconfig-isis-lsp-flags-state-flags-enum;
      description
        "Additional prefix reachability flags";
    }
  }

  grouping OVERLAY-OCNI-ISIS-PREFIX-SUBTLVS-SUBTLV-FLAGS {
    description
      "This container defines sub-TLV 4";
    container state {
      description
        "State parameters of sub-TLV 4";
      uses PREFIX-SUBTLVS-SUBTLV-FLAGS-STATE;
    }
  }

  grouping SUBTLVS-SUBTLV-PREFIX-SIDS-PREFIX-SID-STATE {
    description
      "SUBTLVS SUBTLV PREFIX SIDS PREFIX SID STATE";
    leaf value {
      type uint32;
      description
        "IGP Prefix-SID value";
    }
    leaf algorithm {
      type uint8;
      description
        "Prefix-SID algorithm to be used for path
         computation";
    }
    leaf-list flags {
      type Openconfig-isis-lsp-prefix-sid-state-flags-enum;
      description
        "Flags associated with Prefix Segment-ID";
    }
  }

  grouping OVERLAY-OCNI-ISIS-SUBTLVS-SUBTLV-PREFIX-SIDS-PREFIX-SID {
    description
      "Prefix Segment-ID list";
    container state {
      description
        "State parameters for Prefix-SID";
      uses SUBTLVS-SUBTLV-PREFIX-SIDS-PREFIX-SID-STATE;
    }
  }

  grouping OVERLAY-OCNI-ISIS-MT-IPV6-REACHABILITY-PREFIXES-PREFIX-STATE {
    description
      "State parameters relating an IPv6 prefix
       attribute";
    leaf up-down {
      type boolean;
      description
        "The up/down bit";
    }
    leaf xbit {
      type boolean;
      description
        "The external bit";
    }
    leaf sbit {
      type boolean;
      description
        "The sub-tlv present bit";
    }
    leaf prefix {
      type Yang2bag-string;
      description
        "IPv6 prefix contained within extended
         reachability TLVs";
    }
    leaf metric {
      type uint32;
      description
        "ISIS metric value";
    }
    leaf mt-id {
      type uint16;
      description
        "Multi-topology ID";
    }
  }

  grouping PREFIXES-PREFIXES-ERROR-METRIC-STATE {
    description
      "PREFIXES PREFIXES ERROR METRIC STATE";
    leaf metric {
      type uint8;
      description
        "ISIS error metric value";
    }
    leaf-list flags {
      type Openconfig-isis-lsp-isis-metric-flags-enum;
      description
        "IS-IS error metric flags";
    }
  }

  grouping PREFIXES-PREFIXES-ERROR-METRIC {
    description
      "PREFIXES PREFIXES ERROR METRIC";
    container state {
      description
        "State parameters of error-metric";
      uses PREFIXES-PREFIXES-ERROR-METRIC-STATE;
    }
  }

  grouping PREFIXES-PREFIXES-EXPENSE-METRIC-STATE {
    description
      "PREFIXES PREFIXES EXPENSE METRIC STATE";
    leaf metric {
      type uint8;
      description
        "ISIS expense metric value";
    }
    leaf-list flags {
      type Openconfig-isis-lsp-isis-metric-flags-enum;
      description
        "ISIS Expense Metric Flags";
    }
  }

  grouping PREFIXES-PREFIXES-EXPENSE-METRIC {
    description
      "PREFIXES PREFIXES EXPENSE METRIC";
    container state {
      description
        "State parameters of expense-metric";
      uses PREFIXES-PREFIXES-EXPENSE-METRIC-STATE;
    }
  }

  grouping PREFIXES-PREFIXES-DELAY-METRIC-STATE {
    description
      "PREFIXES PREFIXES DELAY METRIC STATE";
    leaf metric {
      type uint8;
      description
        "ISIS delay metric value";
    }
    leaf-list flags {
      type Openconfig-isis-lsp-isis-metric-flags-enum;
      description
        "ISIS Delay Metric Flags";
    }
  }

  grouping PREFIXES-PREFIXES-DELAY-METRIC {
    description
      "PREFIXES PREFIXES DELAY METRIC";
    container state {
      description
        "State parameters of delay-metric";
      uses PREFIXES-PREFIXES-DELAY-METRIC-STATE;
    }
  }

  grouping PREFIXES-PREFIXES-DEFAULT-METRIC-STATE {
    description
      "PREFIXES PREFIXES DEFAULT METRIC STATE";
    leaf flags {
      type Openconfig-isis-lsp-default-metric-state-flags-enum;
      description
        "ISIS Default-Metric Flags";
    }
    leaf default-metric {
      type uint8;
      description
        "ISIS default metric value";
    }
  }

  grouping PREFIXES-PREFIXES-DEFAULT-METRIC {
    description
      "PREFIXES PREFIXES DEFAULT METRIC";
    container state {
      description
        "State parameters for default-metric";
      uses PREFIXES-PREFIXES-DEFAULT-METRIC-STATE;
    }
  }

  grouping PREFIXES-PREFIXES-STATE {
    description
      "PREFIXES PREFIXES STATE";
    leaf up-down {
      type boolean;
      description
        "The up/down bit";
    }
    leaf prefix {
      type Yang2bag-string;
      description
        "IPv4 prefix contained within reachability TLVs";
    }
  }

  grouping OVERLAY-OCNI-ISIS-PREFIXES-PREFIXES {
    description
      "IPv4 external prefixes and reachability
       attributes";
    container state {
      description
        "State parameters of IPv4 standard prefix";
      uses PREFIXES-PREFIXES-STATE;
    }
    container default-metric {
      description
        "This container defines ISIS Default Metric";
      uses PREFIXES-PREFIXES-DEFAULT-METRIC;
    }
    container delay-metric {
      description
        "This container defines the ISIS delay metric";
      uses PREFIXES-PREFIXES-DELAY-METRIC;
    }
    container expense-metric {
      description
        "This container defines the ISIS expense metric";
      uses PREFIXES-PREFIXES-EXPENSE-METRIC;
    }
    container error-metric {
      description
        "This container defines the ISIS error metric";
      uses PREFIXES-PREFIXES-ERROR-METRIC;
    }
  }

  grouping TOPOLOGY-STATE {
    description
      "TOPOLOGY STATE";
    leaf mt-id {
      type uint16;
      description
        "Multi-topology ID";
    }
    leaf attributes {
      type Openconfig-isis-lsp-attributes-enum;
      description
        "Attributes of the LSP for the associated
         topology";
    }
  }

  grouping OVERLAY-OCNI-ISIS-TOPOLOGY {
    description
      "This list describes a topology";
    container state {
      description
        "State parameters of IS multi-topology TLV 229";
      uses TOPOLOGY-STATE;
    }
  }

  grouping PREFIX-UNDEFINED-SUBTLVS-UNDEFINED-SUBTLV-STATE {
    description
      "PREFIX UNDEFINED SUBTLVS UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-PREFIX-UNDEFINED-SUBTLVS-UNDEFINED-SUBTLV {
    description
      "Sub-TLVs that are not defined in the model or not
       recognised by system";
    container state {
      description
        "State parameters of the undefined sub-TLV";
      uses PREFIX-UNDEFINED-SUBTLVS-UNDEFINED-SUBTLV-STATE;
    }
  }

  grouping PREFIX-SID-STATE {
    description
      "PREFIX SID STATE";
    leaf value {
      type uint32;
      description
        "IGP Prefix-SID value";
    }
    leaf algorithm {
      type uint8;
      description
        "Prefix-SID algorithm to be used for path
         computation";
    }
    leaf-list flags {
      type Openconfig-isis-lsp-prefix-sid-state-flags-enum;
      description
        "Flags associated with Prefix Segment-ID";
    }
  }

  grouping OVERLAY-OCNI-ISIS-PREFIX-SID {
    description
      "Prefix Segment-ID list";
    container state {
      description
        "State parameters for Prefix-SID";
      uses PREFIX-SID-STATE;
    }
  }

  grouping TAG64-STATE {
    description
      "TAG64 STATE";
    leaf-list tag64 {
      type uint64;
      description
        "List of 64-bit tags associated with the prefix";
    }
  }

  grouping OVERLAY-OCNI-ISIS-TAG64 {
    description
      "This container defines sub-TLV 2";
    container state {
      description
        "State parameters of sub-TLV 2";
      uses TAG64-STATE;
    }
  }

  grouping FLAGS-STATE {
    description
      "FLAGS STATE";
    leaf type {
      type Yang2bag-string;
      description
        "The type of subTLV being described";
    }
    leaf-list flags {
      type Openconfig-isis-lsp-flags-state-flags-enum;
      description
        "Additional prefix reachability flags";
    }
  }

  grouping OVERLAY-OCNI-ISIS-FLAGS {
    description
      "This container defines sub-TLV 4";
    container state {
      description
        "State parameters of sub-TLV 4";
      uses FLAGS-STATE;
    }
  }

  grouping OVERLAY-OCNI-ISIS-SUBTLVS-SUBTLV-STATE {
    description
      "State parameters for a prefix";
    leaf type {
      type Yang2bag-string;
      description
        "The type of subTLV being described";
    }
  }

  grouping IPV6-SOURCE-ROUTER-ID-STATE {
    description
      "IPV6 SOURCE ROUTER ID STATE";
    leaf type {
      type Yang2bag-string;
      description
        "The type of subTLV being described";
    }
    leaf ipv6-source-router-id {
      type Yang2bag-string;
      description
        "IPv6 Source router ID address";
    }
  }

  grouping OVERLAY-OCNI-ISIS-IPV6-SOURCE-ROUTER-ID {
    description
      "This container defines sub-TLV 12";
    container state {
      description
        "State parameters of sub-TLV 12";
      uses IPV6-SOURCE-ROUTER-ID-STATE;
    }
  }

  grouping IPV4-SOURCE-ROUTER-ID-STATE {
    description
      "IPV4 SOURCE ROUTER ID STATE";
    leaf type {
      type Yang2bag-string;
      description
        "The type of subTLV being described";
    }
    leaf ipv4-source-router-id {
      type Yang2bag-string;
      description
        "IPv4 Source router ID address";
    }
  }

  grouping OVERLAY-OCNI-ISIS-IPV4-SOURCE-ROUTER-ID {
    description
      "This container defines sub-TLV 11";
    container state {
      description
        "State parameters of sub-TLV 11";
      uses IPV4-SOURCE-ROUTER-ID-STATE;
    }
  }

  grouping TAG-STATE {
    description
      "TAG STATE";
    leaf-list tag32 {
      type uint32;
      description
        "List of 32-bit tags associated with the prefix";
    }
  }

  grouping OVERLAY-OCNI-ISIS-TAG {
    description
      "This container defines sub-TLV 1";
    container state {
      description
        "State parameters of sub-TLV 1";
      uses TAG-STATE;
    }
  }

  grouping OVERLAY-OCNI-ISIS-PREFIX-STATE {
    description
      "State parameters of an IPv4 extended prefix";
    leaf up-down {
      type boolean;
      description
        "The up/down bit";
    }
    leaf sbit {
      type boolean;
      description
        "The Sub-TLV present bit";
    }
    leaf prefix {
      type Yang2bag-string;
      description
        "IPv4 prefix contained within extended
         reachability TLVs";
    }
    leaf metric {
      type uint32;
      description
        "ISIS metric value";
    }
  }

  grouping NLPID-STATE {
    description
      "NLPID STATE";
    leaf-list nlpid {
      type Openconfig-isis-lsp-nlpid-enum;
      description
        "Protocol supported";
    }
  }

  grouping OVERLAY-OCNI-ISIS-NLPID {
    description
      "This container defines TLV 129";
    container state {
      description
        "State parameters of ISIS TLV 129";
      uses NLPID-STATE;
    }
  }

  grouping IPV4-TE-ROUTER-ID-STATE {
    description
      "IPV4 TE ROUTER ID STATE";
    leaf-list router-id {
      type Yang2bag-string;
      description
        "IPv4 Traffic Engineering router ID of the node";
    }
  }

  grouping OVERLAY-OCNI-ISIS-IPV4-TE-ROUTER-ID {
    description
      "This container defines TLV 134";
    container state {
      description
        "State parameters of ISIS TLV 134";
      uses IPV4-TE-ROUTER-ID-STATE;
    }
  }

  grouping ERROR-METRIC-STATE {
    description
      "ERROR METRIC STATE";
    leaf metric {
      type uint8;
      description
        "ISIS error metric value";
    }
    leaf-list flags {
      type Openconfig-isis-lsp-isis-metric-flags-enum;
      description
        "IS-IS error metric flags";
    }
  }

  grouping ERROR-METRIC {
    description
      "ERROR METRIC";
    container state {
      description
        "State parameters of error-metric";
      uses ERROR-METRIC-STATE;
    }
  }

  grouping EXPENSE-METRIC-STATE {
    description
      "EXPENSE METRIC STATE";
    leaf metric {
      type uint8;
      description
        "ISIS expense metric value";
    }
    leaf-list flags {
      type Openconfig-isis-lsp-isis-metric-flags-enum;
      description
        "ISIS Expense Metric Flags";
    }
  }

  grouping EXPENSE-METRIC {
    description
      "EXPENSE METRIC";
    container state {
      description
        "State parameters of expense-metric";
      uses EXPENSE-METRIC-STATE;
    }
  }

  grouping DELAY-METRIC-STATE {
    description
      "DELAY METRIC STATE";
    leaf metric {
      type uint8;
      description
        "ISIS delay metric value";
    }
    leaf-list flags {
      type Openconfig-isis-lsp-isis-metric-flags-enum;
      description
        "ISIS Delay Metric Flags";
    }
  }

  grouping DELAY-METRIC {
    description
      "DELAY METRIC";
    container state {
      description
        "State parameters of delay-metric";
      uses DELAY-METRIC-STATE;
    }
  }

  grouping DEFAULT-METRIC-STATE {
    description
      "DEFAULT METRIC STATE";
    leaf flags {
      type Openconfig-isis-lsp-default-metric-state-flags-enum;
      description
        "ISIS Default-Metric Flags";
    }
    leaf default-metric {
      type uint8;
      description
        "ISIS default metric value";
    }
  }

  grouping DEFAULT-METRIC {
    description
      "DEFAULT METRIC";
    container state {
      description
        "State parameters for default-metric";
      uses DEFAULT-METRIC-STATE;
    }
  }

  grouping NEIGHBORS-STATE {
    description
      "NEIGHBORS STATE";
    leaf system-id {
      type Yang2bag-string;
      description
        "System-ID of IS neighbor";
    }
  }

  grouping OVERLAY-OCNI-ISIS-NEIGHBORS {
    description
      "IS reachability neighbor attributes";
    container state {
      description
        "State parameters of IS standard neighbor";
      uses NEIGHBORS-STATE;
    }
    container default-metric {
      description
        "This container defines ISIS Default Metric";
      uses DEFAULT-METRIC;
    }
    container delay-metric {
      description
        "This container defines the ISIS delay metric";
      uses DELAY-METRIC;
    }
    container expense-metric {
      description
        "This container defines the ISIS expense metric";
      uses EXPENSE-METRIC;
    }
    container error-metric {
      description
        "This container defines the ISIS error metric";
      uses ERROR-METRIC;
    }
  }

  grouping IPV4-SRLG-STATE {
    description
      "IPV4 SRLG STATE";
    leaf instance-number {
      type uint32;
      description
        "An arbitrary unsigned 32-bit integer used to
         disambiguate the instance of TLV 138";
    }
    leaf system-id {
      type Yang2bag-string;
      description
        "Neighbor system ID";
    }
    leaf psn-number {
      type uint8;
      description
        "Pseudonode number if the neighbor is on a LAN
         interface";
    }
    leaf ipv4-interface-address {
      type Yang2bag-string;
      description
        "IPv4 interface address";
    }
    leaf ipv4-neighbor-address {
      type Yang2bag-string;
      description
        "IPv4 neighbor address";
    }
    leaf-list flags {
      type Openconfig-isis-lsp-state-flags-enum;
      description
        "SRLG flags";
    }
    leaf-list srlg-value {
      type uint32;
      description
        "List of SRLG values";
    }
  }

  grouping OVERLAY-OCNI-ISIS-IPV4-SRLG {
    description
      "Instance of the IPv4 SRLG TLV";
    container state {
      description
        "State parameters of TLV 138";
      uses IPV4-SRLG-STATE;
    }
  }

  grouping INSTANCE-ID-STATE {
    description
      "INSTANCE ID STATE";
    leaf instance-id {
      type uint16;
      description
        "An Instance Identifier (IID) to uniquely
         identify an IS-IS instance";
    }
    leaf-list topology-id {
      type uint16;
      description
        "Instance-Specific Topology Identifiers (ITIDs)";
    }
  }

  grouping OVERLAY-OCNI-ISIS-INSTANCE-ID {
    description
      "A list of instance IDs received within TLV 7
       within an IS-IS LSP";
    container state {
      description
        "State parameters of ISIS TLV 7";
      uses INSTANCE-ID-STATE;
    }
  }

  grouping OVERLAY-OCNI-ISIS-NEIGHBORS-STATE {
    description
      "State parameters of extended neighbor";
    leaf system-id {
      type Yang2bag-string;
      description
        "System-id of the neighbor";
    }
    leaf metric {
      type uint32;
      description
        "Metric value";
    }
  }

  grouping UNDEFINED-SUBTLVS-UNDEFINED-SUBTLV-STATE {
    description
      "UNDEFINED SUBTLVS UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-UNDEFINED-SUBTLVS-UNDEFINED-SUBTLV {
    description
      "Sub-TLVs that are not defined in the model or not
       recognised by system";
    container state {
      description
        "State parameters of the undefined sub-TLV";
      uses UNDEFINED-SUBTLVS-UNDEFINED-SUBTLV-STATE;
    }
  }

  grouping OVERLAY-OCNI-ISIS-BANDWIDTH-CONSTRAINT-STATE {
    description
      "State parameters of IS Extended Reachability
       sub-TLV 22";
    leaf model-id {
      type uint8;
      description
        "Identifier for the Bandwidth Constraints  Model
         currently in use by the LSR initiating the IGP
         advertisement";
    }
  }

  grouping CONSTRAINT-STATE {
    description
      "CONSTRAINT STATE";
    leaf constraint-id {
      type uint32;
      description
        "Unique reference for the bandwidth constraint
         level";
    }
    leaf bandwidth {
      type Yang2bag-string;
      units "byte/s";
      description
        "The bandwidth constraint, expressed as a 32-bit
         IEEE floating point number expressed in bytes
         per second";
    }
  }

  grouping OVERLAY-OCNI-ISIS-CONSTRAINT {
    description
      "List of the constraints within the Bandwidth
       Constraints sub-TLV";
    container state {
      description
        "Operational state parameters of the BCN level";
      uses CONSTRAINT-STATE;
    }
  }

  grouping IPV4-NEIGHBOR-ADDRESS-STATE {
    description
      "IPV4 NEIGHBOR ADDRESS STATE";
    leaf-list ipv4-neighbor-address {
      type Yang2bag-string;
      description
        "A single IPv4 address for a neighboring router
         on this link";
    }
  }

  grouping OVERLAY-OCNI-ISIS-IPV4-NEIGHBOR-ADDRESS {
    description
      "This container defines sub-TLV 8";
    container state {
      description
        "State parameters of sub-TLV 8";
      uses IPV4-NEIGHBOR-ADDRESS-STATE;
    }
  }

  grouping IPV4-INTERFACE-ADDRESS-STATE {
    description
      "IPV4 INTERFACE ADDRESS STATE";
    leaf-list ipv4-interface-address {
      type Yang2bag-string;
      description
        "A 4-octet IPv4 address for the interface
         described by the (main) TLV";
    }
  }

  grouping OVERLAY-OCNI-ISIS-IPV4-INTERFACE-ADDRESS {
    description
      "This container defines sub-TLV 6";
    container state {
      description
        "State parameters of sub-TLV 6";
      uses IPV4-INTERFACE-ADDRESS-STATE;
    }
  }

  grouping SETUP-PRIORITY-STATE {
    description
      "SETUP PRIORITY STATE";
    leaf priority {
      type uint8;
      description
        "Setup priority level of 0 through 7 to be used
         by Unreserved Bandwidth sub-TLV 11";
    }
    leaf unreserved-bandwidth {
      type Yang2bag-string;
      description
        "The amount of bandwidth reservable in this
         direction on this link";
    }
  }

  grouping OVERLAY-OCNI-ISIS-SETUP-PRIORITY {
    description
      "Setup priority (0 through 7) for unreserved
       bandwidth";
    container state {
      description
        "State parameters of IS Extended Reachability
         sub-TLV 11";
      uses SETUP-PRIORITY-STATE;
    }
  }

  grouping EXTENDED-ADMIN-GROUP-STATE {
    description
      "EXTENDED ADMIN GROUP STATE";
    leaf-list extended-admin-group {
      type uint32;
      description
        "The extended-admin-group sub-TLV is used in
         addition to the Administrative Groups when it is
         desirable to make more than 32 colors available
         for advertisement in a network";
    }
  }

  grouping OVERLAY-OCNI-ISIS-EXTENDED-ADMIN-GROUP {
    description
      "This container defines sub-TLV 14";
    container state {
      description
        "State parameters of sub-TLV 14";
      uses EXTENDED-ADMIN-GROUP-STATE;
    }
  }

  grouping MAX-RESERVABLE-LINK-BANDWIDTH-STATE {
    description
      "MAX RESERVABLE LINK BANDWIDTH STATE";
    leaf max-reservable-link-bandwidth {
      type Yang2bag-string;
      description
        "The maximum amount of bandwidth that can be
         reserved in this direction on this link";
    }
  }

  grouping OVERLAY-OCNI-ISIS-MAX-RESERVABLE-LINK-BANDWIDTH {
    description
      "This container defines sub-TLV 10";
    container state {
      description
        "State parameters of sub-TLV 10";
      uses MAX-RESERVABLE-LINK-BANDWIDTH-STATE;
    }
  }

  grouping ADMIN-GROUP-STATE {
    description
      "ADMIN GROUP STATE";
    leaf-list admin-group {
      type uint32;
      description
        "The administrative group sub-TLV contains a
         4-octet bit mask assigned by the network
         administrator";
    }
  }

  grouping OVERLAY-OCNI-ISIS-ADMIN-GROUP {
    description
      "This container defines sub-TLV 3";
    container state {
      description
        "State parameters of sub-TLV 3";
      uses ADMIN-GROUP-STATE;
    }
  }

  grouping TE-DEFAULT-METRIC-STATE {
    description
      "TE DEFAULT METRIC STATE";
    leaf te-default-metric {
      type uint32;
      description
        "This metric is administratively assigned and can
         be used to present a differently weighted
         topology to traffic engineering SPF calculations";
    }
  }

  grouping OVERLAY-OCNI-ISIS-TE-DEFAULT-METRIC {
    description
      "This container defines sub-TLV 18";
    container state {
      description
        "State parameters of sub-TLV 18";
      uses TE-DEFAULT-METRIC-STATE;
    }
  }

  grouping ADJACENCY-SID-STATE {
    description
      "ADJACENCY SID STATE";
    leaf value {
      type uint32;
      description
        "Adjacency-SID value";
    }
    leaf weight {
      type uint8;
      description
        "Value that represents the weight of the Adj-SID
         for the purpose of load balancing";
    }
    leaf-list flags {
      type Openconfig-isis-lsp-adjacency-sid-state-flags-enum;
      description
        "Flags associated with Adj-Segment-ID";
    }
  }

  grouping OVERLAY-OCNI-ISIS-ADJACENCY-SID {
    description
      "Adjacency Segment-IDs List";
    container state {
      description
        "State parameters of Adjacency-SID";
      uses ADJACENCY-SID-STATE;
    }
  }

  grouping LAN-ADJACENCY-SID-STATE {
    description
      "LAN ADJACENCY SID STATE";
    leaf value {
      type uint32;
      description
        "LAN Adjacency-SID value";
    }
    leaf weight {
      type uint8;
      description
        "Value that represents the weight of the Adj-SID
         for the purpose of load balancing";
    }
    leaf neighbor-id {
      type Yang2bag-string;
      description
        "System ID of the neighbor associated with the
         LAN- Adj-Segment-ID value";
    }
    leaf-list flags {
      type Openconfig-isis-lsp-lan-adjacency-sid-state-flags-enum;
      description
        "Flags associated with LAN-Adj-Segment-ID";
    }
  }

  grouping OVERLAY-OCNI-ISIS-LAN-ADJACENCY-SID {
    description
      "Adjacency Segment-IDs List";
    container state {
      description
        "State parameters of LAN Adjacency-SID";
      uses LAN-ADJACENCY-SID-STATE;
    }
  }

  grouping IPV6-INTERFACE-ADDRESS-STATE {
    description
      "IPV6 INTERFACE ADDRESS STATE";
    leaf-list ipv6-interface-address {
      type Yang2bag-string;
      description
        "Contains a 16-octet IPv6 address for the
         interface described by the containing  Extended
         IS Reachability TLV";
    }
  }

  grouping OVERLAY-OCNI-ISIS-IPV6-INTERFACE-ADDRESS {
    description
      "This container defines sub-TLV 12";
    container state {
      description
        "State parameters of sub-TLV 12";
      uses IPV6-INTERFACE-ADDRESS-STATE;
    }
  }

  grouping IPV6-NEIGHBOR-ADDRESS-STATE {
    description
      "IPV6 NEIGHBOR ADDRESS STATE";
    leaf-list ipv6-neighbor-address {
      type Yang2bag-string;
      description
        "Contains a 16-octet IPv6 address for a
         neighboring router on the link described by the
         (main) TLV";
    }
  }

  grouping OVERLAY-OCNI-ISIS-IPV6-NEIGHBOR-ADDRESS {
    description
      "This container defines sub-TLV 13";
    container state {
      description
        "State parameters of sub-TLV 13";
      uses IPV6-NEIGHBOR-ADDRESS-STATE;
    }
  }

  grouping MAX-LINK-BANDWIDTH-STATE {
    description
      "MAX LINK BANDWIDTH STATE";
    leaf max-link-bandwidth {
      type Yang2bag-string;
      description
        "The maximum bandwidth that can be used on this
         link in this direction (from the system
         originating the LSP to its neighbors)";
    }
  }

  grouping OVERLAY-OCNI-ISIS-MAX-LINK-BANDWIDTH {
    description
      "This container defines sub-TLV 9";
    container state {
      description
        "State parameters of sub-TLV 9";
      uses MAX-LINK-BANDWIDTH-STATE;
    }
  }

  grouping IPV6-INTERFACE-ADDRESSES-STATE {
    description
      "IPV6 INTERFACE ADDRESSES STATE";
    leaf-list ipv6-interface-address {
      type Yang2bag-string;
      description
        "IPv6 interface addresses of the node";
    }
  }

  grouping OVERLAY-OCNI-ISIS-IPV6-INTERFACE-ADDRESSES {
    description
      "This container defines TLV 232";
    container state {
      description
        "State parameters of ISIS TLV 232";
      uses IPV6-INTERFACE-ADDRESSES-STATE;
    }
  }

  grouping PREFIXES-ERROR-METRIC-STATE {
    description
      "PREFIXES ERROR METRIC STATE";
    leaf metric {
      type uint8;
      description
        "ISIS error metric value";
    }
    leaf-list flags {
      type Openconfig-isis-lsp-isis-metric-flags-enum;
      description
        "IS-IS error metric flags";
    }
  }

  grouping PREFIXES-ERROR-METRIC {
    description
      "PREFIXES ERROR METRIC";
    container state {
      description
        "State parameters of error-metric";
      uses PREFIXES-ERROR-METRIC-STATE;
    }
  }

  grouping PREFIXES-EXPENSE-METRIC-STATE {
    description
      "PREFIXES EXPENSE METRIC STATE";
    leaf metric {
      type uint8;
      description
        "ISIS expense metric value";
    }
    leaf-list flags {
      type Openconfig-isis-lsp-isis-metric-flags-enum;
      description
        "ISIS Expense Metric Flags";
    }
  }

  grouping PREFIXES-EXPENSE-METRIC {
    description
      "PREFIXES EXPENSE METRIC";
    container state {
      description
        "State parameters of expense-metric";
      uses PREFIXES-EXPENSE-METRIC-STATE;
    }
  }

  grouping PREFIXES-DELAY-METRIC-STATE {
    description
      "PREFIXES DELAY METRIC STATE";
    leaf metric {
      type uint8;
      description
        "ISIS delay metric value";
    }
    leaf-list flags {
      type Openconfig-isis-lsp-isis-metric-flags-enum;
      description
        "ISIS Delay Metric Flags";
    }
  }

  grouping PREFIXES-DELAY-METRIC {
    description
      "PREFIXES DELAY METRIC";
    container state {
      description
        "State parameters of delay-metric";
      uses PREFIXES-DELAY-METRIC-STATE;
    }
  }

  grouping PREFIXES-DEFAULT-METRIC-STATE {
    description
      "PREFIXES DEFAULT METRIC STATE";
    leaf flags {
      type Openconfig-isis-lsp-default-metric-state-flags-enum;
      description
        "ISIS Default-Metric Flags";
    }
    leaf default-metric {
      type uint8;
      description
        "ISIS default metric value";
    }
  }

  grouping PREFIXES-DEFAULT-METRIC {
    description
      "PREFIXES DEFAULT METRIC";
    container state {
      description
        "State parameters for default-metric";
      uses PREFIXES-DEFAULT-METRIC-STATE;
    }
  }

  grouping PREFIXES-STATE {
    description
      "PREFIXES STATE";
    leaf up-down {
      type boolean;
      description
        "The up/down bit";
    }
    leaf prefix {
      type Yang2bag-string;
      description
        "IPv4 prefix contained within reachability TLVs";
    }
  }

  grouping OVERLAY-OCNI-ISIS-PREFIXES {
    description
      "IPv4 prefixes and internal reachability
       attributes";
    container state {
      description
        "State parameters of IPv4 standard prefix";
      uses PREFIXES-STATE;
    }
    container default-metric {
      description
        "This container defines ISIS Default Metric";
      uses PREFIXES-DEFAULT-METRIC;
    }
    container delay-metric {
      description
        "This container defines the ISIS delay metric";
      uses PREFIXES-DELAY-METRIC;
    }
    container expense-metric {
      description
        "This container defines the ISIS expense metric";
      uses PREFIXES-EXPENSE-METRIC;
    }
    container error-metric {
      description
        "This container defines the ISIS error metric";
      uses PREFIXES-ERROR-METRIC;
    }
  }

  grouping IPV6-TE-ROUTER-ID-STATE {
    description
      "IPV6 TE ROUTER ID STATE";
    leaf-list router-id {
      type Yang2bag-string;
      description
        "IPv6 Traffic Engineering router ID of the node";
    }
  }

  grouping OVERLAY-OCNI-ISIS-IPV6-TE-ROUTER-ID {
    description
      "This container defines TLV 140";
    container state {
      description
        "State parameters of ISIS TLV 140";
      uses IPV6-TE-ROUTER-ID-STATE;
    }
  }

  grouping PREFIXES-UNDEFINED-SUBTLVS-UNDEFINED-SUBTLV-STATE {
    description
      "PREFIXES UNDEFINED SUBTLVS UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-PREFIXES-UNDEFINED-SUBTLVS-UNDEFINED-SUBTLV {
    description
      "Sub-TLVs that are not defined in the model or not
       recognised by system";
    container state {
      description
        "State parameters of the undefined sub-TLV";
      uses PREFIXES-UNDEFINED-SUBTLVS-UNDEFINED-SUBTLV-STATE;
    }
  }

  grouping SUBTLV-FLAGS-STATE {
    description
      "SUBTLV FLAGS STATE";
    leaf type {
      type Yang2bag-string;
      description
        "The type of subTLV being described";
    }
    leaf-list flags {
      type Openconfig-isis-lsp-flags-state-flags-enum;
      description
        "Additional prefix reachability flags";
    }
  }

  grouping OVERLAY-OCNI-ISIS-SUBTLV-FLAGS {
    description
      "This container defines sub-TLV 4";
    container state {
      description
        "State parameters of sub-TLV 4";
      uses SUBTLV-FLAGS-STATE;
    }
  }

  grouping SUBTLV-IPV6-SOURCE-ROUTER-ID-STATE {
    description
      "SUBTLV IPV6 SOURCE ROUTER ID STATE";
    leaf type {
      type Yang2bag-string;
      description
        "The type of subTLV being described";
    }
    leaf ipv6-source-router-id {
      type Yang2bag-string;
      description
        "IPv6 Source router ID address";
    }
  }

  grouping OVERLAY-OCNI-ISIS-SUBTLV-IPV6-SOURCE-ROUTER-ID {
    description
      "This container defines sub-TLV 12";
    container state {
      description
        "State parameters of sub-TLV 12";
      uses SUBTLV-IPV6-SOURCE-ROUTER-ID-STATE;
    }
  }

  grouping OVERLAY-OCNI-ISIS-PREFIXES-SUBTLVS-SUBTLV-STATE {
    description
      "State parameters for a prefix";
    leaf type {
      type Yang2bag-string;
      description
        "The type of subTLV being described";
    }
  }

  grouping SUBTLV-IPV4-SOURCE-ROUTER-ID-STATE {
    description
      "SUBTLV IPV4 SOURCE ROUTER ID STATE";
    leaf type {
      type Yang2bag-string;
      description
        "The type of subTLV being described";
    }
    leaf ipv4-source-router-id {
      type Yang2bag-string;
      description
        "IPv4 Source router ID address";
    }
  }

  grouping OVERLAY-OCNI-ISIS-SUBTLV-IPV4-SOURCE-ROUTER-ID {
    description
      "This container defines sub-TLV 11";
    container state {
      description
        "State parameters of sub-TLV 11";
      uses SUBTLV-IPV4-SOURCE-ROUTER-ID-STATE;
    }
  }

  grouping PREFIX-SIDS-PREFIX-SID-STATE {
    description
      "PREFIX SIDS PREFIX SID STATE";
    leaf value {
      type uint32;
      description
        "IGP Prefix-SID value";
    }
    leaf algorithm {
      type uint8;
      description
        "Prefix-SID algorithm to be used for path
         computation";
    }
    leaf-list flags {
      type Openconfig-isis-lsp-prefix-sid-state-flags-enum;
      description
        "Flags associated with Prefix Segment-ID";
    }
  }

  grouping OVERLAY-OCNI-ISIS-PREFIX-SIDS-PREFIX-SID {
    description
      "Prefix Segment-ID list";
    container state {
      description
        "State parameters for Prefix-SID";
      uses PREFIX-SIDS-PREFIX-SID-STATE;
    }
  }

  grouping SUBTLV-TAG64-STATE {
    description
      "SUBTLV TAG64 STATE";
    leaf-list tag64 {
      type uint64;
      description
        "List of 64-bit tags associated with the prefix";
    }
  }

  grouping OVERLAY-OCNI-ISIS-SUBTLV-TAG64 {
    description
      "This container defines sub-TLV 2";
    container state {
      description
        "State parameters of sub-TLV 2";
      uses SUBTLV-TAG64-STATE;
    }
  }

  grouping SUBTLV-TAG-STATE {
    description
      "SUBTLV TAG STATE";
    leaf-list tag32 {
      type uint32;
      description
        "List of 32-bit tags associated with the prefix";
    }
  }

  grouping OVERLAY-OCNI-ISIS-SUBTLV-TAG {
    description
      "This container defines sub-TLV 1";
    container state {
      description
        "State parameters of sub-TLV 1";
      uses SUBTLV-TAG-STATE;
    }
  }

  grouping OVERLAY-OCNI-ISIS-PREFIXES-STATE {
    description
      "State parameters of IPv6 prefix attributes";
    leaf up-down {
      type boolean;
      description
        "The up/down bit";
    }
    leaf sbit {
      type boolean;
      description
        "The Sub-TLV present bit";
    }
    leaf prefix {
      type Yang2bag-string;
      description
        "IPv4 prefix contained within extended
         reachability TLVs";
    }
    leaf metric {
      type uint32;
      description
        "ISIS metric value";
    }
  }

  grouping HOST-NAME-STATE {
    description
      "HOST NAME STATE";
    leaf-list host-name {
      type Yang2bag-string;
      description
        "Name of the node";
    }
  }

  grouping OVERLAY-OCNI-ISIS-HOSTNAME {
    description
      "This container defines TLV 137";
    container state {
      description
        "State parameters of ISIS TLV 137";
      uses HOST-NAME-STATE;
    }
  }

  grouping PURGE-OI-STATE {
    description
      "PURGE OI STATE";
    leaf system-id-count {
      type uint8;
      description
        "Number of system IDs carried in this TLV";
    }
    leaf source-system-id {
      type Yang2bag-string;
      description
        "System ID of the Intermediate System that
         inserted this TLV";
    }
    leaf received-system-id {
      type Yang2bag-string;
      description
        "System ID of the Intermediate System from which
         the purge was received";
    }
  }

  grouping OVERLAY-OCNI-ISIS-PURGE-OI {
    description
      "This container defines ISIS purge TLV";
    container state {
      description
        "State parameters of TLV 13";
      uses PURGE-OI-STATE;
    }
  }

  grouping OVERLAY-OCNI-ISIS-TLV-STATE {
    description
      "Operational state parameters relating to the
       specified LSP";
    leaf type {
      type Yang2bag-string;
      description
        "The type of TLV being described";
    }
  }

  grouping IPV6-SRLG-STATE {
    description
      "IPV6 SRLG STATE";
    leaf instance-number {
      type uint32;
      description
        "An arbitrary unsigned 32-bit integer used to
         disambiguate the instance of TLV 138";
    }
    leaf system-id {
      type Yang2bag-string;
      description
        "Neighbor system ID";
    }
    leaf psn-number {
      type uint8;
      description
        "Pseudonode number if the neighbor is on a LAN
         interface";
    }
    leaf ipv6-interface-address {
      type Yang2bag-string;
      description
        "IPv6 interface address or Link Local Identifier";
    }
    leaf ipv6-neighbor-address {
      type Yang2bag-string;
      description
        "IPv6 neighbor address or Link Remote Identifier";
    }
    leaf-list flags {
      type Openconfig-isis-lsp-ipv6-srlg-state-flags-enum;
      description
        "IPv6 SRLG flags";
    }
    leaf-list srlg-value {
      type uint32;
      description
        "SRLG values";
    }
  }

  grouping OVERLAY-OCNI-ISIS-IPV6-SRLG {
    description
      "Instance of the IPv6 SRLG TLV";
    container state {
      description
        "State parameters of TLV 139";
      uses IPV6-SRLG-STATE;
    }
  }

  grouping NEIGHBOR-UNDEFINED-SUBTLVS-UNDEFINED-SUBTLV-STATE {
    description
      "NEIGHBOR UNDEFINED SUBTLVS UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-NEIGHBOR-UNDEFINED-SUBTLVS-UNDEFINED-SUBTLV {
    description
      "Sub-TLVs that are not defined in the model or not
       recognised by system";
    container state {
      description
        "State parameters of the undefined sub-TLV";
      uses NEIGHBOR-UNDEFINED-SUBTLVS-UNDEFINED-SUBTLV-STATE;
    }
  }

  grouping OVERLAY-OCNI-ISIS-NEIGHBOR-STATE {
    description
      "State parameters of MT neighbor";
    leaf mt-id {
      type uint16;
      description
        "Identifier of a topology being announced";
    }
    leaf system-id {
      type Yang2bag-string;
      description
        "System-id of the IS neighbor";
    }
    leaf metric {
      type uint32;
      description
        "ISIS metric value";
    }
  }

  grouping SUBTLV-EXTENDED-ADMIN-GROUP-STATE {
    description
      "SUBTLV EXTENDED ADMIN GROUP STATE";
    leaf-list extended-admin-group {
      type uint32;
      description
        "The extended-admin-group sub-TLV is used in
         addition to the Administrative Groups when it is
         desirable to make more than 32 colors available
         for advertisement in a network";
    }
  }

  grouping OVERLAY-OCNI-ISIS-SUBTLV-EXTENDED-ADMIN-GROUP {
    description
      "This container defines sub-TLV 14";
    container state {
      description
        "State parameters of sub-TLV 14";
      uses SUBTLV-EXTENDED-ADMIN-GROUP-STATE;
    }
  }

  grouping LAN-ADJACENCY-SIDS-LAN-ADJACENCY-SID-STATE {
    description
      "LAN ADJACENCY SIDS LAN ADJACENCY SID STATE";
    leaf value {
      type uint32;
      description
        "LAN Adjacency-SID value";
    }
    leaf weight {
      type uint8;
      description
        "Value that represents the weight of the Adj-SID
         for the purpose of load balancing";
    }
    leaf neighbor-id {
      type Yang2bag-string;
      description
        "System ID of the neighbor associated with the
         LAN- Adj-Segment-ID value";
    }
    leaf-list flags {
      type Openconfig-isis-lsp-lan-adjacency-sid-state-flags-enum;
      description
        "Flags associated with LAN-Adj-Segment-ID";
    }
  }

  grouping OVERLAY-OCNI-ISIS-LAN-ADJACENCY-SIDS-LAN-ADJACENCY-SID {
    description
      "Adjacency Segment-IDs List";
    container state {
      description
        "State parameters of LAN Adjacency-SID";
      uses LAN-ADJACENCY-SIDS-LAN-ADJACENCY-SID-STATE;
    }
  }

  grouping SUBTLV-ADMIN-GROUP-STATE {
    description
      "SUBTLV ADMIN GROUP STATE";
    leaf-list admin-group {
      type uint32;
      description
        "The administrative group sub-TLV contains a
         4-octet bit mask assigned by the network
         administrator";
    }
  }

  grouping OVERLAY-OCNI-ISIS-SUBTLV-ADMIN-GROUP {
    description
      "This container defines sub-TLV 3";
    container state {
      description
        "State parameters of sub-TLV 3";
      uses SUBTLV-ADMIN-GROUP-STATE;
    }
  }

  grouping SUBTLV-IPV6-INTERFACE-ADDRESS-STATE {
    description
      "SUBTLV IPV6 INTERFACE ADDRESS STATE";
    leaf-list ipv6-interface-address {
      type Yang2bag-string;
      description
        "Contains a 16-octet IPv6 address for the
         interface described by the containing  Extended
         IS Reachability TLV";
    }
  }

  grouping OVERLAY-OCNI-ISIS-SUBTLV-IPV6-INTERFACE-ADDRESS {
    description
      "This container defines sub-TLV 12";
    container state {
      description
        "State parameters of sub-TLV 12";
      uses SUBTLV-IPV6-INTERFACE-ADDRESS-STATE;
    }
  }

  grouping SUBTLV-TE-DEFAULT-METRIC-STATE {
    description
      "SUBTLV TE DEFAULT METRIC STATE";
    leaf te-default-metric {
      type uint32;
      description
        "This metric is administratively assigned and can
         be used to present a differently weighted
         topology to traffic engineering SPF calculations";
    }
  }

  grouping OVERLAY-OCNI-ISIS-SUBTLV-TE-DEFAULT-METRIC {
    description
      "This container defines sub-TLV 18";
    container state {
      description
        "State parameters of sub-TLV 18";
      uses SUBTLV-TE-DEFAULT-METRIC-STATE;
    }
  }

  grouping SUBTLV-IPV4-NEIGHBOR-ADDRESS-STATE {
    description
      "SUBTLV IPV4 NEIGHBOR ADDRESS STATE";
    leaf-list ipv4-neighbor-address {
      type Yang2bag-string;
      description
        "A single IPv4 address for a neighboring router
         on this link";
    }
  }

  grouping OVERLAY-OCNI-ISIS-SUBTLV-IPV4-NEIGHBOR-ADDRESS {
    description
      "This container defines sub-TLV 8";
    container state {
      description
        "State parameters of sub-TLV 8";
      uses SUBTLV-IPV4-NEIGHBOR-ADDRESS-STATE;
    }
  }

  grouping UNRESERVED-BANDWIDTH-SETUP-PRIORITY-STATE {
    description
      "UNRESERVED BANDWIDTH SETUP PRIORITY STATE";
    leaf priority {
      type uint8;
      description
        "Setup priority level of 0 through 7 to be used
         by Unreserved Bandwidth sub-TLV 11";
    }
    leaf unreserved-bandwidth {
      type Yang2bag-string;
      description
        "The amount of bandwidth reservable in this
         direction on this link";
    }
  }

  grouping OVERLAY-OCNI-ISIS-UNRESERVED-BANDWIDTH-SETUP-PRIORITY {
    description
      "Setup priority (0 through 7) for unreserved
       bandwidth";
    container state {
      description
        "State parameters of IS Extended Reachability
         sub-TLV 11";
      uses UNRESERVED-BANDWIDTH-SETUP-PRIORITY-STATE;
    }
  }

  grouping OVERLAY-OCNI-ISIS-BANDWIDTH-CONSTRAINTS-BANDWIDTH-CONSTRAINT-STATE {
    description
      "State parameters of IS Extended Reachability
       sub-TLV 22";
    leaf model-id {
      type uint8;
      description
        "Identifier for the Bandwidth Constraints  Model
         currently in use by the LSR initiating the IGP
         advertisement";
    }
  }

  grouping CONSTRAINTS-CONSTRAINT-STATE {
    description
      "CONSTRAINTS CONSTRAINT STATE";
    leaf constraint-id {
      type uint32;
      description
        "Unique reference for the bandwidth constraint
         level";
    }
    leaf bandwidth {
      type Yang2bag-string;
      units "byte/s";
      description
        "The bandwidth constraint, expressed as a 32-bit
         IEEE floating point number expressed in bytes
         per second";
    }
  }

  grouping OVERLAY-OCNI-ISIS-CONSTRAINTS-CONSTRAINT {
    description
      "List of the constraints within the Bandwidth
       Constraints sub-TLV";
    container state {
      description
        "Operational state parameters of the BCN level";
      uses CONSTRAINTS-CONSTRAINT-STATE;
    }
  }

  grouping ADJACENCY-SIDS-ADJACENCY-SID-STATE {
    description
      "ADJACENCY SIDS ADJACENCY SID STATE";
    leaf value {
      type uint32;
      description
        "Adjacency-SID value";
    }
    leaf weight {
      type uint8;
      description
        "Value that represents the weight of the Adj-SID
         for the purpose of load balancing";
    }
    leaf-list flags {
      type Openconfig-isis-lsp-adjacency-sid-state-flags-enum;
      description
        "Flags associated with Adj-Segment-ID";
    }
  }

  grouping OVERLAY-OCNI-ISIS-ADJACENCY-SIDS-ADJACENCY-SID {
    description
      "Adjacency Segment-IDs List";
    container state {
      description
        "State parameters of Adjacency-SID";
      uses ADJACENCY-SIDS-ADJACENCY-SID-STATE;
    }
  }

  grouping SUBTLV-MAX-LINK-BANDWIDTH-STATE {
    description
      "SUBTLV MAX LINK BANDWIDTH STATE";
    leaf max-link-bandwidth {
      type Yang2bag-string;
      description
        "The maximum bandwidth that can be used on this
         link in this direction (from the system
         originating the LSP to its neighbors)";
    }
  }

  grouping OVERLAY-OCNI-ISIS-SUBTLV-MAX-LINK-BANDWIDTH {
    description
      "This container defines sub-TLV 9";
    container state {
      description
        "State parameters of sub-TLV 9";
      uses SUBTLV-MAX-LINK-BANDWIDTH-STATE;
    }
  }

  grouping SUBTLV-MAX-RESERVABLE-LINK-BANDWIDTH-STATE {
    description
      "SUBTLV MAX RESERVABLE LINK BANDWIDTH STATE";
    leaf max-reservable-link-bandwidth {
      type Yang2bag-string;
      description
        "The maximum amount of bandwidth that can be
         reserved in this direction on this link";
    }
  }

  grouping OVERLAY-OCNI-ISIS-SUBTLV-MAX-RESERVABLE-LINK-BANDWIDTH {
    description
      "This container defines sub-TLV 10";
    container state {
      description
        "State parameters of sub-TLV 10";
      uses SUBTLV-MAX-RESERVABLE-LINK-BANDWIDTH-STATE;
    }
  }

  grouping SUBTLV-IPV4-INTERFACE-ADDRESS-STATE {
    description
      "SUBTLV IPV4 INTERFACE ADDRESS STATE";
    leaf-list ipv4-interface-address {
      type Yang2bag-string;
      description
        "A 4-octet IPv4 address for the interface
         described by the (main) TLV";
    }
  }

  grouping OVERLAY-OCNI-ISIS-SUBTLV-IPV4-INTERFACE-ADDRESS {
    description
      "This container defines sub-TLV 6";
    container state {
      description
        "State parameters of sub-TLV 6";
      uses SUBTLV-IPV4-INTERFACE-ADDRESS-STATE;
    }
  }

  grouping SUBTLV-IPV6-NEIGHBOR-ADDRESS-STATE {
    description
      "SUBTLV IPV6 NEIGHBOR ADDRESS STATE";
    leaf-list ipv6-neighbor-address {
      type Yang2bag-string;
      description
        "Contains a 16-octet IPv6 address for a
         neighboring router on the link described by the
         (main) TLV";
    }
  }

  grouping OVERLAY-OCNI-ISIS-SUBTLV-IPV6-NEIGHBOR-ADDRESS {
    description
      "This container defines sub-TLV 13";
    container state {
      description
        "State parameters of sub-TLV 13";
      uses SUBTLV-IPV6-NEIGHBOR-ADDRESS-STATE;
    }
  }

  grouping SUBTLVS-SUBTLV-FLAGS-STATE {
    description
      "SUBTLVS SUBTLV FLAGS STATE";
    leaf type {
      type Yang2bag-string;
      description
        "The type of subTLV being described";
    }
    leaf-list flags {
      type Openconfig-isis-lsp-flags-state-flags-enum;
      description
        "Additional prefix reachability flags";
    }
  }

  grouping OVERLAY-OCNI-ISIS-SUBTLVS-SUBTLV-FLAGS {
    description
      "This container defines sub-TLV 4";
    container state {
      description
        "State parameters of sub-TLV 4";
      uses SUBTLVS-SUBTLV-FLAGS-STATE;
    }
  }

  grouping SUBTLV-PREFIX-SIDS-PREFIX-SID-STATE {
    description
      "SUBTLV PREFIX SIDS PREFIX SID STATE";
    leaf value {
      type uint32;
      description
        "IGP Prefix-SID value";
    }
    leaf algorithm {
      type uint8;
      description
        "Prefix-SID algorithm to be used for path
         computation";
    }
    leaf-list flags {
      type Openconfig-isis-lsp-prefix-sid-state-flags-enum;
      description
        "Flags associated with Prefix Segment-ID";
    }
  }

  grouping OVERLAY-OCNI-ISIS-SUBTLV-PREFIX-SIDS-PREFIX-SID {
    description
      "Prefix Segment-ID list";
    container state {
      description
        "State parameters for Prefix-SID";
      uses SUBTLV-PREFIX-SIDS-PREFIX-SID-STATE;
    }
  }

  grouping SUBTLVS-SUBTLV-IPV6-SOURCE-ROUTER-ID-STATE {
    description
      "SUBTLVS SUBTLV IPV6 SOURCE ROUTER ID STATE";
    leaf type {
      type Yang2bag-string;
      description
        "The type of subTLV being described";
    }
    leaf ipv6-source-router-id {
      type Yang2bag-string;
      description
        "IPv6 Source router ID address";
    }
  }

  grouping OVERLAY-OCNI-ISIS-SUBTLVS-SUBTLV-IPV6-SOURCE-ROUTER-ID {
    description
      "This container defines sub-TLV 12";
    container state {
      description
        "State parameters of sub-TLV 12";
      uses SUBTLVS-SUBTLV-IPV6-SOURCE-ROUTER-ID-STATE;
    }
  }

  grouping SUBTLVS-SUBTLV-IPV4-SOURCE-ROUTER-ID-STATE {
    description
      "SUBTLVS SUBTLV IPV4 SOURCE ROUTER ID STATE";
    leaf type {
      type Yang2bag-string;
      description
        "The type of subTLV being described";
    }
    leaf ipv4-source-router-id {
      type Yang2bag-string;
      description
        "IPv4 Source router ID address";
    }
  }

  grouping OVERLAY-OCNI-ISIS-SUBTLVS-SUBTLV-IPV4-SOURCE-ROUTER-ID {
    description
      "This container defines sub-TLV 11";
    container state {
      description
        "State parameters of sub-TLV 11";
      uses SUBTLVS-SUBTLV-IPV4-SOURCE-ROUTER-ID-STATE;
    }
  }

  grouping OVERLAY-OCNI-ISIS-PREFIX-SUBTLVS-SUBTLV-STATE {
    description
      "State parameters for a prefix";
    leaf type {
      type Yang2bag-string;
      description
        "The type of subTLV being described";
    }
  }

  grouping SUBTLVS-SUBTLV-TAG-STATE {
    description
      "SUBTLVS SUBTLV TAG STATE";
    leaf-list tag32 {
      type uint32;
      description
        "List of 32-bit tags associated with the prefix";
    }
  }

  grouping OVERLAY-OCNI-ISIS-SUBTLVS-SUBTLV-TAG {
    description
      "This container defines sub-TLV 1";
    container state {
      description
        "State parameters of sub-TLV 1";
      uses SUBTLVS-SUBTLV-TAG-STATE;
    }
  }

  grouping SUBTLVS-SUBTLV-TAG64-STATE {
    description
      "SUBTLVS SUBTLV TAG64 STATE";
    leaf-list tag64 {
      type uint64;
      description
        "List of 64-bit tags associated with the prefix";
    }
  }

  grouping OVERLAY-OCNI-ISIS-SUBTLVS-SUBTLV-TAG64 {
    description
      "This container defines sub-TLV 2";
    container state {
      description
        "State parameters of sub-TLV 2";
      uses SUBTLVS-SUBTLV-TAG64-STATE;
    }
  }

  grouping PREFIXES-PREFIX-UNDEFINED-SUBTLVS-UNDEFINED-SUBTLV-STATE {
    description
      "PREFIXES PREFIX UNDEFINED SUBTLVS UNDEFINED
       SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-PREFIXES-PREFIX-UNDEFINED-SUBTLVS-UNDEFINED-SUBTLV {
    description
      "Sub-TLVs that are not defined in the model or not
       recognised by system";
    container state {
      description
        "State parameters of the undefined sub-TLV";
      uses PREFIXES-PREFIX-UNDEFINED-SUBTLVS-UNDEFINED-SUBTLV-STATE;
    }
  }

  grouping OVERLAY-OCNI-ISIS-PREFIXES-PREFIX-STATE {
    description
      "State parameters of an IPv4 extended prefix";
    leaf up-down {
      type boolean;
      description
        "The up/down bit";
    }
    leaf sbit {
      type boolean;
      description
        "The Sub-TLV present bit";
    }
    leaf prefix {
      type Yang2bag-string;
      description
        "IPv4 prefix contained within extended
         reachability TLVs";
    }
    leaf metric {
      type uint32;
      description
        "ISIS metric value";
    }
    leaf mt-id {
      type uint16;
      description
        "Multi-topology ID";
    }
  }

  grouping SRGB-DESCRIPTOR-STATE {
    description
      "SRGB DESCRIPTOR STATE";
    leaf range {
      type uint32;
      description
        "Number of SRGB elements";
    }
    leaf label {
      type Yang2bag-string;
      description
        "The first value of the SRGB when expressed as an
         MPLS label";
    }
  }

  grouping SRGB-DESCRIPTOR {
    description
      "SRGB DESCRIPTOR";
    container state {
      description
        "State parameters of the SR range";
      uses SRGB-DESCRIPTOR-STATE;
    }
  }

  grouping SRGB-DESCRIPTORS {
    description
      "SRGB DESCRIPTORS";
    list srgb-descriptor {
      description
        "Descriptor entry within the SR capabilty sub-TLV";
      uses SRGB-DESCRIPTOR;
    }
  }

  grouping SEGMENT-ROUTING-CAPABILITY-STATE {
    description
      "SEGMENT ROUTING CAPABILITY STATE";
    leaf-list flags {
      type Openconfig-isis-lsp-segment-routing-capability-state-flags-enum;
      description
        "Segment Routing Capability Flags";
    }
  }

  grouping OVERLAY-OCNI-ISIS-SEGMENT-ROUTING-CAPABILITY {
    description
      "This container defines SR Capability sub-TLV 2";
    container state {
      description
        "State parameters of IS SR Router Capability";
      uses SEGMENT-ROUTING-CAPABILITY-STATE;
    }
    container srgb-descriptors {
      description
        "SRGB Descriptors included within the SR
         capability sub-TLV";
      uses SRGB-DESCRIPTORS;
    }
  }

  grouping SEGMENT-ROUTING-ALGORITHM-STATE {
    description
      "SEGMENT ROUTING ALGORITHM STATE";
    leaf algorithm {
      type Openconfig-isis-lsp-algorithm-enum;
      description
        "The Segment Routing algorithm that is described
         by the TLV";
    }
  }

  grouping OVERLAY-OCNI-ISIS-SEGMENT-ROUTING-ALGORITHM {
    description
      "List of the segment routing algorithsm advertised
       within the TLV";
    container state {
      description
        "State parameters of sub-TLV 19 - Segment Routing
         Algorithm";
      uses SEGMENT-ROUTING-ALGORITHM-STATE;
    }
  }

  grouping OVERLAY-OCNI-ISIS-SUBTLV-STATE {
    description
      "State parameters of IS Router Capabilities";
    leaf type {
      type Yang2bag-string;
      description
        "The type of subTLV being described";
    }
  }

  grouping UNDEFINED-SUBTLV-STATE {
    description
      "UNDEFINED SUBTLV STATE";
    leaf type {
      type uint8;
      description
        "TLV Type";
    }
    leaf length {
      type uint8;
      description
        "TLV length";
    }
    leaf value {
      type Yang2bag-string;
      description
        "TLV value";
    }
  }

  grouping OVERLAY-OCNI-ISIS-UNDEFINED-SUBTLV {
    description
      "Sub-TLVs that are not defined in the model or not
       recognised by system";
    container state {
      description
        "State parameters of the undefined sub-TLV";
      uses UNDEFINED-SUBTLV-STATE;
    }
  }

  grouping OVERLAY-OCNI-ISIS-ROUTER-CAPABILITY-STATE {
    description
      "State parameters of TLV 242";
    leaf instance-number {
      type uint32;
      description
        "A unique instance number for the instance of the
         router capabilities TLV";
    }
    leaf router-id {
      type Yang2bag-string;
      description
        "IPv4 router-id";
    }
    leaf-list flags {
      type Openconfig-isis-lsp-router-capability-state-flags-enum;
      description
        "Router capability flags";
    }
  }

  grouping IPV4-INTERFACE-ADDRESSES-STATE {
    description
      "IPV4 INTERFACE ADDRESSES STATE";
    leaf-list ipv4-interface-address {
      type Yang2bag-string;
      description
        "IPv4 address(es) of the interface corresponding
         to the SNPA over which this PDU is to be
         transmitted";
    }
  }

  grouping OVERLAY-OCNI-ISIS-IPV4-INTERFACE-ADDRESSES {
    description
      "This container defines TLV 132";
    container state {
      description
        "State parameters of ISIS TLV 132";
      uses IPV4-INTERFACE-ADDRESSES-STATE;
    }
  }

  grouping AUTHENTICATION-STATE {
    description
      "AUTHENTICATION STATE";
    leaf crypto-type {
      type Openconfig-isis-lsp-crypto-type-enum;
      description
        "Authentication type to be used";
    }
    leaf authentication-key {
      type Yang2bag-string;
      description
        "Authentication key to be used";
    }
  }

  grouping OVERLAY-OCNI-ISIS-AUTHENTICATION {
    description
      "This container defines authentication information
       of the node";
    container state {
      description
        "State parameters of TLV 10";
      uses AUTHENTICATION-STATE;
    }
  }

  grouping AREA-ADDRESS-STATE {
    description
      "AREA ADDRESS STATE";
    leaf-list area-address {
      type Yang2bag-string;
      description
        "Area adress(es) of the IS";
    }
  }

  grouping OVERLAY-OCNI-ISIS-AREA-ADDRESS {
    description
      "This container defines TLV 1";
    container state {
      description
        "State parameters of ISIS TLV 1";
      uses AREA-ADDRESS-STATE;
    }
  }

  grouping OVERLAY-OCNI-ISIS-LSP-STATE {
    description
      "State parameters of Link State PDU";
    leaf lsp-id {
      type Yang2bag-string;
      description
        "LSP ID of the LSP";
    }
    leaf maximum-area-addresses {
      type uint8;
      description
        "Number of area addresses permitted for this ISs
         area";
    }
    leaf version {
      type uint8;
      description
        "PDU version";
    }
    leaf version2 {
      type uint8;
      description
        "PDU version2";
    }
    leaf id-length {
      type uint8;
      description
        "Length of the ID field of NSAP addresses and
         NETs used in this routing domain";
    }
    leaf pdu-type {
      type Openconfig-isis-lsp-pdu-type-enum;
      description
        "Link State PDU type";
    }
    leaf remaining-lifetime {
      type uint16;
      units "second";
      description
        "Remaining lifetime in seconds before the LSP
         expiration";
    }
    leaf sequence-number {
      type uint32;
      description
        "Sequence number of the LSP";
    }
    leaf checksum {
      type uint16;
      description
        "Checksum of the LSP";
    }
    leaf pdu-length {
      type uint16;
      description
        "Total length of the LSP";
    }
    leaf is-type {
      type uint8;
      description
        "Type of neighboring system";
    }
    leaf-list flags {
      type Openconfig-isis-lsp-flags-enum;
      description
        "LSP Type-Block flags";
    }
  }

  grouping UNDEFINED-TLV-STATE {
    description
      "UNDEFINED TLV STATE";
    leaf type {
      type uint8;
      description
        "TLV Type";
    }
    leaf length {
      type uint8;
      description
        "TLV length";
    }
    leaf value {
      type Yang2bag-string;
      description
        "TLV value";
    }
  }

  grouping OVERLAY-OCNI-ISIS-UNDEFINED-TLV {
    description
      "List of TLVs that are not defined within the
       model, or are not recognised by the system";
    container state {
      description
        "State parameters of the undefined TLV";
      uses UNDEFINED-TLV-STATE;
    }
  }

  grouping SYSTEM-LEVEL-COUNTERS-STATE {
    description
      "SYSTEM LEVEL COUNTERS STATE";
    leaf corrupted-lsps {
      type uint32;
      description
        "Number of corrupted in-memory LSPs detected";
    }
    leaf database-overloads {
      type uint32;
      description
        "Number of times the database has become
         overloaded";
    }
    leaf exceed-max-seq-nums {
      type uint32;
      description
        "The number of times the system has attempted to
         exceed the maximum sequence number";
    }
    leaf seq-num-skips {
      type uint32;
      description
        "Number of times a sequence number skip has
         occurred";
    }
    leaf own-lsp-purges {
      type uint32;
      description
        "Number of times a zero-aged copy of the system's
         own LSP is received from some other node";
    }
    leaf id-len-mismatch {
      type uint32;
      description
        "Number of times a PDU is received with a
         different value for ID field length from that of
         the receiving system";
    }
    leaf max-area-address-mismatches {
      type uint32;
      description
        "Number of times a PDU is received with a
         different value for MaximumAreaAddresses from
         that of the receiving system";
    }
    leaf spf-runs {
      type uint32;
      description
        "The number of times SPF was ran at this level";
    }
    leaf lsp-errors {
      type uint32;
      description
        "The number of received LSPs with errors";
    }
  }

  grouping OVERLAY-OCNI-ISIS-SYSTEM-LEVEL-COUNTERS {
    description
      "This container defines ISIS system level counters";
    container state {
      description
        "The container defines a list of system counters
         for the IS";
      uses SYSTEM-LEVEL-COUNTERS-STATE;
    }
  }

  grouping KEY-STATE {
    description
      "KEY STATE";
    leaf auth-password {
      type Yang2bag-string;
      description
        "Authentication key string";
    }
  }

  grouping KEY {
    description
      "KEY";
    container state {
      description
        "This container defines ISIS authentication key
         state";
      uses KEY-STATE;
    }
  }

  grouping OVERLAY-OCNI-ISIS-LEVEL-AUTHENTICATION {
    description
      "This container defines ISIS authentication";
    container key {
      description
        "This container defines ISIS authentication key";
      uses KEY;
    }
  }

  grouping TRAFFIC-ENGINEERING-STATE {
    description
      "TRAFFIC ENGINEERING STATE";
    leaf enabled {
      type boolean;
      description
        "When set to true, the functionality within which
         this leaf is defined is enabled, when set to
         false it is explicitly disabled";
    }
    leaf ipv4-router-id {
      type Yang2bag-ipv4-addr;
      description
        "IPv4 MPLS Traffic Engineering Router-ID";
    }
    leaf ipv6-router-id {
      type Yang2bag-ipv6-addr;
      description
        "IPv6 MPLS Traffic Engineering Router-ID";
    }
  }

  grouping OVERLAY-OCNI-ISIS-TRAFFIC-ENGINEERING {
    description
      "This container defines ISIS TE";
    container state {
      description
        "This container defines ISIS TE state information";
      uses TRAFFIC-ENGINEERING-STATE;
    }
  }

  grouping OVERLAY-OCNI-ISIS-LEVEL-STATE {
    description
      "This container defines ISIS level state
       information";
    leaf level-number {
      type uint8;
      description
        "ISIS level number (level-1, level-2)";
    }
    leaf metric-style {
      type Openconfig-isis-types-metric-style-enum;
      description
        "ISIS metric style types(narrow, wide)";
    }
    leaf authentication-check {
      type boolean;
      description
        "When set to true, reject all ISIS protocol PDUs
         that either have a mismatch in
         authentication-type or authentication-key";
    }
  }

  grouping ROUTE-PREFERENCE-STATE {
    description
      "ROUTE PREFERENCE STATE";
    leaf external-route-preference {
      type uint8;
      description
        "Administrative Distance(preference) for external
         ISIS routes";
    }
    leaf internal-route-preference {
      type uint8;
      description
        "Administrative Distance(preference) for internal
         ISIS routes";
    }
  }

  grouping OVERLAY-OCNI-ISIS-ROUTE-PREFERENCE {
    description
      "This container defines Administrative Distance
       (or preference) assigned to ISIS routes (level1
       internal, level2 internal, level1 external,
       level2 external)";
    container state {
      description
        "This container defines ISIS route preference
         state information";
      uses ROUTE-PREFERENCE-STATE;
    }
  }

  grouping TRANSPORT-STATE {
    description
      "TRANSPORT STATE";
    leaf lsp-mtu-size {
      type uint16;
      units "byte";
      description
        "The maximum size in bytes of an IS-IS Link state
         PDU";
    }
  }

  grouping OVERLAY-OCNI-ISIS-TRANSPORT {
    description
      "This container defines ISIS transport";
    container state {
      description
        "This container defines state information for
         ISIS transport parameters";
      uses TRANSPORT-STATE;
    }
  }

  grouping LSP-GENERATION-STATE {
    description
      "LSP GENERATION STATE";
    leaf lsp-max-wait-interval {
      type uint64;
      units "millisecond";
      description
        "Time interval in milliseconds that specifies max
         interval between two consecutive occurrences of
         an LSP being generated";
    }
    leaf lsp-first-wait-interval {
      type uint64;
      units "millisecond";
      description
        "Time interval in milliseconds that specifies the
         first LSP generation delay";
    }
    leaf lsp-second-wait-interval {
      type uint64;
      units "millisecond";
      description
        "Time interval in milliseconds that specifies the
         millisecond LSP generation delay";
    }
    leaf adaptive-timer {
      type Openconfig-isis-types-adaptive-timer-type-enum;
      description
        "ISIS adaptive timer types (linear, exponential)";
    }
  }

  grouping LSP-GENERATION {
    description
      "LSP GENERATION";
    container state {
      description
        "This container defines state information for
         ISIS LSP Generation timers";
      uses LSP-GENERATION-STATE;
    }
  }

  grouping SPF-STATE {
    description
      "SPF STATE";
    leaf spf-hold-interval {
      type uint64;
      units "millisecond";
      description
        "SPF Hold Down time interval in milliseconds";
    }
    leaf spf-first-interval {
      type uint64;
      units "millisecond";
      description
        "Time interval in milliseconds between the
         detection of topology change and when the SPF
         algorithm runs";
    }
    leaf spf-second-interval {
      type uint64;
      units "millisecond";
      description
        "Time interval in milliseconds between the first
         and second SPF calculation";
    }
    leaf adaptive-timer {
      type Openconfig-isis-types-adaptive-timer-type-enum;
      description
        "ISIS adaptive timer types (linear, exponential)";
    }
  }

  grouping SPF {
    description
      "SPF";
    container state {
      description
        "This container defines state information for
         ISIS SPF timers";
      uses SPF-STATE;
    }
  }

  grouping TIMERS-STATE {
    description
      "TIMERS STATE";
    leaf lsp-lifetime-interval {
      type uint16;
      units "second";
      description
        "Time interval in seconds that specifies how long
         an LSP remains in LSDB without being refreshed";
    }
    leaf lsp-refresh-interval {
      type uint16;
      units "second";
      description
        "Time interval in seconds that specifies how
         often route topology that a device originates is
         transmitted in LSPs";
    }
  }

  grouping OVERLAY-OCNI-ISIS-TIMERS {
    description
      "This container defines ISIS timers";
    container state {
      description
        "This container defines state information for
         ISIS global timers";
      uses TIMERS-STATE;
    }
    container spf {
      description
        "This container defines ISIS SPF timer settings";
      uses SPF;
    }
    container lsp-generation {
      description
        "This container defines ISIS LSP Generation";
      uses LSP-GENERATION;
    }
  }

  grouping MULTI-TOPOLOGY-STATE {
    description
      "MULTI TOPOLOGY STATE";
    leaf afi-name {
      type Yang2bag-string;
      description
        "Address-family type";
    }
    leaf safi-name {
      type Yang2bag-string;
      description
        "Subsequent address-family type";
    }
    leaf enabled {
      type boolean;
      description
        "When set to true, the functionality within which
         this leaf is defined is enabled, when set to
         false it is explicitly disabled";
    }
  }

  grouping MULTI-TOPOLOGY {
    description
      "MULTI TOPOLOGY";
    container state {
      description
        "This container defines AFI-SAFI multi-topology
         state information";
      uses MULTI-TOPOLOGY-STATE;
    }
  }

  grouping AF-STATE {
    description
      "AF STATE";
    leaf afi-name {
      type Yang2bag-string;
      description
        "Address-family type";
    }
    leaf safi-name {
      type Yang2bag-string;
      description
        "Subsequent address-family type";
    }
    leaf metric {
      type uint32;
      description
        "ISIS metric value(default=10)";
    }
    leaf enabled {
      type boolean;
      description
        "When set to true, the functionality within which
         this leaf is defined is enabled, when set to
         false it is explicitly disabled";
    }
  }

  grouping OVERLAY-OCNI-ISIS-AF {
    description
      "Address-family/Subsequent Address-family list";
    container state {
      description
        "This container defines AFI-SAFI State
         information";
      uses AF-STATE;
    }
    container multi-topology {
      description
        "This container defines multi-topology
         address-family configuration and state
         information";
      uses MULTI-TOPOLOGY;
    }
  }

  grouping LEVEL2-TO-LEVEL1-STATE {
    description
      "LEVEL2 TO LEVEL1 STATE";
    leaf-list import-policy {
      type Yang2bag-string;
      description
        "list of policy names in sequence to be applied
         on receiving a routing update in the current
         context, e";
    }
  }

  grouping LEVEL2-TO-LEVEL1 {
    description
      "LEVEL2 TO LEVEL1";
    container state {
      description
        "Operational state parameters relating to the
         propagation of prefixes from IS-IS Level 2 to
         Level 1";
      uses LEVEL2-TO-LEVEL1-STATE;
    }
  }

  grouping LEVEL1-TO-LEVEL2-STATE {
    description
      "LEVEL1 TO LEVEL2 STATE";
    leaf-list import-policy {
      type Yang2bag-string;
      description
        "list of policy names in sequence to be applied
         on receiving a routing update in the current
         context, e";
    }
  }

  grouping LEVEL1-TO-LEVEL2 {
    description
      "LEVEL1 TO LEVEL2";
    container state {
      description
        "Operational state parameters relating to the
         propagation of prefixes from IS-IS Level 1 to
         Level 2";
      uses LEVEL1-TO-LEVEL2-STATE;
    }
  }

  grouping OVERLAY-OCNI-ISIS-INTER-LEVEL-PROPAGATION-POLICIES {
    description
      "Policies to propagate prefixes between IS-IS
       levels";
    container level1-to-level2 {
      description
        "Policies relating to prefixes to be propagated
         from Level 1 to Level 2";
      uses LEVEL1-TO-LEVEL2;
    }
    container level2-to-level1 {
      description
        "Policies relating to prefixes to be propagated
         from Level2 to Level 1";
      uses LEVEL2-TO-LEVEL1;
    }
  }

  grouping OVERLAY-OCNI-ISIS-GLOBAL-STATE {
    description
      "This container defines state for ISIS global
       router";
    leaf authentication-check {
      type boolean;
      description
        "When set to true, reject all ISIS protocol PDUs
         that either have a mismatch in
         authentication-type or authentication-key";
    }
    leaf instance {
      type Yang2bag-string;
      description
        "ISIS Instance";
    }
    leaf level-capability {
      type Openconfig-isis-types-level-type-enum;
      description
        "ISIS level capability(level-1, level-2
         ,vlevel-1-2)";
    }
    leaf max-ecmp-paths {
      type uint8;
      description
        "ISIS max-paths count";
    }
    leaf iid-tlv {
      type boolean;
      description
        "ISIS Instance Identifier TLV";
    }
    leaf fast-flooding {
      type boolean;
      description
        "When set to true, IS will always flood the LSP
         that triggered an SPF before the router actually
         runs the SPF computation";
    }
    leaf-list net {
      type Yang2bag-string;
      description
        "ISIS network entity title (NET)";
    }
  }

  grouping GRACEFUL-RESTART-STATE {
    description
      "GRACEFUL RESTART STATE";
    leaf enabled {
      type boolean;
      description
        "When set to true, the functionality within which
         this leaf is defined is enabled, when set to
         false it is explicitly disabled";
    }
  }

  grouping OVERLAY-OCNI-ISIS-GRACEFUL-RESTART {
    description
      "This container defines ISIS Graceful Restart";
    container state {
      description
        "This container defines state information for
         ISIS graceful-restart";
      uses GRACEFUL-RESTART-STATE;
    }
  }

  grouping NSR-STATE {
    description
      "NSR STATE";
    leaf enabled {
      type boolean;
      description
        "When set to true, the functionality within which
         this leaf is defined is enabled, when set to
         false it is explicitly disabled";
    }
  }

  grouping OVERLAY-OCNI-ISIS-NSR {
    description
      "This container defines ISIS Non-Stop Routing";
    container state {
      description
        "This container defines state for
         Non-Stop-Routing";
      uses NSR-STATE;
    }
  }

  grouping ATTACHED-BIT-STATE {
    description
      "ATTACHED BIT STATE";
    leaf ignore-bit {
      type boolean;
      description
        "When set to true, if the attached bit is set on
         an incoming Level 1 IS-IS, the local system
         ignores it";
    }
    leaf suppress-bit {
      type boolean;
      description
        "When set to true, if the local IS acts as a L1L2
         router, then the attached bit is not advertised
         in locally generated PDUs";
    }
  }

  grouping OVERLAY-OCNI-ISIS-ATTACHED-BIT {
    description
      "This container defines Attached Bit";
    container state {
      description
        "This container defines state for Link State PDU
         Bit";
      uses ATTACHED-BIT-STATE;
    }
  }

  grouping RESET-TRIGGER-STATE {
    description
      "RESET TRIGGER STATE";
    leaf reset-trigger {
      type Yang2bag-string;
      description
        "In the case that the system sets the overload
         bit on start, the system should reset the bit (i";
    }
    leaf delay {
      type uint16;
      units "second";
      description
        "If a reset trigger is specified, the system
         should delay resetting the overload bit for the
         specified number of seconds after the trigger
         occurs";
    }
  }

  grouping OVERLAY-OCNI-ISIS-RESET-TRIGGER {
    description
      "This list describes ISIS Overload reset trigger
       reasons";
    container state {
      description
        "This container defines state for ISIS Overload
         Bit reset triggers";
      uses RESET-TRIGGER-STATE;
    }
  }

  grouping OVERLAY-OCNI-ISIS-OVERLOAD-BIT-STATE {
    description
      "This container defines state for ISIS Overload
       Bit";
    leaf set-bit {
      type boolean;
      description
        "When set to true, IS-IS overload bit is set";
    }
    leaf set-bit-on-boot {
      type boolean;
      description
        "When set to true, the IS-IS overload bit is set
         on system boot";
    }
    leaf advertise-high-metric {
      type boolean;
      description
        "When set to true, the local IS advertises links
         with the highest available metric regardless of
         their configured metric";
    }
  }

  grouping SEGMENT-ROUTING-STATE {
    description
      "SEGMENT ROUTING STATE";
    leaf enabled {
      type boolean;
      description
        "When this leaf is set to true, the segment
         routing extensions are utilised within the IGP";
    }
  }

  grouping OVERLAY-OCNI-ISIS-SEGMENT-ROUTING {
    description
      "Configuration and operational state relating to
       segment routing";
    container state {
      description
        "Operational state parameters relating to segment
         routing for the IGP instance";
      uses SEGMENT-ROUTING-STATE;
    }
  }

  grouping INTERFACE-TIMERS-STATE {
    description
      "INTERFACE TIMERS STATE";
    leaf csnp-interval {
      type uint16;
      units "second";
      description
        "The interval, specified in seconds, at which
         periodic CSNP packets should be transmitted by
         the local IS";
    }
    leaf lsp-pacing-interval {
      type uint64;
      units "millisecond";
      description
        "The interval interval in milliseconds between
         the detection of topology change and when the
         SPF algorithm runs";
    }
  }

  grouping OVERLAY-OCNI-ISIS-INTERFACE-TIMERS {
    description
      "This container describes ISIS interface timers
       configuration";
    container state {
      description
        "This container defines state information for
         ISIS interface timers";
      uses INTERFACE-TIMERS-STATE;
    }
  }

  grouping AUTHENTICATION-KEY-STATE {
    description
      "AUTHENTICATION KEY STATE";
    leaf auth-password {
      type Yang2bag-string;
      description
        "Authentication key string";
    }
  }

  grouping AUTHENTICATION-KEY {
    description
      "AUTHENTICATION KEY";
    container state {
      description
        "This container defines ISIS authentication key
         state";
      uses AUTHENTICATION-KEY-STATE;
    }
  }

  grouping OVERLAY-OCNI-ISIS-INTERFACE-AUTHENTICATION {
    description
      "This container defines ISIS authentication";
    container key {
      description
        "This container defines ISIS authentication key";
      uses AUTHENTICATION-KEY;
    }
  }

  grouping CIRCUIT-COUNTERS-STATE {
    description
      "CIRCUIT COUNTERS STATE";
    leaf adj-changes {
      type uint32;
      description
        "Number of times an adjacency state change has
         occurred on this circuit";
    }
    leaf rejected-adj {
      type uint32;
      description
        "Number of times an adjacency has been rejected
         on this circuit";
    }
    leaf id-field-len-mismatches {
      type uint32;
      description
        "Number of times an IS-IS control PDU with an ID
         field length different from that for this system
         has been received";
    }
    leaf max-area-address-mismatches {
      type uint32;
      description
        "Number of times an IS-IS control PDU with a max
         area address field different from that for this
         system has been received";
    }
    leaf auth-fails {
      type uint32;
      description
        "Number of times an IS-IS control PDU with the
         correct auth type has failed to pass
         authentication validation";
    }
    leaf lan-dis-changes {
      type uint32;
      description
        "Number of times the Designated IS has changed on
         this circuit at this level";
    }
  }

  grouping OVERLAY-OCNI-ISIS-CIRCUIT-COUNTERS {
    description
      "This container defines state information for ISIS
       circuit counters";
    container state {
      description
        "The container defines a list of counters for IS
         circuit";
      uses CIRCUIT-COUNTERS-STATE;
    }
  }

  grouping SEGMENT-ROUTING-PREFIX-SIDS-PREFIX-SID-STATE {
    description
      "SEGMENT ROUTING PREFIX SIDS PREFIX SID STATE";
    leaf prefix {
      type Yang2bag-string;
      description
        "The IP prefix for which the IGP prefix SID
         should be advertised";
    }
    leaf sid-id {
      type Yang2bag-string;
      description
        "The Segment Identifier to be used when
         advertising the IGP Prefix SID";
    }
    leaf label-options {
      type Openconfig-segment-routing-label-options-enum;
      description
        "The options associated with the IGP prefix SID
         for MPLS";
    }
  }

  grouping OVERLAY-OCNI-ISIS-SEGMENT-ROUTING-PREFIX-SIDS-PREFIX-SID {
    description
      "An IGP prefix that should have a segment routing
       IGP-Prefix SID allocated to it";
    container state {
      description
        "Operational state parameters for the IGP-Prefix
         SID";
      uses SEGMENT-ROUTING-PREFIX-SIDS-PREFIX-SID-STATE;
    }
  }

  grouping OVERLAY-OCNI-ISIS-AF-STATE {
    description
      "This container defines AFI-SAFI State information";
    leaf afi-name {
      type Yang2bag-string;
      description
        "Address-family type";
    }
    leaf safi-name {
      type Yang2bag-string;
      description
        "Subsequent address-family type";
    }
    leaf metric {
      type uint32;
      description
        "ISIS metric value(default=10)";
    }
  }

  grouping LEVEL-TIMERS-STATE {
    description
      "LEVEL TIMERS STATE";
    leaf hello-interval {
      type uint32;
      description
        "ISIS hello-interval value";
    }
    leaf hello-multiplier {
      type uint8;
      description
        "ISIS hello-multiplier value";
    }
  }

  grouping OVERLAY-OCNI-ISIS-LEVEL-TIMERS {
    description
      "This container defines ISIS timers";
    container state {
      description
        "This container defines ISIS interface
         hello-timers state";
      uses LEVEL-TIMERS-STATE;
    }
  }

  grouping ADJACENCY-STATE {
    description
      "ADJACENCY STATE";
    leaf system-id {
      type Yang2bag-string;
      description
        "ISIS neighbor system-id";
    }
    leaf neighbor-ipv4-address {
      type Yang2bag-ipv4-addr;
      description
        "ISIS Neighbor IPv4 address";
    }
    leaf neighbor-ipv6-address {
      type Yang2bag-ipv6-addr;
      description
        "ISIS Neighbor IPv6 address";
    }
    leaf neighbor-snpa {
      type Yang2bag-string;
      description
        "ISIS neighbor SNPA";
    }
    leaf local-extended-circuit-id {
      type uint32;
      description
        "Local extended circuit ID";
    }
    leaf neighbor-extended-circuit-id {
      type uint32;
      description
        "ISIS neighbor extended circuit ID";
    }
    leaf priority {
      type uint8;
      description
        "Priority of the neighboring IS(LAN Hello only)";
    }
    leaf dis-system-id {
      type Yang2bag-string;
      description
        "DIS System ID(LAN hello only)";
    }
    leaf neighbor-circuit-type {
      type Openconfig-isis-types-level-type-enum;
      description
        "Received ISIS circuit type (level-1, level-2,
         level-1-2)";
    }
    leaf adjacency-type {
      type Openconfig-isis-types-level-type-enum;
      description
        "Formed ISIS adjacency type(level-1, level-2,
         level-1-2)";
    }
    leaf adjacency-state {
      type Openconfig-isis-types-isis-interface-adj-state-enum;
      description
        "P2P 3-way ISIS adjacency state(up, down, init,
         failed)";
    }
    leaf remaining-hold-time {
      type uint16;
      units "second";
      description
        "Holding time in seconds for adjacency";
    }
    leaf up-time {
      type uint32;
      description
        "Adjacency up time";
    }
    leaf restart-support {
      type boolean;
      description
        "When set to true, Graceful-restart signaling is
         supported";
    }
    leaf restart-suppress {
      type boolean;
      description
        "When set to true, adjacency is not advertised";
    }
    leaf restart-status {
      type boolean;
      description
        "When set to true, neighbor is being helped";
    }
    leaf-list topology {
      type Yang2bag-string;
      description
        "ISIS topology type support(ipv4-unicast,
         ipv6-unicast, ipv4-multicast, ipv6-multicast)";
    }
    leaf-list area-address {
      type Yang2bag-string;
      description
        "List of ISIS area-address(es)";
    }
    leaf-list nlpid {
      type Openconfig-isis-adjacency-state-nlpid-enum;
      description
        "Supported Protocol";
    }
  }

  grouping OVERLAY-OCNI-ISIS-ADJACENCY {
    description
      "List of the local system's IS-IS adjacencies";
    container state {
      description
        "Operational state relating to the IS-IS
         adjacency with the remote system";
      uses ADJACENCY-STATE;
    }
  }

  grouping CNSP-STATE {
    description
      "CNSP STATE";
    leaf received {
      type uint32;
      description
        "The number of the specified type of PDU received
         on the interface";
    }
    leaf processed {
      type uint32;
      description
        "The number of the specified type of PDU received
         on the interface that have been processed by the
         local system";
    }
    leaf sent {
      type uint32;
      description
        "The number of the specified type of PDU that
         have been sent by the local system on the
         interface";
    }
  }

  grouping CNSP {
    description
      "CNSP";
    container state {
      description
        "Packet counters relating to CNSPs";
      uses CNSP-STATE;
    }
  }

  grouping PSNP-STATE {
    description
      "PSNP STATE";
    leaf received {
      type uint32;
      description
        "The number of the specified type of PDU received
         on the interface";
    }
    leaf processed {
      type uint32;
      description
        "The number of the specified type of PDU received
         on the interface that have been processed by the
         local system";
    }
    leaf sent {
      type uint32;
      description
        "The number of the specified type of PDU that
         have been sent by the local system on the
         interface";
    }
  }

  grouping PSNP {
    description
      "PSNP";
    container state {
      description
        "Packet counters relating to PSNPs";
      uses PSNP-STATE;
    }
  }

  grouping IIH-STATE {
    description
      "IIH STATE";
    leaf received {
      type uint32;
      description
        "The number of the specified type of PDU received
         on the interface";
    }
    leaf processed {
      type uint32;
      description
        "The number of the specified type of PDU received
         on the interface that have been processed by the
         local system";
    }
    leaf sent {
      type uint32;
      description
        "The number of the specified type of PDU that
         have been sent by the local system on the
         interface";
    }
  }

  grouping IIH {
    description
      "IIH";
    container state {
      description
        "Operational counters relating to IIH PDUs";
      uses IIH-STATE;
    }
  }

  grouping LSP-STATE {
    description
      "LSP STATE";
    leaf received {
      type uint32;
      description
        "The number of the specified type of PDU received
         on the interface";
    }
    leaf processed {
      type uint32;
      description
        "The number of the specified type of PDU received
         on the interface that have been processed by the
         local system";
    }
    leaf sent {
      type uint32;
      description
        "The number of the specified type of PDU that
         have been sent by the local system on the
         interface";
    }
  }

  grouping PACKET-COUNTERS-LSP {
    description
      "PACKET COUNTERS LSP";
    container state {
      description
        "This container defines LSP PDU counters";
      uses LSP-STATE;
    }
  }

  grouping OVERLAY-OCNI-ISIS-PACKET-COUNTERS {
    description
      "This container defines ISIS interface packet
       counters";
    container lsp {
      description
        "This container defines LSP packet counters";
      uses PACKET-COUNTERS-LSP;
    }
    container iih {
      description
        "This container defines IIH packet counters";
      uses IIH;
    }
    container psnp {
      description
        "This container defines PSNP packet counters";
      uses PSNP;
    }
    container cnsp {
      description
        "Operational state parameters relating to CNSPs";
      uses CNSP;
    }
  }

  grouping OVERLAY-OCNI-ISIS-LEVELS-LEVEL-STATE {
    description
      "This container defines interface ISIS level state
       information";
    leaf level-number {
      type uint8;
      description
        "ISIS level number(level-1, level-2)";
    }
    leaf priority {
      type uint8;
      description
        "ISIS neighbor priority(LAN hello PDU only)";
    }
  }

  grouping HELLO-AUTHENTICATION-KEY-STATE {
    description
      "HELLO AUTHENTICATION KEY STATE";
    leaf auth-password {
      type Yang2bag-string;
      description
        "Authentication key string";
    }
  }

  grouping HELLO-AUTHENTICATION-KEY {
    description
      "HELLO AUTHENTICATION KEY";
    container state {
      description
        "This container defines ISIS authentication key
         state";
      uses HELLO-AUTHENTICATION-KEY-STATE;
    }
  }

  grouping OVERLAY-OCNI-ISIS-HELLO-AUTHENTICATION {
    description
      "This container defines ISIS authentication";
    container key {
      description
        "This container defines ISIS authentication key";
      uses HELLO-AUTHENTICATION-KEY;
    }
  }

  grouping OVERLAY-OCNI-ISIS-INTERFACE-STATE {
    description
      "This container defines state information for ISIS
       interfaces";
    leaf enabled {
      type boolean;
      description
        "When set to true, the functionality within which
         this leaf is defined is enabled, when set to
         false it is explicitly disabled";
    }
    leaf interface-id {
      type Yang2bag-string;
      description
        "Interface for which ISIS configuration is to be
         applied";
    }
    leaf passive {
      type boolean;
      description
        "When set to true, the referenced interface is a
         passive interface such that it is not eligible
         to establish adjacencies with other systems, but
         is advertised into the IS-IS topology";
    }
    leaf hello-padding {
      type Openconfig-isis-types-hello-padding-type-enum;
      description
        "This leaf controls padding type for IS-IS Hello
         PDUs";
    }
    leaf circuit-type {
      type Openconfig-isis-types-circuit-type-enum;
      description
        "ISIS circuit type (p2p, broadcast)";
    }
  }

  grouping AFI-SAFI-AF-STATE {
    description
      "AFI SAFI AF STATE";
    leaf afi-name {
      type Yang2bag-string;
      description
        "Address-family type";
    }
    leaf safi-name {
      type Yang2bag-string;
      description
        "Subsequent address-family type";
    }
    leaf enabled {
      type boolean;
      description
        "When set to true, the functionality within which
         this leaf is defined is enabled, when set to
         false it is explicitly disabled";
    }
  }

  grouping OVERLAY-OCNI-ISIS-AFI-SAFI-AF {
    description
      "Address-family/Subsequent Address-family list";
    container state {
      description
        "This container defines AFI-SAFI State
         information";
      uses AFI-SAFI-AF-STATE;
    }
  }

  grouping OVERLAY-OCNI-ISIS-PROTOCOL-STATE {
    description
      "State parameters relating to the routing protocol
       instance";
    leaf identifier {
      type Yang2bag-string;
      description
        "The protocol identifier for the instance";
    }
    leaf name {
      type Yang2bag-string;
      description
        "A unique name for the protocol instance";
    }
  }

  grouping STATE {
    description
      "STATE";
    leaf id {
      type Yang2bag-string;
      description
        "A unique identifier for this interface - this is
         expressed as a free-text string";
    }
  }

  grouping OVERLAY-OCNI-ISIS-INTERFACE {
    description
      "An interface associated with the network instance";
    container state {
      description
        "Operational state parameters relating to the
         associated interface";
      uses STATE;
    }
  }
}
