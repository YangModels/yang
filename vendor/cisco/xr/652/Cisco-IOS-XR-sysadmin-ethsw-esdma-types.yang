module Cisco-IOS-XR-sysadmin-ethsw-esdma-types {
  namespace "http://www.cisco.com/ns/yang/Cisco-IOS-XR-sysadmin-ethsw-esdma-types";
  prefix esdma_types;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains the YANG enumerated type
definitions used by the Cisco IOS-XR SysAdmin
Control Ethernet commands.

Copyright(c) 2011-2017 by Cisco Systems, Inc.
All rights reserved.

    Copyright (c) 2012-2018 by Cisco Systems, Inc.
     All rights reserved.";
  revision 2018-10-26 {
    description
      "Added esdma-switch-port-type to support fdb-port range";
  }


  typedef esdma-rack-type-enum {
    type enumeration {
      enum "Unknown" {
      }
      enum "FCC" {
      }
      enum "LCC" {
      }
      enum "BSC" {
      }
      enum "COMPUTE" {
      }
    }
    description
      "The valid chassis types supported supported in Sysadmin.";
  }

  typedef esdma-rack-num-enum {
    type enumeration {
      enum "0" {
      }
      enum "1" {
      }
      enum "2" {
      }
      enum "3" {
      }
      enum "4" {
      }
      enum "5" {
      }
      enum "6" {
      }
      enum "7" {
      }
      enum "8" {
      }
      enum "9" {
      }
      enum "10" {
      }
      enum "11" {
      }
      enum "12" {
      }
      enum "13" {
      }
      enum "14" {
      }
      enum "15" {
      }
      enum "F0" {
      }
      enum "F1" {
      }
      enum "F2" {
      }
      enum "F3" {
      }
      enum "B0" {
      }
      enum "B1" {
      }
    }
    description
      "The valid rack numbers supported in Sysadmin.";
  }

  typedef esdma-cpu {
    type enumeration {
      enum "Unknown" {
      }
      enum "RP0" {
      }
      enum "RP1" {
      }
      enum "SC0" {
      }
      enum "SC1" {
      }
      enum "LC0" {
      }
      enum "LC1" {
      }
      enum "LC2" {
      }
      enum "LC3" {
      }
      enum "LC4" {
      }
      enum "LC5" {
      }
      enum "LC6" {
      }
      enum "LC7" {
      }
      enum "LC8" {
      }
      enum "LC9" {
      }
      enum "LC10" {
      }
      enum "LC11" {
      }
      enum "LC12" {
      }
      enum "LC13" {
      }
      enum "LC14" {
      }
      enum "LC15" {
      }
      enum "LC16" {
      }
      enum "LC17" {
      }
      enum "LC18" {
      }
      enum "LC19" {
      }
      enum "FC0" {
      }
      enum "FC1" {
      }
      enum "FC2" {
      }
      enum "FC3" {
      }
      enum "FC4" {
      }
      enum "FC5" {
      }
      enum "CB0" {
      }
    }
    description
      "The set of CPU enumerations that have control plane Ethernet switches or run the MLAP protocol.";
  }

  typedef esdma-switch-type-enum {
    type enumeration {
      enum "RP-SW" {
      }
      enum "SC-SW" {
      }
      enum "LC-SW" {
      }
      enum "F-SW0" {
      }
      enum "F-SW1" {
      }
      enum "FC-SW" {
      }
      enum "EOBC-SW" {
      }
      enum "EPC-SW" {
      }
      enum "CB-SW" {
      }
      enum "Unknown" {
      }
      enum "RP-SW1" {
      }
    }
    description
      "The list of Ethernet switch types";
  }

  typedef esdma-switch-yes-no-enum {
    type enumeration {
      enum "Yes" {
      }
      enum "No" {
      }
    }
  }

  typedef esdma-switch-sfp-inserted-enum {
    type enumeration {
      enum "Unknown" {
      }
      enum "Yes" {
      }
      enum "No" {
      }
      enum "Failed" {
      }
    }
  }

  typedef esdma-switch-sfp-controller-enum {
    type enumeration {
      enum "Unknown" {
      }
      enum "Switch" {
      }
      enum "PHY" {
      }
    }
  }

  typedef esdma-switch-sfp-tranceiver-type-enum {
    type enumeration {
      enum "Unspecified" {
      }
      enum "SFP" {
      }
      enum "QSFP" {
      }
      enum "Unknown" {
      }
    }
  }

  typedef esdma-sfp-encoding-enum {
    type enumeration {
      enum "Unspecified" {
      }
      enum "8B/10B" {
      }
      enum "4B/5B" {
      }
      enum "NRZ" {
      }
      enum "Manchester" {
      }
      enum "SONET Scrambled" {
      }
      enum "64B/66B" {
      }
      enum "Unknown" {
      }
    }
  }

  typedef esdma-qsfp-transceiver-enum {
    type enumeration {
      enum "QSFP-40G-LR4" {
      }
      enum "QSFP-40G-SR4" {
      }
      enum "QSFP-40G-CR4-Active" {
      }
      enum "QSFP-40G-CR4-Passive" {
      }
      enum "Unknown" {
      }
    }
  }

  typedef esdma-switch-sfp-type-enum {
    type enumeration {
      enum "None" {
      }
      enum "SFP-10G-SR" {
      }
      enum "SFP-10G-LR" {
      }
      enum "SFP-10G-LRM" {
      }
      enum "SFP-1G-SX" {
      }
      enum "SFP-1G-LX" {
      }
      enum "SFP-1000Base-T" {
      }
      enum "SFP-40G-SR4" {
      }
      enum "SFP-40G-LR4" {
      }
      enum "Unsupported" {
      }
    }
  }

  typedef esdma-switch-port-type {
    type int32 {
      range "0..127";
    }
    description
      "A type defining the allowable switch port numbers";
  }

  typedef esdma-switch-fdb-ports {
    type int32 {
      range "-1..128";
    }
    description
      "A type defining the allowable switch fdb port numbers";
  }

  typedef esdma-switch-port-state {
    type enumeration {
      enum "Unknown" {
      }
      enum "Test" {
      }
      enum "Down" {
      }
      enum "Up" {
      }
    }
    description
      "The switch port up and down states";
  }

  typedef switch-forwarding-state {
    type enumeration {
      enum "Unknown" {
      }
      enum "-" {
      }
      enum "Disabled" {
      }
      enum "Blocking" {
      }
      enum "Learning" {
      }
      enum "Forwarding" {
      }
    }
    description
      "The set of switch port forwarding states";
  }

  typedef switch-traffic-class-enum {
    type int8 {
      range "-1..7";
    }
  }

  typedef esdma-sdr-id {
    type uint8;
  }

  typedef esd-cir-eir-type {
    type enumeration {
      enum "CIR" {
      }
      enum "PIR" {
      }
    }
  }

  typedef esd-percentage {
    type uint8 {
      range "0..100";
    }
  }

  typedef mlap-ep-type {
    type enumeration {
      enum "Unknown" {
      }
      enum "RP" {
      }
      enum "SC" {
      }
      enum "FC" {
      }
      enum "LC" {
      }
      enum "F-SW" {
      }
      enum "CB" {
      }
    }
  }

  typedef mlap-state-enum {
    type enumeration {
      enum "-" {
      }
      enum "Down" {
      }
      enum "Up" {
      }
      enum "Admin Down" {
      }
      enum "Do Not Use" {
      }
      enum "Invalid" {
      }
      enum "Active" {
      }
      enum "Standby" {
      }
      enum "Rem Managed" {
      }
    }
    description
      "The set of enumerated values that MLAP uses to manage a port's protocol state";
  }

  typedef mlap-protocol-enum {
    type enumeration {
      enum "Internal" {
      }
      enum "External" {
      }
    }
    description
      "The types of MLAP protocol";
  }

  typedef mlap-trace-verbosity {
    type enumeration {
      enum "Off" {
      }
      enum "Low" {
      }
      enum "Medium" {
      }
      enum "High" {
      }
    }
  }

  typedef vlan-id-type {
    type uint16 {
      range "0..4095";
    }
  }

  typedef switch-data-direction-enum {
    type enumeration {
      enum "-" {
      }
      enum "Both" {
      }
      enum "Rx" {
      }
      enum "Tx" {
      }
      enum "Unknown" {
      }
      enum "Invalid" {
      }
    }
    description
      "Switch data direction";
  }

  typedef switch-table-type-enum {
    type enumeration {
      enum "-" {
      }
      enum "Port" {
      }
      enum "VLAN" {
      }
      enum "TCAM" {
      }
      enum "Unknown" {
      }
    }
  }

  typedef switch-match-type-enum {
    type enumeration {
      enum "-" {
      }
      enum "Any" {
      }
      enum "Tagged" {
      }
      enum "Untagged" {
      }
      enum "Unknown" {
      }
    }
  }

  typedef switch-action-type-enum {
    type enumeration {
      enum "-" {
      }
      enum "Translate" {
      }
      enum "Remove Outer" {
      }
      enum "Add Outer" {
      }
      enum "Drop" {
      }
      enum "Forward" {
      }
      enum "Unknown" {
      }
    }
  }

  typedef esdma-sdr-traffic-type {
    type enumeration {
      enum "Unknown" {
      }
      enum "IPC" {
      }
      enum "MgmtEth" {
      }
      enum "All" {
      }
      enum "Invalid" {
      }
    }
  }

  typedef esdma-trunk-member-status {
    type enumeration {
      enum "Disabled" {
      }
      enum "Enabled" {
      }
      enum "-" {
      }
    }
  }
}
