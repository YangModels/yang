module Cisco-IOS-XR-l2-eth-infra-datatypes {
  namespace "http://cisco.com/ns/yang/Cisco-IOS-XR-l2-eth-infra-datatypes";
  prefix l2-eth-infra-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2018 by Cisco Systems, Inc.
     All rights reserved.";

  revision 2015-11-09 {
    description
      "IOS XR 6.0 revision.";
  }

  typedef Vs-mode {
    type enumeration {
      enum "trunk" {
        value 1;
        description
          "VLAN-Switched trunk mode";
      }
      enum "access" {
        value 2;
        description
          "VLAN-Switched access mode";
      }
    }
    description
      "Vs mode";
  }

  typedef Vlan-tag-or-cvp {
    type union {
      type enumeration {
        enum "native-with-cvlan-preservation" {
          value 65534;
          description
            "This is the Native VLAN and C-VLAN
             preservation is enabled";
        }
      }
      type uint32 {
        range "1..65534";
      }
    }
    description
      "Vlan tag or cvp";
  }

  typedef Class-of-service {
    type uint32 {
      range "0..7";
    }
    description
      "Class of service";
  }

  typedef Vlan {
    type enumeration {
      enum "vlan-type-dot1ad" {
        value 1;
        description
          "An 802.1ad VLAN";
      }
      enum "vlan-type-dot1q" {
        value 2;
        description
          "An 802.1q VLAN";
      }
    }
    description
      "Vlan";
  }

  typedef Vlan-tag-or-native {
    type union {
      type enumeration {
        enum "native" {
          value 65535;
          description
            "This is the Native VLAN";
        }
        enum "native-with-cvlan-preservation" {
          value 65534;
          description
            "This is the Native VLAN and C-VLAN
             preservation is enabled";
        }
      }
      type uint32 {
        range "1..65535";
      }
    }
    description
      "Vlan tag or native";
  }

  typedef Vlan-tag-or-null {
    type union {
      type enumeration {
        enum "any" {
          value 0;
          description
            "Match any inner VLAN tag value";
        }
      }
      type uint32 {
        range "0..4094";
      }
    }
    description
      "Vlan tag or null";
  }

  typedef Rewrite {
    type enumeration {
      enum "pop1" {
        value 1;
        description
          "Pop 1 tag";
      }
      enum "pop2" {
        value 2;
        description
          "Pop 2 tags";
      }
      enum "push1" {
        value 3;
        description
          "Push 1 tag";
      }
      enum "push2" {
        value 4;
        description
          "Push 2 tags";
      }
      enum "translate1to1" {
        value 5;
        description
          "Translate 1-to-1";
      }
      enum "translate1to2" {
        value 6;
        description
          "Translate 1-to-2";
      }
      enum "translate2to1" {
        value 7;
        description
          "Translate 2-to-1";
      }
      enum "translate2to2" {
        value 8;
        description
          "Translate 2-to-2";
      }
    }
    description
      "Rewrite";
  }

  typedef Match {
    type enumeration {
      enum "match-default" {
        value 1;
        description
          "All otherwise unmatched packets";
      }
      enum "match-untagged" {
        value 2;
        description
          "Untagged packets";
      }
      enum "match-dot1q" {
        value 3;
        description
          "Match Dot1Q tags";
      }
      enum "match-dot1ad" {
        value 4;
        description
          "Match Dot1ad tags";
      }
      enum "match-dot1q-priority" {
        value 5;
        description
          "Match Dot1Q priority-tagged packets";
      }
      enum "match-dot1ad-priority" {
        value 6;
        description
          "Match Dot1ad priority-tagged packets";
      }
    }
    description
      "Match";
  }

  typedef Ethertype-match {
    type enumeration {
      enum "ppp-over-ethernet" {
        value 34915;
        description
          "PPP over Ethernet";
      }
    }
    description
      "Ethertype match";
  }

  typedef Vlan-tag {
    type uint32 {
      range "1..4094";
    }
    description
      "Vlan tag";
  }

  typedef Vlan-tag-or-any {
    type union {
      type enumeration {
        enum "any" {
          value 4096;
          description
            "Match any VLAN tag value";
        }
      }
      type uint32 {
        range "1..4096";
      }
    }
    description
      "Vlan tag or any";
  }
}
