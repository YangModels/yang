submodule Cisco-IOS-XR-clns-isis-oper-sub1 {
  belongs-to Cisco-IOS-XR-clns-isis-oper {
    prefix Cisco-IOS-XR-clns-isis-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR clns-isis package operational data.
     
     Copyright (c) 2013-2020 by Cisco Systems, Inc.
     All rights reserved.";

  revision 2020-05-12 {
    description
      "Added SRLG and SRLG Static
       2020-03-25
         Added operational data for new features.";
    semver:module-version "3.0.0";
  }
  revision 2019-09-25 {
    description
      "Added operational data for new features
       2019-05-14
       Conditional Advertise-prefix support
       2019-05-03
       move ocni-isis opencfg model from native model to private oper model";
    semver:module-version "2.0.0";
  }
  revision 2019-04-05 {
    description
      "Establish semantic version baseline.";
    semver:module-version "1.0.0";
  }
  revision 2019-03-28 {
    description
      "Upgrade ocni-isis to opencfg model version 0.4.2";
  }
  revision 2019-02-23 {
    description
      "Added is_srv6 flag to ISIS IPv6 route";
  }
  revision 2019-02-16 {
    description
      "Added interface link-group name";
  }
  revision 2018-10-15 {
    description
      "Add SRv6 configured locators";
  }
  revision 2018-10-04 {
    description
      "Update SRv6 locator table";
  }
  revision 2018-05-17 {
    description
      "Update opencfg isis model";
  }
  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  typedef Isis-overload-bit-mode {
    type enumeration {
      enum "isis-overload-bit-unset" {
        value 0;
        description
          "Overload bit not set";
      }
      enum "isis-overload-bit-set" {
        value 1;
        description
          "Overload bit permanently set";
      }
      enum "isis-overload-bit-on-startup-period" {
        value 2;
        description
          "overload bit is set for a timed period when an
           area starts";
      }
      enum "isis-overload-bit-on-startup-bgp" {
        value 3;
        description
          "overload bit set until BGP has converged";
      }
    }
    description
      "Isis overload bit mode";
  }

  typedef Isis-max-metric-mode {
    type enumeration {
      enum "isis-max-metric-unset" {
        value 0;
        description
          "max metric not set";
      }
      enum "isis-max-metric-set" {
        value 1;
        description
          "max metric always set";
      }
      enum "isis-max-metric-on-startup-period" {
        value 2;
        description
          "max metric is set for a timed period when an
           area starts";
      }
      enum "isis-max-metric-on-startup-bgp" {
        value 3;
        description
          "max metric set until BGP has converged";
      }
    }
    description
      "Isis max metric mode";
  }

  typedef Isis-uloop-event {
    type enumeration {
      enum "isis-u-loop-event-none" {
        description
          "isis u loop event none";
      }
      enum "isis-u-loop-event-link-down" {
        description
          "isis u loop event link down";
      }
      enum "isis-u-loop-event-link-up" {
        description
          "isis u loop event link up";
      }
      enum "isis-u-loop-event-ol-bit-set" {
        description
          "isis u loop event ol bit set";
      }
      enum "isis-u-loop-event-ol-bit-unset" {
        description
          "isis u loop event ol bit unset";
      }
    }
    description
      "Isis uloop event";
  }

  typedef Isis-uloop-avoidance {
    type enumeration {
      enum "isis-u-loop-avoidance-type-none" {
        value 0;
        description
          "No MicroLoop avoidance";
      }
      enum "isis-u-loop-avoidance-type-all" {
        value 1;
        description
          "Apply MicroLoop avoidance for all prefixes";
      }
      enum "isis-u-loop-avoidance-type-protected" {
        value 2;
        description
          "Apply MicroLoop avoidance only for protected
           prefixes";
      }
      enum "isis-u-loop-avoidance-type-sr" {
        value 3;
        description
          "Segment Routing MicroLoop avoidance for All
           single-link changes";
      }
    }
    description
      "Isis uloop avoidance";
  }

  typedef Isis-metric-style {
    type enumeration {
      enum "isis-metric-style-narrow" {
        value 0;
        description
          "old-style (ISO 10589) metrics";
      }
      enum "isis-metric-style-wide" {
        value 1;
        description
          "new-style 32-bit metrics";
      }
      enum "isis-metric-style-transition" {
        value 2;
        description
          "send/accept both forms of metric";
      }
      enum "isis-metric-style-narrow-transition" {
        value 3;
        description
          "send old-style (ISO 10589) metrics but accept
           both";
      }
      enum "isis-metric-style-wide-transition" {
        value 4;
        description
          "send new-style 32-bit metrics but accept both";
      }
    }
    description
      "Isis metric style";
  }

  typedef Isis-startup-status {
    type enumeration {
      enum "isis-startup-ssm-active" {
        description
          "Startup-state-machine controlled restart in
           progress";
      }
      enum "isis-startup-ssm-complete" {
        description
          "Startup-state-machine controlled restart
           complete";
      }
      enum "isis-startup-ssm-aborted" {
        description
          "Startup-state-machine controlled restart
           aborted";
      }
      enum "isis-startup-ssm-not-run" {
        description
          "Startup-state-machine controlled not attempted";
      }
    }
    description
      "Isis startup status";
  }

  typedef Isis-nsf-flavor {
    type enumeration {
      enum "isis-nsf-protocol-none" {
        value 0;
        description
          "NSF not configured";
      }
      enum "isis-nsf-protocol-cisco" {
        value 1;
        description
          "Internal checkpoint NSF";
      }
      enum "isis-nsf-protocol-ietf" {
        value 2;
        description
          "IETF-standard NSF";
      }
      enum "isis-nsf-protocol-nsr" {
        value 3;
        description
          "Cisco-proprietary NSR";
      }
    }
    description
      "Isis nsf flavor";
  }

  typedef Isis-edm-label-type-enum {
    type enumeration {
      enum "isis-edm-label-alloc-prefix-sid" {
        value 0;
        description
          "isis edm label alloc prefix sid";
      }
      enum "isis-edm-label-alloc-local-sid" {
        value 1;
        description
          "isis edm label alloc local sid";
      }
      enum "isis-edm-label-alloc-max" {
        value 2;
        description
          "isis edm label alloc max";
      }
    }
    description
      "isislabeltype";
  }

  typedef Isis-err-log-level {
    type enumeration {
      enum "isis-err-log-level-info" {
        value 0;
        description
          "isis err log level info";
      }
      enum "isis-err-log-level-warn" {
        value 1;
        description
          "isis err log level warn";
      }
      enum "isis-err-log-level-critical" {
        value 2;
        description
          "isis err log level critical";
      }
    }
    description
      "Isis err log level";
  }

  typedef Isis-prot-supp {
    type uint8;
    description
      "Isis prot supp";
  }

  typedef Isis-if-af-prefix-unknown-reason {
    type enumeration {
      enum "isis-intf-af-prefix-unknown-adv-suppressed" {
        description
          "isis intf af prefix unknown adv suppressed";
      }
      enum "isis-intf-af-prefix-unknown-global-addr-reg-error" {
        description
          "isis intf af prefix unknown global addr reg
           error";
      }
      enum "isis-intf-af-prefix-unknown-internal-error" {
        description
          "isis intf af prefix unknown internal error";
      }
    }
    description
      "Isis if af prefix unknown reason";
  }

  typedef Isis-if-af-fwd-addr-unknown-reason {
    type enumeration {
      enum "isis-intf-af-fwd-addr-unknown-cfg-passive" {
        description
          "isis intf af fwd addr unknown cfg passive";
      }
      enum "isis-intf-af-fwd-addr-unknown-proto-doesnt-exist" {
        description
          "isis intf af fwd addr unknown proto doesnt
           exist";
      }
      enum "isis-intf-af-fwd-addr-unknown-next-hop-reg-error" {
        description
          "isis intf af fwd addr unknown next hop reg
           error";
      }
      enum "isis-intf-af-fwd-addr-unknown-no-link-local-add" {
        description
          "isis intf af fwd addr unknown no link local add";
      }
      enum "isis-intf-af-fwd-addr-unknown-af-not-up" {
        description
          "isis intf af fwd addr unknown af not up";
      }
      enum "isis-intf-af-fwd-addr-unknown-vrf-enabled" {
        description
          "isis intf af fwd addr unknown vrf enabled";
      }
      enum "isis-intf-af-fwd-addr-unknown-internal-error" {
        description
          "isis intf af fwd addr unknown internal error";
      }
    }
    description
      "Isis if af fwd addr unknown reason";
  }

  typedef Isis-if-af-proto-down-reason {
    type enumeration {
      enum "isis-intf-af-proto-down-imd-conn-fail" {
        description
          "isis intf af proto down imd conn fail";
      }
      enum "isis-intf-af-proto-down-imd-node-doesnt-exist" {
        description
          "isis intf af proto down imd node doesnt exist";
      }
      enum "isis-intf-af-proto-down-imd-exist-reg-error" {
        description
          "isis intf af proto down imd exist reg error";
      }
      enum "isis-intf-af-proto-down-imd-state-reg-error" {
        description
          "isis intf af proto down imd state reg error";
      }
      enum "isis-intf-af-proto-down-af-not-up" {
        description
          "isis intf af proto down af not up";
      }
      enum "isis-intf-af-proto-down-internal-error" {
        description
          "isis intf af proto down internal error";
      }
    }
    description
      "Isis if af proto down reason";
  }

  typedef Isis-if-af-disabled-reason {
    type enumeration {
      enum "isis-intf-af-disabled-no-topo-enabled" {
        description
          "isis intf af disabled no topo enabled";
      }
      enum "isis-intf-af-disabled-internal-error" {
        description
          "isis intf af disabled internal error";
      }
    }
    description
      "Isis if af disabled reason";
  }

  typedef Isis-frr-tiebreaker {
    type enumeration {
      enum "isis-frr-tiebreaker-down-stream" {
        value 0;
        description
          "Backup path is via downstream node";
      }
      enum "isis-frr-tiebreaker-lc-disjoint" {
        value 1;
        description
          "Backup path is line card disjoint";
      }
      enum "isis-frr-tiebreaker-low-est-backup-metric" {
        value 2;
        description
          "Backup path has lowest metric";
      }
      enum "isis-frr-tiebreaker-node-protecting" {
        value 3;
        description
          "Backup path is node protecting";
      }
      enum "isis-frr-tiebreaker-primary-path" {
        value 4;
        description
          "Backup path is ECMP";
      }
      enum "isis-frr-tiebreaker-secondary-path" {
        value 5;
        description
          "Backup path is not an ECMP";
      }
      enum "isis-frr-tiebreaker-srlg-disjoint" {
        value 6;
        description
          "Backup path is SRLG disjoint";
      }
      enum "isis-frr-tiebreaker-default" {
        value 7;
        description
          "Backup path is link protecting";
      }
    }
    description
      "Isis frr tiebreaker";
  }

  typedef Isis-frr {
    type enumeration {
      enum "isis-frr-type-none" {
        value 0;
        description
          "Computation disabled";
      }
      enum "isis-frr-type-per-link" {
        value 1;
        description
          "Prefix independent per-link computation";
      }
      enum "isis-frr-type-per-prefix" {
        value 2;
        description
          "Prefix dependent computation";
      }
      enum "isis-frr-type-sr-u-loop" {
        value 3;
        description
          "Segment Routing Microloop Avoidance computation";
      }
    }
    description
      "Isis frr";
  }

  typedef Isis-if-topo-adv-prefix-disabled-reason {
    type enumeration {
      enum "isis-intf-topo-adv-prefix-disabled-intf-suppressed" {
        description
          "isis intf topo adv prefix disabled intf
           suppressed";
      }
      enum "isis-intf-topo-adv-prefix-disabled-af-not-up" {
        description
          "isis intf topo adv prefix disabled af not up";
      }
      enum "isis-intf-topo-adv-prefix-disabled-af-prefixes-unknown" {
        description
          "isis intf topo adv prefix disabled af prefixes
           unknown";
      }
      enum "isis-intf-topo-adv-prefix-disabled-internal-error" {
        description
          "isis intf topo adv prefix disabled internal
           error";
      }
    }
    description
      "Isis if topo adv prefix disabled reason";
  }

  typedef Isis-if-topo-adj-form-disabled-reason {
    type enumeration {
      enum "isis-intf-topo-adj-form-disabled-intf-passive" {
        description
          "isis intf topo adj form disabled intf passive";
      }
      enum "isis-intf-topo-adj-form-disabled-af-not-up" {
        description
          "isis intf topo adj form disabled af not up";
      }
      enum "isis-intf-topo-adj-form-disabled-af-fwd-addr-unknown" {
        description
          "isis intf topo adj form disabled af fwd addr
           unknown";
      }
      enum "isis-intf-topo-adj-form-disabled-topo-not-cfg" {
        description
          "isis intf topo adj form disabled topo not cfg";
      }
      enum "isis-intf-topo-adj-form-disabled-topo-can-not-participate" {
        description
          "isis intf topo adj form disabled topo can not
           participate";
      }
      enum "isis-intf-topo-adj-form-disabled-idle" {
        description
          "isis intf topo adj form disabled idle";
      }
      enum "isis-intf-topo-adj-form-disabled-internal-error" {
        description
          "isis intf topo adj form disabled internal error";
      }
      enum "isis-intf-topo-adj-form-disabled-mtu" {
        description
          "isis intf topo adj form disabled mtu";
      }
      enum "isis-intf-topo-adj-form-disabled-snpa" {
        description
          "isis intf topo adj form disabled snpa";
      }
      enum "isis-intf-topo-adj-form-disabled-mcast" {
        description
          "isis intf topo adj form disabled mcast";
      }
    }
    description
      "Isis if topo adj form disabled reason";
  }

  typedef Isis-if-topo-disabled-reason {
    type enumeration {
      enum "isis-intf-topo-disabled-not-cfg" {
        description
          "isis intf topo disabled not cfg";
      }
      enum "isis-intf-topo-disabled-internal-error" {
        description
          "isis intf topo disabled internal error";
      }
    }
    description
      "Isis if topo disabled reason";
  }

  typedef Isis-circuit-id {
    type yang:hex-string;
    description
      "Isis circuit id";
  }

  typedef Isis-if-mcast-invalid-reason {
    type enumeration {
      enum "isis-intf-mcast-invalid-join-error" {
        description
          "Error when attempting to join this multicast
           group";
      }
      enum "isis-intf-mcast-invalid-internal-error" {
        description
          "Internal error";
      }
      enum "isis-intf-mcast-invalid-not-yet-needed" {
        description
          "Multicast group membership not yet requested";
      }
    }
    description
      "Isis if mcast invalid reason";
  }

  typedef Isis-if-clns-snpa-unknown-reason {
    type enumeration {
      enum "isis-intf-clns-snpa-unknown-access-error" {
        description
          "isis intf clns snpa unknown access error";
      }
      enum "isis-intf-clns-snpa-unknown-not-lan" {
        description
          "isis intf clns snpa unknown not lan";
      }
      enum "isis-intf-clns-snpa-unknown-internal-error" {
        description
          "isis intf clns snpa unknown internal error";
      }
    }
    description
      "Isis if clns snpa unknown reason";
  }

  typedef Isis-known {
    type enumeration {
      enum "isis-unknown" {
        value 0;
        description
          "Unknown";
      }
      enum "isis-known" {
        value 1;
        description
          "Known";
      }
    }
    description
      "Isis known";
  }

  typedef Isis-if-clns-mtu-invalid-reason {
    type enumeration {
      enum "isis-intf-clns-mtu-invalid-too-small" {
        description
          "isis intf clns mtu invalid too small";
      }
      enum "isis-intf-clns-mtu-invalid-internal-error" {
        description
          "isis intf clns mtu invalid internal error";
      }
    }
    description
      "Isis if clns mtu invalid reason";
  }

  typedef Isis-if-clns-proto-down-reason {
    type enumeration {
      enum "isis-intf-clns-proto-down-add-to-intf-stack-fail" {
        description
          "isis intf clns proto down add to intf stack
           fail";
      }
      enum "isis-intf-clns-proto-down-no-imd-conn" {
        description
          "isis intf clns proto down no imd conn";
      }
      enum "isis-intf-clns-proto-down-imd-node-doesnt-exist" {
        description
          "isis intf clns proto down imd node doesnt exist";
      }
      enum "isis-intf-clns-proto-down-imd-exist-reg-error" {
        description
          "isis intf clns proto down imd exist reg error";
      }
      enum "isis-intf-clns-proto-down-imd-state-reg-error" {
        description
          "isis intf clns proto down imd state reg error";
      }
      enum "isis-intf-clns-proto-down-clns-not-up" {
        description
          "isis intf clns proto down clns not up";
      }
    }
    description
      "Isis if clns proto down reason";
  }

  typedef Isis-up {
    type enumeration {
      enum "isis-down" {
        value 0;
        description
          "Down";
      }
      enum "isis-up" {
        value 1;
        description
          "Up";
      }
    }
    description
      "Isis up";
  }

  typedef Isis-extended-circuit-number {
    type uint32;
    description
      "Isis extended circuit number";
  }

  typedef Isis-circuit-number {
    type uint8;
    description
      "Isis circuit number";
  }

  typedef Isis-if-adv-prefix-disabled-reason {
    type enumeration {
      enum "isis-intf-adv-prefix-disabled-if-cfg-suppressed" {
        description
          "isis intf adv prefix disabled if cfg suppressed";
      }
      enum "isis-intf-adv-prefix-disabled-no-topo-participate" {
        description
          "isis intf adv prefix disabled no topo
           participate";
      }
      enum "isis-intf-adv-prefix-disabled-internal-error" {
        description
          "isis intf adv prefix disabled internal error";
      }
    }
    description
      "Isis if adv prefix disabled reason";
  }

  typedef Isis-if-adj-form-disabled-reason {
    type enumeration {
      enum "isis-intf-adj-form-disabled-cfg-passive" {
        description
          "isis intf adj form disabled cfg passive";
      }
      enum "isis-intf-adj-form-disabled-no-topo-participate" {
        description
          "isis intf adj form disabled no topo participate";
      }
      enum "isis-intf-adj-form-disabled-add-to-intf-stack-fail" {
        description
          "isis intf adj form disabled add to intf stack
           fail";
      }
      enum "isis-intf-adj-form-disabled-clns-io" {
        description
          "isis intf adj form disabled clns io";
      }
      enum "isis-intf-adj-form-disabled-internal-error" {
        description
          "isis intf adj form disabled internal error";
      }
    }
    description
      "Isis if adj form disabled reason";
  }

  typedef Isis-if-disabled-reason {
    type enumeration {
      enum "isis-intf-disabled-no-net-cfg" {
        description
          "isis intf disabled no net cfg";
      }
      enum "isis-intf-disabled-area-missing" {
        description
          "isis intf disabled area missing";
      }
      enum "isis-intf-disabled-no-area-running" {
        description
          "isis intf disabled no area running";
      }
      enum "isis-intf-disabled-no-topos-cfg" {
        description
          "isis intf disabled no topos cfg";
      }
      enum "isis-intf-disabled-no-imd-conn" {
        description
          "isis intf disabled no imd conn";
      }
      enum "isis-intf-disabled-imd-reg-error" {
        description
          "isis intf disabled imd reg error";
      }
      enum "isis-intf-disabled-level-mismatch" {
        description
          "isis intf disabled level mismatch";
      }
      enum "isis-intf-disabled-base-caps-error" {
        description
          "isis intf disabled base caps error";
      }
      enum "isis-intf-disabled-intf-doesnt-exist" {
        description
          "isis intf disabled intf doesnt exist";
      }
      enum "isis-intf-disabled-intf-shutdown" {
        description
          "isis intf disabled intf shutdown";
      }
      enum "isis-intf-disabled-internal-error" {
        description
          "isis intf disabled internal error";
      }
    }
    description
      "Isis if disabled reason";
  }

  typedef Isis-enabled {
    type enumeration {
      enum "isis-disabled" {
        value 0;
        description
          "Disabled";
      }
      enum "isis-enabled" {
        value 1;
        description
          "Enabled";
      }
    }
    description
      "Isis enabled";
  }

  typedef Isis-mesh-group-number {
    type uint32;
    description
      "Isis mesh group number";
  }

  typedef Isis-reachable {
    type enumeration {
      enum "isis-unreachable" {
        value 0;
        description
          "Unreachable";
      }
      enum "isis-reachable" {
        value 1;
        description
          "Reachable";
      }
    }
    description
      "Isis reachable";
  }

  typedef Isis-metric-mode {
    type enumeration {
      enum "isis-metric-mode-fixed" {
        value 0;
        description
          "Fixed";
      }
      enum "isis-metric-mode-relative" {
        value 1;
        description
          "Relative";
      }
      enum "isis-metric-mode-absolute" {
        value 2;
        description
          "Absolute";
      }
    }
    description
      "Isis metric mode";
  }

  typedef Isis-spf-trigger {
    type enumeration {
      enum "isis-spf-trig-config" {
        description
          "Configuration change";
      }
      enum "isis-spf-trig-nsr-fo" {
        description
          "NSR FO is done";
      }
      enum "isis-spf-trig-periodic" {
        description
          "Periodic SPF";
      }
      enum "isis-spf-trig-clear" {
        description
          "Cleared route table";
      }
      enum "isis-spf-trig-null0-intf" {
        description
          "Null0 intf up";
      }
      enum "isis-spf-trig-newadj" {
        description
          "New adjacency";
      }
      enum "isis-spf-trig-deladj" {
        description
          "Deleted adjacency";
      }
      enum "isis-spf-trig-next-hop" {
        description
          "IP nexthop address change";
      }
      enum "isis-spf-trig-metric" {
        description
          "Changed interface metric";
      }
      enum "isis-spf-trig-dis" {
        description
          "Change to elected DIS";
      }
      enum "isis-spf-trig-frr-per-link" {
        description
          "Change to per-link FRR config";
      }
      enum "isis-spf-trig-frr-per-prefix" {
        description
          "Change to per-prefix FRR config";
      }
      enum "isis-spf-trig-ucmp" {
        description
          "Change to UCMP config/calculation";
      }
      enum "isis-spf-trig-new-tunnel" {
        description
          "New TE Autoroute Tunnel";
      }
      enum "isis-spf-trig-del-tunnel" {
        description
          "Deleted TE Autoroute Tunnel";
      }
      enum "isis-spf-trig-chg-tunnel" {
        description
          "Changed TE Autoroute Tunnel";
      }
      enum "isis-spf-trig-new-node" {
        description
          "New LSP zero which participates in topology";
      }
      enum "isis-spf-trig-del-node" {
        description
          "New LSP zero which no longer participates in
           topology";
      }
      enum "isis-spf-trig-newlsp" {
        description
          "Previously unseen LSP fragment";
      }
      enum "isis-spf-trig-lsp-expiry" {
        description
          "LSP expired";
      }
      enum "isis-spf-trig-attach-set" {
        description
          "Attached bit set";
      }
      enum "isis-spf-trig-attach-clr" {
        description
          "Attached bit cleared";
      }
      enum "isis-spf-trig-overload-set" {
        description
          "Overload bit set";
      }
      enum "isis-spf-trig-overload-clr" {
        description
          "Overload bit cleared";
      }
      enum "isis-spf-trig-link-good" {
        description
          "Good news link TLV content change";
      }
      enum "isis-spf-trig-link-bad" {
        description
          "Bad news link TLV content change";
      }
      enum "isis-spf-trig-prefix-good" {
        description
          "Good news prefix TLV content change";
      }
      enum "isis-spf-trig-prefix-bad" {
        description
          "Bad news prefix TLV content change";
      }
      enum "isis-spf-trig-prefix" {
        description
          "Neutral (neither good nor bad news) prefix TLV
           content change";
      }
      enum "isis-spf-trig-area-addr" {
        description
          "Area address TLV content change";
      }
      enum "isis-spf-trig-ip-addr" {
        description
          "IP address TLV content change";
      }
      enum "isis-spf-trig-rtrid" {
        description
          "Router id TLV content change";
      }
      enum "isis-spf-trig-flex-algo" {
        description
          "Flex-Algo support change";
      }
      enum "isis-spf-trig-srv6-cap" {
        description
          "SRv6 router capability change";
      }
      enum "isis-spf-trig-srv6-locator" {
        description
          "SRv6 locator TLV change";
      }
      enum "isis-spf-trig-prefix-policy" {
        description
          "Prefix policy change";
      }
    }
    description
      "Isis spf trigger";
  }

  typedef Isis-spf-class {
    type enumeration {
      enum "isis-spf-frr-sr-u-loop" {
        value 0;
        description
          "Remote microloop avoidance SPF";
      }
      enum "isis-spf-frr-per-link" {
        value 1;
        description
          "FRR per-link SPF";
      }
      enum "isis-spf-partial" {
        value 2;
        description
          "PRC";
      }
      enum "isis-spf-frr-per-prefix" {
        value 3;
        description
          "FRR per-prefix SPF";
      }
      enum "isis-spf-ucmp-calc" {
        value 4;
        description
          "UCMP SPF";
      }
      enum "isis-spf-flex" {
        value 5;
        description
          "Flex-Algo SPF";
      }
      enum "isis-spf-next-hop" {
        value 6;
        description
          "Next Hop";
      }
      enum "isis-spf-incremental" {
        value 7;
        description
          "Incremental SPF";
      }
      enum "isis-spf-full" {
        value 8;
        description
          "Full SPF";
      }
    }
    description
      "Types of route calculation";
  }

  typedef Isis-sh-te-pce-flooding-scope {
    type enumeration {
      enum "none" {
        description
          "Flooding is disabled";
      }
      enum "area" {
        description
          "Area wide flooding";
      }
      enum "domain" {
        description
          "Domain wide flooding";
      }
    }
    description
      "Isis sh te pce flooding scope";
  }

  typedef Isis-sh-te-link {
    type enumeration {
      enum "isis-sh-te-link-p2p" {
        description
          "Tunnel is absolute";
      }
      enum "isis-sh-te-link-broadcast" {
        description
          "Broadcast link";
      }
    }
    description
      "Isis sh te link";
  }

  typedef Srv6-end-function {
    type enumeration {
      enum "unknown" {
        description
          "Unknown";
      }
      enum "end" {
        description
          "End (no PSP/USP)";
      }
      enum "end-with-psp" {
        description
          "End with PSP";
      }
      enum "end-with-usp" {
        description
          "End with USP";
      }
      enum "end-with-psp-usp" {
        description
          "End with PSP/USP";
      }
      enum "end-x" {
        description
          "End.X (no PSP/USP)";
      }
      enum "end-x-with-psp" {
        description
          "End.X with PSP";
      }
      enum "end-x-with-usp" {
        description
          "End.X with USP";
      }
      enum "end-x-with-psp-usp" {
        description
          "End.X with PSP/USP";
      }
      enum "end-tbl" {
        description
          "End.T (no PSP/USP)";
      }
      enum "end-tbl-with-psp" {
        description
          "End.T with PSP";
      }
      enum "end-tbl-with-usp" {
        description
          "End.T with USP";
      }
      enum "end-tbl-with-psp-usp" {
        description
          "End.T with PSP/USP";
      }
      enum "end-b6-insert" {
        description
          "End.B6.Insert";
      }
      enum "end-b6-encaps" {
        description
          "End.B6.Encaps";
      }
      enum "end-bm" {
        description
          "End.BM";
      }
      enum "end-dx6" {
        description
          "End.DX6";
      }
      enum "end-dx4" {
        description
          "End.DX4";
      }
      enum "end-dt6" {
        description
          "End.DT6";
      }
      enum "end-dt4" {
        description
          "End.DT4";
      }
      enum "end-dt46" {
        description
          "End.DT46";
      }
      enum "end-dx2" {
        description
          "End.DX2";
      }
      enum "end-dx2v" {
        description
          "End.DX2V";
      }
      enum "end-dt2u" {
        description
          "End.DT2U";
      }
      enum "end-dt2m" {
        description
          "End.DT2M";
      }
      enum "end-s" {
        description
          "End.S";
      }
      enum "end-b6-insert-red" {
        description
          "End.B6.Insert.Reduced";
      }
      enum "end-b6-encaps-red" {
        description
          "End.B6.Encaps.Reduced";
      }
      enum "end-with-usd" {
        description
          "End with USD";
      }
      enum "end-with-psp-usd" {
        description
          "End with PSP/USD";
      }
      enum "end-with-usp-usd" {
        description
          "End with USP/USD";
      }
      enum "end-with-psp-usp-usd" {
        description
          "End with PSP/USP/USD";
      }
      enum "end-x-with-usd" {
        description
          "End.X with USD";
      }
      enum "end-x-with-psp-usd" {
        description
          "End.X with PSP/USD";
      }
      enum "end-x-with-usp-usd" {
        description
          "End.X with USP/USD";
      }
      enum "end-x-with-psp-usp-usd" {
        description
          "End.X with PSP/USP/USD";
      }
      enum "end-tbl-with-usd" {
        description
          "End.T with USD";
      }
      enum "end-tbl-with-psp-usd" {
        description
          "End.T with PSP/USD";
      }
      enum "end-tbl-with-usp-usd" {
        description
          "End.T with USP/USD";
      }
      enum "end-tbl-with-psp-usp-usd" {
        description
          "End.T with PSP/USP/USD";
      }
      enum "end-op" {
        description
          "End.OP";
      }
      enum "end-otp" {
        description
          "End.OTP";
      }
      enum "u-n-shift-only" {
        description
          "uN Shift-only";
      }
      enum "u-n-only" {
        description
          "uN Only";
      }
      enum "u-n-psp" {
        description
          "uN with PSP";
      }
      enum "u-n-psp-usp" {
        description
          "uN with PSP/USP";
      }
      enum "u-n-usd" {
        description
          "uN with USD";
      }
      enum "u-n-psp-usd" {
        description
          "uN with PSP-USD";
      }
      enum "u-n-usp-usd" {
        description
          "uN with USP-USD";
      }
      enum "u-n-psp-usp-usd" {
        description
          "uN with PSP-USP-USD";
      }
      enum "u-a-shift-only" {
        description
          "uA Shift-only";
      }
      enum "u-a-only" {
        description
          "uA Only";
      }
      enum "u-a-psp" {
        description
          "uA with PSP";
      }
      enum "u-a-usp" {
        description
          "uA with USP";
      }
      enum "u-a-psp-usp" {
        description
          "uA with PSP-USP";
      }
      enum "u-a-usd" {
        description
          "uA with USD";
      }
      enum "u-a-psp-usd" {
        description
          "uA with PSP-USD";
      }
      enum "u-a-usp-usd" {
        description
          "uA with USP-USD";
      }
      enum "u-a-psp-usp-usd" {
        description
          "uA with PSP-USP-USD";
      }
      enum "u-dx6" {
        description
          "uDX6";
      }
      enum "u-dx4" {
        description
          "uDX4";
      }
      enum "u-dt6" {
        description
          "uDT6";
      }
      enum "u-dt4" {
        description
          "uDT4";
      }
      enum "u-dt46" {
        description
          "uDT46";
      }
    }
    description
      "SRv6 End Function Type";
  }

  typedef Isis-sh-route-adv-origin {
    type enumeration {
      enum "isis-sh-route-adv-origin-interface" {
        description
          "IS-IS interface prefix";
      }
      enum "isis-sh-route-adv-origin-redistributed" {
        description
          "Redistributed prefix";
      }
      enum "isis-sh-route-adv-origin-native" {
        description
          "Native prefix";
      }
      enum "isis-sh-route-adv-origin-summary" {
        description
          "Summary prefix";
      }
      enum "isis-sh-route-adv-origin-default" {
        description
          "Explicit origination of default prefix";
      }
    }
    description
      "Origin of a prefix advertisement";
  }

  typedef Isis-prefix-priority {
    type enumeration {
      enum "isis-prefix-priority-critical" {
        value 0;
        description
          "Critical priority prefixes";
      }
      enum "isis-prefix-priority-high" {
        value 1;
        description
          "High priority prefixes";
      }
      enum "isis-prefix-priority-med" {
        value 2;
        description
          "Medium priority prefixes";
      }
      enum "isis-prefix-priority-low" {
        value 3;
        description
          "Low priority prefixes";
      }
    }
    description
      "Isis prefix priority";
  }

  typedef Isis-tilfa-computation {
    type enumeration {
      enum "isis-tilfa-comp-none" {
        description
          "isis tilfa comp none";
      }
      enum "isis-tilfa-comp-link" {
        description
          "isis tilfa comp link";
      }
      enum "isis-tilfa-comp-node" {
        description
          "isis tilfa comp node";
      }
      enum "isis-tilfa-comp-srlg" {
        description
          "isis tilfa comp srlg";
      }
      enum "isis-tilfa-comp-node-srlg" {
        description
          "isis tilfa comp node srlg";
      }
      enum "isis-tilfa-comp-lc" {
        description
          "isis tilfa comp lc";
      }
      enum "isis-tilfa-comp-node-lc" {
        description
          "isis tilfa comp node lc";
      }
      enum "isis-tilfa-comp-srlg-lc" {
        description
          "isis tilfa comp srlg lc";
      }
      enum "isis-tilfa-comp-node-srlg-lc" {
        description
          "isis tilfa comp node srlg lc";
      }
    }
    description
      "Isis tilfa computation";
  }

  typedef Isis-prefix-tag {
    type uint32;
    description
      "Isis prefix tag";
  }

  typedef Isis-metric {
    type uint32;
    description
      "Isis metric";
  }

  typedef Isis-prefix-origin {
    type enumeration {
      enum "isis-prefix-origin-l1-summary-null" {
        value 0;
        description
          "Level 1 Summary Null Route";
      }
      enum "isis-prefix-origin-l1" {
        value 1;
        description
          "Level 1 Route";
      }
      enum "isis-prefix-origin-l2-summary-null" {
        value 2;
        description
          "Level 2 Summary Null Route";
      }
      enum "isis-prefix-origin-l2" {
        value 3;
        description
          "Level 2 Route";
      }
      enum "isis-prefix-origin-inter-area-summary-null" {
        value 4;
        description
          "Level 1 Interarea Summary Null Route";
      }
      enum "isis-prefix-origin-inter-area" {
        value 5;
        description
          "Level 1 Interarea Route";
      }
      enum "isis-prefix-origin-default-nearest-attached" {
        value 6;
        description
          "Nearest Attached Default Route";
      }
      enum "isis-prefix-origin-invalid" {
        value 7;
        description
          "Invalid Origin";
      }
    }
    description
      "Isis prefix origin";
  }

  typedef Isis-string {
    type string;
    description
      "Isis string";
  }

  typedef Isis-redist-proto {
    type enumeration {
      enum "isis-redist-connected" {
        value 0;
        description
          "Redistributed protocol is Connected";
      }
      enum "isis-redist-static" {
        value 1;
        description
          "Redistributed protocol is Static";
      }
      enum "isis-redist-ospf" {
        value 2;
        description
          "Redistributed protocol is OSPF";
      }
      enum "isis-redist-bgp" {
        value 3;
        description
          "Redistributed protocol is BGP";
      }
      enum "isis-redist-isis" {
        value 4;
        description
          "Redistributed protocol is IS-IS";
      }
      enum "isis-redist-ospfv3" {
        value 5;
        description
          "Redistributed protocol is OSPFv3";
      }
      enum "isis-redist-rip" {
        value 6;
        description
          "Redistributed protocol is RIP";
      }
      enum "isis-redist-eigrp" {
        value 7;
        description
          "Redistributed protocol is EIGRP";
      }
      enum "isis-redist-subscriber" {
        value 8;
        description
          "Redistributed protocol is Subscriber";
      }
      enum "isis-redist-application" {
        value 9;
        description
          "Redistributed protocol is Application";
      }
      enum "isis-redist-mobile" {
        value 10;
        description
          "Redistributed protocol is Mobile";
      }
    }
    description
      "Isis redist proto";
  }

  typedef Isis-sh-interface-name {
    type string;
    description
      "Isis sh interface name";
  }

  typedef Isis-valid {
    type enumeration {
      enum "isis-invalid" {
        value 0;
        description
          "Invalid";
      }
      enum "isis-valid" {
        value 1;
        description
          "Valid";
      }
    }
    description
      "Isis valid";
  }

  typedef Isis-lsp-db-op {
    type enumeration {
      enum "isis-lsp-db-clear" {
        description
          "Clear the LSP database";
      }
      enum "isis-lsp-db-insert-new-lsp" {
        description
          "Insertion of new LSP";
      }
      enum "isis-lsp-db-replace-lsp-with-lsp" {
        description
          "LSP replacing LSP";
      }
      enum "isis-lsp-db-purge-lsp" {
        description
          "LSP purged by the local system";
      }
      enum "isis-lsp-db-delete-lsp" {
        description
          "Removal of the LSP from the database";
      }
    }
    description
      "Isis lsp db op";
  }

  typedef Isis-pseudo-node-number {
    type uint8;
    description
      "Isis pseudo node number";
  }

  typedef Isis-lsp-trigger {
    type enumeration {
      enum "isis-lsp-trig-config" {
        description
          "Any configuration change";
      }
      enum "isis-lsp-trig-newadj" {
        description
          "New adjacency came up";
      }
      enum "isis-lsp-trig-deladj" {
        description
          "Adjacency went down";
      }
      enum "isis-lsp-trig-dr-change" {
        description
          "DIS changed, or pseudonode changed";
      }
      enum "isis-lsp-trig-area-set" {
        description
          "Active area set changed";
      }
      enum "isis-lsp-trig-attach" {
        description
          "Attached bit changed state";
      }
      enum "isis-lsp-trig-hippity" {
        description
          "LSPDB overload bit changed state";
      }
      enum "isis-lsp-trig-regen" {
        description
          "LSP regeneration";
      }
      enum "isis-lsp-trig-ip-if-up" {
        description
          "Directly connected IP prefix up";
      }
      enum "isis-lsp-trig-ip-if-down" {
        description
          "Directly connected IP prefix down";
      }
      enum "isis-lsp-trig-ip-inter-area" {
        description
          "Interarea IP route appeared or gone";
      }
      enum "isis-lsp-trig-ip-external" {
        description
          "Redistributed IP route appeared or gone";
      }
      enum "isis-lsp-trig-ip-external-full" {
        description
          "Full IP redistribution";
      }
      enum "isis-lsp-trig-ip-def-orig" {
        description
          "Default information originate changed";
      }
      enum "isis-lsp-trig-ip-addr-chg" {
        description
          "IP interface address changed";
      }
      enum "isis-lsp-trig-te-info" {
        description
          "TE bandwidth resource information";
      }
      enum "isis-lsp-trig-te-pce-info" {
        description
          "TE PCE information";
      }
      enum "isis-lsp-trig-te-fa-info" {
        description
          "TE forwarding adjacency information";
      }
      enum "isis-lsp-trig-nsr-fo" {
        description
          "NSR FO is done";
      }
      enum "isis-lsp-trig-pn-cancel" {
        description
          "Pseudo-node generation canceled";
      }
      enum "isis-lsp-trig-lkgp" {
        description
          "Link-group offset metric change";
      }
      enum "isis-lsp-trig-pp" {
        description
          "Proactive Protection metric change";
      }
      enum "isis-lsp-trig-config-force-send" {
        description
          "Any configuration change that requires all LSPs
           to be updated";
      }
      enum "isis-lsp-trig-config-force-init" {
        description
          "Any configuration change that requires the LBD
           database re-init.";
      }
      enum "isis-lsp-trig-adj-sid-add" {
        description
          "Adjacency SID added";
      }
      enum "isis-lsp-trig-adj-sid-delete" {
        description
          "Adjacency SID deleted";
      }
      enum "isis-lsp-trig-adj-sid-change" {
        description
          "Adjacency SIDs added and/or deleted";
      }
      enum "isis-lsp-trig-msd" {
        description
          "Maximum SID depth change";
      }
      enum "isis-lsp-trig-adj-sid-wait-timer" {
        description
          "Adjacency SID wait timer expired";
      }
      enum "isis-lsp-trig-direct-gen" {
        description
          "Direct LSP generation";
      }
      enum "isis-lsp-trig-flex-algo-enable-disable" {
        description
          "Flex-Algo Enable/Disable";
      }
      enum "isis-lsp-trig-reverse-metric" {
        description
          "Reverse metric";
      }
      enum "isis-lsp-trig-pm-delay-loss" {
        description
          "Link delay/loss changed";
      }
      enum "isis-lsp-trig-pm-bw-util" {
        description
          "Link bandwidth utilization changed";
      }
    }
    description
      "Isis lsp trigger";
  }

  typedef Isis-adj-topo-status {
    type enumeration {
      enum "isis-adj-topo-status-ok" {
        description
          "Topology is included in adjacency";
      }
      enum "isis-adj-topo-status-intf-not-configured" {
        description
          "Topology is not configured on the interface";
      }
      enum "isis-adj-topo-status-intf-not-running" {
        description
          "Topology is not running on the interface";
      }
      enum "isis-adj-topo-status-init-state" {
        description
          "Adjacency is in INIT state";
      }
      enum "isis-adj-topo-status-neighbor-doesnt-participate" {
        description
          "Neighbor doesn't participate in topology";
      }
      enum "isis-adj-topo-status-ipv4-address-tlv-missing" {
        description
          "Neighbor IIH doesn't contain IPv4 address TLV";
      }
      enum "isis-adj-topo-status-ipv4-address-tlv-empty" {
        description
          "Neighbor's IPv4 address TLV is empty";
      }
      enum "isis-adj-topo-status-ipv6-address-tlv-missing" {
        description
          "Neighbor IIH doesn't contain IPv6 address TLV";
      }
      enum "isis-adj-topo-status-ipv6-address-tlv-empty" {
        description
          "Neighbor's IPv6 address TLV is empty";
      }
      enum "isis-adj-topo-status-ipv4-address-matches-ours" {
        description
          "Neighbor's IPv4 address matches ours";
      }
      enum "isis-adj-topo-status-ipv6-address-matches-ours" {
        description
          "Neighbor's IPv6 address matches ours";
      }
      enum "isis-adj-topo-status-ipv4-address-subnet-mismatch" {
        description
          "Neighbor's IPv4 address is in a different
           subnet to ours";
      }
      enum "isis-adj-topo-status-ipv6-address-not-link-local" {
        description
          "Neighbor's IPv6 address is not link local";
      }
    }
    description
      "Status of a topology in an adjacency";
  }

  typedef Isis-dr-priority {
    type uint8;
    description
      "Isis dr priority";
  }

  typedef Isis-adj-bfd-state {
    type enumeration {
      enum "isis-adj-bfd-no-state" {
        value 0;
        description
          "No BFD session created";
      }
      enum "isis-adj-bfd-down-state" {
        value 1;
        description
          "BFD session is DOWN";
      }
      enum "isis-adj-bfd-init-state" {
        value 2;
        description
          "Waiting for BFD session to come UP";
      }
      enum "isis-adj-bfd-up-state" {
        value 3;
        description
          "BFD session is UP";
      }
    }
    description
      "Current BFD state of an adjacency";
  }

  typedef Isis-adj-topo-change {
    type enumeration {
      enum "isis-adj-topo-up-change" {
        value 0;
        description
          "Topology up";
      }
      enum "isis-adj-topo-next-hop-change" {
        value 1;
        description
          "Topology next-hop changed";
      }
      enum "isis-adj-topo-down-change" {
        value 2;
        description
          "Topology down";
      }
    }
    description
      "Per-topology change type for an adjacency";
  }

  typedef Isis-adj-state-reason {
    type enumeration {
      enum "isis-adj-up-nsf-restart" {
        value 0;
        description
          "NSF Restart";
      }
      enum "isis-adj-up-new-adj" {
        value 1;
        description
          "New adjacency";
      }
      enum "isis-adj-up-restarted" {
        value 2;
        description
          "Restarted";
      }
      enum "isis-adj-up-nsf-restored" {
        value 3;
        description
          "Restored during NSF";
      }
      enum "isis-adj-up-chkpt-restored" {
        value 4;
        description
          "Restored from checkpoint";
      }
      enum "isis-adj-init-reason" {
        value 5;
        description
          "Into INIT";
      }
      enum "isis-adj-init-neighbor-forgot" {
        value 6;
        description
          "Neighbor forgot us";
      }
      enum "isis-adj-down-hold-time" {
        value 7;
        description
          "Holdtime expired";
      }
      enum "isis-adj-down-if-down" {
        value 8;
        description
          "Interface state going down";
      }
      enum "isis-adj-down-cfg-mismatch" {
        value 9;
        description
          "Area address/level mismatch";
      }
      enum "isis-adj-down-circ-id" {
        value 10;
        description
          "Circuit ID changed";
      }
      enum "isis-adj-down-nsf-ack-fail" {
        value 11;
        description
          "NSF could not CSNP Ack P2P adjacency";
      }
      enum "isis-adj-down-db-clear" {
        value 12;
        description
          "Clear of the Adjacency DB";
      }
      enum "isis-adj-down-no-common-topology" {
        value 13;
        description
          "Neighbors have no common link topology";
      }
      enum "isis-adj-down-restart-tlv-missing" {
        value 14;
        description
          "Restart TLV missing during IETF NSF restart";
      }
      enum "isis-adj-down-bfd-down" {
        value 15;
        description
          "BFD session has gone DOWN";
      }
      enum "isis-adj-down-3way-down" {
        value 16;
        description
          "3-way state down";
      }
    }
    description
      "Isis adj state reason";
  }

  typedef Isis-level {
    type enumeration {
      enum "isis-level0" {
        value 0;
        description
          "isis level0";
      }
      enum "isis-level1" {
        value 1;
        description
          "isis level1";
      }
      enum "isis-level2" {
        value 2;
        description
          "isis level2";
      }
    }
    description
      "Isis level";
  }

  typedef Isis-srv6-endpoint-func {
    type uint16;
    description
      "Isis srv6 endpoint func";
  }

  typedef Isis-ip-prefix-length {
    type uint8;
    description
      "Isis ip prefix length";
  }

  typedef Isis-ipv6-address {
    type inet:ipv6-address;
    description
      "Isis ipv6 address";
  }

  typedef Isis-nodal-sid-value {
    type uint32;
    description
      "Isis nodal sid value";
  }

  typedef Isis-ipv4-address {
    type inet:ipv4-address;
    description
      "Isis ipv4 address";
  }

  typedef Isis-sub-af-id {
    type enumeration {
      enum "unicast" {
        value 0;
        description
          "Unicast";
      }
      enum "multicast" {
        value 1;
        description
          "Multicast";
      }
    }
    description
      "Isis sub af id";
  }

  typedef Isis-af-id {
    type enumeration {
      enum "ipv4" {
        value 0;
        description
          "IPv4";
      }
      enum "ipv6" {
        value 1;
        description
          "IPv6";
      }
    }
    description
      "Isis af id";
  }

  typedef Isis-media-class {
    type enumeration {
      enum "isis-media-class-lan" {
        value 0;
        description
          "LAN";
      }
      enum "isis-media-class-p2p" {
        value 1;
        description
          "P2P";
      }
      enum "isis-media-class-loop-back" {
        value 2;
        description
          "Loopback";
      }
    }
    description
      "Isis media class";
  }

  typedef Isis-levels {
    type enumeration {
      enum "isis-levels-none" {
        value 0;
        description
          "isis levels none";
      }
      enum "isis-levels-1" {
        value 1;
        description
          "isis levels 1";
      }
      enum "isis-levels-2" {
        value 2;
        description
          "isis levels 2";
      }
      enum "isis-levels-12" {
        value 3;
        description
          "isis levels 12";
      }
      enum "isis-levels-total" {
        value 4;
        description
          "isis levels total";
      }
    }
    description
      "Isis levels";
  }

  typedef Isis-adj-state {
    type enumeration {
      enum "isis-adj-up-state" {
        value 0;
        description
          "Adjacency up";
      }
      enum "isis-adj-init-state" {
        value 1;
        description
          "Adjacency initializing";
      }
      enum "isis-adj-failed-state" {
        value 2;
        description
          "Adjacency down/failed";
      }
    }
    description
      "Isis adj state";
  }

  grouping ISIS-SH-CHKPT-TE-TUNNEL {
    description
      "Checkpointed TE tunnel";
    leaf checkpoint-te-level {
      type Isis-level;
      description
        "TE database level";
    }
    leaf checkpoint-te-system-id {
      type xr:Osi-system-id;
      description
        "Destination system ID";
    }
    leaf checkpoint-te-interface {
      type xr:Interface-name;
      description
        "Tunnel interface";
    }
    leaf checkpoint-te-flags {
      type uint32;
      description
        "Tunnel flags";
    }
    leaf checkpoint-te-nexthop {
      type Isis-ipv4-address;
      description
        "Tunnel next-hop IP address";
    }
    leaf checkpoint-te-metric {
      type int32;
      description
        "Tunnel metric";
    }
    leaf checkpoint-te-metric-mode {
      type Isis-metric-mode;
      description
        "Tunnel metric mode";
    }
    leaf checkpoint-te-bandwidth {
      type uint32;
      description
        "Tunnel bandwidth";
    }
    leaf checkpoint-te-object-id {
      type uint32;
      description
        "Tunnel checkpoint object ID";
    }
  }

  grouping NSR-STATS-GBL-TYPE {
    description
      "NSR STATS GBL TYPE";
    leaf no-of-l1-lsp {
      type uint32;
      description
        "no of l1 lsp";
    }
    leaf no-of-l2-lsp {
      type uint32;
      description
        "no of l2 lsp";
    }
    leaf no-of-l1-adj {
      type uint16;
      description
        "no of l1 adj";
    }
    leaf no-of-l2-adj {
      type uint16;
      description
        "no of l2 adj";
    }
    leaf no-of-live-interface {
      type uint16;
      description
        "no of live interface";
    }
    leaf no-of-ptp-interface {
      type uint16;
      description
        "no of ptp interface";
    }
    leaf no-of-lan-interface {
      type uint16;
      description
        "no of lan interface";
    }
    leaf no-of-loopback-interface {
      type uint16;
      description
        "no of loopback interface";
    }
    leaf no-of-te-tunnels {
      type uint16;
      description
        "no of te tunnels";
    }
    leaf no-of-te-links {
      type uint16;
      description
        "no of te links";
    }
    leaf no-of-ipv4-routes {
      type uint32;
      description
        "no of ipv4 routes";
    }
    leaf no-of-ipv6-routes {
      type uint32;
      description
        "no of ipv6 routes";
    }
    leaf seqnum {
      type uint32;
      description
        "seqnum";
    }
  }

  grouping NSR-STATS-GBL-ARR-TYPE {
    description
      "NSR STATS GBL ARR TYPE";
    container self {
      description
        "self";
      uses NSR-STATS-GBL-TYPE;
    }
    list peer {
      max-elements "3";
      description
        "peer";
      uses NSR-STATS-GBL-TYPE;
    }
  }

  grouping ISIS-SH-NSR-STATS-GLOBAL {
    description
      "IS-IS process NSR statistics";
    container isis-nsr-stats-data {
      description
        "ISIS NSR STATS Data";
      uses NSR-STATS-GBL-ARR-TYPE;
    }
    leaf isis-vm-state {
      type uint16;
      description
        "ISIS VM STATE";
    }
  }

  grouping ISIS-SH-MESH-ENTRY {
    description
      "Mesh-group informaiton for one interface";
    list isis-sh-mesh-entry {
      description
        "Next entry in list";
      leaf mesh-group-interface {
        type xr:Interface-name;
        description
          "This interface";
      }
      leaf mesh-group-number {
        type Isis-mesh-group-number;
        description
          "Mesh-group number";
      }
    }
  }

  grouping ISIS-SH-MESH-GROUPS {
    description
      "IS-IS mesh-group data";
    container mesh-group-configured-interface-list {
      description
        "List of mesh-group-configured interfaces";
      uses ISIS-SH-MESH-ENTRY;
    }
  }

  grouping ISIS-SH-CHKPT-LSP {
    description
      "Checkpointed LSP";
    leaf checkpoint-lsp-object-id {
      type uint32;
      description
        "LSP Checkpoint table object ID";
    }
    leaf checkpoint-lsp-level {
      type uint8;
      description
        "LSP level";
    }
    leaf checkpoint-lsp-local-flag {
      type boolean;
      description
        "TRUE if this is a local LSP";
    }
    leaf checkpoint-lsp-id {
      type xr:Isis-lsp-id;
      description
        "LSP ID";
    }
  }

  grouping ISIS-SH-NBR-SUMM-LEVEL {
    description
      "Neighbor states for one level";
    leaf neighbor-up-count {
      type uint32;
      description
        "Neighbors up";
    }
    leaf neighbor-init-count {
      type uint32;
      description
        "Neighbors being initialized";
    }
    leaf neighbor-down-count {
      type uint32;
      description
        "Neighbors down";
    }
  }

  grouping ISIS-SH-NBR-SUMM {
    description
      "Neighbor summary data";
    container level1-neighbors {
      description
        "L1-only neighbors";
      uses ISIS-SH-NBR-SUMM-LEVEL;
    }
    container level2-neighbors {
      description
        "L2-only neighbors";
      uses ISIS-SH-NBR-SUMM-LEVEL;
    }
    container level12-neigbors {
      description
        "L12 neighbors";
      uses ISIS-SH-NBR-SUMM-LEVEL;
    }
  }

  grouping ISIS-SH-DDADJ-SID {
    description
      "Delay Deletion Protected Adj-SID data";
    container id {
      description
        "Topology ID";
      uses ISIS-TOPO-ID-TYPE;
    }
    container neighbor-ip-address {
      description
        "Neighbor IP address";
      uses ISIS-IP-ADDR-TYPE;
    }
    leaf adj-sid-value {
      type Isis-nodal-sid-value;
      description
        "Protected adjacency sid value";
    }
    leaf is-madj-sid {
      type boolean;
      description
        "Is manual adjacency sid";
    }
    leaf interface {
      type Isis-sh-interface-name;
      description
        "Interface";
    }
    leaf level {
      type Isis-level;
      description
        "Level this data applies to";
    }
    leaf neighbor-id {
      type xr:Osi-system-id;
      description
        "Neighbor ID";
    }
    leaf remaining-time {
      type uint32;
      description
        "Remaining time before deletion";
    }
  }

  grouping ISIS-SH-AREA {
    description
      "Per-area IS-IS protocol data";
    leaf lsp-mtu {
      type uint32;
      description
        "Configured LSP MTU";
    }
  }

  grouping ISIS-SH-OVRLD-TOPO-INFO {
    description
      "BGP Timer expiry Information per Topology";
    container id {
      description
        "Topology ID";
      uses ISIS-TOPO-ID-TYPE;
    }
    container overload-bit-b-gp-expiry-time-per-topo {
      description
        "Timestamp for BGP Timer Expiry per Topology";
      uses ISIS-SH-TIMESTAMP-TYPE;
    }
  }

  grouping ISIS-SH-OVRLD-BIT {
    description
      "Overload bit Configuration and Operational data";
    container overload-bit-status-change-time {
      description
        "Timestamp when status changes";
      uses ISIS-SH-TIMESTAMP-TYPE;
    }
    container overload-bit-startup-epiry-time {
      description
        "Timestamp for OnStartup Timer Expiry";
      uses ISIS-SH-TIMESTAMP-TYPE;
    }
    container overload-bit-bgp-expiry-time {
      description
        "Timestamp for BGP Timer Expiry";
      uses ISIS-SH-TIMESTAMP-TYPE;
    }
    leaf level {
      type Isis-level;
      description
        "Level this data applies to";
    }
    leaf currently-active {
      type boolean;
      description
        "Overload bit Currently Active";
    }
    leaf mode {
      type Isis-overload-bit-mode;
      description
        "Overload bit mode type";
    }
    leaf overload-bit-on-startup-secs {
      type uint32;
      description
        "Time after reboot";
    }
    leaf advertise-external-prefix {
      type boolean;
      description
        "Advertise Overload bit for external prefixes";
    }
    leaf advertise-inter-level-prefix {
      type boolean;
      description
        "Advertisze Overload bit for interlevel prefixes";
    }
    list overload-bit-expiry-per-topo {
      description
        "Timestamp for BGP Timer Expiry per Toplogy";
      uses ISIS-SH-OVRLD-TOPO-INFO;
    }
  }

  grouping ISIS-SH-MXM {
    description
      "Max Metric Operational data";
    container max-metric-status-change-time {
      description
        "Timestamp when status changes";
      uses ISIS-SH-TIMESTAMP-TYPE;
    }
    container max-metric-startup-epiry-time {
      description
        "Timestamp for OnStartup Timer Expiry";
      uses ISIS-SH-TIMESTAMP-TYPE;
    }
    container max-metric-bgp-expiry-time {
      description
        "Timestamp for BGP Timer Expiry";
      uses ISIS-SH-TIMESTAMP-TYPE;
    }
    leaf active {
      type boolean;
      description
        "Maximum Metric Currently Active";
    }
    leaf level {
      type Isis-level;
      description
        "Level this data applies to";
    }
    leaf max-metric-mode {
      type Isis-max-metric-mode;
      description
        "mode of the max-metric";
    }
    leaf max-metric-redist-pfx {
      type boolean;
      description
        "Override prefix metric from another protocol";
    }
    leaf max-metric-inter-level-pfx {
      type boolean;
      description
        "Override prefix metric from another ISIS Level";
    }
    leaf max-metric-default-route {
      type boolean;
      description
        "Override default route metric";
    }
    leaf max-metric-srv6-locators {
      type boolean;
      description
        "Override Segment routing ipv6 metric";
    }
    leaf max-metric-trigger-expired {
      type boolean;
      description
        "Check MaxMetric Trigger Expiry";
    }
    leaf max-metric-on-startup-secs {
      type uint32;
      description
        "Time after reboot";
    }
  }

  grouping ISIS-SH-TOPO-LOCATOR {
    description
      "Configured SRv6 Locator";
    leaf locator-active {
      type boolean;
      description
        "Locator exists in global configuration";
    }
    leaf anycast-locator {
      type boolean;
      description
        "Anycast Locator";
    }
    leaf locator-out-of-resources {
      type boolean;
      description
        "Locator has no more SIDs available";
    }
    leaf locator-name {
      type string;
      description
        "Locator name";
    }
  }

  grouping ISIS-SH-TOPO-AREA {
    description
      "Per-topology, per-area IS-IS protocol data";
    leaf level {
      type Isis-level;
      description
        "The level this data refers to";
    }
    leaf uses-default-link-topo-flag {
      type boolean;
      description
        "Does this topology use the default link topology";
    }
    leaf generated-metric-style {
      type Isis-metric-style;
      description
        "Generate metric style";
    }
    leaf accepted-metric-style {
      type Isis-metric-style;
      description
        "Accept metric style";
    }
    leaf metric {
      type Isis-metric;
      description
        "Metric";
    }
    leaf ispf-state {
      type Isis-enabled;
      description
        "ISPF state";
    }
    leaf te-enabled {
      type boolean;
      description
        "Indicates whether MPLS TE is enabled";
    }
    leaf uloop-avoidance-type {
      type Isis-uloop-avoidance;
      description
        "Microloop avoidance type";
    }
    leaf rib-update-delay {
      type uint32;
      description
        "Microloop RIB update delay";
    }
    leaf sr-uloop-is-active {
      type boolean;
      description
        "Explicit paths installed in the RIB";
    }
    leaf duration {
      type uint32;
      description
        "SR microloop avoidance duration";
    }
    leaf sr-uloop-event {
      type Isis-uloop-event;
      description
        "SR microloop avoidance event";
    }
    leaf sr-uloop-near-node-id {
      type xr:Isis-node-id;
      description
        "SR microloop near node";
    }
    leaf sr-uloop-far-node-id {
      type xr:Isis-node-id;
      description
        "SR microloop far node";
    }
  }

  grouping ISIS-SH-REDIST-ENTRY {
    description
      "Redistributed protocol entry";
    list isis-sh-redist-entry {
      description
        "Next entry in list";
      container protocol-details {
        description
          "Relevant details of the redistributed protocol";
        uses ISIS-SH-REDIST-ENTRY-PROTO;
      }
    }
  }

  grouping ISIS-SH-TOPO {
    description
      "Per-topology IS-IS instance data";
    container id {
      description
        "Topology ID";
      uses ISIS-TOPO-ID-TYPE;
    }
    container redist-protocols-list {
      description
        "List of redistributed protocols";
      uses ISIS-SH-REDIST-ENTRY;
    }
    leaf default-admin-distance {
      type uint32;
      description
        "Default administrative distance";
    }
    leaf advertise-passive-only {
      type boolean;
      description
        "Advertise passive interface prefixes only";
    }
    leaf wait-redist-complete {
      type boolean;
      description
        "Waiting for redist complete RIB event";
    }
    leaf rib-connected {
      type boolean;
      description
        "Rib Connected";
    }
    leaf sr-mpls-enabled {
      type boolean;
      description
        "SR-MPLS is enabled";
    }
    leaf srv6-enabled {
      type boolean;
      description
        "SRv6 is enabled";
    }
    list per-area-data {
      description
        "Per-area data";
      uses ISIS-SH-TOPO-AREA;
    }
    list srv6-configured-locator {
      description
        "Configured SRv6 locators";
      uses ISIS-SH-TOPO-LOCATOR;
    }
  }

  grouping ISIS-SH-PROTO {
    description
      "Information about an IS-IS instance";
    leaf vrf-context {
      type Isis-string;
      description
        "VRF context";
    }
    leaf nsap-system-id {
      type xr:Osi-system-id;
      description
        "Local system ID";
    }
    leaf valid-nsap-system-id {
      type boolean;
      description
        "Indicates if system ID valid";
    }
    leaf instance-id {
      type uint16;
      description
        "instance id";
    }
    leaf running-levels {
      type Isis-levels;
      description
        "Levels running";
    }
    leaf configured-nsf-flavor {
      type Isis-nsf-flavor;
      description
        "Configured NSF type";
    }
    leaf last-restart-nsf-flavor {
      type Isis-nsf-flavor;
      description
        "NSF type of last restart";
    }
    leaf last-restart-status {
      type Isis-startup-status;
      description
        "Last restart status";
    }
    leaf te-connection {
      type Isis-up;
      description
        "TE connection";
    }
    leaf remaining-time-for-next-nsf-restart {
      type uint32;
      description
        "Time remaining until the next NSF restart may be
         attempted";
    }
    leaf adj-form-count {
      type uint32;
      description
        "Adj Forming count";
    }
    leaf adj-full-count {
      type uint32;
      description
        "Adj Full count";
    }
    leaf adj-stagger-enabled {
      type boolean;
      description
        "Adjacency Stagger Enabled";
    }
    leaf adj-stagger-init {
      type uint32;
      description
        "Adjacency Stagger Initiall Number of Forming
         Neighbors Allowed";
    }
    leaf adj-stagger-max {
      type uint32;
      description
        "Adjacency Stagger Max Number of Forming
         Neighbors Allowed";
    }
    leaf srgb-allocated {
      type boolean;
      description
        "Is SRGB allocated ?";
    }
    leaf srgb-start {
      type uint32;
      description
        "First label in SRGB";
    }
    leaf srgb-end {
      type uint32;
      description
        "Last label in SRGB";
    }
    leaf srlb-allocated {
      type boolean;
      description
        "Is SRLB allocated ?";
    }
    leaf srlb-start {
      type uint32;
      description
        "First label in SRLB";
    }
    leaf srlb-end {
      type uint32;
      description
        "Last label in SRLB";
    }
    list manual-area-address {
      description
        "Manual area addresses";
      leaf entry {
        type xr:Osi-area-address;
        description
          "Manual area addresses";
      }
    }
    list active-area-address {
      description
        "Active area addresses";
      leaf entry {
        type xr:Osi-area-address;
        description
          "Active area addresses";
      }
    }
    list per-topo-data {
      description
        "Per-topology data";
      uses ISIS-SH-TOPO;
    }
    list per-level-max-metric-data {
      description
        "Per-level max-metric data";
      uses ISIS-SH-MXM;
    }
    list per-level-overload-bit-data {
      description
        "Per-level overload bit data";
      uses ISIS-SH-OVRLD-BIT;
    }
    list per-area-data {
      max-elements "2";
      description
        "Per-area data";
      uses ISIS-SH-AREA;
    }
    list dd-adj-sid-data {
      description
        "Delay Deletion Protected Adj-SID data";
      uses ISIS-SH-DDADJ-SID;
    }
  }

  grouping ISIS-TRAFFIC-INTF-AREA-LAN-TYPE {
    description
      "Per-interface, per-area LAN-only statistics";
    container iih-count {
      description
        "IIH statistics";
      uses ISIS-TRAFFIC-PDU-COUNT-TYPE;
    }
    leaf memory-exhausted-iih-count {
      type uint32;
      description
        "IIHs not sent due to memory exhaustion";
    }
    leaf dis-election-count {
      type uint32;
      description
        "DIS elections";
    }
  }

  grouping ISIS-TRAFFIC-INTF-AREA-TYPE {
    description
      "Per-interface, per-area statistics";
    container lsp-count {
      description
        "LSP statistics";
      uses ISIS-TRAFFIC-PDU-COUNT-TYPE;
    }
    container csnp-count {
      description
        "CSNP statistics";
      uses ISIS-TRAFFIC-PDU-COUNT-TYPE;
    }
    container psnp-count {
      description
        "PSNP statistics";
      uses ISIS-TRAFFIC-PDU-COUNT-TYPE;
    }
    leaf lsp-drop-count {
      type uint32;
      description
        "Count of LSPs dropped due to minimum arrival
         time config";
    }
    leaf lsp-flooding-dup-count {
      type uint32;
      description
        "Count of LSPs already received by neighbors and
         not flooded";
    }
  }

  grouping ISIS-SH-TRAFFIC-INTF-AREA {
    description
      "Per-interface, per-area data";
    container statistics {
      description
        "Statistics";
      uses ISIS-TRAFFIC-INTF-AREA-TYPE;
    }
    container lan-data {
      description
        "LAN interface statistics. NULL for non-LAN
         interfaces";
      uses ISIS-TRAFFIC-INTF-AREA-LAN-TYPE;
    }
    leaf level {
      type Isis-level;
      description
        "Level of the area this data relates to";
    }
  }

  grouping ISIS-TRAFFIC-PDU-COUNT-TYPE {
    description
      "Per-interface, per-PDU statistics";
    leaf pdu-receive-count {
      type uint32;
      description
        "PDUs received";
    }
    leaf pdu-send-count {
      type uint32;
      description
        "PDUs sent";
    }
  }

  grouping ISIS-TRAFFIC-INTF-P2P-TYPE {
    description
      "Per-interface point-to-point statistics";
    container iih-count {
      description
        "IIH statistics";
      uses ISIS-TRAFFIC-PDU-COUNT-TYPE;
    }
    leaf memory-exhausted-iih-count {
      type uint32;
      description
        "IIHs not sent due to memory exhaustion";
    }
    leaf lsp-retransmit-count {
      type uint32;
      description
        "LSP retransmissions";
    }
  }

  grouping ISIS-SH-TRAFFIC-INTF {
    description
      "IS-IS interface traffic data";
    container p2p-statistics {
      description
        "P2P interface statistics. NULL for non-P2P
         interfaces";
      uses ISIS-TRAFFIC-INTF-P2P-TYPE;
    }
    leaf traffic-interface {
      type xr:Interface-name;
      description
        "Interface to which traffic statistics apply";
    }
    leaf interface-media-type {
      type Isis-media-class;
      description
        "Interface media class";
    }
    list per-area-data {
      description
        "Per-area data";
      uses ISIS-SH-TRAFFIC-INTF-AREA;
    }
  }

  grouping ISIS-SH-LABEL {
    description
      "Label data";
    container label-prefix {
      description
        "label prefix";
      uses ISIS-IP-PREFIX-TYPE;
    }
    leaf label-type {
      type Isis-edm-label-type-enum;
      description
        "label type";
    }
    leaf label-flags {
      type uint8;
      description
        "label flags";
    }
    leaf label-refcount {
      type uint8;
      description
        "label refcount";
    }
    leaf label-value {
      type uint32;
      description
        "label value";
    }
    leaf label-interface {
      type Isis-sh-interface-name;
      description
        "label interface";
    }
    leaf label-ifh {
      type xr:Interface-name;
      description
        "label ifh";
    }
    leaf label-table-id {
      type uint32;
      description
        "label table id";
    }
    leaf label-af-id {
      type Isis-af-id;
      description
        "label af id";
    }
    list conflict-label-prefix {
      description
        "conflict label prefix";
      uses ISIS-IP-PREFIX-TYPE;
    }
  }

  grouping ISIS-SH-CHKPT-IDB {
    description
      "Checkpointed interface";
    leaf checkpoint-object-id {
      type uint32;
      description
        "Checkpoint object ID";
    }
    leaf interface-name-xr {
      type string;
      description
        "Interface name";
    }
    leaf checkpoint-interface-handle {
      type xr:Interface-name;
      description
        "Local interface handle";
    }
    leaf local-circuit-number {
      type Isis-circuit-number;
      description
        "Local circuit number";
    }
    leaf dis-areas {
      type Isis-levels;
      description
        "Areas in which this system is DIS";
    }
    leaf has-adjacency {
      type boolean;
      description
        "TRUE if there is an adjacency on this interface";
    }
    leaf local-snpa {
      type xr:Isis-snpa;
      description
        "SNPA of this interface";
    }
    leaf has-joined-mcast-group {
      type boolean;
      description
        "TRUE if multicast group registration succeeded
         on this interface";
    }
    leaf has-achieved-ldp-sync {
      type boolean;
      description
        "MPLS LDP sync status";
    }
    leaf has-achieved-ld-pv6-sync {
      type boolean;
      description
        "MPLS LDPv6 sync status";
    }
  }

  grouping ISIS-SH-ERR-LOG-ENT {
    description
      "An error log entry";
    container generic-data {
      description
        "Generic entry data";
      uses ISIS-SH-GENERIC-LOG-ENT;
    }
    leaf error-log-level {
      type Isis-err-log-level;
      description
        "Logging level";
    }
    leaf error-code {
      type uint32;
      description
        "Error code";
    }
    leaf error-reason {
      type string;
      description
        "Error details";
    }
  }

  grouping ISIS-SH-ERR-LOG-STRUC {
    description
      "Error log structure";
    list log-entry {
      description
        "Error Log entries";
      uses ISIS-SH-ERR-LOG-ENT;
    }
  }

  grouping ISIS-MIB-CIRC-ENTRY {
    description
      "isisCircEntry";
    leaf isis-circ-index {
      type uint32;
      description
        "isisCircIndex";
    }
    leaf isis-circ-if-index {
      type int32;
      description
        "isisCircIfIndex";
    }
    leaf isis-circ-admin-state {
      type int32;
      description
        "isisCircAdminState";
    }
    leaf isis-circ-exist-state {
      type int32;
      description
        "isisCircExistState";
    }
    leaf isis-circ-type {
      type int32;
      description
        "isisCircType";
    }
    leaf isis-circ-ext-domain {
      type int32;
      description
        "isisCircExtDomain";
    }
    leaf isis-circ-level-type {
      type int32;
      description
        "isisCircLevelType";
    }
    leaf isis-circ-passive-circuit {
      type int32;
      description
        "isisCircPassiveCircuit";
    }
    leaf isis-circ-mesh-group-enabled {
      type int32;
      description
        "isisCircMeshGroupEnabled";
    }
    leaf isis-circ-mesh-group {
      type uint32;
      description
        "isisCircMeshGroup";
    }
    leaf isis-circ-small-hellos {
      type int32;
      description
        "isisCircSmallHellos";
    }
    leaf isis-circ-last-up-time {
      type uint32;
      description
        "isisCircLastUpTime";
    }
    leaf isis-circ3-way-enabled {
      type int32;
      description
        "isisCirc3WayEnabled";
    }
    leaf isis-circ-extended-circ-id {
      type uint32;
      description
        "isisCircExtendedCircID";
    }
  }

  grouping ISIS-MIB-SYS-OBJECT {
    description
      "isisSysObject";
    leaf isis-sys-version {
      type int32;
      description
        "isisSysVersion";
    }
    leaf isis-sys-level-type {
      type int32;
      description
        "isisSysLevelType";
    }
    leaf sys-id {
      type xr:Osi-system-id;
      description
        "sys id";
    }
    leaf isis-sys-max-path-splits {
      type uint32;
      description
        "isisSysMaxPathSplits";
    }
    leaf isis-sys-max-lsp-gen-int {
      type uint32;
      description
        "isisSysMaxLSPGenInt";
    }
    leaf isis-sys-poll-es-hello-rate {
      type uint32;
      description
        "isisSysPollESHelloRate";
    }
    leaf isis-sys-wait-time {
      type uint32;
      description
        "isisSysWaitTime";
    }
    leaf isis-sys-admin-state {
      type int32;
      description
        "isisSysAdminState";
    }
    leaf isis-sys-l2to-l1-leaking {
      type int32;
      description
        "isisSysL2toL1Leaking";
    }
    leaf isis-sys-max-age {
      type uint32;
      description
        "isisSysMaxAge";
    }
    leaf isis-sys-receive-lsp-buffer-size {
      type uint32;
      description
        "isisSysReceiveLSPBufferSize";
    }
    leaf isis-sys-notification-enable {
      type int32;
      description
        "isisSysNotificationEnable";
    }
    list sys-prot-supported {
      description
        "sys prot supported";
      leaf entry {
        type uint8;
        description
          "sys prot supported";
      }
    }
  }

  grouping ISIS-MIB-SUMM-ADDR-ENTRY {
    description
      "isisSummAddrEntry";
    container ip-prefix {
      description
        "ip prefix";
      uses ISIS-IP-PREFIX-TYPE;
    }
    leaf isis-summ-addr-metric {
      type uint32;
      description
        "isisSummAddrMetric";
    }
    leaf isis-summ-addr-full-metric {
      type uint32;
      description
        "isisSummAddrFullMetric";
    }
  }

  grouping ISIS-MIB-SUMM-ADDR-TABLE {
    description
      "isisSummAddrTable";
    list isis-summ-addr-entry {
      description
        "isis summ addr entry";
      uses ISIS-MIB-SUMM-ADDR-ENTRY;
    }
  }

  grouping ISIS-MIB-ADJ-ENTRY {
    description
      "isisISAdjEntry";
    leaf isis-is-adj-index {
      type uint32;
      description
        "isisISAdjIndex";
    }
    leaf isis-is-adj-state {
      type int32;
      description
        "isisISAdjState";
    }
    leaf isis-is-adj3-way-state {
      type int32;
      description
        "isisISAdj3WayState";
    }
    leaf nbr-snpa-addr {
      type xr:Isis-snpa;
      description
        "nbr snpa addr";
    }
    leaf isis-is-adj-neigh-sys-type {
      type int32;
      description
        "isisISAdjNeighSysType";
    }
    leaf nbr-system-id {
      type xr:Osi-system-id;
      description
        "nbr system id";
    }
    leaf isis-is-adj-nbr-extended-circ-id {
      type uint32;
      description
        "isisISAdjNbrExtendedCircID";
    }
    leaf isis-is-adj-usage {
      type int32;
      description
        "isisISAdjUsage";
    }
    leaf isis-is-adj-hold-timer {
      type uint32;
      description
        "isisISAdjHoldTimer";
    }
    leaf isis-is-adj-neigh-priority {
      type uint32;
      description
        "isisISAdjNeighPriority";
    }
    leaf isis-is-adj-last-up-time {
      type uint32;
      description
        "isisISAdjLastUpTime";
    }
    leaf isis-circ-index {
      type uint32;
      description
        "isisCircIndex";
    }
    leaf prot-supp {
      type Isis-prot-supp;
      description
        "prot supp";
    }
    list area-addr {
      description
        "area addr";
      leaf entry {
        type xr:Osi-area-address;
        description
          "area addr";
      }
    }
    list ip-addr {
      description
        "ip addr";
      uses ISIS-IP-ADDR-TYPE;
    }
  }

  grouping ISIS-MIB-CIRC-ADJ-TABLE {
    description
      "intermediateIsisISAdjTable";
    list circuit-adj {
      description
        "circuit adj";
      uses ISIS-MIB-ADJ-ENTRY;
    }
  }

  grouping ISIS-MIB-CIRC-LEVEL-ENTRY {
    description
      "isisCircLevelEntry";
    leaf isis-circ-level-index {
      type int32;
      description
        "isisCircLevelIndex";
    }
    leaf isis-circ-level-metric {
      type uint32;
      description
        "isisCircLevelMetric";
    }
    leaf isis-circ-level-wide-metric {
      type uint32;
      description
        "isisCircLevelWideMetric";
    }
    leaf isis-circ-level-is-priority {
      type uint32;
      description
        "isisCircLevelISPriority";
    }
    leaf isis-circ-level-id-octet {
      type uint32;
      description
        "isisCircLevelIDOctet";
    }
    leaf circuit-id {
      type Isis-circuit-id;
      description
        "circuit id";
    }
    leaf circuit-lan-id {
      type Isis-circuit-id;
      description
        "circuit lan id";
    }
    leaf isis-circ-level-hello-multiplier {
      type uint32;
      description
        "isisCircLevelHelloMultiplier";
    }
    leaf isis-circ-level-hello-timer {
      type uint32;
      description
        "isisCircLevelHelloTimer";
    }
    leaf isis-circ-level-dr-hello-timer {
      type uint32;
      description
        "isisCircLevelDRHelloTimer";
    }
    leaf isis-circ-level-lsp-throttle {
      type uint32;
      description
        "isisCircLevelLSPThrottle";
    }
    leaf isis-circ-level-min-lsp-retrans-int {
      type uint32;
      description
        "isisCircLevelMinLSPRetransInt";
    }
    leaf isis-circ-level-csnp-interval {
      type uint32;
      description
        "isisCircLevelCSNPInterval";
    }
    leaf isis-circ-level-part-snp-interval {
      type uint32;
      description
        "isisCircLevelPartSNPInterval";
    }
    leaf isis-circ-index {
      type uint32;
      description
        "isisCircIndex";
    }
  }

  grouping ISIS-MIB-IP-RA-ENTRY {
    description
      "isisIPRAEntry";
    container ip-prefix {
      description
        "ip prefix";
      uses ISIS-IP-PREFIX-TYPE;
    }
    leaf isis-ipra-next-hop-index {
      type uint32;
      description
        "isisIPRANextHopIndex";
    }
    leaf isis-ipra-metric {
      type uint32;
      description
        "isisIPRAMetric";
    }
    leaf isis-ipra-metric-type {
      type int32;
      description
        "isisIPRAMetricType";
    }
    leaf isis-ipra-full-metric {
      type uint32;
      description
        "isisIPRAFullMetric";
    }
    leaf isis-ipra-source-type {
      type int32;
      description
        "isisIPRASourceType";
    }
    leaf isis-sys-level-index {
      type int32;
      description
        "isisSysLevelIndex";
    }
  }

  grouping ISIS-MIB-IP-RA-TABLE {
    description
      "isisIPRATable";
    list route {
      description
        "route";
      uses ISIS-MIB-IP-RA-ENTRY;
    }
  }

  grouping ISIS-MIB-YANG-MODEL-LSP-ENTRY {
    description
      "isisLSPListEntry";
    leaf isis-lsp-level {
      type int32;
      description
        "isisLSPLevel";
    }
    leaf lsp-lspid {
      type xr:Isis-lsp-id;
      description
        "lsp lspid";
    }
    leaf isis-lsptlv-index {
      type uint32;
      description
        "isisLSPTLVIndex";
    }
    leaf isis-lsptlv-seq {
      type uint32;
      description
        "isisLSPTLVSeq";
    }
    leaf isis-lsptlv-checksum {
      type uint16;
      description
        "isisLSPTLVChecksum";
    }
    leaf isis-lsptlv-type {
      type uint8;
      description
        "isisLSPTLVType";
    }
    leaf isis-lsptlv-len {
      type uint8;
      description
        "isisLSPTLVLen";
    }
    leaf isis-lsptlv-value {
      type yang:hex-string;
      description
        "isisLSPTLVValue";
    }
  }

  grouping ISIS-MIB-LSP-SUMMARY-LIST-ENTRY {
    description
      "isisLSPSummaryListEntry";
    leaf isis-lsp-level {
      type int32;
      description
        "isisLSPLevel";
    }
    leaf summ-lspid {
      type xr:Isis-lsp-id;
      description
        "summ lspid";
    }
    leaf isis-lsp-seq {
      type uint32;
      description
        "isisLSPSeq";
    }
    leaf isis-lsp-zero-life {
      type int32;
      description
        "isisLSPZeroLife";
    }
    leaf isis-lsp-checksum {
      type uint32;
      description
        "isisLSPChecksum";
    }
    leaf isis-lsp-lifetime-remain {
      type uint32;
      description
        "isisLSPLifetimeRemain";
    }
    leaf isis-lsppdu-length {
      type uint32;
      description
        "isisLSPPDULength";
    }
    leaf isis-lsp-attributes {
      type uint8;
      description
        "isisLSPAttributes";
    }
  }

  grouping ISIS-MIB-SYS-STAT-LEVEL-ENTRY {
    description
      "isisSystemCounterEntry";
    leaf isis-sys-stat-level {
      type int32;
      description
        "isisSysStatLevel";
    }
    leaf isis-sys-stat-corr-ls-ps {
      type uint32;
      description
        "isisSysStatCorrLSPs";
    }
    leaf isis-sys-stat-auth-type-fails {
      type uint32;
      description
        "isisSysStatAuthTypeFails";
    }
    leaf isis-sys-stat-auth-fails {
      type uint32;
      description
        "isisSysStatAuthFails";
    }
    leaf isis-sys-stat-lsp-dbase-oloads {
      type uint32;
      description
        "isisSysStatLSPDbaseOloads";
    }
    leaf isis-sys-stat-man-addr-drop-from-areas {
      type uint32;
      description
        "isisSysStatManAddrDropFromAreas";
    }
    leaf isis-sys-stat-attmpt-to-ex-max-seq-nums {
      type uint32;
      description
        "isisSysStatAttmptToExMaxSeqNums";
    }
    leaf isis-sys-stat-seq-num-skips {
      type uint32;
      description
        "isisSysStatSeqNumSkips";
    }
    leaf isis-sys-stat-own-lsp-purges {
      type uint32;
      description
        "isisSysStatOwnLSPPurges";
    }
    leaf isis-sys-stat-id-field-len-mismatches {
      type uint32;
      description
        "isisSysStatIDFieldLenMismatches";
    }
    leaf isis-sys-stat-part-changes {
      type uint32;
      description
        "isisSysStatPartChanges";
    }
    leaf isis-sys-stat-spf-runs {
      type uint32;
      description
        "isisSysStatSPFRuns";
    }
    leaf isis-sys-stat-lsp-errors {
      type uint32;
      description
        "isisSysStatLSPErrors";
    }
  }

  grouping ISIS-MIB-SYS-LEVEL-ENTRY {
    description
      "isisSysLevelEntry";
    leaf isis-sys-level-index {
      type int32;
      description
        "isisSysLevelIndex";
    }
    leaf isis-sys-level-orig-lsp-buff-size {
      type uint32;
      description
        "isisSysLevelOrigLSPBuffSize";
    }
    leaf isis-sys-level-min-lsp-gen-int {
      type uint32;
      description
        "isisSysLevelMinLSPGenInt";
    }
    leaf isis-sys-level-state {
      type int32;
      description
        "isisSysLevelState";
    }
    leaf isis-sys-level-set-overload {
      type int32;
      description
        "isisSysLevelSetOverload";
    }
    leaf isis-sys-level-set-overload-until {
      type uint32;
      description
        "isisSysLevelSetOverloadUntil";
    }
    leaf isis-sys-level-metric-style {
      type int32;
      description
        "isisSysLevelMetricStyle";
    }
    leaf isis-sys-level-spf-considers {
      type int32;
      description
        "isisSysLevelSPFConsiders";
    }
    leaf isis-sys-level-te-enabled {
      type int32;
      description
        "isisSysLevelTEEnabled";
    }
  }

  grouping ISIS-MIB-PACKET-COUNTER-ENTRY {
    description
      "isisPacketCounterEntry";
    leaf isis-packet-count-level {
      type int32;
      description
        "isisPacketCountLevel";
    }
    leaf isis-packet-count-direction {
      type int32;
      description
        "isisPacketCountDirection";
    }
    leaf isis-packet-count-ii-hello {
      type uint32;
      description
        "isisPacketCountIIHello";
    }
    leaf isis-packet-count-is-hello {
      type uint32;
      description
        "isisPacketCountISHello";
    }
    leaf isis-packet-count-es-hello {
      type uint32;
      description
        "isisPacketCountESHello";
    }
    leaf isis-packet-count-lsp {
      type uint32;
      description
        "isisPacketCountLSP";
    }
    leaf isis-packet-count-csnp {
      type uint32;
      description
        "isisPacketCountCSNP";
    }
    leaf isis-packet-count-psnp {
      type uint32;
      description
        "isisPacketCountPSNP";
    }
    leaf isis-packet-count-unknown {
      type uint32;
      description
        "isisPacketCountUnknown";
    }
    leaf isis-circ-index {
      type uint32;
      description
        "isisCircIndex";
    }
  }

  grouping ISIS-AREA-ADDRESS-TYPE {
    description
      "IS-IS area address";
    leaf area-address-length {
      type uint8;
      units "byte";
      description
        "area address length (bytes)";
    }
    leaf area-address {
      type yang:hex-string;
      description
        "Encoded area address";
    }
  }

  grouping ISIS-MIB-AREA-ADDR-TABLE {
    description
      "isisAreaAddrTable";
    list area-addr {
      description
        "area addr";
      uses ISIS-AREA-ADDRESS-TYPE;
    }
  }

  grouping ISIS-MIB-CIRCUIT-COUNTER-ENTRY {
    description
      "isisCircuitCounterEntry";
    leaf isis-circuit-type {
      type int32;
      description
        "isisCircuitType";
    }
    leaf isis-circ-adj-changes {
      type uint32;
      description
        "isisCircAdjChanges";
    }
    leaf isis-circ-num-adj {
      type uint32;
      description
        "isisCircNumAdj";
    }
    leaf isis-circ-init-fails {
      type uint32;
      description
        "isisCircInitFails";
    }
    leaf isis-circ-rej-adjs {
      type uint32;
      description
        "isisCircRejAdjs";
    }
    leaf isis-circ-id-field-len-mismatches {
      type uint32;
      description
        "isisCircIDFieldLenMismatches";
    }
    leaf isis-circ-max-area-addr-mismatches {
      type uint32;
      description
        "isisCircMaxAreaAddrMismatches";
    }
    leaf isis-circ-auth-type-fails {
      type uint32;
      description
        "isisCircAuthTypeFails";
    }
    leaf isis-circ-auth-fails {
      type uint32;
      description
        "isisCircAuthFails";
    }
    leaf isis-circ-lan-des-is-changes {
      type uint32;
      description
        "isisCircLANDesISChanges";
    }
    leaf isis-circ-index {
      type uint32;
      description
        "isisCircIndex";
    }
  }

  grouping ISIS-SH-FLEX-ALGO-AREA {
    description
      "Flex Algo Area";
    leaf level {
      type Isis-level;
      description
        "Level";
    }
    leaf disabled {
      type boolean;
      description
        "Flex-Algo Disabled";
    }
    leaf definition-priority {
      type uint32;
      description
        "Flex-Algo Definition Priority";
    }
    leaf metric-type {
      type uint8;
      description
        "Flex-Algo Metric Type";
    }
    leaf prefix-metric {
      type boolean;
      description
        "Flex-Algo Prefix Metric";
    }
    leaf definition-local {
      type boolean;
      description
        "Flex-Algo Definition Is Local";
    }
    leaf definition-equal-local {
      type boolean;
      description
        "Flex-Algo Definition Is Equal To Local";
    }
    leaf definition-node-id {
      type xr:Isis-node-id;
      description
        "Flex-Algo Definition Node-ID";
    }
  }

  grouping ISIS-SH-FLEX-ALGO {
    description
      "Flex Algo";
    leaf number {
      type uint32;
      description
        "Flex-Algo Number";
    }
    leaf local-priority {
      type uint32;
      description
        "Flex_algo Local Priority";
    }
    leaf frr-disabled {
      type boolean;
      description
        "Flex-Algo FRR Disabled";
    }
    leaf microloop-avoidance-disabled {
      type boolean;
      description
        "Flex-Algo Microloop Avoidance Disabled";
    }
    list area {
      description
        "Per Area Flex-Algo";
      uses ISIS-SH-FLEX-ALGO-AREA;
    }
  }

  grouping ISIS-SH-CHKPT-ADJ {
    description
      "Checkpointed adjacency";
    leaf checkpoint-adjacency-object-id {
      type uint32;
      description
        "Checkpoint object ID";
    }
    leaf checkpoint-adjacency-system-id {
      type xr:Osi-system-id;
      description
        "Neighbor system ID";
    }
    leaf checkpoint-adjacency-snpa {
      type xr:Isis-snpa;
      description
        "Neighbor SNPA";
    }
    leaf checkpoint-adjacency-interface {
      type xr:Interface-name;
      description
        "Local interface";
    }
    leaf checkpoint-adjacency-level {
      type Isis-level;
      description
        "Adjacency level";
    }
    leaf checkpoint-adjacency-holdtime {
      type uint16;
      description
        "Adjacency holdtime (s)";
    }
    leaf checkpoint-adjacency-lan-priority {
      type Isis-dr-priority;
      description
        "Adjacency LAN priority";
    }
    leaf checkpoint-adjacency-circuit-number {
      type Isis-circuit-number;
      description
        "Neighbor circuit number";
    }
    list checkpoint-adjacency-per-address-family-next-hop {
      description
        "Per address family next hops";
      uses ISIS-IP-ADDR-TYPE;
    }
  }

  grouping ISIS-SH-IF-AF-PREFIX-DATA {
    description
      "Address prefix info";
    leaf is-unnumbered {
      type boolean;
      description
        "Is the interface unnumbered";
    }
    list prefix {
      description
        "Array of global prefixes";
      uses ISIS-IP-PREFIX-TYPE;
    }
  }

  grouping ISIS-SH-IF-AF-PREFIX-UNKNOWN {
    description
      "Address prefix unknown info";
    leaf reason-code {
      type Isis-if-af-prefix-unknown-reason;
      description
        "Reason why the global prefix(es) is(are) unknown";
    }
  }

  grouping ISIS-SH-IF-AF-PREFIX-STATUS {
    description
      "ISIS SH IF AF PREFIX STATUS";
    container unknown {
      when "../status = 'isis-unknown'" {
        description
          "../Status = 'ISIS_UNKNOWN'";
      }
      description
        "Unknown state for the global prefixes";
      uses ISIS-SH-IF-AF-PREFIX-UNKNOWN;
    }
    container prefix-data {
      when "../status = 'isis-known'" {
        description
          "../Status = 'ISIS_KNOWN'";
      }
      description
        "Global prefix data for the Address Family";
      uses ISIS-SH-IF-AF-PREFIX-DATA;
    }
    leaf status {
      type Isis-known;
      description
        "Status";
    }
  }

  grouping ISIS-IP-ADDR-TYPE {
    description
      "ISIS IP ADDR TYPE";
    leaf af-name {
      type Isis-af-id;
      description
        "AFName";
    }
    leaf ipv4 {
      when "../af-name = 'ipv4'" {
        description
          "../AFName = 'IPv4'";
      }
      type Isis-ipv4-address;
      description
        "IPV4 address type";
    }
    leaf ipv6 {
      when "../af-name = 'ipv6'" {
        description
          "../AFName = 'IPv6'";
      }
      type Isis-ipv6-address;
      description
        "IPV6 address type";
    }
  }

  grouping ISIS-SH-IF-AF-FWD-ADDR-DATA {
    description
      "Address-family forwarding address data";
    leaf unnumbered-interface-name {
      type string;
      description
        "If the interface is unnumbered, then its name,
         else NULL";
    }
    list forwarding-address {
      description
        "Array of forwarding addresses";
      uses ISIS-IP-ADDR-TYPE;
    }
  }

  grouping ISIS-SH-IF-AF-FWD-ADDR-UNKNOWN {
    description
      "Forwarding address unknown data";
    leaf reason-code {
      type Isis-if-af-fwd-addr-unknown-reason;
      description
        "Reason why the forwarding address(es) of an AF
         is(are) unknown";
    }
  }

  grouping ISIS-SH-IF-AF-FWD-ADDR-STATUS {
    description
      "ISIS SH IF AF FWD ADDR STATUS";
    container unknown {
      when "../status = 'isis-unknown'" {
        description
          "../Status = 'ISIS_UNKNOWN'";
      }
      description
        "Unknown forwarding address data";
      uses ISIS-SH-IF-AF-FWD-ADDR-UNKNOWN;
    }
    container forwarding-address-data {
      when "../status = 'isis-known'" {
        description
          "../Status = 'ISIS_KNOWN'";
      }
      description
        "Known Forwarding address data";
      uses ISIS-SH-IF-AF-FWD-ADDR-DATA;
    }
    leaf status {
      type Isis-known;
      description
        "Status";
    }
  }

  grouping ISIS-SH-IF-AF-PROTO-DOWN {
    description
      "Address family protocol down info";
    leaf reason-code {
      type Isis-if-af-proto-down-reason;
      description
        "Reason why the Address Family protocol status is
         down";
    }
  }

  grouping ISIS-SH-IF-AF-PROTO-STATUS {
    description
      "ISIS SH IF AF PROTO STATUS";
    container disabled {
      when "../status = 'isis-down'" {
        description
          "../Status = 'ISIS_DOWN'";
      }
      description
        "Disabled state of the Address Family protocol";
      uses ISIS-SH-IF-AF-PROTO-DOWN;
    }
    leaf status {
      type Isis-up;
      description
        "Status";
    }
  }

  grouping ISIS-SH-IF-AF-ENABLED {
    description
      "Enabled address-family info of an interface";
    container protocol-status {
      description
        "Protocol status of the AF";
      uses ISIS-SH-IF-AF-PROTO-STATUS;
    }
    container forwarding-address-status {
      description
        "Forwarding status of the AF";
      uses ISIS-SH-IF-AF-FWD-ADDR-STATUS;
    }
    container prefix-status {
      description
        "Prefix status of the AF";
      uses ISIS-SH-IF-AF-PREFIX-STATUS;
    }
  }

  grouping ISIS-SH-IF-AF-DISABLED {
    description
      "Address family disabled info";
    leaf reason-code {
      type Isis-if-af-disabled-reason;
      description
        "Reason why the Address Family is disabled";
    }
  }

  grouping ISIS-SH-IF-AF-STATUS {
    description
      "ISIS SH IF AF STATUS";
    container disabled {
      when "../status = 'isis-disabled'" {
        description
          "../Status = 'ISIS_DISABLED'";
      }
      description
        "Disabled info for the AF of an interface";
      uses ISIS-SH-IF-AF-DISABLED;
    }
    container af-data {
      when "../status = 'isis-enabled'" {
        description
          "../Status = 'ISIS_ENABLED'";
      }
      description
        "Enabled data for the AF of an interface";
      uses ISIS-SH-IF-AF-ENABLED;
    }
    leaf status {
      type Isis-enabled;
      description
        "Status";
    }
  }

  grouping ISIS-SH-IF-AF {
    description
      "Per Address family info";
    container af-status {
      description
        "Address Family status of the interface";
      uses ISIS-SH-IF-AF-STATUS;
    }
    leaf af-name {
      type Isis-af-id;
      description
        "Address Family Identifier of the interface";
    }
  }

  grouping ISIS-SH-MADJ-SID-IF {
    description
      "Manual Adjacency SID Interface Configuration and
       Operation";
    leaf manual-adjacency-sid-label {
      type Isis-nodal-sid-value;
      description
        "Manual Adjacency SID Label";
    }
    leaf manual-adjacency-sid-index {
      type Isis-nodal-sid-value;
      description
        "Manual Adjacency SID Index (if configured as
         index)";
    }
    leaf manual-adjacency-sid-type {
      type uint8;
      description
        "Manual Adjacency SID Type (Absolute or Index)";
    }
    leaf sid-protected {
      type boolean;
      description
        "SID configured as protected by backup path";
    }
    leaf sid-active {
      type boolean;
      description
        "SID is in use";
    }
  }

  grouping ISIS-FRR-TIEBREAKER-SORTED {
    description
      "FRR Tie Breaker Structure";
    leaf tie-breaker {
      type Isis-frr-tiebreaker;
      description
        "Tie Breaker Type";
    }
    leaf index {
      type uint8;
      description
        "Tie Breaker Index";
    }
  }

  grouping ISIS-SH-IF-FRR-LEVEL {
    description
      "Per level FRR information";
    leaf frr-type {
      type Isis-frr;
      description
        "FRR type configured per level for this interface";
    }
    leaf is-frr {
      type boolean;
      description
        "Is FRR enabled per level on this interface";
    }
    leaf is-remote-lfa {
      type boolean;
      description
        "Is FRR Remote LFA enabled per level for this
         interface";
    }
    leaf is-ti-lfa {
      type boolean;
      description
        "Is FRR TI LFA enabled per level for this
         interface";
    }
    leaf ti-lfa-node-tie-breaker-index {
      type uint8;
      description
        "TI LFA node-protecting Tie breaker index";
    }
    leaf ti-lfa-srlg-tie-breaker {
      type uint8;
      description
        "TI LFA srlg Tie breaker index";
    }
    leaf ti-lfa-linecard-disjoint-tie-breaker {
      type uint8;
      description
        "TI LFA Linecard Disjoint Tie breaker index";
    }
    leaf is-tie-breakers-configured {
      type boolean;
      description
        "Is Tiebreaker configured per level for this
         interface";
    }
    list frr-tie-breaker {
      max-elements "8";
      description
        "FRR TieBreakers array per level for this
         interface";
      uses ISIS-FRR-TIEBREAKER-SORTED;
    }
  }

  grouping ISIS-SH-IF-TOPO-ADV-PREFIX-DISABLED {
    description
      "Topology info when prefix advertisement is
       disabled";
    leaf reason-code {
      type Isis-if-topo-adv-prefix-disabled-reason;
      description
        "Reason why the prefix advertisement status of a
         topology is disabled";
    }
  }

  grouping ISIS-SH-IF-TOPO-ADV-PREFIX-STATUS {
    description
      "ISIS SH IF TOPO ADV PREFIX STATUS";
    container disabled {
      when "../status = 'isis-disabled'" {
        description
          "../Status = 'ISIS_DISABLED'";
      }
      description
        "Disabled state for the prefix advertisement
         status of a topology";
      uses ISIS-SH-IF-TOPO-ADV-PREFIX-DISABLED;
    }
    leaf status {
      type Isis-enabled;
      description
        "Status";
    }
  }

  grouping ISIS-SH-IF-TOPO-ADJ-FORM-DISABLED {
    description
      "Topology info when adjacency formation is
       disabled";
    leaf reason-code {
      type Isis-if-topo-adj-form-disabled-reason;
      description
        "Reason why the adjacency formation status of a
         topology is disabled";
    }
  }

  grouping ISIS-SH-IF-TOPO-ADJ-FORM-STATUS {
    description
      "ISIS SH IF TOPO ADJ FORM STATUS";
    container disabled {
      when "../status = 'isis-disabled'" {
        description
          "../Status = 'ISIS_DISABLED'";
      }
      description
        "Disabled state for the adjacency formation
         status of a topology";
      uses ISIS-SH-IF-TOPO-ADJ-FORM-DISABLED;
    }
    leaf status {
      type Isis-enabled;
      description
        "Status";
    }
  }

  grouping ISIS-SH-IF-TOPO-ENABLED {
    description
      "Enabled topology info of an interface";
    container adjacency-form-status {
      description
        "Adjacency formation status of a topology";
      uses ISIS-SH-IF-TOPO-ADJ-FORM-STATUS;
    }
    container adv-prefix-status {
      description
        "Prefix advertisement status of a topology";
      uses ISIS-SH-IF-TOPO-ADV-PREFIX-STATUS;
    }
    container level1-frr {
      description
        "Level1 FRR information";
      uses ISIS-SH-IF-FRR-LEVEL;
    }
    container level2-frr {
      description
        "Level2 FRR information";
      uses ISIS-SH-IF-FRR-LEVEL;
    }
    leaf level1-metric {
      type Isis-metric;
      description
        "L1 metric for this topology";
    }
    leaf level2-metric {
      type Isis-metric;
      description
        "L2 metric for this topology";
    }
    leaf level1-weight {
      type Isis-metric;
      description
        "L1 metric for this topology";
    }
    leaf level2-weight {
      type Isis-metric;
      description
        "L2 metric for this topology";
    }
    leaf max-label-supported {
      type uint8;
      description
        "MPLS maximum number of pri labels supported";
    }
    leaf max-bkp-label-supported {
      type uint8;
      description
        "MPLS maximum number of backup labels supported";
    }
    leaf max-srte-label-supported {
      type uint8;
      description
        "MPLS maximum number of srte labels supported";
    }
    leaf max-srat-label-supported {
      type uint8;
      description
        "MPLS maximum number of sr auto-tunnel labels
         supported";
    }
    leaf level1ldp-sync-enabled {
      type boolean;
      description
        "MPLS LDP sync enabled status for L1";
    }
    leaf level2ldp-sync-enabled {
      type boolean;
      description
        "MPLS LDP sync enabled status for L2";
    }
    leaf ldp-sync-status {
      type boolean;
      description
        "Status of MPLS LDP synchronization";
    }
    leaf ld-pv6-sync-status {
      type boolean;
      description
        "Status of MPLS LDPv6 synchronization";
    }
    leaf level1-offset-metric {
      type Isis-metric;
      description
        "L1 metric-offset for this topology";
    }
    leaf level2-offset-metric {
      type Isis-metric;
      description
        "L2 metric-offset for this topology";
    }
    leaf level1-lkgp-configured {
      type boolean;
      description
        "Link-Group configure status for L1";
    }
    leaf level2-lkgp-configured {
      type boolean;
      description
        "Link-Group configure status for L2";
    }
    leaf level1pp-metric {
      type Isis-metric;
      description
        "L1 PP-metric for this topology";
    }
    leaf level2pp-metric {
      type Isis-metric;
      description
        "L2 PP-metric for this topology";
    }
    leaf level1pp-configured {
      type boolean;
      description
        "PP configure status for L1";
    }
    leaf level2pp-configured {
      type boolean;
      description
        "PP configure status for L2";
    }
    leaf link-group-name {
      type string;
      description
        "Link-Group name";
    }
    leaf l1-adv-pfx-policy {
      type string;
      description
        "L1 Advertise Prefix Policy Name";
    }
    leaf l2-adv-pfx-policy {
      type string;
      description
        "L2 Advertise Prefix Policy Name";
    }
    leaf l1-adv-pfx-pass {
      type boolean;
      description
        "L1 Advertise Prefix Policy Pass";
    }
    leaf l2-adv-pfx-pass {
      type boolean;
      description
        "L2 Advertise Prefix Policy Pass";
    }
    list manual-adj-sid {
      description
        "Array of Manual Adjacency SIDs";
      uses ISIS-SH-MADJ-SID-IF;
    }
  }

  grouping ISIS-SH-IF-TOPO-DISABLED {
    description
      "Disabled topology info of an interface";
    leaf reason-code {
      type Isis-if-topo-disabled-reason;
      description
        "Reason why the topology is disabled";
    }
  }

  grouping ISIS-SH-IF-TOPO-STATUS {
    description
      "ISIS SH IF TOPO STATUS";
    container disabled {
      when "../status = 'isis-disabled'" {
        description
          "../Status = 'ISIS_DISABLED'";
      }
      description
        "Disabled information of a topology";
      uses ISIS-SH-IF-TOPO-DISABLED;
    }
    container enabled {
      when "../status = 'isis-enabled'" {
        description
          "../Status = 'ISIS_ENABLED'";
      }
      description
        "Enabled information of a topology";
      uses ISIS-SH-IF-TOPO-ENABLED;
    }
    leaf status {
      type Isis-enabled;
      description
        "Status";
    }
  }

  grouping ISIS-SH-IF-TOPO {
    description
      "Per topology info of an interface";
    container topology-id {
      description
        "Topology identifier";
      uses ISIS-TOPO-ID-TYPE;
    }
    container status {
      description
        "Status of the topology";
      uses ISIS-SH-IF-TOPO-STATUS;
    }
  }

  grouping ISIS-SH-IF-AREA-ACTIVE-LAN {
    description
      "Per-interface, per-area data for active LAN
       interface";
    leaf circuit-lan-id {
      type Isis-circuit-id;
      description
        "Circuit LAN ID";
    }
    leaf time-until-next-iih {
      type uint32;
      description
        "Time (ms) until next IIH";
    }
    leaf interface-priority {
      type Isis-dr-priority;
      description
        "Interface's DIS-election priority";
    }
    leaf dispriority {
      type Isis-dr-priority;
      description
        "Priority of current DIS on this LAN";
    }
    leaf are-we-dis {
      type boolean;
      description
        "Flag indicating if this LAN circuit is the DIS";
    }
  }

  grouping ISIS-SH-IF-AREA-ACTIVE {
    description
      "Per-area data for an interface";
    container lan-data {
      description
        "LAN data, NULL iff interface has non-LAN media
         type";
      uses ISIS-SH-IF-AREA-ACTIVE-LAN;
    }
    leaf level {
      type Isis-level;
      description
        "Level of the area";
    }
    leaf adjacency-count {
      type uint32;
      description
        "Number of adjacencies";
    }
    leaf lsp-pacing-interval {
      type uint32;
      description
        "LSP pacing time period (ms)";
    }
    leaf psnp-transmit-queue-size {
      type uint32;
      description
        "No. of SNP entries queued to be transmitted";
    }
    leaf hello-interval {
      type uint32;
      description
        "Hello interval";
    }
    leaf hello-multiplier {
      type uint32;
      description
        "Hello Multiplier";
    }
  }

  grouping ISIS-SH-IF-CLNS-P2P-OVER-LAN {
    description
      "Point-to-point over LAN specific CLNS state";
    container multicast-status {
      description
        "Multicast group membership status";
      uses ISIS-SH-IF-MCAST-STATUS;
    }
  }

  grouping ISIS-SH-IF-CLNS-P2P {
    description
      "Point-to-point CLNS state";
    container p2p-over-lan-data {
      description
        "Point-to-point over LAN data";
      uses ISIS-SH-IF-CLNS-P2P-OVER-LAN;
    }
  }

  grouping ISIS-SH-IF-MCAST-INVALID {
    description
      "Invalid multicast info";
    leaf reason-code {
      type Isis-if-mcast-invalid-reason;
      description
        "Reason why the multicast status is invalid";
    }
  }

  grouping ISIS-SH-IF-MCAST-STATUS {
    description
      "ISIS SH IF MCAST STATUS";
    container invalid {
      when "../status = 'isis-invalid'" {
        description
          "../Status = 'ISIS_INVALID'";
      }
      description
        "Information pertaining to the invalid multicast
         status";
      uses ISIS-SH-IF-MCAST-INVALID;
    }
    leaf status {
      type Isis-valid;
      description
        "Status";
    }
  }

  grouping ISIS-SH-IF-AREA-CLNS {
    description
      "Per interface per area CLNS state";
    container multicast-status {
      description
        "Multicast group membership status";
      uses ISIS-SH-IF-MCAST-STATUS;
    }
    leaf level {
      type Isis-level;
      description
        "Level of the area";
    }
  }

  grouping ISIS-SH-IF-CLNS-LAN {
    description
      "LAN specific CLNS state";
    list per-area-data {
      description
        "Array of per area CLNS data";
      uses ISIS-SH-IF-AREA-CLNS;
    }
  }

  grouping ISIS-SH-IF-CLNS-MEDIA-SPECIFIC-STATUS {
    description
      "Media Specific CLNS state";
    container clns-lan-data {
      when "../clns-media-type = 'isis-media-class-lan'" {
        description
          "../CLNSMediaType = 'ISIS_MEDIA_CLASS_LAN'";
      }
      description
        "LAN state";
      uses ISIS-SH-IF-CLNS-LAN;
    }
    container clns-p2p-data {
      when "../clns-media-type = 'isis-media-class-p2p'" {
        description
          "../CLNSMediaType = 'ISIS_MEDIA_CLASS_P2P'";
      }
      description
        "Point-to-point state";
      uses ISIS-SH-IF-CLNS-P2P;
    }
    leaf clns-media-type {
      type Isis-media-class;
      description
        "CLNSMediaType";
    }
  }

  grouping ISIS-SH-IF-CLNS-SNPA-KNOWN {
    description
      "CLNS SNPA info";
    leaf snpa {
      type xr:Isis-snpa;
      description
        "Valid SNPA";
    }
  }

  grouping ISIS-SH-IF-CLNS-SNPA-UNKNOWN {
    description
      "Interface info with CLNS SNPA unknown";
    leaf reason-code {
      type Isis-if-clns-snpa-unknown-reason;
      description
        "Reason why the SNPA is unknown";
    }
  }

  grouping ISIS-SH-IF-CLNS-SNPA-STATUS {
    description
      "ISIS SH IF CLNS SNPA STATUS";
    container unknown {
      when "../status = 'isis-unknown'" {
        description
          "../Status = 'ISIS_UNKNOWN'";
      }
      description
        "Information pertaining to the unknown SNPA state";
      uses ISIS-SH-IF-CLNS-SNPA-UNKNOWN;
    }
    container known {
      when "../status = 'isis-known'" {
        description
          "../Status = 'ISIS_KNOWN'";
      }
      description
        "Information pertaining to the known SNPA state";
      uses ISIS-SH-IF-CLNS-SNPA-KNOWN;
    }
    leaf status {
      type Isis-known;
      description
        "Status";
    }
  }

  grouping ISIS-SH-IF-CLNS-MTU-INVALID {
    description
      "Interface info with invalid MTU";
    leaf reason-code {
      type Isis-if-clns-mtu-invalid-reason;
      description
        "Reason why the MTU is invalid";
    }
  }

  grouping ISIS-SH-IF-CLNS-MTU-STATUS {
    description
      "ISIS SH IF CLNS MTU STATUS";
    container invalid {
      when "../status = 'isis-invalid'" {
        description
          "../Status = 'ISIS_INVALID'";
      }
      description
        "Information pertaining to the invalid CLNS MTU";
      uses ISIS-SH-IF-CLNS-MTU-INVALID;
    }
    leaf status {
      type Isis-valid;
      description
        "Status";
    }
    leaf mtu {
      when "../status = 'isis-valid'" {
        description
          "../Status = 'ISIS_VALID'";
      }
      type uint32;
      description
        "Valid MTU";
    }
  }

  grouping ISIS-SH-IF-CLNS-PROTO-DOWN {
    description
      "Interface info when CLNS is down";
    leaf reason-code {
      type Isis-if-clns-proto-down-reason;
      description
        "Reason why CLNS is down";
    }
  }

  grouping ISIS-SH-IF-CLNS-STATUS {
    description
      "ISIS SH IF CLNS STATUS";
    container clns-down-info {
      when "../status = 'isis-down'" {
        description
          "../Status = 'ISIS_DOWN'";
      }
      description
        "State describing why CLNS is down";
      uses ISIS-SH-IF-CLNS-PROTO-DOWN;
    }
    leaf status {
      type Isis-up;
      description
        "Status";
    }
  }

  grouping ISIS-SH-IF-CLNS {
    description
      "CLNS I/O data for an interface";
    container clns-status {
      description
        "Is CLNS protcol up or if not, the reason why it
         is not up";
      uses ISIS-SH-IF-CLNS-STATUS;
    }
    container mtu-info {
      description
        "A valid MTU or the reason for the MTU being
         invalid";
      uses ISIS-SH-IF-CLNS-MTU-STATUS;
    }
    container snpa-state {
      description
        "SNPA state";
      uses ISIS-SH-IF-CLNS-SNPA-STATUS;
    }
    container media-specific-state {
      description
        "Media Specific CLNS state";
      uses ISIS-SH-IF-CLNS-MEDIA-SPECIFIC-STATUS;
    }
    leaf time-until-next-lsp {
      type uint32;
      description
        "Time until next LSP may be sent (ms)";
    }
    leaf lsp-transmit-requested-flag {
      type boolean;
      description
        "TRUE if an LSP transmission has been requested";
    }
    leaf lsp-transmitted-flag {
      type boolean;
      description
        "TRUE if an LSP transmission has been sent,
         indicates LastLSPLevelTransmitted and
         LastLSP_IDTransmitted valid";
    }
    leaf lsp-txmitd-b2b-limit {
      type uint32;
      description
        "Number of LSPs that can be sent back to back in
         the current window without exceeding the pacing
         limit";
    }
    leaf lsp-txmt-b2b-msecs {
      type uint32;
      units "millisecond";
      description
        "Time im msecs indicating the end of the window
         in which the 'back to back lsps to be sent'
         counter applies";
    }
    leaf last-lsp-level-transmitted {
      type Isis-level;
      description
        "Level of the Last LSP Transmitted";
    }
    leaf last-lsp-id-transmitted {
      type xr:Isis-lsp-id;
      description
        "Last LSP ID Transmitted";
    }
  }

  grouping ISIS-SH-IF-BFD-TYPE {
    description
      "Per-interface BFD data";
    leaf enabled {
      type boolean;
      description
        "IPv4 BFD enabled status";
    }
    leaf ipv6-enabled {
      type boolean;
      description
        "IPv6 BFD enabled status";
    }
    leaf interval {
      type uint32;
      units "millisecond";
      description
        "BFD hello minimum interval in milliseconds";
    }
    leaf multiplier {
      type uint32;
      description
        "BFD hello multiplier";
    }
  }

  grouping ISIS-SH-IF-ACTIVE-P2P {
    description
      "Per-interface data";
    leaf time-until-next-iih {
      type uint32;
      description
        "Time in ms before the next IIH can be sent";
    }
    leaf retransmit-lsp-queue-size {
      type uint32;
      description
        "No. of LSPs queued to be retransmitted";
    }
    leaf retransmit-lsp-interval {
      type uint32;
      description
        "Time in ms until the next scheduled LSP is
         retransmitted";
    }
    leaf extended-circuit-number {
      type Isis-extended-circuit-number;
      description
        "Extended Circuit Number valid for a P2P
         interface";
    }
  }

  grouping ISIS-SH-IF-ADV-PREFIX-DISABLED {
    description
      "Interface info when prefix advertisement is
       disabled";
    leaf reason-code {
      type Isis-if-adv-prefix-disabled-reason;
      description
        "Reason why the interface is not able to
         advertise prefixes";
    }
  }

  grouping ISIS-SH-IF-ADV-PREFIX-STATUS {
    description
      "ISIS SH IF ADV PREFIX STATUS";
    container disabled {
      when "../status = 'isis-disabled'" {
        description
          "../Status = 'ISIS_DISABLED'";
      }
      description
        "Disabled info for the prefix advertisement
         status";
      uses ISIS-SH-IF-ADV-PREFIX-DISABLED;
    }
    leaf status {
      type Isis-enabled;
      description
        "Status";
    }
  }

  grouping ISIS-SH-IF-ADJ-FORM-DISABLED {
    description
      "Interface info when adjacency formation is
       disabled";
    leaf reason-code {
      type Isis-if-adj-form-disabled-reason;
      description
        "Reason why the interface is not able to form
         adjacencies";
    }
  }

  grouping ISIS-SH-IF-ADJ-FORM-STATUS {
    description
      "ISIS SH IF ADJ FORM STATUS";
    container disabled {
      when "../status = 'isis-disabled'" {
        description
          "../Status = 'ISIS_DISABLED'";
      }
      description
        "Disabled info for the adjacency formation status";
      uses ISIS-SH-IF-ADJ-FORM-DISABLED;
    }
    leaf status {
      type Isis-enabled;
      description
        "Status";
    }
  }

  grouping ISIS-SH-IF-ENABLED {
    description
      "State of an enabled interface";
    container adjacency-form-status {
      description
        "Interface's Adjacency Formation status";
      uses ISIS-SH-IF-ADJ-FORM-STATUS;
    }
    container adv-prefix-status {
      description
        "Interface's Prefix Advertisement status";
      uses ISIS-SH-IF-ADV-PREFIX-STATUS;
    }
    container p2p-data {
      description
        "Data for an active P2P interface, NULL if not
         active or P2P";
      uses ISIS-SH-IF-ACTIVE-P2P;
    }
    container bfd-data {
      description
        "The BFD data for the given interface";
      uses ISIS-SH-IF-BFD-TYPE;
    }
    container clns-data {
      description
        "Interface data specific to CLNS I/O services";
      uses ISIS-SH-IF-CLNS;
    }
    leaf interface-media-type {
      type Isis-media-class;
      description
        "Media type of the interface";
    }
    leaf enabled-circuit-type {
      type Isis-levels;
      description
        "Enabled Circuit type of the interface";
    }
    leaf local-circuit-number {
      type Isis-circuit-number;
      description
        "Local Circuit Number of the interface";
    }
    leaf rsi-srlg-registered {
      type boolean;
      description
        "Rsi Srlg Registered";
    }
    leaf bandwidth {
      type uint32;
      description
        "Bandwidth of the interface";
    }
    leaf delay-norm-interval {
      type uint32;
      description
        "Delay Normalization Interval";
    }
    leaf delay-norm-offset {
      type uint32;
      description
        "Delay Normalization Offset";
    }
    leaf avg-delay {
      type uint32;
      description
        "Normalized Avarage Delay";
    }
    leaf min-delay {
      type uint32;
      description
        "Normalized Minimum Delay";
    }
    leaf max-delay {
      type uint32;
      description
        "Normalizewd Maximum Delay";
    }
    leaf avg-dela-rawy {
      type uint32;
      description
        "Raw Avarage Delay";
    }
    leaf min-delay-raw {
      type uint32;
      description
        "Raw Minimum Delay";
    }
    leaf max-delay-raw {
      type uint32;
      description
        "Raw Maximum Delay";
    }
    list underlying-interface {
      description
        "Underlying interface list for bundle interfaces";
      uses ISIS-SH-INTF-DET;
    }
    list per-area-data {
      description
        "Array of area information for an active
         interface";
      uses ISIS-SH-IF-AREA-ACTIVE;
    }
    list per-topology-data {
      description
        "Array of topology information";
      uses ISIS-SH-IF-TOPO;
    }
    list per-address-family-data {
      description
        "Array of address family information";
      uses ISIS-SH-IF-AF;
    }
  }

  grouping ISIS-SH-IF-DISABLED {
    description
      "Disabled interface info";
    leaf reason-code {
      type Isis-if-disabled-reason;
      description
        "Reason why the interface is disabled";
    }
  }

  grouping ISIS-SH-IF-STATUS {
    description
      "ISIS SH IF STATUS";
    container disabled {
      when "../status = 'isis-disabled'" {
        description
          "../Status = 'ISIS_DISABLED'";
      }
      description
        "The interface state if disabled";
      uses ISIS-SH-IF-DISABLED;
    }
    container enabled {
      when "../status = 'isis-enabled'" {
        description
          "../Status = 'ISIS_ENABLED'";
      }
      description
        "The interface state if enabled";
      uses ISIS-SH-IF-ENABLED;
    }
    leaf status {
      type Isis-enabled;
      description
        "Status";
    }
  }

  grouping ISIS-SH-IF-CFG-STATUS {
    description
      "Configured state of an interface";
    leaf adjacency-form-status {
      type boolean;
      description
        "Configured adjacency formation status";
    }
    leaf adv-prefix-status {
      type boolean;
      description
        "Configured prefix advertisement status";
    }
  }

  grouping ISIS-SH-IF {
    description
      "All the Information of an IS-IS interface";
    container configured-status {
      description
        "Configured interface status";
      uses ISIS-SH-IF-CFG-STATUS;
    }
    container interface-status-and-data {
      description
        "Information about the interface status and its
         data";
      uses ISIS-SH-IF-STATUS;
    }
    leaf configured-circuit-type {
      type Isis-levels;
      description
        "Configured circuit type for the interface";
    }
    leaf mesh-group {
      type Isis-mesh-group-number;
      description
        "Interface mesh group";
    }
    leaf is-type {
      type Isis-levels;
      description
        "IS-type of the router";
    }
    leaf nsr-intf {
      type boolean;
      description
        "ISIS NSR Interface";
    }
  }

  grouping ISIS-SH-SRLG-STATIC-NAME {
    description
      "ISIS Static Link SRLG Name ";
    leaf srlg-name {
      type string;
      description
        "SRLGName";
    }
  }

  grouping ISIS-SH-SRLG-STATIC {
    description
      "SRLG Static";
    leaf local-ipv4-addr {
      type Isis-ipv4-address;
      description
        "LocalIPv4Addr";
    }
    leaf remote-ipv4-addr {
      type Isis-ipv4-address;
      description
        "RemoteIPv4Addr";
    }
    list srlg-name-xr {
      description
        "SRLGNames";
      uses ISIS-SH-SRLG-STATIC-NAME;
    }
  }

  grouping NSR-STATUS-NII-INTF {
    description
      "NSR STATUS NII INTF";
    leaf exist {
      type boolean;
      description
        "exist";
    }
    leaf brought-up {
      type boolean;
      description
        "brought up";
    }
    leaf retry-timer {
      type boolean;
      description
        "retry timer";
    }
    leaf running {
      type boolean;
      description
        "running";
    }
    leaf has-adj {
      type boolean;
      description
        "has adj";
    }
  }

  grouping NSR-STATUS-TE {
    description
      "NSR STATUS TE";
    leaf enabled {
      type uint8;
      description
        "enabled";
    }
    leaf conn-up {
      type uint8;
      description
        "conn up";
    }
    leaf te-link-cb {
      type uint8;
      description
        "te link cb";
    }
    leaf te-tunnel-cb {
      type uint8;
      description
        "te tunnel cb";
    }
    leaf adv-sync-data {
      type uint8;
      description
        "adv sync data";
    }
    leaf link-purge-time-on {
      type uint8;
      description
        "link purge time on";
    }
    leaf tunnel-purge-time-on {
      type uint8;
      description
        "tunnel purge time on";
    }
    leaf has-info-from-te {
      type uint8;
      description
        "has info from te";
    }
  }

  grouping NSR-STATUS-DS {
    description
      "NSR STATUS DS";
    container conn-ts {
      description
        "conn ts";
      uses ISIS-SH-TIMESTAMP-TYPE;
    }
    container conn-cb-ts {
      description
        "conn cb ts";
      uses ISIS-SH-TIMESTAMP-TYPE;
    }
    container pub-ts {
      description
        "pub ts";
      uses ISIS-SH-TIMESTAMP-TYPE;
    }
    container pub-cb-ts {
      description
        "pub cb ts";
      uses ISIS-SH-TIMESTAMP-TYPE;
    }
    container reg-ts {
      description
        "reg ts";
      uses ISIS-SH-TIMESTAMP-TYPE;
    }
    container reg-cb-ts {
      description
        "reg cb ts";
      uses ISIS-SH-TIMESTAMP-TYPE;
    }
    container unreg-ts {
      description
        "unreg ts";
      uses ISIS-SH-TIMESTAMP-TYPE;
    }
    container unreg-cb-ts {
      description
        "unreg cb ts";
      uses ISIS-SH-TIMESTAMP-TYPE;
    }
    container disconn-cb-ts {
      description
        "disconn cb ts";
      uses ISIS-SH-TIMESTAMP-TYPE;
    }
    container notify-cb-ts {
      description
        "notify cb ts";
      uses ISIS-SH-TIMESTAMP-TYPE;
    }
    container del-cb-ts {
      description
        "del cb ts";
      uses ISIS-SH-TIMESTAMP-TYPE;
    }
    container remove-srv-ts {
      description
        "remove srv ts";
      uses ISIS-SH-TIMESTAMP-TYPE;
    }
    container conn-status-ts {
      description
        "conn status ts";
      uses ISIS-SH-TIMESTAMP-TYPE;
    }
    leaf conn {
      type uint8;
      description
        "conn";
    }
    leaf conn-cb {
      type uint8;
      description
        "conn cb";
    }
    leaf pub {
      type uint8;
      description
        "pub";
    }
    leaf pub-cb {
      type uint8;
      description
        "pub cb";
    }
    leaf reg {
      type uint8;
      description
        "reg";
    }
    leaf reg-cb {
      type uint8;
      description
        "reg cb";
    }
    leaf unreg {
      type uint8;
      description
        "unreg";
    }
    leaf unreg-cb {
      type uint8;
      description
        "unreg cb";
    }
    leaf disconn-cb {
      type uint8;
      description
        "disconn cb";
    }
    leaf notify-cb {
      type uint8;
      description
        "notify cb";
    }
    leaf notify-peer-xr {
      type yang:hex-string;
      description
        "notify peer xr";
    }
    leaf del-cb {
      type uint8;
      description
        "del cb";
    }
    leaf remove-srv {
      type uint8;
      description
        "remove srv";
    }
    leaf conn-status {
      type boolean;
      description
        "conn status";
    }
    list notify-peer {
      max-elements "4";
      description
        "notify peer";
      uses ISIS-SH-TIMESTAMP-TYPE;
    }
  }

  grouping NSR-STATUS-PM {
    description
      "NSR STATUS PM";
    leaf reg {
      type uint8;
      description
        "reg";
    }
    leaf conn-cb {
      type uint8;
      description
        "conn cb";
    }
    leaf disconn-cb {
      type uint8;
      description
        "disconn cb";
    }
    leaf conn-status {
      type boolean;
      description
        "conn status";
    }
  }

  grouping NSR-STATUS-NCD {
    description
      "NSR STATUS NCD";
    leaf vm-idx {
      type uint8;
      description
        "vm idx";
    }
    leaf conn-up {
      type boolean;
      description
        "conn up";
    }
    leaf endp-hdl {
      type uint8;
      description
        "endp hdl";
    }
    leaf chksum {
      type uint16;
      description
        "chksum";
    }
    leaf send-seqnum {
      type uint32;
      description
        "send seqnum";
    }
    leaf recv-cnt {
      type uint32;
      description
        "recv cnt";
    }
  }

  grouping NSR-STATUS-GEN {
    description
      "NSR STATUS GEN";
    leaf my-nodeid {
      type uint32;
      description
        "my nodeid";
    }
    leaf my-process-id {
      type uint32;
      description
        "my process id";
    }
    leaf pm-issu-role {
      type uint8;
      description
        "pm issu role";
    }
    leaf pm-ha-role {
      type uint8;
      description
        "pm ha role";
    }
    leaf sysmgr-ha-role {
      type uint8;
      description
        "sysmgr ha role";
    }
    leaf nsr-send-ready {
      type uint8;
      description
        "nsr send ready";
    }
    leaf nsr-send-unready {
      type uint8;
      description
        "nsr send unready";
    }
    leaf nsr-send-err {
      type uint32;
      description
        "nsr send err";
    }
    leaf nsr-recv-err {
      type uint32;
      description
        "nsr recv err";
    }
    leaf retry-flag {
      type uint32;
      description
        "retry flag";
    }
    leaf nsr-enabled {
      type boolean;
      description
        "nsr enabled";
    }
    leaf nsr-configured {
      type boolean;
      description
        "nsr configured";
    }
    leaf nsf-configured {
      type boolean;
      description
        "nsf configured";
    }
    leaf failover {
      type boolean;
      description
        "failover";
    }
    leaf lanid-req-needed {
      type boolean;
      description
        "lanid req needed";
    }
  }

  grouping NSR-STATUS-INFRA-TYPE {
    description
      "NSR STATUS INFRA TYPE";
    container gen {
      description
        "gen";
      uses NSR-STATUS-GEN;
    }
    container pm {
      description
        "pm";
      uses NSR-STATUS-PM;
    }
    container ds {
      description
        "ds";
      uses NSR-STATUS-DS;
    }
    container te {
      description
        "te";
      uses NSR-STATUS-TE;
    }
    list ncd {
      max-elements "5";
      description
        "ncd";
      uses NSR-STATUS-NCD;
    }
    list nii-idb {
      max-elements "3";
      description
        "nii idb";
      uses NSR-STATUS-NII-INTF;
    }
  }

  grouping NSR-STATUS-GBL-TYPE {
    description
      "NSR STATUS GBL TYPE";
    list full-sync-achieved {
      max-elements "3";
      description
        "full sync achieved";
      leaf entry {
        type uint32;
        description
          "full sync achieved";
      }
    }
    list man-sync-count {
      max-elements "3";
      description
        "man sync count";
      leaf entry {
        type uint32;
        description
          "man sync count";
      }
    }
    list nsr-chg-count {
      max-elements "3";
      description
        "nsr chg count";
      leaf entry {
        type uint32;
        description
          "nsr chg count";
      }
    }
    list uptime {
      max-elements "3";
      description
        "uptime";
      leaf entry {
        type uint32;
        description
          "uptime";
      }
    }
    list uptime-valid {
      min-elements 3;
      max-elements "3";
      description
        "uptime valid";
      leaf entry {
        type boolean;
        description
          "Array entry.";
      }
    }
  }

  grouping ISIS-SH-NSR-STATUS-GLOBAL {
    description
      "IS-IS process NSR status";
    container isis-nsr-peer {
      description
        "ISIS NSR PEER STATUS";
      uses NSR-STATUS-GBL-TYPE;
    }
    container isis-nsr-infra {
      description
        "ISIS NSR Infra";
      uses NSR-STATUS-INFRA-TYPE;
    }
    leaf isis-vm-state {
      type uint16;
      description
        "ISIS VM STATE";
    }
  }

  grouping ISIS-SH-SRLG {
    description
      "ISIS SRLG";
    leaf srlg-name-xr {
      type string;
      description
        "SRLG Name";
    }
    leaf srlg-value {
      type uint32;
      description
        "SRLG Value";
    }
    leaf srlg-admin-weight {
      type uint32;
      description
        "SRLG Admin Weight";
    }
    leaf srlg-value-set {
      type boolean;
      description
        "SRLG value set";
    }
    leaf srlg-admin-weight-set {
      type boolean;
      description
        "SRLG Admin Weight Set";
    }
    leaf srlg-isis-cfg {
      type boolean;
      description
        "SRLG ISIS Configuration";
    }
    leaf srlg-global-cfg {
      type boolean;
      description
        "SRLG Global Configuration";
    }
  }

  grouping ISIS-SH-IPV6-TOPO-REACHABLE-DETAILS {
    description
      "Status of a reachable IPv6 IS";
    leaf root-distance {
      type Isis-metric;
      description
        "Distance to the IS";
    }
    leaf multicast-root-distance {
      type Isis-metric;
      description
        "Distance to the IS";
    }
    list paths {
      description
        "First hops towards the IS";
      uses ISIS-SH-IPV6-PATH;
    }
    list multicast-path {
      description
        "Multicast intact first hops towards the IS";
      uses ISIS-SH-IPV6-PATH;
    }
    list parent {
      description
        "Parents of the IS within the SPT";
      uses ISIS-SH-TOPO-NEIGHBOR;
    }
    list children {
      description
        "Children of the IS within the SPT";
      uses ISIS-SH-TOPO-NEIGHBOR;
    }
  }

  grouping ISIS-SH-IPV6-TOPO-REACHABLE-STATUS {
    description
      "Reachability status of an IPv6 IS";
    container reachable-details {
      when "../reachable-status = 'isis-reachable'" {
        description
          "../ReachableStatus = 'ISIS_REACHABLE'";
      }
      description
        "Status of the IS within the SPT";
      uses ISIS-SH-IPV6-TOPO-REACHABLE-DETAILS;
    }
    leaf reachable-status {
      type Isis-reachable;
      description
        "ReachableStatus";
    }
  }

  grouping ISIS-SH-IPV6-TOPO-ENTRY {
    description
      "IPv6 IS Link Topology Entry";
    container reachability-status {
      description
        "Is the IS reachable, and, if so, its status
         within the SPT";
      uses ISIS-SH-IPV6-TOPO-REACHABLE-STATUS;
    }
    container advertised-prefix-item-counts {
      description
        "Per-priority counts of prefix items advertised
         by the IS";
      uses ISIS-PER-PRIORITY-COUNTS;
    }
    leaf source-address {
      type Isis-ipv6-address;
      description
        "Source Address";
    }
    leaf is-participant {
      type boolean;
      description
        "Does the IS participate in the topology?";
    }
    leaf is-overloaded {
      type boolean;
      description
        "Is the IS overloaded?";
    }
    leaf is-attached {
      type boolean;
      description
        "Is the IS attached?";
    }
  }

  grouping ISIS-SH-TOPO-SUMMARY-NODE-STATS {
    description
      "Reachability counters";
    leaf reachable-node-count {
      type uint32;
      description
        "Number of nodes reachable in SPT";
    }
    leaf unreachable-node-count {
      type uint32;
      description
        "Number of nodes unreachable in SPT";
    }
    leaf unreachable-participant-node-count {
      type uint32;
      description
        "Number of participating nodes unreachable in SPT";
    }
  }

  grouping ISIS-SH-TOPO-SUMMARY {
    description
      "Summary Statistics for an IS Topology";
    container router-node-count {
      description
        "Node Counts for System nodes";
      uses ISIS-SH-TOPO-SUMMARY-NODE-STATS;
    }
    container pseudonode-node-count {
      description
        "Node Counts for Pseudonode nodes";
      uses ISIS-SH-TOPO-SUMMARY-NODE-STATS;
    }
  }

  grouping ISIS-SH-TOPO-NEIGHBOR {
    description
      "SPT Neighbor";
    leaf neighbor-id {
      type xr:Osi-system-id;
      description
        "Neighbor ID";
    }
    leaf intermediate-pseudonode {
      type xr:Isis-node-id;
      description
        "Pseudonode between system and its neighbor";
    }
  }

  grouping ISIS-SH-IPV4-TOPO-REACHABLE-DETAILS {
    description
      "Status of a reachable IPv4 IS";
    leaf root-distance {
      type Isis-metric;
      description
        "Distance to the IS";
    }
    leaf multicast-root-distance {
      type Isis-metric;
      description
        "Distance to the IS";
    }
    list paths {
      description
        "First hops towards the IS";
      uses ISIS-SH-IPV4-PATH;
    }
    list multicast-path {
      description
        "Multicast intact first hops towards the IS";
      uses ISIS-SH-IPV4-PATH;
    }
    list parent {
      description
        "Parents of the IS within the SPT";
      uses ISIS-SH-TOPO-NEIGHBOR;
    }
    list children {
      description
        "Children of the IS within the SPT";
      uses ISIS-SH-TOPO-NEIGHBOR;
    }
  }

  grouping ISIS-SH-IPV4-TOPO-REACHABLE-STATUS {
    description
      "Reachability status of an IPv4 IS";
    container reachable-details {
      when "../reachable-status = 'isis-reachable'" {
        description
          "../ReachableStatus = 'ISIS_REACHABLE'";
      }
      description
        "Status of the IS within the SPT";
      uses ISIS-SH-IPV4-TOPO-REACHABLE-DETAILS;
    }
    leaf reachable-status {
      type Isis-reachable;
      description
        "ReachableStatus";
    }
  }

  grouping ISIS-SH-IPV4-TOPO-ENTRY {
    description
      "IPv4 IS Link Topology Entry";
    container reachability-status {
      description
        "Is the IS reachable, and, if so, its status
         within the SPT";
      uses ISIS-SH-IPV4-TOPO-REACHABLE-STATUS;
    }
    container advertised-prefix-item-counts {
      description
        "Per-priority counts of prefix items advertised
         by the IS";
      uses ISIS-PER-PRIORITY-COUNTS;
    }
    leaf source-address {
      type Isis-ipv4-address;
      description
        "Source Address";
    }
    leaf is-participant {
      type boolean;
      description
        "Does the IS participate in the topology?";
    }
    leaf is-overloaded {
      type boolean;
      description
        "Is the IS overloaded?";
    }
    leaf is-attached {
      type boolean;
      description
        "Is the IS attached?";
    }
  }

  grouping ISIS-SH-TE-TUNNEL {
    description
      "MPLS TE tunnel";
    leaf te-system-id {
      type xr:Osi-system-id;
      description
        "Destination system ID";
    }
    leaf te-interface {
      type xr:Interface-name;
      description
        "Tunnel interface";
    }
    leaf te-bandwidth {
      type uint32;
      description
        "Tunnel bandwidth";
    }
    leaf teigp-metric {
      type int32;
      description
        "Tunnel metric";
    }
    leaf te-next-hop-ip-address {
      type inet:ipv4-address;
      description
        "Tunnel next-hop IP address";
    }
    leaf te-mode-type {
      type Isis-metric-mode;
      description
        "Tunnel metric mode";
    }
    leaf teipv4fa-enabled {
      type boolean;
      description
        "Indicates whether MPLS TE IPv4 forwarding
         adjacency is enabled";
    }
    leaf teipv6fa-enabled {
      type boolean;
      description
        "Indicates whether MPLS TE IPv6 forwarding
         adjacency is enabled";
    }
    leaf teipv4aa-enabled {
      type boolean;
      description
        "Indicates whether MPLS TE IPv4 autoroute
         announce is enabled";
    }
    leaf teipv6aa-enabled {
      type boolean;
      description
        "Indicates whether MPLS TE IPv6 autoroute
         announce is enabled";
    }
    leaf te-checkpoint-object-id {
      type uint32;
      description
        "Tunnel checkpoint object ID";
    }
    leaf te-segment-routing-enabled {
      type boolean;
      description
        "Indicates whether MPLS TE segment routing is
         enabled";
    }
    leaf te-segment-routing-strict-spf {
      type boolean;
      description
        "Indicates whether MPLS TE segment routing strict
         SPF is enabled";
    }
    leaf te-segment-routing-exclude {
      type boolean;
      description
        "Indicates whether Segment routing labeled
         traffic exclusion is enabled";
    }
  }

  grouping ISIS-SH-SPF-LOG-ROUTE-UPDATE-PREFIX-COUNTS {
    description
      "Prefix item counts for the route update phase";
    container unreachable {
      description
        "Number of unreachable prefixes in the database";
      uses ISIS-PER-PRIORITY-COUNTS;
    }
    container reachable {
      description
        "Number of reachable prefixes in the database";
      uses ISIS-PER-PRIORITY-COUNTS;
    }
    container added {
      description
        "Number of prefixes added during calculation";
      uses ISIS-PER-PRIORITY-COUNTS;
    }
    container deleted {
      description
        "Number of prefixes deleted during calculation";
      uses ISIS-PER-PRIORITY-COUNTS;
    }
    container modified {
      description
        "Number of prefixes modified, i.e. a first hop
         and/or metric change";
      uses ISIS-PER-PRIORITY-COUNTS;
    }
    container touched {
      description
        "Number of prefixes considered whilst updating
         the routing table";
      uses ISIS-PER-PRIORITY-COUNTS;
    }
  }

  grouping ISIS-SH-SPF-LOG-ROUTE-UPDATE-NODE-COUNTS {
    description
      "Node counts for the route update phase";
    container per-priority-touched {
      description
        "Per-priority count of nodes considered during
         route update";
      uses ISIS-PER-PRIORITY-COUNTS;
    }
    leaf total-touched {
      type uint32;
      description
        "Total number of nodes considered during route
         update";
    }
  }

  grouping ISIS-PER-PRIORITY-TIMINGS {
    description
      "Per-priority timings";
    container critical {
      description
        "Critical priority";
      uses ISIS-TIMINGS-TYPE;
    }
    container high {
      description
        "High priority";
      uses ISIS-TIMINGS-TYPE;
    }
    container medium {
      description
        "Medium priority";
      uses ISIS-TIMINGS-TYPE;
    }
    container low {
      description
        "Low priority";
      uses ISIS-TIMINGS-TYPE;
    }
  }

  grouping ISIS-SH-SPF-LOG-ROUTE-UPDATE-TIMINGS-BREAKDOWN {
    description
      "Breakdown of the time taken to perform the route
       update";
    container local-rib-update {
      description
        "Time to update IS-IS's local RIB";
      uses ISIS-PER-PRIORITY-TIMINGS;
    }
    container global-rib-build {
      description
        "Time to build the update to send to the global
         RIB";
      uses ISIS-PER-PRIORITY-TIMINGS;
    }
    container global-rib-send {
      description
        "Time to send the update to the global RIB";
      uses ISIS-PER-PRIORITY-TIMINGS;
    }
  }

  grouping ISIS-SH-SPF-LOG-ROUTE-UPDATE {
    description
      "Statistics for the route update phase of the
       calculation";
    container duration {
      description
        "Duration of the routing table update";
      uses ISIS-TIMINGS-TYPE;
    }
    container duration-breakdown {
      description
        "Breakdown of the time taken by the routing table
         update";
      uses ISIS-SH-SPF-LOG-ROUTE-UPDATE-TIMINGS-BREAKDOWN;
    }
    container node-counts {
      description
        "Node counts";
      uses ISIS-SH-SPF-LOG-ROUTE-UPDATE-NODE-COUNTS;
    }
    container item-counts {
      description
        "Prefix item counts";
      uses ISIS-SH-SPF-LOG-ROUTE-UPDATE-PREFIX-COUNTS;
    }
    container route-counts {
      description
        "Distinct prefix counts";
      uses ISIS-SH-SPF-LOG-ROUTE-UPDATE-PREFIX-COUNTS;
    }
    container rib-batch-counts {
      description
        "Number of RIB batches sent";
      uses ISIS-PER-PRIORITY-COUNTS;
    }
  }

  grouping ISIS-SH-SPF-LOG-SPT-CALC-NODE-COUNTS {
    description
      "Node counts for the SPT calculation phase";
    leaf unreachable {
      type uint32;
      description
        "Number of unreachable nodes in the database";
    }
    leaf reachable {
      type uint32;
      description
        "Number of reachable nodes in the database";
    }
    leaf added {
      type uint32;
      description
        "Number of nodes added to the SPT";
    }
    leaf deleted {
      type uint32;
      description
        "Number of nodes deleted from the SPT";
    }
    leaf modified {
      type uint32;
      description
        "Number of modified nodes (first hop and/or
         metric change)";
    }
    leaf touched {
      type uint32;
      description
        "Number of nodes touched whilst calculating the
         SPT";
    }
  }

  grouping ISIS-TIMINGS-TYPE {
    description
      "Duration of an event in real and CPU time";
    leaf real-duration {
      type uint32;
      units "millisecond";
      description
        "Real time duration in milliseconds";
    }
    leaf cpu-duration {
      type uint32;
      units "millisecond";
      description
        "CPU time duration in milliseconds";
    }
  }

  grouping ISIS-SH-SPF-LOG-SPT-CALC {
    description
      "Statistics for the SPT calculation phase";
    container duration {
      description
        "Duration of the SPT calculation";
      uses ISIS-TIMINGS-TYPE;
    }
    container node-counts {
      description
        "Node counts";
      uses ISIS-SH-SPF-LOG-SPT-CALC-NODE-COUNTS;
    }
  }

  grouping ISIS-SH-SPF-LOG-TRIGGERS {
    description
      "The reasons for running a calculation";
    container trigger-prefix {
      description
        "ID of a changed prefix in the first trigger LSP,
         if any";
      uses ISIS-IP-PREFIX-TYPE;
    }
    leaf unique-trigger-count {
      type uint32;
      description
        "Number of unique triggers on this run";
    }
    leaf first-trigger-lsp-id {
      type xr:Isis-lsp-id;
      description
        "ID of the first LSP to trigger the calculation,
         if any";
    }
    leaf trigger-link {
      type xr:Isis-node-id;
      description
        "ID of a changed link in the first trigger LSP,
         if any";
    }
    leaf trigger-next-hop-id {
      type xr:Osi-system-id;
      description
        "ID of a changed next hop, if any";
    }
    leaf is-sr-uloop-calculation {
      type boolean;
      description
        "Is this SR micro loop calculation?";
    }
    leaf is-sr-uloop-link-down {
      type boolean;
      description
        "Is this SR micro loop calculation for link down?";
    }
    list trigger {
      description
        "Triggers applying to this log entry";
      leaf entry {
        type Isis-spf-trigger;
        description
          "Triggers applying to this log entry";
      }
    }
  }

  grouping ISIS-SH-SPF-LOG-ENT {
    description
      "IS-IS route calculation log entry";
    container generic-data {
      description
        "Generic entry data.";
      uses ISIS-SH-GENERIC-LOG-ENT;
    }
    container triggers {
      description
        "Trigger information";
      uses ISIS-SH-SPF-LOG-TRIGGERS;
    }
    container spt-calculation-statistics {
      description
        "Statistics for the SPT calculation phase";
      uses ISIS-SH-SPF-LOG-SPT-CALC;
    }
    container route-update-statistics {
      description
        "Statistics for the route update phase";
      uses ISIS-SH-SPF-LOG-ROUTE-UPDATE;
    }
    leaf class {
      type Isis-spf-class;
      description
        "Type of calculation.";
    }
    leaf wait-enforced {
      type uint32;
      units "millisecond";
      description
        "Time between the first trigger and the start of
         the route calculation, in milliseconds.";
    }
    leaf next-wait-interval {
      type uint32;
      units "millisecond";
      description
        "Minimum time from end of this route calculation
         until the start of the next, in milliseconds";
    }
    leaf updated-lsp-count {
      type uint32;
      description
        "Number of LSPs which arrived during the route
         calculation";
    }
  }

  grouping ISIS-SH-SPF-LOG-STRUC {
    description
      "Log of IS-IS route calculations";
    list log-entry {
      description
        "SPF Log entries";
      uses ISIS-SH-SPF-LOG-ENT;
    }
  }

  grouping ISIS-SH-TE-LOG-ENT {
    description
      "MPLS TE log entry";
    container generic-data {
      description
        "Generic entry data";
      uses ISIS-SH-GENERIC-LOG-ENT;
    }
    leaf neighbor-ip-address {
      type inet:ipv4-address;
      description
        "Neighbor ip address";
    }
    leaf status {
      type boolean;
      description
        "Up (TRUE) or down";
    }
    leaf log-interface {
      type xr:Interface-name;
      description
        "Interface";
    }
    leaf te-log-neighbor-system-id {
      type xr:Osi-system-id;
      description
        "Neighbor system ID";
    }
  }

  grouping ISIS-SH-TE-LOG-STRUC {
    description
      "MPLS TE log";
    list log-entry {
      description
        "Log entries";
      uses ISIS-SH-TE-LOG-ENT;
    }
  }

  grouping ISIS-SH-TE-PCE-ADV {
    description
      "TE PCE advertisements for an IS-IS level";
    leaf pce-adv-data-present {
      type boolean;
      description
        "Indicates whether any PCE advertisements are
         present";
    }
    leaf pce-flooding-scope {
      type Isis-sh-te-pce-flooding-scope;
      description
        "Flooding scope for PCE advertisement";
    }
    leaf pce-address-ipv4 {
      type inet:ipv4-address;
      description
        "IPv4 PCE address";
    }
    leaf pce-path-scope-bits {
      type uint8;
      description
        "PCE path scope bits";
    }
    leaf pce-path-scope-prefs {
      type uint16;
      description
        "PCE path scope preferences";
    }
  }

  grouping ISIS-SH-TE-ADV-SUB-TLV {
    description
      "MPLS TE advertisement sub TLV";
    leaf te-sub-tlv-type {
      type uint16;
      description
        "Type of sub TLV";
    }
    leaf te-sub-tlv-length {
      type uint16;
      description
        "Length of sub TLV";
    }
    leaf te-sub-tlv-value {
      type yang:hex-string;
      description
        "Value of sub TLV";
    }
  }

  grouping ISIS-SH-TE-ADV-ENTRY {
    description
      "MPLS TE advertisement";
    leaf te-neighbor-system-id {
      type xr:Osi-system-id;
      description
        "Neighbor system ID";
    }
    leaf link-type {
      type Isis-sh-te-link;
      description
        "Link type";
    }
    leaf local-ip-address {
      type inet:ipv4-address;
      description
        "Local IP address";
    }
    leaf te-neighbor-ip-address {
      type inet:ipv4-address;
      description
        "Neighbor IP address";
    }
    leaf te-metric {
      type uint32;
      description
        "TE metric";
    }
    leaf te-physical-link-bandwidth {
      type uint32;
      description
        "Physical link bandwidth";
    }
    leaf te-reserved-link-bandwidth {
      type uint32;
      description
        "Reservable link bandwidth in global pool";
    }
    leaf te-subpool-reserved-link-bandwidth {
      type uint32;
      description
        "Reservable link bandwidth in subpool";
    }
    leaf te-affinity {
      type uint32;
      description
        "Affinity bits";
    }
    leaf te-ext-admin-num {
      type uint32;
      description
        "TE Ext Admin Number";
    }
    leaf te-sub-tlv-data-present {
      type boolean;
      description
        "Indicates whether any TE sub TLVs are present";
    }
    list te-transmitted-bandwidth {
      max-elements "8";
      description
        "Bandwidth in use in global pool";
      leaf entry {
        type uint32;
        description
          "Bandwidth in use in global pool";
      }
    }
    list te-subpool-transmitted-bandwidth {
      max-elements "8";
      description
        "Bandwidth in use in subpool";
      leaf entry {
        type uint32;
        description
          "Bandwidth in use in subpool";
      }
    }
    list te-ext-admin-sub {
      max-elements "8";
      description
        "TE Extended Admin Group";
      leaf entry {
        type uint32;
        description
          "TE Extended Admin Group";
      }
    }
    list te-sub-tlv {
      description
        "List of TE sub TLVs";
      uses ISIS-SH-TE-ADV-SUB-TLV;
    }
  }

  grouping ISIS-SH-TE-ADV {
    description
      "TE advertisements for an IS-IS level";
    container tepceadv {
      description
        "TE PCE advertisements";
      uses ISIS-SH-TE-PCE-ADV;
    }
    leaf te-adv-data-present {
      type boolean;
      description
        "Indicates whether any TE advertisements are
         present";
    }
    leaf te-system-id {
      type xr:Osi-system-id;
      description
        "Local system ID";
    }
    leaf te-local-router-id {
      type inet:ipv4-address;
      description
        "Local TE router ID";
    }
    list te-adv {
      description
        "List of TE advertisement entries";
      uses ISIS-SH-TE-ADV-ENTRY;
    }
  }

  grouping ISIS-SRV6-RSVD-OPCODE {
    description
      "ISIS SRV6 RSVD OPCODE";
    leaf function-type {
      type Srv6-end-function;
      description
        "FunctionType";
    }
    leaf sid {
      type Isis-ipv6-address;
      description
        "SID";
    }
    leaf block-length {
      type uint8;
      description
        "Block Length";
    }
    leaf node-length {
      type uint8;
      description
        "Node Length";
    }
    leaf func-length {
      type uint8;
      description
        "Func Length";
    }
    leaf args-length {
      type uint8;
      description
        "Args Length";
    }
  }

  grouping ISIS-IP-PREFIX-TYPE {
    description
      "ISIS IP PREFIX TYPE";
    container ipv4 {
      when "../af-name = 'ipv4'" {
        description
          "../AFName = 'IPv4'";
      }
      description
        "ipv4";
      uses ISIS-IPV4-PREFIX-TYPE;
    }
    container ipv6 {
      when "../af-name = 'ipv6'" {
        description
          "../AFName = 'IPv6'";
      }
      description
        "ipv6";
      uses ISIS-IPV6-PREFIX-TYPE;
    }
    leaf af-name {
      type Isis-af-id;
      description
        "AFName";
    }
  }

  grouping ISIS-SH-SRV6-LOCATOR {
    description
      "SRv6 Locator";
    container locator-prefix {
      description
        "LocatorPrefix";
      uses ISIS-IP-PREFIX-TYPE;
    }
    leaf locator-name {
      type string;
      description
        "LocatorName";
    }
    leaf locator-id {
      type uint32;
      description
        "LocatorID";
    }
    leaf locator-format {
      type uint32;
      description
        "LocatorFormat";
    }
    leaf locator-flags {
      type uint16;
      description
        "LocatorFlags";
    }
    leaf number-of-auto-sids {
      type uint8;
      description
        "NumberOfAutoSIDs";
    }
    leaf algorithm {
      type uint8;
      description
        "Algorithm";
    }
    leaf locator-active {
      type boolean;
      description
        "Currently active";
    }
    leaf anycast-locator {
      type boolean;
      description
        "Anycast Locator";
    }
    leaf locator-out-of-resources {
      type boolean;
      description
        "Out of resources";
    }
    list auto-sid {
      max-elements "5";
      description
        "Reserved Opcodes";
      uses ISIS-SRV6-RSVD-OPCODE;
    }
  }

  grouping ISIS-PER-PRIORITY-COUNTS {
    description
      "Per-priority counts";
    leaf critical {
      type uint32;
      description
        "Critical priority";
    }
    leaf high {
      type uint32;
      description
        "High priority";
    }
    leaf medium {
      type uint32;
      description
        "Medium priority";
    }
    leaf low {
      type uint32;
      description
        "Low priority";
    }
  }

  grouping ISIS-SH-FRR-LEVEL-SUMMARY {
    description
      "FRR backup statistics for one level";
    container all-paths-protected {
      description
        "Number of prefixes with all paths having FRR
         backup";
      uses ISIS-PER-PRIORITY-COUNTS;
    }
    container some-paths-protected {
      description
        "Number of prefixes with some paths having FRR
         backup";
      uses ISIS-PER-PRIORITY-COUNTS;
    }
    container unprotected {
      description
        "Number of reachable prefixes without FRR backup";
      uses ISIS-PER-PRIORITY-COUNTS;
    }
  }

  grouping ISIS-SH-FRR-SUMMARY {
    description
      "FRR summary for an ISIS topology";
    container level1-prefixes {
      description
        "FRR summary for prefixes reachable in L1";
      uses ISIS-SH-FRR-LEVEL-SUMMARY;
    }
    container level2-prefixes {
      description
        "FRR summary for prefixes reachable in L2";
      uses ISIS-SH-FRR-LEVEL-SUMMARY;
    }
    container unreachable-prefixes {
      description
        "Unreachable prefixes";
      uses ISIS-PER-PRIORITY-COUNTS;
    }
  }

  grouping ISIS-SH-IPV6-ROUTE-SUMMARIZATION-STATUS {
    description
      "Summarization status";
    container summary-prefix {
      when "../is-valid = 'isis-valid'" {
        description
          "../IsValid = 'ISIS_VALID'";
      }
      description
        "Summarizing Prefix";
      uses ISIS-IPV6-PREFIX-TYPE;
    }
    leaf is-valid {
      type Isis-valid;
      description
        "IsValid";
    }
  }

  grouping ISIS-SH-IPV6-ROUTE-ADV {
    description
      "How a prefix is advertised in a particular level";
    container summarization-status {
      description
        "Status of summarization for the prefix";
      uses ISIS-SH-IPV6-ROUTE-SUMMARIZATION-STATUS;
    }
    leaf level {
      type Isis-level;
      description
        "Level in which the prefix is advertised";
    }
    leaf advertising-origin {
      type Isis-sh-route-adv-origin;
      description
        "The origin of the advertisement";
    }
    leaf metric {
      type Isis-metric;
      description
        "Metric with which the prefix is advertised";
    }
    leaf is-propagated {
      type boolean;
      description
        "Has the prefix been propagated from another
         level?";
    }
    leaf is-external-metric {
      type boolean;
      description
        "Is the metric an external metric?";
    }
    leaf is-external-reachability {
      type boolean;
      description
        "Is the prefix external to the IS-IS domain?";
    }
    leaf is-interarea {
      type boolean;
      description
        "Is the up/down bit set?";
    }
    list tags {
      description
        "Tags associated with the prefix";
      leaf entry {
        type Isis-prefix-tag;
        description
          "Tags associated with the prefix";
      }
    }
    list nodal-sid {
      description
        "Nodal SIDs with the prefix item";
      uses ISIS-NODAL-SID-TYPE;
    }
    list flex-sid {
      description
        "Flex-Algo SIDs with the prefix item";
      uses ISIS-SID-METRIC-TYPE;
    }
  }

  grouping ISIS-SH-IPV6-ROUTE-NATIVE-SOURCE {
    description
      "Source of a native route";
    leaf source-lsp-id {
      type xr:Isis-lsp-id;
      description
        "ID of the LSP advertising the prefix";
    }
    leaf source-address {
      type Isis-ipv6-address;
      description
        "Source address of the IS advertising the prefix";
    }
    list tags {
      description
        "Tags associated with the prefix item";
      leaf entry {
        type Isis-prefix-tag;
        description
          "Tags associated with the prefix item";
      }
    }
    list nodal-sid {
      description
        "Nodal SIDs with the prefix item";
      uses ISIS-NODAL-SID-TYPE;
    }
  }

  grouping ISIS-SH-IPV6-UCMP-PATH {
    description
      "IPv6 path to a destination";
    container frr-backup {
      description
        "FRR backup for this path";
      uses ISIS-SH-IPV6-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf neighbor-snpa {
      type xr:Isis-snpa;
      description
        "Next hop neighbor's SNPA";
    }
    leaf tag {
      type Isis-prefix-tag;
      description
        "Tag associated with the path";
    }
    leaf total-ucmp-distance {
      type Isis-metric;
      description
        "Distance to the network via this UCMP next hop";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf is-sr-exclude-tunnel-interface {
      type boolean;
      description
        "Is path via an SR-exclude TE tunnel";
    }
    leaf outgoing-label {
      type uint32;
      description
        "SR-MPLS label";
    }
  }

  grouping ISIS-SH-IPV6-FRR-BACKUP {
    description
      "FRR backup path";
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf tunnel-egress-interface {
      type Isis-sh-interface-name;
      description
        "Tunnel interface to send the packet out of";
    }
    leaf neighbor-snpa {
      type xr:Isis-snpa;
      description
        "Next hop neighbor's SNPA";
    }
    leaf remote-lfa-system-id {
      type xr:Osi-system-id;
      description
        "Remote LFA PQ Node's ID";
    }
    leaf remote-lfa-router-id {
      type Isis-ipv6-address;
      description
        "Remote LFA Router ID";
    }
    leaf remote-lfa-system-pid {
      type xr:Osi-system-id;
      description
        "Remote LFA PQ Node's ID";
    }
    leaf remote-lfa-router-pid {
      type Isis-ipv6-address;
      description
        "Remote LFA Router ID";
    }
    leaf total-backup-distance {
      type Isis-metric;
      description
        "Distance to the network via this backup path";
    }
    leaf segment-routing-sid-value {
      type Isis-nodal-sid-value;
      description
        "Segment routing sid value received from first
         hop";
    }
    leaf num-sid {
      type uint32;
      description
        "Number of SIDs in TI-LFA/rLFA";
    }
    leaf backup-repair-list-size {
      type uint32;
      description
        "Backup Repair List Size";
    }
    leaf tilfa-computation {
      type Isis-tilfa-computation;
      description
        "Ti LFA computation which provided backup path";
    }
    leaf prefix-source-node-id {
      type string;
      description
        "PrefixSourceNodeID";
    }
    leaf is-downstream {
      type boolean;
      description
        "Is the backup path via downstream node?";
    }
    leaf is-lc-disjoint {
      type boolean;
      description
        "Is the backup path line card disjoint with
         primary?";
    }
    leaf is-node-protecting {
      type boolean;
      description
        "Is the backup path node protecting?";
    }
    leaf is-primary-path {
      type boolean;
      description
        "Is the backup path an ECMP to the network?";
    }
    leaf is-srlg-disjoint {
      type boolean;
      description
        "Is the backup path SRLG disjoint with primary?";
    }
    leaf is-remote-lfa {
      type boolean;
      description
        "Is the backup path via a Remote LFA?";
    }
    leaf is-epcfrr-lfa {
      type boolean;
      description
        "Is the backup path via a TI-LFA?";
    }
    leaf is-strict-spflfa {
      type boolean;
      description
        "Is the backup path TI-LFA strict SPF?";
    }
    leaf is-s-rv6 {
      type boolean;
      description
        "Is the backup path SRv6?";
    }
    leaf is-tunnel-requested {
      type boolean;
      description
        "Is SR TE tunnel requested";
    }
    leaf weight {
      type Isis-metric;
      description
        "Weight configured on the interface";
    }
    leaf outgoing-label {
      type uint32;
      description
        "SR-MPLS label";
    }
    list segment-routing-sid-value-entry {
      max-elements "3";
      description
        "Segment routing sid values for TI-LFA/rLFA";
      leaf entry {
        type Isis-nodal-sid-value;
        description
          "Segment routing sid values for TI-LFA/rLFA";
      }
    }
    list backup-repair {
      description
        "BAckup Repair List";
      uses ISIS-SH-REP-EL;
    }
  }

  grouping ISIS-SH-IPV6-PATH {
    description
      "IPv6 path to a destination";
    container frr-backup {
      description
        "FRR backup for this path";
      uses ISIS-SH-IPV6-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf neighbor-snpa {
      type xr:Isis-snpa;
      description
        "Next hop neighbor's SNPA";
    }
    leaf tag {
      type Isis-prefix-tag;
      description
        "Tag associated with the path";
    }
    leaf tunnel-interface {
      type Isis-sh-interface-name;
      description
        "Explicit path tunnel interface";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf is-sr-exclude-tunnel-interface {
      type boolean;
      description
        "Is path via an SR-exclude TE tunnel";
    }
    leaf is-s-rv6 {
      type boolean;
      description
        "Is the path SRv6?";
    }
    leaf outgoing-label {
      type uint32;
      description
        "SR-MPLS label";
    }
    list uloop-explicit {
      description
        "Uloop Explicit List";
      uses ISIS-SH-REP-EL;
    }
    list nnh {
      description
        "Next next hops";
      uses ISIS-SH-NNH;
    }
  }

  grouping ISIS-SH-IPV6-ROUTE-NATIVE-PREFERENCE {
    description
      "Paths and sources for a native route at a
       particular preference";
    leaf origin {
      type Isis-prefix-origin;
      description
        "Origin of route";
    }
    leaf metric {
      type Isis-metric;
      description
        "Distance to network";
    }
    leaf multicast-metric {
      type Isis-metric;
      description
        "Multicast-intact distance to network";
    }
    leaf is-external-metric {
      type boolean;
      description
        "Is the metric an external metric?";
    }
    leaf administrative-distance {
      type uint16;
      description
        "Administrative Distance";
    }
    list paths {
      description
        "First hops toward the prefix";
      uses ISIS-SH-IPV6-PATH;
    }
    list ucmp-next-hop {
      description
        "UCMP first hops toward the prefix";
      uses ISIS-SH-IPV6-UCMP-PATH;
    }
    list multicast-path {
      description
        "Multicast intact first hops toward the prefix";
      uses ISIS-SH-IPV6-PATH;
    }
    list srte-path {
      description
        "SR-TE native first hops toward the prefix";
      uses ISIS-SH-IPV6-PATH;
    }
    list explicit-path {
      description
        "SR microloop avoidance paths";
      uses ISIS-SH-IPV6-PATH;
    }
    list source {
      description
        "Sources advertising the prefix";
      uses ISIS-SH-IPV6-ROUTE-NATIVE-SOURCE;
    }
    list multicast-source {
      description
        "Multicast-intact sources advertising the prefix";
      uses ISIS-SH-IPV6-ROUTE-NATIVE-SOURCE;
    }
  }

  grouping ISIS-SH-IPV6-ROUTE-NATIVE-DETAILS {
    description
      "Details of a native IS-IS route to a prefix";
    container primary {
      description
        "Primary paths to prefix";
      uses ISIS-SH-IPV6-ROUTE-NATIVE-PREFERENCE;
    }
    leaf priority {
      type Isis-prefix-priority;
      description
        "Relative importance of the prefix";
    }
    leaf is-filtered-by-dl {
      type boolean;
      description
        "Is the prefix filtered out by distribution list?";
    }
    leaf local-label {
      type uint32;
      description
        "Prefix local label for SR-MPLS";
    }
    list backup {
      description
        "Backup paths to prefix";
      uses ISIS-SH-IPV6-ROUTE-NATIVE-PREFERENCE;
    }
  }

  grouping ISIS-SH-IPV6-ROUTE-NATIVE-STATUS {
    description
      "Status of a native IS-IS route to a prefix";
    container native-details {
      when "../is-valid = 'isis-valid'" {
        description
          "../IsValid = 'ISIS_VALID'";
      }
      description
        "Details of the native route";
      uses ISIS-SH-IPV6-ROUTE-NATIVE-DETAILS;
    }
    leaf is-valid {
      type Isis-valid;
      description
        "IsValid";
    }
  }

  grouping ISIS-SH-IPV6-ROUTE {
    description
      "IS-IS IPv6 route";
    container connected-status {
      description
        "Status of IS-IS directly connected routes to the
         prefix";
      uses ISIS-SH-ROUTE-CONN-STATUS;
    }
    container redistributed-status {
      description
        "Status of other protocols' routes redistributed
         into IS-IS";
      uses ISIS-SH-ROUTE-REDIST-STATUS;
    }
    container native-status {
      description
        "Status of native IS-IS routes to the prefix";
      uses ISIS-SH-IPV6-ROUTE-NATIVE-STATUS;
    }
    list per-level-advertising-detail {
      description
        "Per level details of how the local system
         advertises the prefix";
      uses ISIS-SH-IPV6-ROUTE-ADV;
    }
  }

  grouping ISIS-SID-METRIC-TYPE {
    description
      "ISIS SID METRIC TYPE";
    container nodal-sid {
      description
        "nodal sid";
      uses ISIS-NODAL-SID-TYPE;
    }
    leaf metric {
      type uint32;
      description
        "metric";
    }
  }

  grouping ISIS-IPV4-PREFIX-TYPE {
    description
      "IPv4 address and prefix length";
    leaf prefix {
      type Isis-ipv4-address;
      description
        "prefix";
    }
    leaf prefix-length {
      type Isis-ip-prefix-length;
      description
        "prefix length";
    }
  }

  grouping ISIS-SH-IPV4-ROUTE-SUMMARIZATION-STATUS {
    description
      "Summarization status";
    container summary-prefix {
      when "../is-valid = 'isis-valid'" {
        description
          "../IsValid = 'ISIS_VALID'";
      }
      description
        "Summarizing Prefix";
      uses ISIS-IPV4-PREFIX-TYPE;
    }
    leaf is-valid {
      type Isis-valid;
      description
        "IsValid";
    }
  }

  grouping ISIS-SH-IPV4-ROUTE-ADV {
    description
      "How a prefix is advertised in a particular level";
    container summarization-status {
      description
        "Status of summarization for the prefix";
      uses ISIS-SH-IPV4-ROUTE-SUMMARIZATION-STATUS;
    }
    leaf level {
      type Isis-level;
      description
        "Level in which the prefix is advertised";
    }
    leaf advertising-origin {
      type Isis-sh-route-adv-origin;
      description
        "The origin of the advertisement";
    }
    leaf metric {
      type Isis-metric;
      description
        "Metric with which the prefix is advertised";
    }
    leaf is-propagated {
      type boolean;
      description
        "Has the prefix been propagated from another
         level?";
    }
    leaf is-external-metric {
      type boolean;
      description
        "Is the metric an external metric?";
    }
    leaf is-external-reachability {
      type boolean;
      description
        "Is the prefix external to the IS-IS domain?";
    }
    leaf is-interarea {
      type boolean;
      description
        "Is the up/down bit set?";
    }
    list tags {
      description
        "Tags associated with the prefix";
      leaf entry {
        type Isis-prefix-tag;
        description
          "Tags associated with the prefix";
      }
    }
    list nodal-sid {
      description
        "Nodal SIDs with the prefix item";
      uses ISIS-NODAL-SID-TYPE;
    }
    list flex-sid {
      description
        "Flex-Algo SIDs with the prefix item";
      uses ISIS-SID-METRIC-TYPE;
    }
  }

  grouping ISIS-NODAL-SID-TYPE {
    description
      "ISIS NODAL SID TYPE";
    leaf sid-value {
      type Isis-nodal-sid-value;
      description
        "sid value";
    }
    leaf rflag {
      type uint8;
      description
        "rflag";
    }
    leaf nflag {
      type uint8;
      description
        "nflag";
    }
    leaf pflag {
      type uint8;
      description
        "pflag";
    }
    leaf eflag {
      type uint8;
      description
        "eflag";
    }
    leaf vflag {
      type uint8;
      description
        "vflag";
    }
    leaf lflag {
      type uint8;
      description
        "lflag";
    }
    leaf algorithm {
      type uint8;
      description
        "algorithm";
    }
  }

  grouping ISIS-SH-IPV4-ROUTE-NATIVE-SOURCE {
    description
      "Source of a native route";
    leaf source-lsp-id {
      type xr:Isis-lsp-id;
      description
        "ID of the LSP advertising the prefix";
    }
    leaf source-address {
      type Isis-ipv4-address;
      description
        "Source address of the IS advertising the prefix";
    }
    list tags {
      description
        "Tags associated with the prefix item";
      leaf entry {
        type Isis-prefix-tag;
        description
          "Tags associated with the prefix item";
      }
    }
    list nodal-sid {
      description
        "Nodal SIDs with the prefix item";
      uses ISIS-NODAL-SID-TYPE;
    }
  }

  grouping ISIS-SH-IPV4-UCMP-PATH {
    description
      "IPv4 path to a destination";
    container frr-backup {
      description
        "FRR backup for this path";
      uses ISIS-SH-IPV4-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf neighbor-snpa {
      type xr:Isis-snpa;
      description
        "Next hop neighbor's SNPA";
    }
    leaf tag {
      type Isis-prefix-tag;
      description
        "Tag associated with the path";
    }
    leaf total-ucmp-distance {
      type Isis-metric;
      description
        "Distance to the network via this UCMP next hop";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf is-sr-exclude-tunnel-interface {
      type boolean;
      description
        "Is path via an SR-exclude TE tunnel";
    }
    leaf outgoing-label {
      type uint32;
      description
        "SR-MPLS label";
    }
  }

  grouping ISIS-SH-NNH {
    description
      "Next next hops for a prefix";
    leaf link-id-set {
      type boolean;
      description
        "If link_id is given";
    }
    leaf ipv4-set {
      type boolean;
      description
        "If ipv4 address is given";
    }
    leaf link-id {
      type uint32;
      description
        "link ID of the next next hop";
    }
    leaf ipv4-address {
      type Isis-ipv4-address;
      description
        "Ipv4 address of the next next hop";
    }
  }

  grouping ISIS-SH-REP-EL {
    description
      "OSPF Repair Element";
    leaf repair-element-node-id {
      type string;
      description
        "RepairElementNodeID";
    }
    leaf repair-ipv4-addr {
      type Isis-ipv4-address;
      description
        "RepairIPv4Addr";
    }
    leaf repair-ipv6-addr {
      type Isis-ipv6-address;
      description
        "RepairIPv6Addr";
    }
    leaf repair-label {
      type uint32;
      description
        "Repair Label";
    }
    leaf repair-element-type {
      type uint32;
      description
        "Repair Element Type";
    }
    leaf repair-strict-spf-label {
      type uint32;
      description
        "Repair Strict SPF Label";
    }
    leaf repair-s-rv6sid {
      type Isis-ipv6-address;
      description
        "Repair SRv6 SID";
    }
    leaf repair-s-rv6-end-func {
      type Isis-srv6-endpoint-func;
      description
        "Repair SRv6 End Function";
    }
    leaf repair-s-rv6-strict-spfsid {
      type Isis-ipv6-address;
      description
        "Repair SRv6 Strict SPF SID";
    }
    leaf repair-s-rv6-strict-spf-end-func {
      type Isis-srv6-endpoint-func;
      description
        "Repair SRv6 Strict SPF End Function";
    }
  }

  grouping ISIS-SH-IPV4-FRR-BACKUP {
    description
      "FRR backup path";
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf tunnel-egress-interface {
      type Isis-sh-interface-name;
      description
        "Tunnel Interface to send the packet out of";
    }
    leaf neighbor-snpa {
      type xr:Isis-snpa;
      description
        "Next hop neighbor's SNPA";
    }
    leaf remote-lfa-system-id {
      type xr:Osi-system-id;
      description
        "Remote LFA PQ Node's ID";
    }
    leaf remote-lfa-router-id {
      type Isis-ipv4-address;
      description
        "Remote LFA Router ID";
    }
    leaf remote-lfa-system-pid {
      type xr:Osi-system-id;
      description
        "Remote LFA PQ Node's ID";
    }
    leaf remote-lfa-router-pid {
      type Isis-ipv4-address;
      description
        "Remote LFA Router ID";
    }
    leaf total-backup-distance {
      type Isis-metric;
      description
        "Distance to the network via this backup path";
    }
    leaf segment-routing-sid-value {
      type Isis-nodal-sid-value;
      description
        "Segment routing sid value received from first
         hop";
    }
    leaf num-sid {
      type uint32;
      description
        "Number of SIDs in TI-LFA/rLFA";
    }
    leaf backup-repair-list-size {
      type uint32;
      description
        "Backup Repair List Size";
    }
    leaf tilfa-computation {
      type Isis-tilfa-computation;
      description
        "Ti LFA computation which provided backup path";
    }
    leaf prefix-source-node-id {
      type string;
      description
        "PrefixSourceNodeID";
    }
    leaf is-downstream {
      type boolean;
      description
        "Is the backup path via downstream node?";
    }
    leaf is-lc-disjoint {
      type boolean;
      description
        "Is the backup path line card disjoint with
         primary?";
    }
    leaf is-node-protecting {
      type boolean;
      description
        "Is the backup path node protecting?";
    }
    leaf is-primary-path {
      type boolean;
      description
        "Is the backup path an ECMP to the network?";
    }
    leaf is-srlg-disjoint {
      type boolean;
      description
        "Is the backup path SRLG disjoint with primary?";
    }
    leaf is-remote-lfa {
      type boolean;
      description
        "Is the backup path via a Remote LFA?";
    }
    leaf is-epcfrr-lfa {
      type boolean;
      description
        "Is the backup path via a TI-LFA?";
    }
    leaf is-strict-spflfa {
      type boolean;
      description
        "Is the backup path TI-LFA strict SPF?";
    }
    leaf is-tunnel-requested {
      type boolean;
      description
        "Is SR TE tunnel requested";
    }
    leaf weight {
      type Isis-metric;
      description
        "Weight configured on the interface";
    }
    leaf outgoing-label {
      type uint32;
      description
        "SR-MPLS label";
    }
    list segment-routing-sid-value-entry {
      max-elements "3";
      description
        "Segment routing sid values for TI-LFA/rLFA";
      leaf entry {
        type Isis-nodal-sid-value;
        description
          "Segment routing sid values for TI-LFA/rLFA";
      }
    }
    list backup-repair {
      description
        "Backup Repair List";
      uses ISIS-SH-REP-EL;
    }
  }

  grouping ISIS-SH-IPV4-PATH {
    description
      "IPv4 path to a destination";
    container frr-backup {
      description
        "FRR backup for this path";
      uses ISIS-SH-IPV4-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf neighbor-snpa {
      type xr:Isis-snpa;
      description
        "Next hop neighbor's SNPA";
    }
    leaf tag {
      type Isis-prefix-tag;
      description
        "Tag associated with the path";
    }
    leaf tunnel-interface {
      type Isis-sh-interface-name;
      description
        "Explicit path tunnel interface";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf is-sr-exclude-tunnel-interface {
      type boolean;
      description
        "Is path via an SR-exclude TE tunnel";
    }
    leaf outgoing-label {
      type uint32;
      description
        "SR-MPLS label";
    }
    list uloop-explicit {
      description
        "Uloop Explicit List";
      uses ISIS-SH-REP-EL;
    }
    list nnh {
      description
        "Next next hops";
      uses ISIS-SH-NNH;
    }
  }

  grouping ISIS-SH-IPV4-ROUTE-NATIVE-PREFERENCE {
    description
      "Paths and sources for a native route at a
       particular preference";
    leaf origin {
      type Isis-prefix-origin;
      description
        "Origin of route";
    }
    leaf metric {
      type Isis-metric;
      description
        "Distance to network";
    }
    leaf multicast-metric {
      type Isis-metric;
      description
        "Multicast-intact distance to network";
    }
    leaf is-external-metric {
      type boolean;
      description
        "Is the metric an external metric?";
    }
    leaf administrative-distance {
      type uint16;
      description
        "Administrative Distance";
    }
    list paths {
      description
        "First hops toward the prefix";
      uses ISIS-SH-IPV4-PATH;
    }
    list ucmp-next-hop {
      description
        "UCMP first hops toward the prefix";
      uses ISIS-SH-IPV4-UCMP-PATH;
    }
    list multicast-path {
      description
        "Multicast intact first hops toward the prefix";
      uses ISIS-SH-IPV4-PATH;
    }
    list srte-path {
      description
        "SR-TE native first hops toward the prefix";
      uses ISIS-SH-IPV4-PATH;
    }
    list explicit-path {
      description
        "SR microloop avoidance paths";
      uses ISIS-SH-IPV4-PATH;
    }
    list source {
      description
        "Sources advertising the prefix";
      uses ISIS-SH-IPV4-ROUTE-NATIVE-SOURCE;
    }
    list multicast-source {
      description
        "Multicast-intact sources advertising the prefix";
      uses ISIS-SH-IPV4-ROUTE-NATIVE-SOURCE;
    }
  }

  grouping ISIS-SH-IPV4-ROUTE-NATIVE-DETAILS {
    description
      "Details of a native IS-IS route to a prefix";
    container primary {
      description
        "Primary paths to prefix";
      uses ISIS-SH-IPV4-ROUTE-NATIVE-PREFERENCE;
    }
    leaf priority {
      type Isis-prefix-priority;
      description
        "Relative importance of the prefix";
    }
    leaf is-filtered-by-dl {
      type boolean;
      description
        "Is the prefix filtered out by distribution list?";
    }
    leaf local-label {
      type uint32;
      description
        "Prefix local label for SR-MPLS";
    }
    list backup {
      description
        "Backup paths to prefix";
      uses ISIS-SH-IPV4-ROUTE-NATIVE-PREFERENCE;
    }
  }

  grouping ISIS-SH-IPV4-ROUTE-NATIVE-STATUS {
    description
      "Status of a native IS-IS route to a prefix";
    container native-details {
      when "../is-valid = 'isis-valid'" {
        description
          "../IsValid = 'ISIS_VALID'";
      }
      description
        "Details of the native route";
      uses ISIS-SH-IPV4-ROUTE-NATIVE-DETAILS;
    }
    leaf is-valid {
      type Isis-valid;
      description
        "IsValid";
    }
  }

  grouping ISIS-SH-REDIST-ENTRY-PROTO {
    description
      "Redistributed protocol information";
    leaf protocol {
      type Isis-redist-proto;
      description
        "Protocol";
    }
    leaf isis-instance-id {
      when "../protocol = 'isis-redist-isis'" {
        description
          "../Protocol = 'ISIS_REDIST_ISIS'";
      }
      type Isis-string;
      description
        "IS-IS instance identifier";
    }
    leaf ospf-process-id {
      when "../protocol = 'isis-redist-ospf'" {
        description
          "../Protocol = 'ISIS_REDIST_OSPF'";
      }
      type Isis-string;
      description
        "OSPF process identifier";
    }
    leaf ospfv3-process-id {
      when "../protocol = 'isis-redist-ospfv3'" {
        description
          "../Protocol = 'ISIS_REDIST_OSPFV3'";
      }
      type Isis-string;
      description
        "OSPFv3 process identifier";
    }
    leaf bgp-as-number {
      when "../protocol = 'isis-redist-bgp'" {
        description
          "../Protocol = 'ISIS_REDIST_BGP'";
      }
      type Isis-string;
      description
        "BGP Autonomous System number";
    }
    leaf eigrp-as-number {
      when "../protocol = 'isis-redist-eigrp'" {
        description
          "../Protocol = 'ISIS_REDIST_EIGRP'";
      }
      type Isis-string;
      description
        "EIGRP Autonomous System number";
    }
    leaf application-name {
      when "../protocol = 'isis-redist-application'" {
        description
          "../Protocol = 'ISIS_REDIST_APPLICATION'";
      }
      type Isis-string;
      description
        "Application Name";
    }
  }

  grouping ISIS-SH-ROUTE-REDIST-LEVEL-DETAILS {
    description
      "Details of a route redistributed into a
       particular level";
    container owner {
      description
        "Protocol redistributing the route";
      uses ISIS-SH-REDIST-ENTRY-PROTO;
    }
    leaf level {
      type Isis-level;
      description
        "Level into which the route is redistributed";
    }
  }

  grouping ISIS-SH-ROUTE-REDIST-DETAILS {
    description
      "ISIS SH ROUTE REDIST DETAILS";
    list isis-sh-route-redist-detail {
      description
        "isis sh route redist detail";
      uses ISIS-SH-ROUTE-REDIST-LEVEL-DETAILS;
    }
  }

  grouping ISIS-SH-ROUTE-REDIST-STATUS {
    description
      "Status of redistributed routes to a prefix";
    container redistribution-details {
      when "../is-valid = 'isis-valid'" {
        description
          "../IsValid = 'ISIS_VALID'";
      }
      description
        "Per level details of the redistributed route";
      uses ISIS-SH-ROUTE-REDIST-DETAILS;
    }
    leaf is-valid {
      type Isis-valid;
      description
        "IsValid";
    }
  }

  grouping ISIS-SH-ROUTE-CONN-DETAILS {
    description
      "Details of an IS-IS directly connected prefix";
    list interface {
      description
        "Interfaces";
      leaf entry {
        type Isis-sh-interface-name;
        description
          "Interfaces";
      }
    }
  }

  grouping ISIS-SH-ROUTE-CONN-STATUS {
    description
      "Status of an IS-IS directly connected prefix";
    container connected-details {
      when "../is-valid = 'isis-valid'" {
        description
          "../IsValid = 'ISIS_VALID'";
      }
      description
        "Details of the directly connected prefix";
      uses ISIS-SH-ROUTE-CONN-DETAILS;
    }
    leaf is-valid {
      type Isis-valid;
      description
        "IsValid";
    }
  }

  grouping ISIS-SH-IPV4-ROUTE {
    description
      "IS-IS IPv4 route";
    container connected-status {
      description
        "Status of IS-IS directly connected routes to the
         prefix";
      uses ISIS-SH-ROUTE-CONN-STATUS;
    }
    container redistributed-status {
      description
        "Status of other protocols' routes redistributed
         into IS-IS";
      uses ISIS-SH-ROUTE-REDIST-STATUS;
    }
    container native-status {
      description
        "Status of native IS-IS routes to the prefix";
      uses ISIS-SH-IPV4-ROUTE-NATIVE-STATUS;
    }
    list per-level-advertising-detail {
      description
        "Per level details of how the local system
         advertises the prefix";
      uses ISIS-SH-IPV4-ROUTE-ADV;
    }
  }

  grouping ISIS-SH-LSP-DB-LOG-ENT {
    description
      "LSP Database Log Entry";
    container generic-data {
      description
        "Generic entry data";
      uses ISIS-SH-GENERIC-LOG-ENT;
    }
    container new-lsp-entry {
      description
        "Entry being inserted or the updated version of
         an old entry.";
      uses ISIS-SH-LSP-HEADER;
    }
    container old-lsp-entry {
      description
        "Entry being replaced.";
      uses ISIS-SH-LSP-HEADER;
    }
    leaf lspdb-operation {
      type Isis-lsp-db-op;
      description
        "Operation applying to this entry.";
    }
  }

  grouping ISIS-SH-LSP-DB-LOG-STRUC {
    description
      "LSP Database Log";
    list log-entry {
      description
        "Entries";
      uses ISIS-SH-LSP-DB-LOG-ENT;
    }
  }

  grouping ISIS-SH-LSP-LOG-ENT {
    description
      "LSP-log entry";
    container generic-data {
      description
        "Generic entry data";
      uses ISIS-SH-GENERIC-LOG-ENT;
    }
    leaf trigger-count {
      type uint32;
      description
        "Number of triggers on this run. May not be equal
         to the number of trigger event types if one or
         more trigger events has occurred more than once.";
    }
    leaf delayed-trigger-count {
      type uint32;
      description
        "Number of delayed triggers";
    }
    leaf log-interface {
      type xr:Interface-name;
      description
        "Appropriate interface, if any";
    }
    leaf pseudo-node-number {
      type Isis-pseudo-node-number;
      description
        "Pseudo-node number";
    }
    list trigger {
      description
        "Triggers applying to this log entry.";
      leaf entry {
        type Isis-lsp-trigger;
        description
          "Triggers applying to this log entry.";
      }
    }
  }

  grouping ISIS-SH-LSP-LOG-STRUC {
    description
      "LSP log";
    list log-entry {
      description
        "Log entries";
      uses ISIS-SH-LSP-LOG-ENT;
    }
  }

  grouping ISIS-SH-LSP-HEADER {
    description
      "Contents of an IS-IS LSP header";
    leaf lsp-id {
      type xr:Isis-lsp-id;
      description
        "The LSP ID";
    }
    leaf local-lsp-flag {
      type boolean;
      description
        "TRUE if this is a locally generated LSP";
    }
    leaf lsp-active-flag {
      type boolean;
      description
        "TRUE if this LSP has not expired";
    }
    leaf lsp-holdtime {
      type uint16;
      units "second";
      description
        "Time, in seconds, until LSP expiry (if active)
         or deletion (if expired) ";
    }
    leaf lsp-rcvd-holdtime {
      type uint16;
      units "second";
      description
        "Time, in seconds, for the received LSP it will
         be zero for the local LSP ";
    }
    leaf lsp-sequence-number {
      type uint32;
      description
        "The LSP sequence number";
    }
    leaf lsp-checksum {
      type uint16;
      description
        "The LSP checksum";
    }
    leaf lsp-partition-repair-supported-flag {
      type boolean;
      description
        "TRUE if partition repair is supported";
    }
    leaf lsp-attached-flag {
      type boolean;
      description
        "TRUE if attached bit is set";
    }
    leaf lsp-overloaded-flag {
      type boolean;
      description
        "TRUE if the overload bit is set";
    }
    leaf lsp-nonv1a-flag {
      type uint16;
      description
        "TRUE if the LSP is non-v1a, XXX for testing";
    }
    leaf lsp-level {
      type Isis-levels;
      description
        "The type of the IS sourcing the LSP";
    }
    leaf lsp-length {
      type uint16;
      description
        "The total length of the LSP";
    }
    leaf max-area-addresses {
      type uint8;
      description
        "max area addresses";
    }
    leaf id-length {
      type uint8;
      description
        "System Id length";
    }
    leaf version {
      type uint8;
      description
        "isis version";
    }
    leaf version2 {
      type uint8;
      description
        "isis version2";
    }
  }

  grouping ISIS-SH-LSP {
    description
      "An IS-IS LSP";
    container lsp-header-data {
      description
        "Information from the LSP header";
      uses ISIS-SH-LSP-HEADER;
    }
    leaf lsp-body {
      type yang:hex-string;
      description
        "LSP as received/sent over the wire, starting
         from the LSP ID field";
    }
  }

  grouping ISIS-SH-ADJ-BFD-ITEM {
    description
      "BFD TLV item";
    leaf mtid {
      type uint16;
      description
        "Topology ID";
    }
    leaf nlpid {
      type uint8;
      description
        "Network Layer Protocol ID";
    }
  }

  grouping ISIS-SH-ADJ-TOPO {
    description
      "Per-topology per-adjacency data";
    container id {
      description
        "Topology ID";
      uses ISIS-TOPO-ID-TYPE;
    }
    leaf topology-status {
      type Isis-adj-topo-status;
      description
        "Status of topology in adjacency";
    }
    leaf parallel-p2p-link-suppressed-flag {
      type boolean;
      description
        "TRUE if suppressed parallel point-to-point link";
    }
  }

  grouping ISIS-SH-ADJ {
    description
      "An IS-IS adjacency";
    leaf adjacency-system-id {
      type xr:Osi-system-id;
      description
        "Neighbor system ID";
    }
    leaf adjacency-snpa {
      type xr:Isis-snpa;
      description
        "Neighbor SNPA";
    }
    leaf adjacency-interface {
      type xr:Interface-name;
      description
        "Local interface";
    }
    leaf adjacency-media-type {
      type Isis-media-class;
      description
        "Link media type";
    }
    leaf adjacency-state {
      type Isis-adj-state;
      description
        "Adjacency state";
    }
    leaf adjacency-bfd-state {
      type Isis-adj-bfd-state;
      description
        "Adjacency IPv4 BFD state";
    }
    leaf adjacency-ipv6bfd-state {
      type Isis-adj-bfd-state;
      description
        "Adjacency IPv6 BFD state";
    }
    leaf adj-ipv4bfd-retry-running {
      type boolean;
      description
        "Is IPv4 BFD retry timer running";
    }
    leaf adj-ipv6bfd-retry-running {
      type boolean;
      description
        "Is IPv6 BFD retry timer running";
    }
    leaf adj-ipv4bfd-retry-exp {
      type uint32;
      description
        "Time to expiration of IPv4 BFD retry timer (s)";
    }
    leaf adj-ipv6bfd-retry-exp {
      type uint32;
      description
        "Time to expiration of IPv6 BFD retry timer (s)";
    }
    leaf adj-ipv4bfd-retry-count {
      type uint32;
      description
        "IPv4 BFD retry counter";
    }
    leaf adj-ipv6bfd-retry-count {
      type uint32;
      description
        "IPv6 BFD retry counter";
    }
    leaf adjacency-uptime-valid-flag {
      type boolean;
      description
        "TRUE if AdjacencyUptime is set";
    }
    leaf adjacency-uptime {
      type uint32;
      description
        "How long the adjacency has been up (s)";
    }
    leaf adjacency-holdtime {
      type uint32;
      description
        "Time (s) until adjacency declared down if no IIH
         received";
    }
    leaf adjacency-checkpoint-object-id {
      type uint32;
      description
        "Adjacency checkpoint object ID";
    }
    leaf adjacency-ietf-nsf-capable-flag {
      type boolean;
      description
        "TRUE if neighbor is IETF-NSF capable";
    }
    leaf adjacency-dispriority {
      type Isis-dr-priority;
      description
        "Priority of DIS on this LAN. Valid only if
         aj_media_class is ISIS_MEDIA_CLASS_LAN";
    }
    leaf adjacency-neighbor-priority {
      type Isis-dr-priority;
      description
        "Neighbor IS priority. Valid only if
         aj_media_class is ISIS_MEDIA_CLASS_LAN";
    }
    leaf adjacency-local-priority {
      type Isis-dr-priority;
      description
        "Local IS priority. Valid only if aj_media_class
         is ISIS_MEDIA_CLASS_LAN";
    }
    leaf local-dis-flag {
      type boolean;
      description
        "TRUE if local system is DIS. Valid only if
         AdjacencyMediaType is ISIS_MEDIA_CLASS_LAN";
    }
    leaf neighbor-dis-flag {
      type boolean;
      description
        "TRUE if neighbor is DIS. Valid only if
         AdjacencyMediaType is ISIS_MEDIA_CLASS_LAN";
    }
    leaf nsr-standby {
      type uint8;
      description
        "ISIS NSR STANDBY";
    }
    leaf bfd-required {
      type boolean;
      description
        "ISIS BFD Required";
    }
    leaf neighbor-useable {
      type boolean;
      description
        "ISIS Neighbor Useable";
    }
    leaf bfd-change-pending {
      type boolean;
      description
        "ISIS BFD change pending";
    }
    list adjacency-area-address {
      description
        "Area addresses active over this adjacency";
      leaf entry {
        type xr:Osi-area-address;
        description
          "Area addresses active over this adjacency";
      }
    }
    list adjacency-topology {
      description
        "Per-topology data";
      uses ISIS-SH-ADJ-TOPO;
    }
    list adjacency-per-address-family-data {
      description
        "Per-address-family data";
      uses ISIS-SH-ADJ-AF;
    }
    list bfdtlv {
      description
        "BFD TLV content";
      uses ISIS-SH-ADJ-BFD-ITEM;
    }
  }

  grouping ISIS-SH-LSP-DB-SUMMARY-ALL-FRAGMENTS-STATS {
    description
      "All fragment counters";
    container node-counters {
      description
        "Summary by class of node";
      uses ISIS-SH-LSP-DB-SUMMARY-NODE-CLASS-COUNTERS;
    }
  }

  grouping ISIS-SH-LSP-DB-SUMMARY-TOPO-CLASS-COUNTERS {
    description
      "Per-topology related info";
    container id {
      description
        "Topology ID";
      uses ISIS-TOPO-ID-TYPE;
    }
    container overloaded-lsp-count {
      description
        "Number of LSPs with their per-topology overload
         bit set";
      uses ISIS-SH-LSP-DB-SUMMARY-STATUS-CLASS-COUNTERS;
    }
    container attached-lsp-count {
      description
        "Number of LSPs with their per-topology attached
         bit set";
      uses ISIS-SH-LSP-DB-SUMMARY-STATUS-CLASS-COUNTERS;
    }
  }

  grouping ISIS-SH-LSP-DB-SUMMARY-STATUS-CLASS-COUNTERS {
    description
      "LSP status counters";
    leaf active-lsp-count {
      type uint32;
      description
        "Number of active LSPs";
    }
    leaf purged-lsp-count {
      type uint32;
      description
        "Number of purged LSPs";
    }
  }

  grouping ISIS-SH-LSP-DB-SUMMARY-NODE-CLASS-COUNTERS {
    description
      "LSP node type counters";
    container route-lsp-count {
      description
        "Router LSPs";
      uses ISIS-SH-LSP-DB-SUMMARY-STATUS-CLASS-COUNTERS;
    }
    container pseudo-node-lsp-count {
      description
        "Pseudonode LSPs";
      uses ISIS-SH-LSP-DB-SUMMARY-STATUS-CLASS-COUNTERS;
    }
  }

  grouping ISIS-SH-LSP-DB-SUMMARY-FRAGMENT-0-STATS {
    description
      "Fragment-0 counters";
    container node-counters {
      description
        "Summary by class of node";
      uses ISIS-SH-LSP-DB-SUMMARY-NODE-CLASS-COUNTERS;
    }
    list per-topology-counter {
      description
        "Per topology counters";
      uses ISIS-SH-LSP-DB-SUMMARY-TOPO-CLASS-COUNTERS;
    }
  }

  grouping ISIS-SH-LSP-DB-SUMMARY {
    description
      "Summary Statistics for an IS-IS LSP Database";
    container fragment0lsp-stats {
      description
        "Statistics for fragment 0 LSPs";
      uses ISIS-SH-LSP-DB-SUMMARY-FRAGMENT-0-STATS;
    }
    container all-fragment-lsp-stats {
      description
        "Statistics for all LSP fragments";
      uses ISIS-SH-LSP-DB-SUMMARY-ALL-FRAGMENTS-STATS;
    }
  }

  grouping ISIS-ADJ-LOG-TOPO-TYPE {
    description
      "Per-topology per-adjacency log data";
    container id {
      description
        "Topology ID";
      uses ISIS-TOPO-ID-TYPE;
    }
    leaf change {
      type Isis-adj-topo-change;
      description
        "Change";
    }
  }

  grouping ISIS-SH-GENERIC-LOG-ENT {
    description
      "Generic portion of a log entry";
    container timestamp {
      description
        "Time in UTC relative to Jan 1st, 1970";
      uses ISIS-SH-TIMESTAMP-TYPE;
    }
  }

  grouping ISIS-SH-ADJ-LOG-ENT {
    description
      "An adjacency log entry";
    container generic-data {
      description
        "Generic entry data";
      uses ISIS-SH-GENERIC-LOG-ENT;
    }
    leaf adj-log-neighbor-system-id {
      type xr:Osi-system-id;
      description
        "Neighbor system ID";
    }
    leaf interface-name {
      type string;
      description
        "Interface name";
    }
    leaf prev-adj-state {
      type Isis-adj-state;
      description
        "Previous adjacency state";
    }
    leaf cur-adj-state {
      type Isis-adj-state;
      description
        "Current adjacency state";
    }
    leaf state-reason {
      type Isis-adj-state-reason;
      description
        "Reason adjacency changed state";
    }
    list adjacency-per-topology-change {
      description
        "Per-topology changes";
      uses ISIS-ADJ-LOG-TOPO-TYPE;
    }
  }

  grouping ISIS-SH-ADJ-LOG-STRUC {
    description
      "Adjacency log structure";
    list log-entry {
      description
        "Adjacency Log entries";
      uses ISIS-SH-ADJ-LOG-ENT;
    }
  }

  grouping ISIS-AREA-TOPO-STATS-TYPE {
    description
      "Per-area, per-topology traffic statistics";
    leaf spf-run-count {
      type uint32;
      description
        "Number of full SPF calculations run";
    }
    leaf ispf-run-count {
      type uint32;
      description
        "Number of ISPF calculations run";
    }
    leaf nhc-run-count {
      type uint32;
      description
        "Number of Next Hop Calculations run";
    }
    leaf prc-run-count {
      type uint32;
      description
        "Number of PRCs run";
    }
    leaf periodic-run-count {
      type uint32;
      description
        "Number of periodic SPF calculations run";
    }
  }

  grouping ISIS-SH-TRAFFIC-AREA-TOPO {
    description
      "Per-area, per-topology traffic data";
    container id {
      description
        "Topology ID";
      uses ISIS-TOPO-ID-TYPE;
    }
    container statistics {
      description
        "Statistics";
      uses ISIS-AREA-TOPO-STATS-TYPE;
    }
  }

  grouping ISIS-AREA-STATS-TYPE {
    description
      "Per-area traffic statistics";
    leaf system-lsp-build-count {
      type uint32;
      description
        "Number of times system LSP rebuilt";
    }
    leaf system-lsp-refresh-count {
      type uint32;
      description
        "Number of times system LSP refreshed";
    }
  }

  grouping ISIS-SH-TRAFFIC-AREA {
    description
      "Per-area traffic data";
    container statistics {
      description
        "Statistics";
      uses ISIS-AREA-STATS-TYPE;
    }
    leaf level {
      type Isis-level;
      description
        "Level this data applies to";
    }
    list per-topology-data {
      description
        "Per-topoogy statistics";
      uses ISIS-SH-TRAFFIC-AREA-TOPO;
    }
  }

  grouping ISIS-SH-TIMESTAMP-TYPE {
    description
      "Timestamp for an event";
    leaf seconds {
      type uint32;
      units "second";
      description
        "Timestamp value (seconds)";
    }
    leaf nano-seconds {
      type uint32;
      units "nanosecond";
      description
        "Timestamp value (nanoseconds)";
    }
  }

  grouping ISIS-TRAFFIC-GLOBAL-TYPE {
    description
      "IS-IS process traffic statistics";
    container avg-hello-process-time {
      description
        "Average hello process time";
      uses ISIS-SH-TIMESTAMP-TYPE;
    }
    container avg-csnp-process-time {
      description
        "Average CSNP process time";
      uses ISIS-SH-TIMESTAMP-TYPE;
    }
    container avg-psnp-process-time {
      description
        "Average PSNP process time";
      uses ISIS-SH-TIMESTAMP-TYPE;
    }
    container avg-lsp-process-time {
      description
        "Average LSP process time";
      uses ISIS-SH-TIMESTAMP-TYPE;
    }
    container avg-hello-transmit-time {
      description
        "Average hello transmit time";
      uses ISIS-SH-TIMESTAMP-TYPE;
    }
    container avg-csnp-transmit-time {
      description
        "Average CSNP transmit time";
      uses ISIS-SH-TIMESTAMP-TYPE;
    }
    container avg-psnp-transmit-time {
      description
        "Average PSNP transmit time";
      uses ISIS-SH-TIMESTAMP-TYPE;
    }
    container avg-lsp-transmit-time {
      description
        "Average LSP transmit time";
      uses ISIS-SH-TIMESTAMP-TYPE;
    }
    leaf fast-psnp-lookup-count {
      type uint32;
      description
        "Fast-PSNP cache lookups";
    }
    leaf fast-psnp-lookup-hit-count {
      type uint32;
      description
        "Fast-PSNP cache hits";
    }
    leaf fast-csnp-lookup-count {
      type uint32;
      description
        "Fast-CSNP cache lookups";
    }
    leaf fast-csnp-lookup-hit-count {
      type uint32;
      description
        "Fast-CSNP cache hits";
    }
    leaf fast-csnp-cache-update-count {
      type uint32;
      description
        "Fast-CSNP cache updates";
    }
    leaf zero-holdtime-lsp-count {
      type uint32;
      description
        "LSPs received with holdtime 0";
    }
    leaf invalid-checksum-lsp-count {
      type uint32;
      description
        "LSPs received with invalid checksum";
    }
    leaf iih-dropped-count {
      type uint32;
      description
        "IIHs dropped - Not Used";
    }
    leaf lsp-dropped-count {
      type uint32;
      description
        "LSPs dropped";
    }
    leaf snp-dropped-count {
      type uint32;
      description
        "SNPs dropped";
    }
    leaf maximum-iih-queue-length {
      type uint32;
      description
        "Maximum IIH queue length - Not Used";
    }
    leaf maximum-pdu-queue-length {
      type uint32;
      description
        "Maximum update PDU queue length";
    }
    leaf pdu-queue-length {
      type uint32;
      description
        "Update PDU queue length";
    }
    leaf avg-hello-recv-rate {
      type uint32;
      units "packet/s";
      description
        "Average hello receive rate in packets per second";
    }
    leaf avg-csnp-recv-rate {
      type uint32;
      units "packet/s";
      description
        "Average csnp receive rate in packets per second";
    }
    leaf avg-psnp-recv-rate {
      type uint32;
      units "packet/s";
      description
        "Average psnp receive rate in packets per second";
    }
    leaf avg-lsp-recv-rate {
      type uint32;
      units "packet/s";
      description
        "Average LSP receive rate in packets per second";
    }
    leaf avg-hello-send-rate {
      type uint32;
      units "packet/s";
      description
        "Average hello send rate in packets per second";
    }
    leaf avg-csnp-send-rate {
      type uint32;
      units "packet/s";
      description
        "Average csnp send rate in packets per second";
    }
    leaf avg-psnp-send-rate {
      type uint32;
      units "packet/s";
      description
        "Average psnp send rate in packets per second";
    }
    leaf avg-lsp-send-rate {
      type uint32;
      units "packet/s";
      description
        "Average LSP send rate in packets per second";
    }
  }

  grouping ISIS-SH-TRAFFIC-GLOBAL {
    description
      "IS-IS process traffic data";
    container statistics {
      description
        "Statistics";
      uses ISIS-TRAFFIC-GLOBAL-TYPE;
    }
    list per-area-data {
      description
        "Per-area data";
      uses ISIS-SH-TRAFFIC-AREA;
    }
  }

  grouping ISIS-SH-HOST {
    description
      "Bag representing a host (IS)";
    leaf local-is-flag {
      type boolean;
      description
        "TRUE if this is the local IS";
    }
    leaf host-levels {
      type Isis-levels;
      description
        "Host levels";
    }
    leaf host-name {
      type string;
      description
        "Host name";
    }
  }

  grouping ISIS-IPV6-ENDX-SID-BACKUP-INFO {
    description
      "IPv6 End.X SID backup information";
    leaf backup-stack-size {
      type uint8;
      description
        "Number of SIDs in the backup path stack";
    }
    leaf backup-node-address {
      type Isis-ipv6-address;
      description
        "Neighbor address used as adjacency backup target";
    }
    leaf backup-nexthop {
      type Isis-ipv6-address;
      description
        "Backup path nexthop address";
    }
    leaf backup-interface {
      type xr:Interface-name;
      description
        "Backup path interface";
    }
    list backup-stack {
      description
        "Backup path SID stack";
      uses ISIS-IPV6-PREFIX-TYPE;
    }
  }

  grouping ISIS-IPV6-PREFIX-TYPE {
    description
      "IPv4 address and prefix length";
    leaf prefix {
      type Isis-ipv6-address;
      description
        "prefix";
    }
    leaf prefix-length {
      type Isis-ip-prefix-length;
      description
        "prefix length";
    }
  }

  grouping ISIS-IPV6-ENDX-SID {
    description
      "IPv6 End.X SID";
    container end-xsid {
      description
        "End.X SID value";
      uses ISIS-IPV6-PREFIX-TYPE;
    }
    container end-xsid-backup {
      description
        "End.X SID Backup Info";
      uses ISIS-IPV6-ENDX-SID-BACKUP-INFO;
    }
    leaf end-xsid-function {
      type Isis-srv6-endpoint-func;
      description
        "End.X SID Function";
    }
    leaf algorithm {
      type uint32;
      description
        "End.X SID Algorithm";
    }
    leaf block-length {
      type uint8;
      description
        "Block Length";
    }
    leaf node-length {
      type uint8;
      description
        "Node Length";
    }
    leaf func-length {
      type uint8;
      description
        "Func Length";
    }
    leaf args-length {
      type uint8;
      description
        "Args Length";
    }
  }

  grouping ISIS-SH-ADJ-PER-LOCATOR {
    description
      "IPv6 Adjacency Per-Locator Data";
    container end-xsid {
      description
        "SRv6 End.X SID";
      uses ISIS-IPV6-ENDX-SID;
    }
    container non-frr-end-xsid {
      description
        "SRv6 End.X SID not eligible for FRR protection";
      uses ISIS-IPV6-ENDX-SID;
    }
    leaf algorithm {
      type uint32;
      description
        "Algorithm";
    }
  }

  grouping ISIS-IPV6-ADJ-SID-BACKUP-INFO {
    description
      "IPv6 Adjacency SID backup information";
    leaf backup-label-stack-size {
      type uint8;
      description
        "Number of labels in the backup path label stack";
    }
    leaf backup-node-address {
      type Isis-ipv6-address;
      description
        "Neighbor address used as adjacency backup target";
    }
    leaf backup-nexthop {
      type Isis-ipv6-address;
      description
        "Backup path nexthop address";
    }
    leaf backup-interface {
      type xr:Interface-name;
      description
        "Backup path interface";
    }
    list backup-label-stack {
      description
        "Backup path label stack";
      leaf entry {
        type uint32;
        description
          "Backup path label stack";
      }
    }
  }

  grouping ISIS-IPV6-ADJ-SID {
    description
      "IPv6 Adjacency SID";
    container adjacency-sid-backup {
      description
        "Adjacency SID Backup Info";
      uses ISIS-IPV6-ADJ-SID-BACKUP-INFO;
    }
    container adjacency-sid-backup-te {
      description
        "Adjacency SID Backup Info TE";
      uses ISIS-IPV6-ADJ-SID-BACKUP-INFO;
    }
    leaf adjacency-sid-value {
      type Isis-nodal-sid-value;
      description
        "Adjacency SID value";
    }
  }

  grouping ISIS-SH-ADJ-IPV6 {
    description
      "IPv6 Specific Per-Adjacency Data";
    container adjacency-sid {
      description
        "Adjacency SID";
      uses ISIS-IPV6-ADJ-SID;
    }
    container non-frr-adjacency-sid {
      description
        "Adjacency SID not eligible for FRR protection";
      uses ISIS-IPV6-ADJ-SID;
    }
    leaf next-hop {
      type Isis-ipv6-address;
      description
        "Adjacency next hop";
    }
    list interface-address {
      description
        "Adjacency interface addresses";
      leaf entry {
        type Isis-ipv6-address;
        description
          "Adjacency interface addresses";
      }
    }
    list underlying-adjacency-sid {
      description
        "Per bundle member Adjacency sid";
      leaf entry {
        type Isis-nodal-sid-value;
        description
          "Per bundle member Adjacency sid";
      }
    }
    list underlying-interface {
      description
        "Underlying interface list for bundle interfaces";
      uses ISIS-SH-INTF-DET;
    }
    list end-xsid {
      description
        "Per Locator ENDX SID";
      uses ISIS-SH-ADJ-PER-LOCATOR;
    }
  }

  grouping ISIS-SH-INTF-DET {
    description
      "Interface Detail";
    leaf interface-index {
      type uint32;
      description
        "Local interface handle";
    }
    leaf interface-name {
      type string;
      description
        "Interface name";
    }
  }

  grouping ISIS-IPV4-ADJ-SID-BACKUP-INFO {
    description
      "IPv4 Adjacency SID backup information";
    leaf backup-label-stack-size {
      type uint8;
      description
        "Number of labels in the backup path label stack";
    }
    leaf backup-node-address {
      type Isis-ipv4-address;
      description
        "Neighbor address used as adjacency backup target";
    }
    leaf backup-nexthop {
      type Isis-ipv4-address;
      description
        "Backup path nexthop address";
    }
    leaf backup-interface {
      type xr:Interface-name;
      description
        "Backup path interface";
    }
    list backup-label-stack {
      description
        "Backup path label stack";
      leaf entry {
        type uint32;
        description
          "Backup path label stack";
      }
    }
  }

  grouping ISIS-IPV4-ADJ-SID {
    description
      "IPv4 Adjacency SID";
    container adjacency-sid-backup {
      description
        "Adjacency SID Backup Info";
      uses ISIS-IPV4-ADJ-SID-BACKUP-INFO;
    }
    container adjacency-sid-backup-te {
      description
        "Adjacency SID Backup Info TE";
      uses ISIS-IPV4-ADJ-SID-BACKUP-INFO;
    }
    leaf adjacency-sid-value {
      type Isis-nodal-sid-value;
      description
        "Adjacency SID value";
    }
  }

  grouping ISIS-SH-ADJ-IPV4 {
    description
      "IPv4 Specific Per-Adjacency Data";
    container adjacency-sid {
      description
        "Adjacency SID";
      uses ISIS-IPV4-ADJ-SID;
    }
    container non-frr-adjacency-sid {
      description
        "Adjacency SID not eligible for FRR protection";
      uses ISIS-IPV4-ADJ-SID;
    }
    leaf next-hop {
      type Isis-ipv4-address;
      description
        "Adjacency next hop";
    }
    list interface-address {
      description
        "Adjacency interface addresses";
      leaf entry {
        type Isis-ipv4-address;
        description
          "Adjacency interface addresses";
      }
    }
    list underlying-adjacency-sid {
      description
        "Per bundle member Adjacency sid";
      leaf entry {
        type Isis-nodal-sid-value;
        description
          "Per bundle member Adjacency sid";
      }
    }
    list underlying-interface {
      description
        "Underlying interface list for bundle interfaces";
      uses ISIS-SH-INTF-DET;
    }
  }

  grouping ISIS-SH-ADJ-AF {
    description
      "ISIS SH ADJ AF";
    container ipv4 {
      when "../af-name = 'ipv4'" {
        description
          "../AFName = 'IPv4'";
      }
      description
        "IPV4 neighbor info";
      uses ISIS-SH-ADJ-IPV4;
    }
    container ipv6 {
      when "../af-name = 'ipv6'" {
        description
          "../AFName = 'IPv6'";
      }
      description
        "IPV6 neighbor info";
      uses ISIS-SH-ADJ-IPV6;
    }
    leaf af-name {
      type Isis-af-id;
      description
        "AFName";
    }
  }

  grouping ISIS-TOPO-ID-TYPE {
    description
      "Identification of an IS-IS topology";
    leaf af-name {
      type Isis-af-id;
      description
        "AF name";
    }
    leaf saf-name {
      type Isis-sub-af-id;
      description
        "Sub-AF name";
    }
    leaf vrf-name {
      type string;
      description
        "VRF Name";
    }
    leaf topology-name {
      type string;
      description
        "Topology Name";
    }
  }

  grouping ISIS-SH-NBR {
    description
      "A neighbor IS";
    leaf neighbor-system-id {
      type xr:Osi-system-id;
      description
        "Neighbor system ID";
    }
    leaf neighbor-snpa {
      type xr:Isis-snpa;
      description
        "Neighbor SNPA";
    }
    leaf local-interface {
      type xr:Interface-name;
      description
        "Local interface";
    }
    leaf neighbor-state {
      type Isis-adj-state;
      description
        "Neighbor (adjacency) state";
    }
    leaf neighbor-circuit-type {
      type Isis-levels;
      description
        "Circuit type";
    }
    leaf neighbor-ietf-nsf-capable-flag {
      type uint32;
      description
        "TRUE if neighbor is IETF-NSF capable";
    }
    leaf neighbor-media-type {
      type Isis-media-class;
      description
        "Link media type";
    }
    leaf neighbor-holdtime {
      type uint32;
      description
        "Time (s) until neighbor declared down if no IIH
         received";
    }
    leaf neighbor-uptime-valid-flag {
      type boolean;
      description
        "TRUE if NeighborUptime is set";
    }
    leaf neighbor-uptime {
      type uint32;
      description
        "How long the neighbor has been up (s)";
    }
    leaf nsr-standby {
      type boolean;
      description
        "ISIS NSR STANDBY";
    }
    list neighbor-active-area-address {
      description
        "Active area addresses";
      leaf entry {
        type xr:Osi-area-address;
        description
          "Active area addresses";
      }
    }
    list topologies-supported {
      description
        "Topologies supported by both neighbor and local
         system";
      uses ISIS-TOPO-ID-TYPE;
    }
    list neighbor-per-address-family-data {
      description
        "Per address-family data";
      uses ISIS-SH-ADJ-AF;
    }
  }
}
