module Cisco-IOS-XR-clns-isis-oper {
  namespace "http://cisco.com/ns/yang/Cisco-IOS-XR-clns-isis-oper";
  prefix clns-isis-oper;

  import ietf-inet-types {
    prefix inet;
  }
  import Cisco-IOS-XR-types {
    prefix xr;
  }
  import cisco-semver {
    prefix semver;
  }
  import Cisco-IOS-XR-clns-isis-datatypes {
    prefix dt1;
  }
  include Cisco-IOS-XR-clns-isis-oper-sub2 {
    revision-date 2020-05-12;
  }
  include Cisco-IOS-XR-clns-isis-oper-sub1 {
    revision-date 2020-05-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clns-isis package operational data.
     
     This module contains definitions
     for the following management objects:
       isis: IS-IS operational data
     
     Copyright (c) 2013-2020 by Cisco Systems, Inc.
     All rights reserved.";

  revision 2020-05-12 {
    description
      "Added SRLG and SRLG Static
       2020-03-25
         Added operational data for new features.";
    semver:module-version "3.0.0";
  }
  revision 2019-09-25 {
    description
      "Added operational data for new features
       2019-05-14
       Conditional Advertise-prefix support
       2019-05-03
       move ocni-isis opencfg model from native model to private oper model";
    semver:module-version "2.0.0";
  }
  revision 2019-04-05 {
    description
      "Establish semantic version baseline.";
    semver:module-version "1.0.0";
  }
  revision 2019-03-28 {
    description
      "Upgrade ocni-isis to opencfg model version 0.4.2";
  }
  revision 2019-02-23 {
    description
      "Added is_srv6 flag to ISIS IPv6 route";
  }
  revision 2019-02-16 {
    description
      "Added interface link-group name";
  }
  revision 2018-10-15 {
    description
      "Add SRv6 configured locators";
  }
  revision 2018-10-04 {
    description
      "Update SRv6 locator table";
  }
  revision 2018-05-17 {
    description
      "Update opencfg isis model";
  }
  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  grouping POLICY-MI {
    description
      "Common node of policy-ipv4-active,
       policy-ipv4-backup, policy-ipv6-active,
       policy-ipv6-backup";
    list policy-mi {
      key "mi-id";
      description
        "Mapping Item";
      leaf mi-id {
        type xr:Cisco-ios-xr-string;
        description
          "Mapping Item ID (0, 1, 2, ...)";
      }
      uses SRMS-MI-T-B;
    }
  }

  grouping INSTANCE {
    description
      "Common node of instances, instances-standby";
    list instance {
      key "instance-name";
      description
        "IS-IS instance";
      container neighbors {
        description
          "Neighbor table";
        list neighbor {
          description
            "A single neighbor router";
          leaf system-id {
            type xr:Osi-system-id;
            description
              "System ID";
          }
          leaf interface-name {
            type xr:Interface-name;
            description
              "Interface name";
          }
          uses ISIS-SH-NBR;
        }
      }
      container host-names {
        description
          "Hostname table";
        list host-name {
          key "system-id";
          description
            "Hostname table entry";
          leaf system-id {
            type xr:Osi-system-id;
            description
              "System ID";
          }
          uses ISIS-SH-HOST;
        }
      }
      container statistics-global {
        description
          "Per-instance statistics";
        uses ISIS-SH-TRAFFIC-GLOBAL;
      }
      container levels {
        description
          "Level table";
        list level {
          key "level";
          description
            "Per-level operational data";
          container adjacency-log {
            description
              "Log of adjacency changes within a single
               level";
            uses ISIS-SH-ADJ-LOG-STRUC;
          }
          container lsp-table-summary {
            description
              "Summary information for one level's LSP
               database";
            uses ISIS-SH-LSP-DB-SUMMARY;
          }
          container adjacencies {
            description
              "Adjacency table";
            list adjacency {
              description
                "A single IS-IS adjacency";
              leaf system-id {
                type xr:Osi-system-id;
                description
                  "System ID";
              }
              leaf interface-name {
                type xr:Interface-name;
                description
                  "Interface name";
              }
              uses ISIS-SH-ADJ;
            }
          }
          container detailed-lsps {
            description
              "Detailed LSP table. Use to retrieve LSPs with
               TLV content.";
            list detailed-lsp {
              key "lsp-id";
              description
                "An IS-IS LSP with detailed TLV data included";
              leaf lsp-id {
                type xr:Isis-lsp-id;
                description
                  "LSP ID";
              }
              uses ISIS-SH-LSP;
            }
          }
          container lsps {
            description
              "LSP table";
            list lsp {
              key "lsp-id";
              description
                "An IS-IS LSP (header information only)";
              leaf lsp-id {
                type xr:Isis-lsp-id;
                description
                  "LSP ID";
              }
              uses ISIS-SH-LSP;
            }
          }
          container lsp-log {
            description
              "LSP-log for a single level";
            uses ISIS-SH-LSP-LOG-STRUC;
          }
          container database-log {
            description
              "Database-log for a single level";
            uses ISIS-SH-LSP-DB-LOG-STRUC;
          }
          leaf level {
            type dt1:Isis-internal-level;
            description
              "Level";
          }
        }
      }
      container topologies {
        description
          "Topology table";
        list topology {
          description
            "Per-topology data";
          container ipv4frr-flex-tables {
            description
              "IPv4 FRR Flex-Algo tables";
            list ipv4frr-flex-table {
              key "flex-alg";
              description
                "IPv4 FRR Flex-Algo table";
              leaf flex-alg {
                type uint32;
                description
                  "Flex Algo";
              }
              list ipv4frr-flex-backup {
                description
                  "Flex-Algo FRR backup for an IPv4 network";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
          }
          container ipv6-flex-route-tables {
            description
              "IPv6 Flex-Algo local route tables";
            list ipv6-flex-route-table {
              key "flex-alg";
              description
                "IPv6 Flex-Algo local route table";
              leaf flex-alg {
                type uint32;
                description
                  "Flex Algo";
              }
              list ipv6-flex-route {
                description
                  "An IPv6 route known to IS-IS";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
          }
          container frr-summary {
            description
              "FRR summary information for a particular
               IS-IS topology";
            uses ISIS-SH-FRR-SUMMARY;
          }
          container srv6-locators {
            description
              "SRv6 Locator Table";
            list srv6-locator {
              key "name";
              description
                "An SRv6 Locator";
              leaf name {
                type xr:Cisco-ios-xr-string;
                description
                  "Locator Name";
              }
              uses ISIS-SH-SRV6-LOCATOR;
            }
          }
          container topology-levels {
            description
              "Per-topology level table";
            list topology-level {
              key "level";
              description
                "Per-level topology operational data";
              container te-advertisements {
                description
                  "TE advertisements for a single level and
                   topology. Only available within the IPv4
                   Unicast topology.";
                uses ISIS-SH-TE-ADV;
              }
              container te-adjacency-log {
                description
                  "TE adjacency-log for a single level and
                   topology. Only available within the IPv4
                   Unicast topology.";
                uses ISIS-SH-TE-LOG-STRUC;
              }
              container spf-log {
                description
                  "Log of route calculations for a single
                   level and topology";
                uses ISIS-SH-SPF-LOG-STRUC;
              }
              container te-tunnels {
                description
                  "TE tunnels table. Only available within the
                   IPv4 Unicast topology.";
                list te-tunnel {
                  description
                    "A single TE tunnel advertized by IS-IS";
                  leaf system-id {
                    type xr:Osi-system-id;
                    description
                      "System ID";
                  }
                  leaf interface-name {
                    type xr:Interface-name;
                    description
                      "Interface name";
                  }
                  uses ISIS-SH-TE-TUNNEL;
                }
              }
              container ipv4-link-topologies {
                description
                  "IPv4 IS Topology table";
                list ipv4-link-topology {
                  key "system-id";
                  description
                    "An IS in an IPv4 Link Topology";
                  leaf system-id {
                    type xr:Osi-system-id;
                    description
                      "System ID";
                  }
                  uses ISIS-SH-IPV4-TOPO-ENTRY;
                }
              }
              container topology-summary {
                description
                  "Summary information for a particular IS
                   Topology";
                uses ISIS-SH-TOPO-SUMMARY;
              }
              container ipv6-link-topologies {
                description
                  "IPv6 IS Topology table";
                list ipv6-link-topology {
                  key "system-id";
                  description
                    "An IS in an IPv6 Link Topology";
                  leaf system-id {
                    type xr:Osi-system-id;
                    description
                      "System ID";
                  }
                  uses ISIS-SH-IPV6-TOPO-ENTRY;
                }
              }
              leaf level {
                type dt1:Isis-internal-level;
                description
                  "Level";
              }
            }
          }
          container ipv6-routes {
            description
              "IPv6 local route";
            list ipv6-route {
              description
                "An IPv6 route known to IS-IS";
              leaf prefix {
                type inet:ipv6-address-no-zone;
                description
                  "Prefix";
              }
              leaf prefix-length {
                type dt1:Isis-ipv6-prefix-length;
                description
                  "Prefix Length";
              }
              uses ISIS-SH-IPV6-ROUTE;
            }
          }
          container ipv6frr-flex-tables {
            description
              "IPv6 FRR Flex-Algo tables";
            list ipv6frr-flex-table {
              key "flex-alg";
              description
                "IPv6 FRR Flex-Algo table";
              leaf flex-alg {
                type uint32;
                description
                  "Flex Algo";
              }
              list ipv6frr-flex-backup {
                description
                  "Flex-algo FRR backup for an IPv6 network";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
          }
          container ipv6frr-backups {
            description
              "IPv6 FRR table";
            list ipv6frr-backup {
              description
                "FRR backup for an IPv6 network";
              leaf prefix {
                type inet:ipv6-address-no-zone;
                description
                  "Prefix";
              }
              leaf prefix-length {
                type dt1:Isis-ipv6-prefix-length;
                description
                  "Prefix Length";
              }
              uses ISIS-SH-IPV6-ROUTE;
            }
          }
          container ipv4frr-backups {
            description
              "IPv4 FRR table";
            list ipv4frr-backup {
              description
                "FRR backup for an IPv4 network";
              leaf prefix {
                type inet:ipv4-address-no-zone;
                description
                  "Prefix";
              }
              leaf prefix-length {
                type dt1:Isis-ipv4-prefix-length;
                description
                  "Prefix Length";
              }
              uses ISIS-SH-IPV4-ROUTE;
            }
          }
          container ipv4-flex-route-tables {
            description
              "IPv4 Flex-Algo local route tables";
            list ipv4-flex-route-table {
              key "flex-alg";
              description
                "IPv4 Flex-Algo local route table";
              leaf flex-alg {
                type uint32;
                description
                  "Flex Algo";
              }
              list ipv4-flex-route {
                description
                  "An IPv4 route known to IS-IS";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
          }
          container ipv4-routes {
            description
              "IPv4 local route table";
            list ipv4-route {
              description
                "An IPv4 route known to IS-IS";
              leaf prefix {
                type inet:ipv4-address-no-zone;
                description
                  "Prefix";
              }
              leaf prefix-length {
                type dt1:Isis-ipv4-prefix-length;
                description
                  "Prefix Length";
              }
              uses ISIS-SH-IPV4-ROUTE;
            }
          }
          leaf af-name {
            type dt1:Isis-address-family;
            description
              "Address family";
          }
          leaf saf-name {
            type dt1:Isis-sub-address-family;
            description
              "Sub address family";
          }
          leaf topology-name {
            type dt1:Isis-topology-name;
            description
              "Topology Name";
          }
        }
      }
      container srlgs {
        description
          "SRLG Table";
        list srlg {
          key "srlg-name";
          description
            "SRLG Data";
          leaf srlg-name {
            type xr:Cisco-ios-xr-string;
            description
              "srlg name";
          }
          uses ISIS-SH-SRLG;
        }
      }
      container nsr-status {
        description
          "NSR Status information";
        uses ISIS-SH-NSR-STATUS-GLOBAL;
      }
      container srlg-statics {
        description
          "SRLG Static Table";
        list srlg-static {
          key "srlg-name";
          description
            "SRLG Static Data";
          leaf srlg-name {
            type xr:Cisco-ios-xr-string;
            description
              "srlg name";
          }
          uses ISIS-SH-SRLG-STATIC;
        }
      }
      container interfaces {
        description
          "Interface table";
        list interface {
          key "interface-name";
          description
            "Information about one IS-IS interface";
          leaf interface-name {
            type xr:Interface-name;
            description
              "Interface name";
          }
          uses ISIS-SH-IF;
        }
      }
      container checkpoint-adjacencies {
        description
          "Checkpointed adjacency table";
        list checkpoint-adjacency {
          description
            "A checkpointed IS-IS adjacency";
          leaf level {
            type dt1:Isis-internal-level;
            description
              "Level";
          }
          leaf system-id {
            type xr:Osi-system-id;
            description
              "System ID";
          }
          leaf interface-name {
            type xr:Interface-name;
            description
              "Interface name";
          }
          uses ISIS-SH-CHKPT-ADJ;
        }
      }
      container flex-algos {
        description
          "Flex Algo Table";
        list flex-algo {
          key "flex-algo";
          description
            "Flex Algo Definition Data";
          leaf flex-algo {
            type uint32;
            description
              "Flex Algo";
          }
          uses ISIS-SH-FLEX-ALGO;
        }
      }
      container srms {
        description
          "Segment Routing Mapping Server operational data";
        container policy {
          description
            "Policy operational data";
          container policy-ipv4 {
            description
              "IPv4 policy operational data";
            container policy-ipv4-active {
              description
                "IPv4 active policy operational data";
              uses POLICY-MI;
            }
            container policy-ipv4-backup {
              description
                "IPv4 backup policy operational data";
              uses POLICY-MI;
            }
          }
          container policy-ipv6 {
            description
              "IPv6 policy operational data";
            container policy-ipv6-backup {
              description
                "IPv6 backup policy operational data";
              uses POLICY-MI;
            }
            container policy-ipv6-active {
              description
                "IPv6 active policy operational data";
              uses POLICY-MI;
            }
          }
        }
      }
      container mib {
        description
          "IS-IS MIB";
        container circuit-counter-table-entries {
          description
            "Circuit specific counters for the system";
          list circuit-counter-table-entry {
            key "circ-index circuit-type";
            description
              "Each circuit has a circuit counter table
               entry";
            leaf circ-index {
              type uint32;
              description
                "Circuit Index";
            }
            leaf circuit-type {
              type dt1:Isis-circuit;
              description
                "Circuit Type";
            }
            uses ISIS-MIB-CIRCUIT-COUNTER-ENTRY;
          }
        }
        container area-addr-table {
          description
            "area addresses table";
          uses ISIS-MIB-AREA-ADDR-TABLE;
        }
        container packet-counter-table-entries {
          description
            "Info about IS-IS protocol traffic on a circuit";
          list packet-counter-table-entry {
            key "circ-index level packet-count-direction";
            description
              "Info about IS-IS protocol traffic on one
               level";
            leaf circ-index {
              type uint32;
              description
                "Circuit Index";
            }
            leaf level {
              type dt1:Isis-internal-level;
              description
                "Level";
            }
            leaf packet-count-direction {
              type dt1:Isis-packet-count-direction;
              description
                "Direction";
            }
            uses ISIS-MIB-PACKET-COUNTER-ENTRY;
          }
        }
        container mib-levels {
          description
            "MIB Level table";
          list mib-level {
            key "level";
            description
              "Per-level operational data";
            container sys-level-table {
              description
                "Level specific info about the system";
              uses ISIS-MIB-SYS-LEVEL-ENTRY;
            }
            container system-counter-table {
              description
                "Systemwide counters for this system";
              uses ISIS-MIB-SYS-STAT-LEVEL-ENTRY;
            }
            container lsp-summary-entries {
              description
                "Table of LSP headers";
              list lsp-summary-entry {
                key "lsp-id";
                description
                  "Summary description of an LSP stored in
                   this system";
                leaf lsp-id {
                  type xr:Isis-lsp-id;
                  description
                    "LSP ID";
                }
                uses ISIS-MIB-LSP-SUMMARY-LIST-ENTRY;
              }
            }
            container lsptlv-entries {
              description
                "Table of LSPs in the database";
              list lsptlv-entry {
                description
                  "Each entry describes a TLV within an LSP in
                   the database";
                leaf lsp-id {
                  type string;
                  description
                    "LSP ID";
                }
                leaf tlv-index {
                  type uint32;
                  description
                    "TLV Index";
                }
                uses ISIS-MIB-YANG-MODEL-LSP-ENTRY;
              }
            }
            leaf level {
              type dt1:Isis-internal-level;
              description
                "Level";
            }
          }
        }
        container redistribute-addr-table {
          description
            "redistributed prefix table";
          uses ISIS-MIB-IP-RA-TABLE;
        }
        container man-area-addr-table {
          description
            "Manually configured area addresses table";
          uses ISIS-MIB-AREA-ADDR-TABLE;
        }
        container circ-level-table-entries {
          description
            "Level specific info about circuits used by the
             system";
          list circ-level-table-entry {
            key "circ-index level";
            description
              "circuit for specific level on the system";
            leaf circ-index {
              type uint32;
              description
                "Circuit Index";
            }
            leaf level {
              type dt1:Isis-internal-level;
              description
                "Level";
            }
            uses ISIS-MIB-CIRC-LEVEL-ENTRY;
          }
        }
        container is-adj-table-entries {
          description
            "Intermediate System adjacencies table";
          list is-adj-table-entry {
            key "circ-index is-adj-index";
            description
              "Each adjacency has an adjacency table entry";
            leaf circ-index {
              type uint32;
              description
                "Circuit Index";
            }
            leaf is-adj-index {
              type uint32;
              description
                "IS Adj Index";
            }
            uses ISIS-MIB-CIRC-ADJ-TABLE;
          }
        }
        container summ-addr-table {
          description
            "IP summary address table";
          uses ISIS-MIB-SUMM-ADDR-TABLE;
        }
        container sysobjs {
          description
            "Mib system objects";
          uses ISIS-MIB-SYS-OBJECT;
        }
        container circ-table-entries {
          description
            "Circuit table";
          list circ-table-entry {
            key "circ-index";
            description
              "Circuit table entry";
            leaf circ-index {
              type uint32;
              description
                "Circuit Index";
            }
            uses ISIS-MIB-CIRC-ENTRY;
          }
        }
      }
      container error-log {
        description
          "Log of errors and warnings";
        uses ISIS-SH-ERR-LOG-STRUC;
      }
      container checkpoint-interfaces {
        description
          "Checkpointed interface table";
        list checkpoint-interface {
          key "interface-name";
          description
            "Checkpointed information about one IS-IS
             interface";
          leaf interface-name {
            type xr:Interface-name;
            description
              "Interface name";
          }
          uses ISIS-SH-CHKPT-IDB;
        }
      }
      container sr-labels {
        description
          "SR Label table";
        list sr-label {
          key "label";
          description
            "SrLabel table entry";
          leaf label {
            type uint32;
            description
              "SR Label";
          }
          uses ISIS-SH-LABEL;
        }
      }
      container interface-statistics {
        description
          "Interface statistics table";
        list interface-statistic {
          key "interface-name";
          description
            "Statistics data for one IS-IS interface";
          leaf interface-name {
            type xr:Interface-name;
            description
              "Interface name";
          }
          uses ISIS-SH-TRAFFIC-INTF;
        }
      }
      container protocol {
        description
          "Basic protocol information about an IS-IS
           instance";
        uses ISIS-SH-PROTO;
      }
      container neighbor-summaries {
        description
          "Neighbor-summary table";
        list neighbor-summary {
          key "interface-name";
          description
            "Neighbor-summary data for a single interface";
          leaf interface-name {
            type xr:Interface-name;
            description
              "Interface name";
          }
          uses ISIS-SH-NBR-SUMM;
        }
      }
      container checkpoint-lsps {
        description
          "Checkpointed LSP table";
        list checkpoint-lsp {
          description
            "A checkpointed IS-IS LSP";
          leaf level {
            type dt1:Isis-internal-level;
            description
              "Level";
          }
          leaf lsp-id {
            type xr:Isis-lsp-id;
            description
              "LSP ID";
          }
          uses ISIS-SH-CHKPT-LSP;
        }
      }
      container mesh-groups {
        description
          "Mesh-group information";
        uses ISIS-SH-MESH-GROUPS;
      }
      container nsr-statistics {
        description
          "NSR Statistics information";
        uses ISIS-SH-NSR-STATS-GLOBAL;
      }
      container checkpoint-te-tunnels {
        description
          "Checkpointed TE tunnel table";
        list checkpoint-te-tunnel {
          description
            "A checkpointed TE tunnel";
          leaf level {
            type dt1:Isis-internal-level;
            description
              "Level";
          }
          leaf interface-name {
            type xr:Interface-name;
            description
              "Interface name";
          }
          uses ISIS-SH-CHKPT-TE-TUNNEL;
        }
      }
      leaf instance-name {
        type dt1:Isis-instance-name;
        description
          "Instance identifier";
      }
    }
  }

  container isis {
    config false;
    description
      "IS-IS operational data";
    container instances {
      description
        "Per-instance active ISIS operational data";
      uses INSTANCE;
    }
    container instances-standby {
      description
        "Standby ISIS operational data";
      uses INSTANCE;
    }
  }
}
