module Cisco-IOS-XR-um-netconf-yang-cfg {
  namespace "http://cisco.com/ns/yang/Cisco-IOS-XR-um-netconf-yang-cfg";
  prefix um-netconf-yang-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR netconf-yang package configuration.
     
     This YANG module augments the
     modules with configuration data.
     
     Copyright (c) 2019-2020 by Cisco Systems, Inc.
     All rights reserved.";

  revision 2020-03-06 {
    description
      "- Removed models/openconfig/disable as the config has been deprecated.
       - Added a new container to enable with-defaults support.";
    semver:module-version "2.0.0";
  }
  revision 2019-06-10 {
    description
      "Establish semantic version baseline.";
    semver:module-version "1.0.1";
  }
  revision 2019-03-30 {
    description
      "Initial version";
  }

  container netconf-yang {
    description
      "NETCONF YANG configuration commands";
    container agent {
      description
        "NETCONF YANG agent configuration commands";
      container ssh {
        presence "Indicates a ssh node is configured.";
        description
          "Enable NETCONF-YANG agent over SSH connection";
      }
      container with-defaults-support {
        description
          "with-defaults support enabled";
        container enable {
          presence "Indicates a enable node is configured.";
          description
            "Enable with-defaults support";
        }
      }
      leaf rate-limit {
        type uint32 {
          range "4096..4294967295" {
            description
              "Number of bytes to process per sec";
          }
        }
        description
          "Rate limit";
      }
      container session {
        description
          "Session settings";
        leaf limit {
          type uint32 {
            range "1..50" {
              description
                "Count of allowable concurrent netconf-yang sessions (default = 50)";
            }
          }
          description
            "Maximum count of concurrent sessions (default = 50)";
        }
        leaf idle-timeout {
          type uint32 {
            range "1..1440" {
              description
                "Idle timeout in minutes";
            }
          }
          description
            "Non-active session lifetime";
        }
        leaf absolute-timeout {
          type uint32 {
            range "1..1440" {
              description
                "Absolute timeout in minutes";
            }
          }
          description
            "Absolute session lifetime";
        }
      }
    }
  }
}
