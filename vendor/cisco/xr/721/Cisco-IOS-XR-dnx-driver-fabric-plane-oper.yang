module Cisco-IOS-XR-dnx-driver-fabric-plane-oper {
  namespace "http://cisco.com/ns/yang/Cisco-IOS-XR-dnx-driver-fabric-plane-oper";
  prefix dnx-driver-fabric-plane-oper;

  import cisco-semver {
    prefix semver;
  }
  include Cisco-IOS-XR-dnx-driver-fabric-plane-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dnx-driver-fabric-plane package operational data.
     
     This module contains definitions
     for the following management objects:
       fabric: Admin fabric oper data
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  container fabric {
    config false;
    description
      "Admin fabric oper data";
    container plane-table {
      description
        "Plane state table for Fabric ";
      container statistics {
        description
          "Show Calvados Plane Statistics";
        uses FSDBB-PLANE-STATS-INFO-XML;
      }
      container plane {
        description
          "Show Calvados Plane State";
        uses FSDBB-PLANE-INFO-XML;
      }
    }
  }
}
