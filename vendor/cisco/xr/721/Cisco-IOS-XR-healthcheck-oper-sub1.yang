submodule Cisco-IOS-XR-healthcheck-oper-sub1 {
  belongs-to Cisco-IOS-XR-healthcheck-oper {
    prefix Cisco-IOS-XR-healthcheck-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR healthcheck package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping HCMGR-INFRA-SRV {
    description
      "Healthcheck infra service metrics";
    leaf metric-name {
      type string;
      description
        "Metric Name";
    }
  }

  grouping HCMGR-METRIC-THLD {
    description
      "Metric thresholds";
    leaf minor {
      type uint32;
      description
        "Minor threshold";
    }
    leaf severe {
      type uint32;
      description
        "Severe threshold";
    }
    leaf critical {
      type uint32;
      description
        "Critical threshold";
    }
  }

  grouping HCMGR-SYS-RES {
    description
      "Healthcheck system resource metrics";
    container threshold {
      description
        "Metric threshold";
      uses HCMGR-METRIC-THLD;
    }
    leaf metric-name {
      type string;
      description
        "Metric name";
    }
  }

  grouping HCMGR-STATUS-DATA {
    description
      "Healthcheck Status data";
    leaf collector-pid {
      type int32;
      description
        "Healthcheck collector pid";
    }
    leaf collector-cadence {
      type string;
      description
        "Healthcheck collector cadence";
    }
    leaf service-status {
      type string;
      description
        "Healthcheck service status";
    }
    leaf time-started {
      type string;
      description
        "Healthcheck enabled time";
    }
    leaf time-stopped {
      type string;
      description
        "Healthcheck disabled time";
    }
    leaf cpu-avg-util {
      type string;
      description
        "CPU average utilization";
    }
    list sys-resource {
      description
        "System resource metrics";
      uses HCMGR-SYS-RES;
    }
    list infra-service {
      description
        "Infra service metrics";
      uses HCMGR-INFRA-SRV;
    }
  }

  grouping HCMGR-REPORT-METRIC-DATA {
    description
      "Healthcheck report metric data";
    leaf name {
      type string;
      description
        "Metric name";
    }
    leaf service-msg {
      type string;
      description
        "Metric service msg";
    }
    leaf state {
      type string;
      description
        "Metric state";
    }
    leaf health-msg {
      type string;
      description
        "Metric health msg";
    }
  }

  grouping HCMGR-REPORT-DATA {
    description
      "Healthcheck Report data";
    list metric {
      description
        "Metric bags ";
      uses HCMGR-REPORT-METRIC-DATA;
    }
  }
}
