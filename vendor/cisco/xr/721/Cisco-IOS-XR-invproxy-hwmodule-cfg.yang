module Cisco-IOS-XR-invproxy-hwmodule-cfg {
  namespace "http://cisco.com/ns/yang/Cisco-IOS-XR-invproxy-hwmodule-cfg";
  prefix invproxy-hwmodule-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR invproxy-hwmodule package configuration.
     
     This model is deprecated and is replaced by
     Cisco-IOS-XR-hw-module-cfg.yang which will provide the
     compatible functionalities.
     
     This module contains definitions
     for the following management objects:
       hw-module-admin: Hardware module information
     
     Copyright (c) 2013-2020 by Cisco Systems, Inc.
     All rights reserved.";

  revision 2020-03-31 {
    description
      "Deprecated the model, replaced by Cisco-IOS-XR-hw-module-cfg
       2019-12-03
         IOS XR 7.0.12 revision.";
    semver:module-version "1.1.0";
  }
  revision 2019-10-15 {
    description
      "IOS XR 7.0.12 revision.";
    semver:module-version "1.0.1";
  }
  revision 2019-04-05 {
    description
      "Establish semantic version baseline.";
    semver:module-version "1.0.0";
  }
  revision 2015-11-09 {
    description
      "IOS XR 6.0 revision.";
  }

  typedef Admin-power-state {
    type enumeration {
      enum "unshut" {
        value 0;
        description
          "Power On";
      }
      enum "shut" {
        value 1;
        description
          "Power Off";
      }
    }
    description
      "Admin power state";
  }

  container hw-module-admin {
    status deprecated;
    description
      "This model is deprecated and is replaced by
       Cisco-IOS-XR-hw-module-cfg.yang which will
       provide the compatible functionalities.  Hardware
       module information";
    container nodes {
      description
        "List of nodes";
      list node {
        key "location";
        description
          "Node object";
        leaf admin-power-state {
          type Admin-power-state;
          description
            "Set the admin state of the hw-module";
        }
        leaf location {
          type string;
          description
            "hw-module location";
        }
      }
    }
  }
}
