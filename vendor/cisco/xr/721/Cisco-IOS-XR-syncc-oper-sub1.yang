submodule Cisco-IOS-XR-syncc-oper-sub1 {
  belongs-to Cisco-IOS-XR-syncc-oper {
    prefix Cisco-IOS-XR-syncc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR syncc package operational data.
     
     Copyright (c) 2013-2019 by Cisco Systems, Inc.
     All rights reserved.";

  revision 2019-04-05 {
    description
      "Establish semantic version baseline.";
    semver:module-version "1.0.1";
  }
  revision 2016-06-08 {
    description
      "Schema added.";
  }
  revision 2015-11-09 {
    description
      "IOS XR 6.0 revision.";
  }

  typedef Source-state-name {
    type enumeration {
      enum "not-valid" {
        description
          "Invalid";
      }
      enum "unqualified" {
        description
          "Unqualified state";
      }
      enum "available" {
        description
          "Available state";
      }
      enum "failed" {
        description
          "Failed state";
      }
      enum "unmonitored" {
        description
          "Unmonitored state";
      }
      enum "error" {
        description
          "Error state";
      }
    }
    description
      "Syncc source state name";
  }

  typedef Source {
    type enumeration {
      enum "invalid" {
        description
          "Invalid state";
      }
      enum "ethernet-line-interface" {
        description
          "Ethernet interface ";
      }
      enum "sonet-line-interface" {
        description
          "SONET interface ";
      }
      enum "clock-interface" {
        description
          "Clock interface state";
      }
      enum "internal" {
        description
          "Internal state";
      }
      enum "ptp" {
        description
          "PTP";
      }
      enum "satellite-access" {
        description
          "Satellite Access";
      }
      enum "ntp" {
        description
          "NTP";
      }
      enum "gnss-receiver" {
        description
          "Gnss Receiver";
      }
    }
    description
      "Syncc source type";
  }

  typedef Interface-state {
    type enumeration {
      enum "up" {
        description
          "Up state";
      }
      enum "down" {
        description
          "Down state";
      }
      enum "admin-down" {
        description
          "Admin down state";
      }
    }
    description
      "Interface state";
  }

  typedef Ql-option-1 {
    type enumeration {
      enum "quality-level-none" {
        description
          "No value";
      }
      enum "o1" {
        description
          "Option 1";
      }
      enum "o2-g1" {
        description
          "Option 2 Gen 1";
      }
      enum "o2-g2" {
        description
          "Option 2 Gen 2";
      }
    }
    description
      "Quality level options";
  }

  typedef Direct {
    type enumeration {
      enum "receive-transmit" {
        description
          "Receive or transmit";
      }
      enum "transmit" {
        description
          "Transmit";
      }
      enum "receive" {
        description
          "Receive";
      }
    }
    description
      "Direction status";
  }

  typedef Smode2 {
    type enumeration {
      enum "ami-mode" {
        description
          "AMI";
      }
      enum "b8zs" {
        description
          "B8ZS submode";
      }
      enum "hdb3" {
        description
          "HDB3 submode";
      }
      enum "submode2-none" {
        description
          "No mode is selected";
      }
    }
    description
      "Second mode type";
  }

  typedef Smode1 {
    type enumeration {
      enum "extended-super-frame" {
        description
          "Extended Superframe(ESF)";
      }
      enum "d4" {
        description
          "D4 channel unit";
      }
      enum "non-crc4" {
        description
          "Non CRC 4 mode";
      }
      enum "crc4" {
        description
          "CRC 4";
      }
      enum "submode1-none" {
        description
          "No mode is selected";
      }
    }
    description
      "First mode type";
  }

  typedef Clock-modes {
    type enumeration {
      enum "t1" {
        description
          "T1 mode";
      }
      enum "e1" {
        description
          "E1 mode";
      }
      enum "two-m" {
        description
          "2048M mode";
      }
      enum "input64k" {
        description
          "64kCC input";
      }
      enum "output6m" {
        description
          "6312M output";
      }
      enum "uti" {
        description
          "Universal transport interface(UTI)";
      }
      enum "none" {
        description
          "No mode is selected";
      }
    }
    description
      "Different clock modes";
  }

  typedef Node-state {
    type enumeration {
      enum "active" {
        value 1;
        description
          "Node in active mode";
      }
      enum "standby" {
        value 2;
        description
          "Node in standby mode";
      }
    }
    description
      "Different modes of a node";
  }

  typedef Syncc-states {
    type enumeration {
      enum "initializing" {
        description
          "Initial  state";
      }
      enum "running" {
        description
          "Running  state";
      }
      enum "normal" {
        description
          "Normal  state";
      }
      enum "shutdown" {
        description
          "Shutdown  state";
      }
    }
    description
      "Different syncc states";
  }

  grouping SYNCC-TIMING-SOURCE {
    description
      "Controllers timing source status";
    leaf input {
      type uint8;
      description
        "Input number";
    }
    leaf slot {
      type uint8;
      description
        "Slot number";
    }
    leaf port {
      type uint8;
      description
        "Port number";
    }
    leaf clock-source {
      type Source;
      description
        "Status of syncc source type";
    }
    leaf rank {
      type uint8;
      description
        "Rank of sync timing source table";
    }
    leaf quality-level-option {
      type uint8;
      description
        "Quality level option";
    }
    leaf quality-level-value {
      type uint8;
      description
        "Quality level value";
    }
    leaf user-priority {
      type uint8;
      description
        "User priority of sync timing source table";
    }
    leaf clock-state {
      type Source-state-name;
      description
        "Status of clock state";
    }
    leaf is-select {
      type boolean;
      description
        "True if selected";
    }
  }

  grouping SYNCC-TIMING-SRC-TBL1 {
    description
      "Structure containing timing source table";
    list timing-status-t0 {
      max-elements "11";
      description
        "Scheduling PLL T0 ";
      uses SYNCC-TIMING-SOURCE;
    }
    list timing-status-t4 {
      max-elements "11";
      description
        "Scheduling PLL T4 ";
      uses SYNCC-TIMING-SOURCE;
    }
    list timing-status1588 {
      max-elements "11";
      description
        "Scheduling PLL 1588 ";
      uses SYNCC-TIMING-SOURCE;
    }
  }

  grouping SYNCC-TIMING-SRC-TBL {
    description
      "Syncc timing source table information";
    list syncc-instance {
      description
        "List of syncc timing table information";
      uses SYNCC-TIMING-SRC-TBL1;
    }
  }

  grouping SYNCC-CLOCK-SETTING {
    description
      "SYNCC clock information";
    leaf is-configured-port0 {
      type boolean;
      description
        "True if clock is configured for port 0";
    }
    leaf is-configured-port1 {
      type boolean;
      description
        "True if clock is configured for port 1";
    }
    leaf is-configured-port2 {
      type boolean;
      description
        "True if clock is configured for port 2";
    }
    leaf is-configured-port3 {
      type boolean;
      description
        "True if clock is configured for port 3";
    }
    leaf mode-port0 {
      type Clock-modes;
      description
        "Clock setting mode for port 0";
    }
    leaf mode-port1 {
      type Clock-modes;
      description
        "Clock setting mode for port 1";
    }
    leaf mode-port2 {
      type Clock-modes;
      description
        "Clock setting mode for port 2";
    }
    leaf mode-port3 {
      type Clock-modes;
      description
        "Clock setting mode for port 3";
    }
    leaf submode1-port0 {
      type Smode1;
      description
        "First submode for port 0";
    }
    leaf submode1-port1 {
      type Smode1;
      description
        "First submode for port 1";
    }
    leaf submode1-port2 {
      type Smode1;
      description
        "First submode for port 2";
    }
    leaf submode1-port3 {
      type Smode1;
      description
        "First submode for port 3";
    }
    leaf submode2-port0 {
      type Smode2;
      description
        "Second submode for port 0";
    }
    leaf submode2-port1 {
      type Smode2;
      description
        "Second submode for port 1";
    }
    leaf submode2-port2 {
      type Smode2;
      description
        "Second submode for port 2";
    }
    leaf submode2-port3 {
      type Smode2;
      description
        "Second submode for port 3";
    }
    leaf submode3-port0 {
      type uint32;
      description
        "Third submode for port 0";
    }
    leaf submode3-port1 {
      type uint32;
      description
        "Third submode for port 1";
    }
    leaf submode3-port2 {
      type uint32;
      description
        "Third submode for port 2";
    }
    leaf submode3-port3 {
      type uint32;
      description
        "Third submode for port 3";
    }
    leaf shutdown-port0 {
      type uint32;
      description
        "Configure disable value for port 0";
    }
    leaf shutdown-port1 {
      type uint32;
      description
        "Configure disable value for port 1";
    }
    leaf shutdown-port2 {
      type uint32;
      description
        "Configure disable value for port 2";
    }
    leaf shutdown-port3 {
      type uint32;
      description
        "Configure disable value for port 3";
    }
    leaf direction-port0 {
      type Direct;
      description
        "Direction of interface for port 0";
    }
    leaf direction-port1 {
      type Direct;
      description
        "Direction of interface for port 1";
    }
    leaf direction-port2 {
      type Direct;
      description
        "Direction of interface for port 2";
    }
    leaf direction-port3 {
      type Direct;
      description
        "Direction of interface for port 3";
    }
    leaf baudrate-port0 {
      type uint32;
      description
        "Baudrate for port 0";
    }
    leaf baudrate-port1 {
      type uint32;
      description
        "Baudrate for port 1";
    }
    leaf baudrate-port2 {
      type uint32;
      description
        "Baudrate for port 2";
    }
    leaf baudrate-port3 {
      type uint32;
      description
        "Baudrate for port 3";
    }
    leaf quality-option-port0 {
      type Ql-option-1;
      description
        "Quality Level option of port 0";
    }
    leaf quality-option-port1 {
      type Ql-option-1;
      description
        "Quality Level option of the port 1";
    }
    leaf quality-option-port2 {
      type Ql-option-1;
      description
        "Quality Level option of the port 2";
    }
    leaf quality-option-port3 {
      type Ql-option-1;
      description
        "Quality Level option of the port 3";
    }
    leaf transmit-ssm-port0 {
      type uint32;
      description
        "Transmit SSM for port 0";
    }
    leaf transmit-ssm-port1 {
      type uint32;
      description
        "Transmit SSM for port 1";
    }
    leaf transmit-ssm-port2 {
      type uint32;
      description
        "Transmit SSM for port 2";
    }
    leaf transmit-ssm-port3 {
      type uint32;
      description
        "Transmit SSM for port 3";
    }
    leaf recieve-ssm-port0 {
      type uint32;
      description
        "Receive SSM for port 0";
    }
    leaf recieve-ssm-port1 {
      type uint32;
      description
        "Receive SSM for port 1";
    }
    leaf recieve-ssm-port2 {
      type uint32;
      description
        "Receive SSM for port 2";
    }
    leaf recieve-ssm-port3 {
      type uint32;
      description
        "Receive SSM for port 3";
    }
    leaf interface-state-port0 {
      type Interface-state;
      description
        "Interface state for port 0";
    }
    leaf interface-state-port1 {
      type Interface-state;
      description
        "Interface state for port 1";
    }
    leaf interface-state-port2 {
      type Interface-state;
      description
        "Interface state for port 2";
    }
    leaf interface-state-port3 {
      type Interface-state;
      description
        "Interface state for port 3";
    }
  }

  grouping SYNCC-CLOCK-SETTING-TBLN {
    description
      "Clock table information";
    list clock {
      max-elements "1";
      description
        "Clock table for an RP";
      uses SYNCC-CLOCK-SETTING;
    }
  }

  grouping SYNCC-CLOCK-SETTING-NEWTBL {
    description
      "SYNCC interface information";
    list syncc-instance {
      description
        "List of syncc clock information ";
      uses SYNCC-CLOCK-SETTING-TBLN;
    }
  }

  grouping SYNCC-INTERNAL-STATE1 {
    description
      "Structure containing SYNCC internal state";
    leaf controller-state {
      type Syncc-states;
      description
        "Syncc controller state";
    }
    leaf syncc-node-state {
      type Node-state;
      description
        "Status of syncc node mode";
    }
    leaf verbose-level {
      type uint32;
      description
        "Verbose level number";
    }
    leaf initial-count {
      type uint32;
      description
        "Initial count number";
    }
    leaf shutdown-count {
      type uint32;
      description
        "Shutdown count number";
    }
    leaf set-input-count {
      type uint32;
      description
        "Set the value of input count";
    }
    leaf set-capability-count {
      type uint32;
      description
        "Set the value of display count";
    }
    leaf get-clock-count {
      type uint32;
      description
        "Clock count number";
    }
    leaf set-clock-out-count {
      type uint32;
      description
        "Set clock count";
    }
    leaf sync-enable-count {
      type uint32;
      description
        "Sync enable count number";
    }
    leaf sync-disable-count {
      type uint32;
      description
        "Sync disable count number";
    }
    leaf capability-count {
      type uint32;
      description
        "Interface capability count";
    }
    leaf set-quality-level-count {
      type uint32;
      description
        "Value of quality level count";
    }
    leaf input-notification {
      type uint32;
      description
        "Selects proper input result notification";
    }
    leaf capability-notification {
      type uint32;
      description
        "Value of interface capability notification";
    }
    leaf status-notification {
      type uint32;
      description
        "Notification of source status";
    }
    leaf resync-notification {
      type uint32;
      description
        "Value of resync notification";
    }
  }

  grouping SYNCC-INTERNAL-STATE {
    description
      "Syncc internal state information";
    list syncc-instance {
      description
        "List of syncc states";
      uses SYNCC-INTERNAL-STATE1;
    }
  }
}
