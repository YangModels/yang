module Cisco-IOS-XR-lcmode-cfg {
  namespace "http://cisco.com/ns/yang/Cisco-IOS-XR-lcmode-cfg";
  prefix lcmode-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lcmode package configuration.
     
     This module contains definitions
     for the following management objects:
       lcmode: LC MODE configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Lc-mode {
    type enumeration {
      enum "10g-grey-mxp" {
        value 1;
        description
          "10G GREY MXP LC MODE";
      }
      enum "100g-txp" {
        value 2;
        description
          "100G TXP LC MODE";
      }
    }
    description
      "Lc mode";
  }

  container lcmode {
    description
      "LC MODE configuration";
    list slot-info {
      key "lc-slot";
      description
        "location of LC";
      leaf lcmode-type {
        type Lc-mode;
        description
          "LCMODE config type";
      }
      leaf lc-slot {
        type xr:Cisco-ios-xr-string;
        description
          "LC location";
      }
    }
  }
}
