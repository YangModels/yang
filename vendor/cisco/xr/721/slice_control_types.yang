module slice_control_types {
  namespace "http://www.cisco.com/calvados/calvados_controllers/slice_control/types";
  prefix slice_control_type;

  organization "Cisco Systems, Inc.";

  contact
    "Cisco Systems, Inc.
     Customer Service
    
     Postal: 170 West Tasman Drive
     San Jose, CA 95134
    
     Tel: +1 800 553-NETS
    
     E-mail: cs-yang@cisco.com";

  description 
    "This module contains definitions
     for the Calvados model objects.

     Copyright (c) 2012-2020 by Cisco Systems, Inc.
     All rights reserved.";

  revision "2015-08-30" {
    description "Initial version.";
  }

  typedef pll_device_id_type {
    type string {
      pattern 'all|[0-2]';
    }
  }

  typedef pll_id_type {
    type string {
      pattern '[0-3]';
    }
  }

  typedef curr_sensor_id_type {
    type string {
      pattern 'all|(0?[0-9]|1[0-5])';
    }
  }

  typedef eeprom_id_type {
    type string {
      pattern 'all|[0-1]';
    }
  }

  typedef optics_id_type {
    type string {
      pattern 'all|[0-4]';
    }
  }

  typedef phy_id_type {
    type string {
      pattern 'all|[0-9]';
    }
  }

  typedef temp_sensor_id_type {
    type string {
      pattern 'all|(0?[0-9]|1[0-9]|2[0-1])';
    }
  }

  typedef volt_sensor_id_type {
    type string {
      pattern 'all|(0?[0-9]|1[0-9]|2[0-1])';
    }
  }

  typedef slice_id_type {
    type string {
      pattern '[0-2]|all';
    }
  }

  typedef slice_controller_id_type {
    type string {
      pattern '[0-1]|all';
    }
  }

  typedef slice_location_type {
    type string {
      pattern '((0?[0-9]|1[0-5])/(0?[0-7]))';
    }
  }
}
