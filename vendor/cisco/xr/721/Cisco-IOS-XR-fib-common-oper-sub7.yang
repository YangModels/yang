submodule Cisco-IOS-XR-fib-common-oper-sub7 {
  belongs-to Cisco-IOS-XR-fib-common-oper {
    prefix Cisco-IOS-XR-fib-common-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2020 by Cisco Systems, Inc.
     All rights reserved.";

  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  grouping FIB-STATISTICS-BAG-DROPS {
    description
      "FIB drop statistics";
    leaf no-route-packets {
      type uint64;
      description
        "Fib stats for no route pkts";
    }
    leaf punt-unreachable-packets {
      type uint64;
      description
        "Punt generate unreach pkt";
    }
    leaf df-unreachable-packets {
      type uint64;
      description
        "DF unreachable pkt";
    }
    leaf encapsulation-failure-packets {
      type uint64;
      description
        "Fib stats for encapsulation failure pkts";
    }
    leaf incomplete-adjacency-packets {
      type uint64;
      description
        "Fib stats for incomplete adjacency pkts";
    }
    leaf unresolved-prefix-packets {
      type uint64;
      description
        "Fib stats for unresolved prefix pkts";
    }
    leaf unsupported-feature-packets {
      type uint64;
      description
        "Fib stats for unsupported feature pkt";
    }
    leaf discard-packets {
      type uint64;
      description
        "Fib stats for discarded pkts";
    }
    leaf checksum-error-packets {
      type uint64;
      description
        "Fib stats for checksum error pkts";
    }
    leaf fragmenation-consumed-packets {
      type uint64;
      description
        "frag consumed packet pkt";
    }
    leaf fragmenation-failure-packets {
      type uint64;
      description
        "Fib stats for fragmenation failure pkt";
    }
    leaf null-packets {
      type uint64;
      description
        "null0 pkt";
    }
    leaf rpf-check-failure-packets {
      type uint64;
      description
        "RPF check failures pkt";
    }
    leaf acl-in-rpf-packets {
      type uint64;
      description
        "ACL in RPF pkt";
    }
    leaf rp-destination-drop-packets {
      type uint64;
      description
        "rp dest drop pkt";
    }
    leaf total-number-of-drop-packets {
      type uint64;
      description
        "Fib stats for the total number of dropped pkts";
    }
    leaf mpls-disabled-interface {
      type uint64;
      description
        "Fib number of drops for mpls disabled interfaces";
    }
    leaf gre-lookup-failed-drop {
      type uint64;
      description
        "GRE tunnel lookup failed drop pkt";
    }
    leaf gre-error-drop {
      type uint64;
      description
        "GRE processing errors";
    }
    leaf lisp-punt-drops {
      type uint64;
      description
        "LISP Punt drops";
    }
    leaf lisp-encap-error-drops {
      type uint64;
      description
        "Fib stats for Lisp encap error drops";
    }
    leaf lisp-decap-error-drops {
      type uint64;
      description
        "Fib stats for Lisp decap error drops";
    }
    leaf multi-label-drops {
      type uint64;
      description
        "Drops for the packets with multi[le labels";
    }
    leaf unreachable-sr-label-drops {
      type uint64;
      description
        "No route or unresolved route of MPLS SR labels";
    }
    leaf ttl-expired-sr-label-drops {
      type uint64;
      description
        "TTL expired drops of MPLS SR labels";
    }
  }
}
