submodule Cisco-IOS-XR-fabric-plane-health-oper-sub1 {
  belongs-to Cisco-IOS-XR-fabric-plane-health-oper {
    prefix Cisco-IOS-XR-fabric-plane-health-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fabric-plane-health package operational data.
     
     Copyright (c) 2013-2020 by Cisco Systems, Inc.
     All rights reserved.";

  revision 2020-06-26 {
    description
      "Yang Schema added with task-name.";
    semver:module-version "1.0.0";
  }
  revision 2019-04-05 {
    description
      "Establish semantic version baseline.";
  }
  revision 2015-11-09 {
    description
      "IOS XR 6.0 revision.";
  }

  grouping FSDB-PLA-HEALTH-INFO {
    description
      "FSDB PLA HEALTH INFO";
    leaf fabid-address {
      type string {
        length "0..128";
      }
      description
        "fabid address";
    }
    leaf fabid-status {
      type string;
      description
        "fabid status";
    }
    leaf show-fabid-unreachable {
      type boolean;
      description
        "show fabid unreachable";
    }
    leaf plane-0-mask {
      type string {
        length "0..32";
      }
      description
        "plane 0 mask";
    }
    leaf plane-1-mask {
      type string {
        length "0..32";
      }
      description
        "plane 1 mask";
    }
    leaf plane-2-mask {
      type string {
        length "0..32";
      }
      description
        "plane 2 mask";
    }
    leaf plane-3-mask {
      type string {
        length "0..32";
      }
      description
        "plane 3 mask";
    }
    leaf plane-4-mask {
      type string {
        length "0..32";
      }
      description
        "plane 4 mask";
    }
    leaf plane-5-mask {
      type string {
        length "0..32";
      }
      description
        "plane 5 mask";
    }
    leaf plane-6-mask {
      type string {
        length "0..32";
      }
      description
        "plane 6 mask";
    }
    leaf plane-7-mask {
      type string {
        length "0..32";
      }
      description
        "plane 7 mask";
    }
    leaf total-links {
      type int32;
      description
        "total links";
    }
    leaf total-up-links {
      type int32;
      description
        "total up links";
    }
    leaf min-links-per-asic {
      type int32;
      description
        "min links per asic";
    }
    leaf max-links-per-asic {
      type int32;
      description
        "max links per asic";
    }
    leaf min-up-links-per-asic {
      type int32;
      description
        "min up links per asic";
    }
    leaf max-up-links-per-asic {
      type int32;
      description
        "max up links per asic";
    }
  }

  grouping NPU-FABRIC-HEALTH-EDM-ASIC {
    description
      "NPU FABRIC HEALTH EDM ASIC";
    leaf rack-num {
      type uint32;
      description
        "rack num";
    }
    leaf slot-num {
      type uint32;
      description
        "slot num";
    }
    leaf asic-instance {
      type uint32;
      description
        "asic instance";
    }
    leaf asic-state-str {
      type string {
        length "0..32";
      }
      description
        "asic state str";
    }
    leaf asic-state {
      type uint32;
      description
        "asic state";
    }
    leaf fab-reach {
      type boolean;
      description
        "fab reach";
    }
    leaf asic-valid {
      type boolean;
      description
        "asic valid";
    }
    leaf is-below {
      type boolean;
      description
        "is below";
    }
    leaf total-bw {
      type uint32;
      description
        "total bw";
    }
    leaf total-availbw {
      type uint32;
      description
        "total availbw";
    }
    leaf total-reqdbw {
      type uint32;
      description
        "total reqdbw";
    }
  }

  grouping NPU-FABRIC-HEALTH-INFO {
    description
      "NPU FABRIC HEALTH INFO";
    leaf fe-status {
      type boolean;
      description
        "fe status";
    }
    leaf total-asics {
      type uint32;
      description
        "total asics";
    }
    list asic-list-ptr {
      description
        "asic list ptr";
      uses NPU-FABRIC-HEALTH-EDM-ASIC;
    }
  }

  grouping FSDB-EDM-RACK-PLANE-INFO {
    description
      "FSDB EDM RACK PLANE INFO";
    leaf plane-id {
      type uint32;
      description
        "plane id";
    }
    leaf plane-state {
      type string;
      description
        "plane state";
    }
    leaf asics-total {
      type int32;
      description
        "asics total";
    }
    leaf asics-up {
      type int32;
      description
        "asics up";
    }
    leaf asics-dn {
      type int32;
      description
        "asics dn";
    }
    leaf num-reachable-fabids {
      type int32;
      description
        "num reachable fabids";
    }
  }

  grouping FSDB-EDM-RACK-INFO {
    description
      "FSDB EDM RACK INFO";
    container activerp-card-npu-info {
      description
        "activerp card npu info";
      uses NPU-FABRIC-HEALTH-INFO;
    }
    leaf is-valid {
      type boolean;
      description
        "is valid";
    }
    leaf fsdb-status {
      type string;
      description
        "fsdb status";
    }
    leaf npu-fe-status {
      type string;
      description
        "npu fe status";
    }
    leaf rack-num {
      type string {
        length "0..32";
      }
      description
        "rack num";
    }
    leaf rack-type {
      type string;
      description
        "rack type";
    }
    leaf sfe-asics-total {
      type int32;
      description
        "sfe asics total";
    }
    leaf sfe-asics-up {
      type int32;
      description
        "sfe asics up";
    }
    leaf sfe-asics-dn {
      type int32;
      description
        "sfe asics dn";
    }
    leaf fia-asics-total {
      type int32;
      description
        "fia asics total";
    }
    leaf fia-asics-up {
      type int32;
      description
        "fia asics up";
    }
    leaf fia-asics-dn {
      type int32;
      description
        "fia asics dn";
    }
    leaf num-valid-fabids {
      type int32;
      description
        "num valid fabids";
    }
    leaf show-rack-plane-detail {
      type boolean;
      description
        "show rack plane detail";
    }
    list rack-plane-info {
      max-elements "8";
      description
        "rack plane info";
      uses FSDB-EDM-RACK-PLANE-INFO;
    }
    list lc-card-npu-info {
      max-elements "18";
      description
        "lc card npu info";
      uses NPU-FABRIC-HEALTH-INFO;
    }
    list fsdb-pla-ptr {
      description
        "fsdb pla ptr";
      uses FSDB-PLA-HEALTH-INFO;
    }
  }

  grouping FSDBAGG-EDM-SYS-PLANE-INFO {
    description
      "FSDBAGG EDM SYS PLANE INFO";
    leaf plane-id {
      type uint32;
      description
        "plane id";
    }
    leaf admin-state {
      type string;
      description
        "admin state";
    }
    leaf plane-state {
      type string;
      description
        "plane state";
    }
    leaf racks-w-plane-fault {
      type int32;
      description
        "racks w plane fault";
    }
    leaf is-data-drop {
      type boolean;
      description
        "is data drop";
    }
  }

  grouping FSDBAGG-EDM-FABRIC-HEALTH {
    description
      "FSDBAGG EDM FABRIC HEALTH";
    leaf aggr-status {
      type string;
      description
        "aggr status";
    }
    leaf rack-total {
      type int32;
      description
        "rack total";
    }
    leaf rack-lcc {
      type int32;
      description
        "rack lcc";
    }
    leaf rack-fcc {
      type int32;
      description
        "rack fcc";
    }
    leaf plane-up {
      type int32;
      description
        "plane up";
    }
    leaf plane-dn {
      type int32;
      description
        "plane dn";
    }
    leaf plane-mcast-dn {
      type int32;
      description
        "plane mcast dn";
    }
    leaf plane-admin-dn {
      type int32;
      description
        "plane admin dn";
    }
    leaf sfe-asics-total {
      type int32;
      description
        "sfe asics total";
    }
    leaf sfe-asics-up {
      type int32;
      description
        "sfe asics up";
    }
    leaf sfe-asics-dn {
      type int32;
      description
        "sfe asics dn";
    }
    leaf fia-asics-total {
      type int32;
      description
        "fia asics total";
    }
    leaf fia-asics-up {
      type int32;
      description
        "fia asics up";
    }
    leaf fia-asics-dn {
      type int32;
      description
        "fia asics dn";
    }
    leaf show-sys-plane-detail {
      type boolean;
      description
        "show sys plane detail";
    }
    list sys-plane-info {
      max-elements "8";
      description
        "sys plane info";
      uses FSDBAGG-EDM-SYS-PLANE-INFO;
    }
    list rack-health-bag {
      description
        "rack health bag";
      uses FSDB-EDM-RACK-INFO;
    }
  }

  grouping FSDBAGG-EDM-PLANE-STATS {
    description
      "FSDBAGG EDM PLANE STATS";
    leaf planeid {
      type uint32;
      description
        "planeid";
    }
    leaf rx-data-cells {
      type uint64;
      description
        "rx data cells";
    }
    leaf tx-data-cells {
      type uint64;
      description
        "tx data cells";
    }
    leaf rx-ce-cells {
      type uint64;
      description
        "rx ce cells";
    }
    leaf rx-ce-cells-is-overflow {
      type boolean;
      description
        "rx ce cells is overflow";
    }
    leaf rx-uce-cells {
      type uint64;
      description
        "rx uce cells";
    }
    leaf rx-uce-cells-is-overflow {
      type boolean;
      description
        "rx uce cells is overflow";
    }
    leaf rx-pe-cells {
      type uint64;
      description
        "rx pe cells";
    }
    leaf rx-pe-cells-is-overflow {
      type boolean;
      description
        "rx pe cells is overflow";
    }
    leaf ucast-lost-cells {
      type uint32;
      description
        "ucast lost cells";
    }
    leaf mcast-lost-cells {
      type uint32;
      description
        "mcast lost cells";
    }
    leaf asic-internal-drops {
      type uint32;
      description
        "asic internal drops";
    }
    leaf last-clear-elapsed {
      type uint32;
      description
        "last clear elapsed";
    }
    leaf is-asic-internal-error {
      type boolean;
      description
        "is asic internal error";
    }
    leaf last-clear-ts {
      type string {
        length "0..128";
      }
      description
        "last clear ts";
    }
    leaf last-clear-reason {
      type string;
      description
        "last clear reason";
    }
    leaf last-clear-req-ts {
      type string {
        length "0..128";
      }
      description
        "last clear req ts";
    }
    leaf last-clear-status {
      type string;
      description
        "last clear status";
    }
  }

  grouping FSDBAGG-EDM-PLANE-INFO {
    description
      "FSDBAGG EDM PLANE INFO";
    leaf planeid {
      type int32;
      description
        "planeid";
    }
    leaf admin-state {
      type string;
      description
        "admin state";
    }
    leaf ucast-oper-state {
      type string;
      description
        "ucast oper state";
    }
    leaf ucast-cnt-dn {
      type int32;
      description
        "ucast cnt dn";
    }
    leaf ucast-cnt-some-up {
      type int32;
      description
        "ucast cnt some up";
    }
    leaf total-bundles {
      type int32;
      description
        "total bundles";
    }
    leaf down-bundles {
      type int32;
      description
        "down bundles";
    }
    leaf ppu-state {
      type string {
        length "0..128";
      }
      description
        "ppu state";
    }
  }
}
