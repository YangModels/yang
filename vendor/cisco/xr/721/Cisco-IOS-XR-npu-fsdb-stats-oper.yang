module Cisco-IOS-XR-npu-fsdb-stats-oper {
  namespace "http://cisco.com/ns/yang/Cisco-IOS-XR-npu-fsdb-stats-oper";
  prefix npu-fsdb-stats-oper;

  import Cisco-IOS-XR-types {
    prefix xr;
  }
  import cisco-semver {
    prefix semver;
  }
  include Cisco-IOS-XR-npu-fsdb-stats-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR npu-fsdb-stats package operational data.
     
     This module contains definitions
     for the following management objects:
       npu: Fabric Data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Link-option-string {
    type string {
      pattern "(flap)|(topo)|(fsm)";
    }
    description
      "flap:Display link flap info, topo:Display link
       topo info, fsm:Link state FSM info";
  }

  typedef Npu-max-asic-instances {
    type uint32 {
      range "0..255";
    }
    description
      "Npu max asic instances";
  }

  typedef Link-info-max-number {
    type uint32 {
      range "0..215";
    }
    description
      "Link info max number";
  }

  container npu {
    config false;
    description
      "Fabric Data";
    list node {
      key "node-name";
      description
        "Data for particular node";
      container rx-link-information {
        description
          "NPU link rx information";
        container link-options {
          description
            "Option table for link rx information";
          list link-option {
            key "option";
            description
              "Option : topo , fsm , flap";
            container rx-asic-instances {
              description
                "Instance table for rx information";
              list rx-asic-instance {
                key "instance";
                description
                  "Instance number for rx link information";
                container rx-links {
                  description
                    "Link table class for rx information";
                  list rx-link {
                    description
                      "Link number for rx link information";
                    leaf start-number {
                      type Link-info-max-number;
                      description
                        "Start number";
                    }
                    leaf end-number {
                      type Link-info-max-number;
                      description
                        "End number";
                    }
                    leaf status-option {
                      type xr:Cisco-ios-xr-string;
                      description
                        "RX link status option";
                    }
                    list rx-link {
                      key "link";
                      description
                        "Single link information";
                      leaf link {
                        type uint32;
                        description
                          "Single link";
                      }
                      uses NPU-EDM-RXLINK;
                    }
                  }
                }
                leaf instance {
                  type Npu-max-asic-instances;
                  description
                    "Receive instance";
                }
              }
            }
            leaf option {
              type Link-option-string;
              description
                "Link option";
            }
          }
        }
      }
      container driver-info {
        description
          "NPU Driver Info";
        uses NPU-EDM-DRIVER-INFO;
      }
      container tx-link-information {
        description
          "NPU link TX information";
        container tx-status-option-table {
          description
            "Link table for tx information";
          container tx-status-option {
            description
              "Option: data, ctrl, all- for now none";
            container tx-asic-instances {
              description
                "Instance table for tx information";
              list tx-asic-instance {
                key "instance";
                description
                  "Instance number for tx link information";
                container tx-links {
                  description
                    "Link table for tx information";
                  list tx-link {
                    description
                      "Link number for tx link information";
                    leaf start-number {
                      type Link-info-max-number;
                      description
                        "Start number";
                    }
                    leaf end-number {
                      type Link-info-max-number;
                      description
                        "End number";
                    }
                    list tx-link {
                      key "link";
                      description
                        "Single link information";
                      leaf link {
                        type uint32;
                        description
                          "Single Link";
                      }
                      uses NPU-EDM-TXLINK;
                    }
                  }
                }
                leaf instance {
                  type Npu-max-asic-instances;
                  description
                    "Transmit instance";
                }
              }
            }
          }
        }
      }
      container instance-tables {
        description
          "NPU statistics";
        list instance-table {
          key "instance";
          description
            "Instance Number";
          container fmac-link-tables {
            description
              "FMAC statistics";
            list fmac-link-table {
              key "link";
              description
                "Link Number";
              container fmac-brief-statistics {
                description
                  "NPU FMAC Statistics";
                uses NPU-EDM-STATS-ASIC-FMAC-INFO;
              }
              leaf link {
                type uint32;
                description
                  "Link Number";
              }
            }
          }
          leaf instance {
            type uint32;
            description
              "Instance Number";
          }
        }
      }
      leaf node-name {
        type xr:Node-id;
        description
          "Node ID";
      }
    }
  }
}
