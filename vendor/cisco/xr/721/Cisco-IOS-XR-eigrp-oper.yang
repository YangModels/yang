module Cisco-IOS-XR-eigrp-oper {
  namespace "http://cisco.com/ns/yang/Cisco-IOS-XR-eigrp-oper";
  prefix eigrp-oper;

  import Cisco-IOS-XR-types {
    prefix xr;
  }
  import cisco-semver {
    prefix semver;
  }
  import Cisco-IOS-XR-eigrp-datatypes {
    prefix dt1;
  }
  include Cisco-IOS-XR-eigrp-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR eigrp package operational data.
     
     This module contains definitions
     for the following management objects:
       eigrp: EIGRP operational data
     
     Copyright (c) 2013-2019 by Cisco Systems, Inc.
     All rights reserved.";

  revision 2019-04-05 {
    description
      "Establish semantic version baseline.";
    semver:module-version "1.0.1";
  }
  revision 2018-04-05 {
    description
      "Oper supported provided for oper data.";
  }
  revision 2015-11-09 {
    description
      "IOS XR 6.0 revision.";
  }

  container eigrp {
    config false;
    description
      "EIGRP operational data";
    container processes {
      description
        "Operational data for an EIGRP process";
      list process {
        key "process-id";
        description
          "Operational data for an EIGRP process";
        container vrfs-xr {
          description
            "List of VRFs";
          list vrf {
            key "vrf-name";
            description
              "A VRF";
            leaf vrf-name {
              type xr:Cisco-ios-xr-string;
              description
                "VRF Name";
            }
            uses EIGRP-VRFS-BD;
          }
        }
        container vrfs {
          description
            "List of VRFs";
          list vrf {
            key "vrf-name";
            description
              "Operational data for a VRF";
            container afs {
              description
                "List of Address Families";
              list af {
                key "af-name";
                description
                  "Operational data for one AF";
                container protocol {
                  description
                    "Address family specific protocol
                     information";
                  uses EIGRP-SHOW-PROT-VRF-BD;
                }
                container ases {
                  description
                    "List of Autonomous Systems";
                  list as {
                    key "asn";
                    description
                      "Operational data for one AS";
                    container static-neighbors {
                      description
                        "EIGRP static neighbors";
                      list static-neighbor {
                        key "neighbor-address";
                        description
                          "Information on one static EIGRP
                           neighbor";
                        leaf neighbor-address {
                          type xr:Cisco-ios-xr-string;
                          description
                            "Neighbor Address";
                        }
                        uses EIGRP-SHOW-STATIC-NEIGHBORS-BD;
                      }
                    }
                    container topology-routes {
                      description
                        "EIGRP topology table";
                      list topology-route {
                        description
                          "Information about one EIGRP route";
                        leaf prefix {
                          type xr:Cisco-ios-xr-string;
                          description
                            "IP Prefix";
                        }
                        leaf prefix-length {
                          type uint32 {
                            range "0..128";
                          }
                          description
                            "IP Prefix length";
                        }
                        uses EIGRP-SHOW-ROUTE-BD;
                      }
                    }
                    container eigrp-accounting {
                      description
                        "Accounting info for one VRF AF";
                      uses EIGRP-SHOW-ACCOUNTING-BD;
                    }
                    container eigrp-traffic {
                      description
                        "Traffic info for one VRF AF";
                      uses EIGRP-SHOW-TRAFFIC-BD;
                    }
                    container eigrp-topology-summary {
                      description
                        "Topology summary info for one VRF AF";
                      uses EIGRP-SHOW-TOP-SUMMARY-BD;
                    }
                    container interfaces {
                      description
                        "EIGRP interfaces";
                      list interface {
                        key "interface-name";
                        description
                          "Information for an EIGRP interface";
                        leaf interface-name {
                          type xr:Interface-name;
                          description
                            "Interface Name";
                        }
                        uses EIGRP-SHOW-INTERFACES-BD;
                      }
                    }
                    container eigrp-events {
                      description
                        "Events for a specific VRF AF";
                      uses EIGRP-SHOW-EVENTS-BD;
                    }
                    container neighbors {
                      description
                        "EIGRP neighbors";
                      list neighbor {
                        key "neighbor-address";
                        description
                          "Information on one EIGRP neighbor";
                        leaf neighbor-address {
                          type xr:Cisco-ios-xr-string;
                          description
                            "Neighbor Address";
                        }
                        uses EIGRP-SHOW-NEIGHBORS-BD;
                      }
                    }
                    container eigrp-statistics {
                      description
                        "Statistics for a specific VRF AF";
                      uses EIGRP-SHOW-AF-STATS-BD;
                    }
                    leaf asn {
                      type uint32 {
                        range "1..65535";
                      }
                      description
                        "AS number";
                    }
                  }
                }
                leaf af-name {
                  type dt1:Eigrp-af;
                  description
                    "Address Family";
                }
              }
            }
            leaf vrf-name {
              type xr:Cisco-ios-xr-string;
              description
                "VRF Name";
            }
          }
        }
        leaf process-id {
          type xr:Cisco-ios-xr-string {
            length "1..32";
          }
          description
            "AS number or Virtual instance name of the
             EIGRP process";
        }
      }
    }
  }
}
