module Cisco-IOS-XR-fabhfr-mib-cfg {
  namespace "http://cisco.com/ns/yang/Cisco-IOS-XR-fabhfr-mib-cfg";
  prefix fabhfr-mib-cfg;

  import cisco-semver {
    prefix semver;
  }
  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fabhfr-mib package configuration.
     
     This YANG module augments the
       Cisco-IOS-XR-snmp-agent-cfg
     module with configuration data.
     
     Copyright (c) 2013-2019 by Cisco Systems, Inc.
     All rights reserved.";

  revision 2019-04-05 {
    description
      "Establish semantic version baseline.";
    semver:module-version "1.0.1";
  }
  revision 2017-05-31 {
    description
      "Yang Schema added.";
  }
  revision 2015-11-09 {
    description
      "IOS XR 6.0 revision.";
  }

  augment "/a1:snmp/a1:notification" {
    description
      "This augment extends the configuration data of
       'Cisco-IOS-XR-snmp-agent-cfg'";
    container fabric-crs {
      description
        "CISCO-FABRIC-HFR-MIB notification configuration";
      leaf bundle-state {
        type empty;
        description
          "Enable cfhBundleStateNotification notification";
      }
      leaf plane-state {
        type empty;
        description
          "Enable cfhPlaneStateNotification notification";
      }
      leaf bundle-downed-link {
        type empty;
        description
          "Enable cfhBundleDownedLinkNotification
           notification";
      }
    }
  }
}
