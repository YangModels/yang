module Cisco-IOS-XR-healthcheck-oper {
  namespace "http://cisco.com/ns/yang/Cisco-IOS-XR-healthcheck-oper";
  prefix healthcheck-oper;

  import cisco-semver {
    prefix semver;
  }
  include Cisco-IOS-XR-healthcheck-oper-sub2 {
    revision-date 2019-04-05;
  }
  include Cisco-IOS-XR-healthcheck-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package operational data.
     
     This module contains definitions
     for the following management objects:
       health-check: Healthcheck Operational data space
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container health-check {
    config false;
    description
      "Healthcheck Operational data space";
    container metric-info {
      description
        "Metric Info";
      container fpd {
        description
          "FPD Metric";
        uses HCMGR-FPD-METRIC-DATA;
      }
      container redundancy {
        description
          "REDUNDANCY Metric";
        uses HCMGR-REDUNDANCY-METRIC-DATA;
      }
      container fabric-health {
        description
          "FABRIC-HEALTH Metric";
        uses HCMGR-FABRIC-HEALTH-METRIC-DATA;
      }
      container platform {
        description
          "PLATFORM Metric";
        uses HCMGR-PLATFORM-METRIC-DATA;
      }
      container free-memory {
        description
          "Free Memory Metric";
        uses HCMGR-FREE-MEM-METRIC-DATA;
      }
      container filesystem {
        description
          "Filesystem Metric";
        uses HCMGR-FILESYSTEM-METRIC-DATA;
      }
      container shared-memory {
        description
          "Shared Memory Metric";
        uses HCMGR-SHARED-MEM-METRIC-DATA;
      }
      container cpu {
        description
          "CPU Metric";
        uses HCMGR-CPU-METRIC-DATA;
      }
    }
    container report-info {
      description
        "Report data bag";
      uses HCMGR-REPORT-DATA;
    }
    container status-info {
      description
        "Status data bag";
      uses HCMGR-STATUS-DATA;
    }
  }
}
