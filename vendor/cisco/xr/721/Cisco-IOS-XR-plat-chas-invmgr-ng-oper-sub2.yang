submodule Cisco-IOS-XR-plat-chas-invmgr-ng-oper-sub2 {
  belongs-to Cisco-IOS-XR-plat-chas-invmgr-ng-oper {
    prefix Cisco-IOS-XR-plat-chas-invmgr-ng-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR plat-chas-invmgr-ng package operational data.
     
     This model is deprecated and is replaced by
     Cisco-IOS-XR-platform-oper.yang,Cisco-IOS-XR-platform-inventory-oper.yang which will provide the
     compatible functionalities.
     
     Copyright (c) 2013-2020 by Cisco Systems, Inc.
     All rights reserved.";

  revision 2020-05-14 {
    description
      "Deprecated the model, replaced by Cisco-IOS-XR-platform-oper and Cisco-IOS-XR-platform-inventory-oper
       2020-01-30
         Fixed the model to include module container under cards";
    semver:module-version "2.0.0";
  }
  revision 2019-10-15 {
    description
      "Added oper-state leaf to PLATFORM-INFO.";
    semver:module-version "1.1.0";
  }
  revision 2019-04-05 {
    description
      "Establish semantic version baseline.";
    semver:module-version "1.0.0";
  }
  revision 2018-01-22 {
    description
      "Fixing incorrect spelling for node-description in module.";
  }
  revision 2015-11-09 {
    description
      "IOS XR 6.0 revision.";
  }

  typedef Node-state {
    type enumeration {
      enum "not-present" {
        value 0;
        description
          "Not present";
      }
      enum "present" {
        value 1;
        description
          "Present";
      }
      enum "reset" {
        value 2;
        description
          "Reset";
      }
      enum "rommon" {
        value 3;
        description
          "Card booting or rommon";
      }
      enum "mbi-boot" {
        value 4;
        description
          "MBI booting";
      }
      enum "mbi-run" {
        value 5;
        description
          "Running MBI";
      }
      enum "xr-run" {
        value 6;
        description
          "Running ENA";
      }
      enum "bring-down" {
        value 7;
        description
          "Bringdown";
      }
      enum "xr-fail" {
        value 8;
        description
          "ENA failure";
      }
      enum "fdiag-run" {
        value 9;
        description
          "Running FDIAG";
      }
      enum "fdiag-fail" {
        value 10;
        description
          "FDIAG failure";
      }
      enum "power" {
        value 11;
        description
          "Powered";
      }
      enum "unpower" {
        value 12;
        description
          "Unpowered";
      }
      enum "mdr-warm-reload" {
        value 13;
        description
          "MDR warm reload";
      }
      enum "mdr-mbi-run" {
        value 14;
        description
          "MDR running MBI";
      }
      enum "maintenance-mode" {
        value 15;
        description
          "Maintenance mode";
      }
      enum "admin-down" {
        value 16;
        description
          "Admin down";
      }
      enum "not-monitor" {
        value 17;
        description
          "No MON";
      }
      enum "unknown-card" {
        value 18;
        description
          "Unknown";
      }
      enum "failed" {
        value 19;
        description
          "Failed";
      }
      enum "ok" {
        value 20;
        description
          "OK";
      }
      enum "missing" {
        value 21;
        description
          "Missing";
      }
      enum "diag-download" {
        value 22;
        description
          "Field diag downloading";
      }
      enum "diag-not-monitor" {
        value 23;
        description
          "Field diag unmonitor";
      }
      enum "fabric-diag-not-monitor" {
        value 24;
        description
          "Fabric field diag unmonitor";
      }
      enum "diag-rp-launch" {
        value 25;
        description
          "Field diag RP launching";
      }
      enum "diag-run" {
        value 26;
        description
          "Field diag running";
      }
      enum "diag-pass" {
        value 27;
        description
          "Field diag pass";
      }
      enum "diag-fail" {
        value 28;
        description
          "Field diag fail";
      }
      enum "diag-timeout" {
        value 29;
        description
          "Field diag timeout";
      }
      enum "disable" {
        value 30;
        description
          "Disable";
      }
      enum "spa-boot" {
        value 31;
        description
          "SPA booting";
      }
      enum "not-allowed-online" {
        value 32;
        description
          "Not allowed online";
      }
      enum "stop" {
        value 33;
        description
          "Stopped";
      }
      enum "incomp-version" {
        value 34;
        description
          "Incompatible FW version";
      }
      enum "fpd-hold" {
        value 35;
        description
          "FPD hold";
      }
      enum "xr-preparation" {
        value 36;
        description
          "XR preparation";
      }
      enum "sync-ready" {
        value 37;
        description
          "Sync ready state";
      }
      enum "xr-isolate" {
        value 38;
        description
          "Node isolate state";
      }
      enum "ready" {
        value 39;
        description
          "Ready";
      }
      enum "invalid" {
        value 40;
        description
          "Invalid";
      }
      enum "operational" {
        value 41;
        description
          "Operational";
      }
      enum "operational-lock" {
        value 42;
        description
          "Operational lock";
      }
      enum "going-down" {
        value 43;
        description
          "Going down";
      }
      enum "going-offline" {
        value 44;
        description
          "Going offline";
      }
      enum "going-online" {
        value 45;
        description
          "Going online";
      }
      enum "offline" {
        value 46;
        description
          "Offline";
      }
      enum "up" {
        value 47;
        description
          "Up";
      }
      enum "down" {
        value 48;
        description
          "Down";
      }
      enum "max" {
        value 49;
        description
          "Max";
      }
      enum "unknown" {
        value 50;
        description
          "Unknown";
      }
      enum "not-applicable" {
        value 51;
        description
          "N/A";
      }
    }
    description
      "Node state detail";
  }

  typedef Card-redundancy-state {
    type enumeration {
      enum "red-state-none" {
        value 0;
        description
          "Not Applicable";
      }
      enum "active" {
        value 1;
        description
          "Active";
      }
      enum "standby" {
        value 2;
        description
          "Standby";
      }
    }
    description
      "Redundancy state detail";
  }

  grouping VM-INFO {
    description
      "VM Info";
    leaf node-description {
      type string;
      description
        "Node Type";
    }
    leaf red-role {
      type string;
      description
        "Node Redundency Role";
    }
    leaf partner-name {
      type string;
      description
        "Partner Name";
    }
    leaf software-status {
      type string;
      description
        "SW status";
    }
    leaf node-ip {
      type string;
      description
        "Node IP Address";
    }
    leaf node-name {
      type string;
      description
        "Node name";
    }
  }

  grouping PLATFORM-INFO {
    description
      "Platform information";
    leaf card-type {
      type string;
      description
        "Card type";
    }
    leaf card-redundancy-state {
      type Card-redundancy-state;
      description
        "Redundancy state";
    }
    leaf plim {
      type string;
      description
        "PLIM";
    }
    leaf state {
      type Node-state;
      description
        "State";
    }
    leaf is-monitored {
      type boolean;
      description
        "True if monitor state is active";
    }
    leaf is-powered {
      type boolean;
      description
        "True if power state is active";
    }
    leaf is-shutdown {
      type boolean;
      description
        "True if shutdown state is active";
    }
    leaf admin-state {
      type string;
      description
        "Admin state";
    }
    leaf node-name {
      type string;
      description
        "Node name";
    }
    leaf oper-state {
      type string;
      description
        "Operational state";
    }
  }
}
