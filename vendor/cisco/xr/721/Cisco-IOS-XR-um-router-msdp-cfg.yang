module Cisco-IOS-XR-um-router-msdp-cfg {
  namespace "http://cisco.com/ns/yang/Cisco-IOS-XR-um-router-msdp-cfg";
  prefix um-router-msdp-cfg;

  import cisco-semver {
    prefix semver;
  }
  import Cisco-IOS-XR-types {
    prefix xr;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR router msdp configuration.
     
     Copyright (c) 2019 by Cisco Systems, Inc.
     All rights reserved.";

  revision 2019-08-20 {
    description
      "Initial release";
    semver:module-version "1.0.0";
  }

  container router {
    description
      "Enable a routing process";
    container msdp {
      description
        "MSDP configuration subcommands";
      leaf connect-source {
        type xr:Interface-name;
        description
          "Configure source address used for MSDP connection";
      }
      leaf originator-id {
        type xr:Interface-name;
        description
          "Configure MSDP Originator ID";
      }
      leaf nsr-delay {
        type uint32 {
          range "5..90" {
            description
              "NSR-Ready wait period in seconds";
          }
        }
        description
          "Configure NSR-Ready delay period for MSDP Peer";
      }
      leaf ttl-threshold {
        type uint32 {
          range "1..255" {
            description
              "TTL Threshold Value";
          }
        }
        description
          "Configure TTL Thresold for MSDP Peer";
      }
      container cache-sa-state {
        description
          "Configure this systems SA cache access-lists";
        leaf list {
          type xr:Cisco-ios-xr-string {
            length "1..32" {
              description
                "Access list name";
            }
          }
          description
            "Access-list";
        }
        leaf rp-list {
          type xr:Cisco-ios-xr-string {
            length "1..32" {
              description
                "Access list name";
            }
          }
          description
            "Access-list for originating RP";
        }
      }
      leaf cache-sa-holdtime {
        type uint32 {
          range "150..3600" {
            description
              "Holdtime period in secs";
          }
        }
        description
          "Configure Cache SA State holdtime period";
      }
      container sa-filter {
        description
          "Filter SA messages from peer";
        container in {
          description
            "Enable incoming SA filtering";
          leaf list {
            type xr:Cisco-ios-xr-string {
              length "1..32" {
                description
                  "Access list name";
              }
            }
            description
              "Access-list";
          }
          leaf rp-list {
            type xr:Cisco-ios-xr-string {
              length "1..32" {
                description
                  "Access list name";
              }
            }
            description
              "Access-list for originating RP";
          }
        }
        container out {
          description
            "Enable outgoing SA filtering";
          leaf list {
            type xr:Cisco-ios-xr-string {
              length "1..32" {
                description
                  "Access list name";
              }
            }
            description
              "Access-list";
          }
          leaf rp-list {
            type xr:Cisco-ios-xr-string {
              length "1..32" {
                description
                  "Access list name";
              }
            }
            description
              "Access-list for originating RP";
          }
        }
      }
      leaf default-peer {
        type inet:ipv4-address-no-zone;
        description
          "Default MSDP peer to accept SA messages from";
      }
      container maximum {
        description
          "Maximum state limits";
        leaf external-sa {
          type uint32 {
            range "1..75000" {
              description
                "Maximum number of SA accepted by this router";
            }
          }
          description
            "Maximum number of SA accepted by this router in this context";
        }
        leaf peer-external-sa {
          type uint32 {
            range "1..75000" {
              description
                "Maximum number of SA accepted by this peer";
            }
          }
          description
            "Maximum number of SA accepted by this peer";
        }
      }
      container keepalive {
        presence "Indicates a keepalive node is configured.";
        description
          "Configure global KeepAlive period for MSDP Peer";
        leaf keepalive-period {
          type uint32 {
            range "1..60" {
              description
                "KeepAlive Period in seconds";
            }
          }
          mandatory true;
          description
            "Configure global KeepAlive period for MSDP Peer";
        }
        leaf peer-timeout-period {
          type uint32 {
            range "1..75" {
              description
                "Peer Timeout Period in seconds";
            }
          }
          mandatory true;
          description
            "Peer Timeout Period in seconds";
        }
      }
      container global {
        description
          "Global MSDP configuration";
        container maximum {
          description
            "Maximum state limits";
          leaf external-sa {
            type uint32 {
              range "1..75000" {
                description
                  "Maximum number of external SA accepted by this router";
              }
            }
            description
              "Externally learned active source limits";
          }
        }
      }
      container peers {
        description
          "MSDP Peer configuration subcommands";
        list peer {
          key "peer-address";
          leaf peer-address {
            type inet:ipv4-address-no-zone;
            description
              "Peer name or address";
          }
          leaf connect-source {
            type xr:Interface-name;
            description
              "Configure source address used for MSDP connection";
          }
          leaf remote-as {
            type xr:Bgp-as-number;
            description
              "Configure the remote AS of this peer";
          }
          leaf description {
            type string {
              length "1..1024" {
                description
                  "Up to 80 characters describing this peer";
              }
            }
            description
              "Peer specific description";
          }
          leaf mesh-group {
            type xr:Cisco-ios-xr-string {
              length "1..32" {
                description
                  "Name of mesh-group";
              }
            }
            description
              "Configure an MSDP mesh-group";
          }
          container sa-filter {
            description
              "Filter SA messages from peer";
            container in {
              description
                "Enable incoming SA filtering";
              leaf list {
                type xr:Cisco-ios-xr-string {
                  length "1..32" {
                    description
                      "Access list name";
                  }
                }
                description
                  "Access-list";
              }
              leaf rp-list {
                type xr:Cisco-ios-xr-string {
                  length "1..32" {
                    description
                      "Access list name";
                  }
                }
                description
                  "Access-list for originating RP";
              }
            }
            container out {
              description
                "Enable outgoing SA filtering";
              leaf list {
                type xr:Cisco-ios-xr-string {
                  length "1..32" {
                    description
                      "Access list name";
                  }
                }
                description
                  "Access-list";
              }
              leaf rp-list {
                type xr:Cisco-ios-xr-string {
                  length "1..32" {
                    description
                      "Access list name";
                  }
                }
                description
                  "Access-list for originating RP";
              }
            }
          }
          leaf ttl-threshold {
            type uint32 {
              range "1..255" {
                description
                  "TTL Threshold Value";
              }
            }
            description
              "Configure TTL Thresold for MSDP Peer";
          }
          container shutdown {
            presence "Indicates a shutdown node is configured.";
            description
              "MSDP Peer Shutdown";
          }
          container maximum {
            description
              "maximum number of SA accepted by this peer";
            leaf external-sa {
              type uint32 {
                range "1..75000" {
                  description
                    "maximum number of SA accepted by this peer";
                }
              }
              description
                "maximum number of SA accepted by this peer";
            }
          }
          container password {
            description
              "Configure password used for MSDP connection";
            leaf encrypted {
              type xr:Proprietary-password;
              description
                "Specifies an ENCRYPTED password will follow";
            }
          }
          container keepalive {
            presence "Indicates a keepalive node is configured.";
            description
              "Configure KeepAlive period for MSDP Peer";
            leaf keepalive-period {
              type uint32 {
                range "1..60" {
                  description
                    "KeepAlive Period in seconds";
                }
              }
              mandatory true;
              description
                "Configure KeepAlive period for MSDP Peer";
            }
            leaf peer-timeout-period {
              type uint32 {
                range "1..75" {
                  description
                    "Peer Timeout Period in seconds";
                }
              }
              mandatory true;
              description
                "Peer Timeout Period in seconds";
            }
          }
          container nsr-down {
            presence "Indicates a nsr-down node is configured.";
            description
              "Disable NSR for the peer";
          }
        }
      }
      container vrfs {
        description
          "VRF configs";
        list vrf {
          key "vrf-name";
          description
            "VRF configs";
          leaf vrf-name {
            type xr:Cisco-ios-xr-string {
              length "1..32" {
                description
                  "VRF name";
              }
            }
            description
              "VRF configs";
          }
          container peers {
            description
              "MSDP Peer configuration subcommands";
            list peer {
              key "peer-address";
              leaf peer-address {
                type inet:ipv4-address-no-zone;
                description
                  "Peer name or address";
              }
              leaf connect-source {
                type xr:Interface-name;
                description
                  "Configure source address used for MSDP connection";
              }
              leaf remote-as {
                type xr:Bgp-as-number;
                description
                  "Configure the remote AS of this peer";
              }
              leaf description {
                type string {
                  length "1..1024" {
                    description
                      "Up to 80 characters describing this peer";
                  }
                }
                description
                  "Peer specific description";
              }
              leaf mesh-group {
                type xr:Cisco-ios-xr-string {
                  length "1..32" {
                    description
                      "Name of mesh-group";
                  }
                }
                description
                  "Configure an MSDP mesh-group";
              }
              container sa-filter {
                description
                  "Filter SA messages from peer";
                container in {
                  description
                    "Enable incoming SA filtering";
                  leaf list {
                    type xr:Cisco-ios-xr-string {
                      length "1..32" {
                        description
                          "Access list name";
                      }
                    }
                    description
                      "Access-list";
                  }
                  leaf rp-list {
                    type xr:Cisco-ios-xr-string {
                      length "1..32" {
                        description
                          "Access list name";
                      }
                    }
                    description
                      "Access-list for originating RP";
                  }
                }
                container out {
                  description
                    "Enable outgoing SA filtering";
                  leaf list {
                    type xr:Cisco-ios-xr-string {
                      length "1..32" {
                        description
                          "Access list name";
                      }
                    }
                    description
                      "Access-list";
                  }
                  leaf rp-list {
                    type xr:Cisco-ios-xr-string {
                      length "1..32" {
                        description
                          "Access list name";
                      }
                    }
                    description
                      "Access-list for originating RP";
                  }
                }
              }
              leaf ttl-threshold {
                type uint32 {
                  range "1..255" {
                    description
                      "TTL Threshold Value";
                  }
                }
                description
                  "Configure TTL Thresold for MSDP Peer";
              }
              container shutdown {
                presence "Indicates a shutdown node is configured.";
                description
                  "MSDP Peer Shutdown";
              }
              container maximum {
                description
                  "maximum number of SA accepted by this peer";
                leaf external-sa {
                  type uint32 {
                    range "1..75000" {
                      description
                        "maximum number of SA accepted by this peer";
                    }
                  }
                  description
                    "maximum number of SA accepted by this peer";
                }
              }
              container password {
                description
                  "Configure password used for MSDP connection";
                leaf encrypted {
                  type xr:Proprietary-password;
                  description
                    "Specifies an ENCRYPTED password will follow";
                }
              }
              container keepalive {
                presence "Indicates a keepalive node is configured.";
                description
                  "Configure KeepAlive period for MSDP Peer";
                leaf keepalive-period {
                  type uint32 {
                    range "1..60" {
                      description
                        "KeepAlive Period in seconds";
                    }
                  }
                  mandatory true;
                  description
                    "Configure KeepAlive period for MSDP Peer";
                }
                leaf peer-timeout-period {
                  type uint32 {
                    range "1..75" {
                      description
                        "Peer Timeout Period in seconds";
                    }
                  }
                  mandatory true;
                  description
                    "Peer Timeout Period in seconds";
                }
              }
              container nsr-down {
                presence "Indicates a nsr-down node is configured.";
                description
                  "Disable NSR for the peer";
              }
            }
          }
          leaf connect-source {
            type xr:Interface-name;
            description
              "Configure source address used for MSDP connection";
          }
          leaf originator-id {
            type xr:Interface-name;
            description
              "Configure MSDP Originator ID";
          }
          leaf ttl-threshold {
            type uint32 {
              range "1..255" {
                description
                  "TTL Threshold Value";
              }
            }
            description
              "Configure TTL Thresold for MSDP Peer";
          }
          container cache-sa-state {
            description
              "Configure this systems SA cache access-lists";
            leaf list {
              type xr:Cisco-ios-xr-string {
                length "1..32" {
                  description
                    "Access list name";
                }
              }
              description
                "Access-list";
            }
            leaf rp-list {
              type xr:Cisco-ios-xr-string {
                length "1..32" {
                  description
                    "Access list name";
                }
              }
              description
                "Access-list for originating RP";
            }
          }
          leaf cache-sa-holdtime {
            type uint32 {
              range "150..3600" {
                description
                  "Holdtime period in secs";
              }
            }
            description
              "Configure Cache SA State holdtime period";
          }
          container sa-filter {
            description
              "Filter SA messages from peer";
            container in {
              description
                "Enable incoming SA filtering";
              leaf list {
                type xr:Cisco-ios-xr-string {
                  length "1..32" {
                    description
                      "Access list name";
                  }
                }
                description
                  "Access-list";
              }
              leaf rp-list {
                type xr:Cisco-ios-xr-string {
                  length "1..32" {
                    description
                      "Access list name";
                  }
                }
                description
                  "Access-list for originating RP";
              }
            }
            container out {
              description
                "Enable outgoing SA filtering";
              leaf list {
                type xr:Cisco-ios-xr-string {
                  length "1..32" {
                    description
                      "Access list name";
                  }
                }
                description
                  "Access-list";
              }
              leaf rp-list {
                type xr:Cisco-ios-xr-string {
                  length "1..32" {
                    description
                      "Access list name";
                  }
                }
                description
                  "Access-list for originating RP";
              }
            }
          }
          leaf default-peer {
            type inet:ipv4-address-no-zone;
            description
              "Default MSDP peer to accept SA messages from";
          }
          container maximum {
            description
              "Maximum state limits";
            leaf external-sa {
              type uint32 {
                range "1..75000" {
                  description
                    "Maximum number of SA accepted by this router";
                }
              }
              description
                "Maximum number of SA accepted by this router in this context";
            }
            leaf peer-external-sa {
              type uint32 {
                range "1..75000" {
                  description
                    "Maximum number of SA accepted by this peer";
                }
              }
              description
                "Maximum number of SA accepted by this peer";
            }
          }
          container keepalive {
            presence "Indicates a keepalive node is configured.";
            description
              "Configure global KeepAlive period for MSDP Peer";
            leaf keepalive-period {
              type uint32 {
                range "1..60" {
                  description
                    "KeepAlive Period in seconds";
                }
              }
              mandatory true;
              description
                "Configure global KeepAlive period for MSDP Peer";
            }
            leaf peer-timeout-period {
              type uint32 {
                range "1..75" {
                  description
                    "Peer Timeout Period in seconds";
                }
              }
              mandatory true;
              description
                "Peer Timeout Period in seconds";
            }
          }
        }
      }
    }
  }
}
