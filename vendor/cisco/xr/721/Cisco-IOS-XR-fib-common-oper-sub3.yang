submodule Cisco-IOS-XR-fib-common-oper-sub3 {
  belongs-to Cisco-IOS-XR-fib-common-oper {
    prefix Cisco-IOS-XR-fib-common-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2020 by Cisco Systems, Inc.
     All rights reserved.";

  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Bag-string {
    type string;
    description
      "Bag string";
  }

  grouping FIB-OC-AFT-PREFIX-STATE {
    description
      "FIB OC AFT PREFIX STATE";
    leaf prefix-index {
      type string;
      description
        "IP prefix or MPLS label";
    }
  }

  grouping FIB-OC-INTERF-REF-STATE {
    description
      "FIB OC INTERF REF STATE";
    leaf interface {
      type string;
      description
        "Interface name";
    }
    leaf subinterface {
      type uint32;
      description
        "Sub-Interface index";
    }
  }

  grouping FIB-OC-INTERF-REF {
    description
      "FIB OC INTERF REF";
    container state {
      description
        "AFT entry interface ref state";
      uses FIB-OC-INTERF-REF-STATE;
    }
  }

  grouping FIB-OC-AFT-PATH-STATE {
    description
      "FIB OC AFT PATH STATE";
    leaf index {
      type uint64;
      description
        "Index";
    }
    leaf weight {
      type uint32;
      description
        "Path Weight";
    }
    leaf ip-address {
      type string;
      description
        "IP address";
    }
    leaf network-instance {
      type Bag-string;
      description
        "VRF name where the nexthop is resolved";
    }
    leaf-list popped-mpls-label-stack {
      type Bag-string;
      description
        "Stack of the Popped mpls labels";
    }
    leaf-list pushed-mpls-label-stack {
      type Bag-string;
      description
        "Next Hop Pushed mpls label stack";
    }
  }

  grouping FIB-OC-AFT-PATH {
    description
      "FIB OC AFT PATH";
    container state {
      description
        "OC AFT entry next-hop state";
      uses FIB-OC-AFT-PATH-STATE;
    }
    container interface-ref {
      description
        "AFT entry next-hop interface ref";
      uses FIB-OC-INTERF-REF;
    }
  }
}
