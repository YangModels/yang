module Cisco-IOS-XR-platform-oper {
  namespace "http://cisco.com/ns/yang/Cisco-IOS-XR-platform-oper";
  prefix platform-oper;

  import Cisco-IOS-XR-types {
    prefix xr;
  }
  import cisco-semver {
    prefix semver;
  }
  include Cisco-IOS-XR-platform-oper-sub1 {
    revision-date 2020-05-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platform package operational data.
     
     This module contains definitions
     for the following management objects:
       platform: Platform information
     
     Copyright (c) 2013-2020 by Cisco Systems, Inc.
     All rights reserved.";

  revision 2020-05-14 {
    description
      "New model, replaces Cisco-IOS-XR-plat-chas-invmgr-ng-oper";
    semver:module-version "1.0.0";
  }
  revision 2019-04-05 {
    description
      "Establish semantic version baseline.";
  }
  revision 2015-11-09 {
    description
      "IOS XR 6.0 revision.";
  }

  grouping STATE {
    description
      "Common node of instance, slot";
    container state {
      description
        "State information";
      uses PLATFORM-INFO;
    }
  }

  container platform {
    config false;
    description
      "Platform information";
    container racks {
      description
        "Table of racks";
      list rack {
        key "rack-name";
        description
          "Rack name";
        container slots {
          description
            "Table of slots";
          list slot {
            key "slot-name";
            description
              "Slot name";
            container instances {
              description
                "Table of Instances";
              list instance {
                key "instance-name";
                description
                  "Instance name";
                leaf instance-name {
                  type string;
                  description
                    "Instance name";
                }
                uses STATE;
              }
            }
            leaf slot-name {
              type xr:Cisco-ios-xr-string;
              description
                "Slot name";
            }
            uses STATE;
          }
        }
        leaf rack-name {
          type xr:Cisco-ios-xr-string;
          description
            "Rack name";
        }
      }
    }
  }
}
