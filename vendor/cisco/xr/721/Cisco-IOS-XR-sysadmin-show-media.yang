module Cisco-IOS-XR-sysadmin-show-media {
  namespace "http://www.cisco.com/ns/yang/Cisco-IOS-XR-sysadmin-show-media";
  prefix mediasvrh;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin to
     report back memory utilization in sysadmin.
     
     Copyright (c) 2018-2020 by Cisco Systems, Inc.
     All rights reserved.";

  revision 2020-04-08 {
    description
      "Suppressing raw output";
    semver:module-version "1.0.0";
  }
  revision 2019-04-15 {
    description
      "Establish semantic version baseline.";
    semver:module-version "1.0.0";
  }
  revision 2019-02-06 {
    description
      "Initial revision";
  }

  container ShowMedia {
    config false;
    description
      "Show the memory usage in sysadmin";
    list all-locations {
      key "location";
      description
        "all location, from where the information is to be fetched";
      leaf location {
        type string;
        description
          "Location, from where the information is to be fetched";
      }
      leaf show_media_report {
        type string;
        description
          "show media report";
      }
    }
  }
}
