module Cisco-IOS-XR-sysadmin-ethsw-esdma-sfp {
  namespace "http://www.cisco.com/ns/yang/Cisco-IOS-XR-sysadmin-ethsw-esdma-sfp";
  prefix esdma_sfp;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch sfp' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-sfp-summary-group {
    container summary {
      tailf:callpoint "esdma_switch_sfp_summary_data";
      tailf:info "Display SFP summary information";
      list location {
        key "rack card switch-id";
        tailf:info "Location information for SFP information";
        tailf:cli-full-command;
        tailf:cli-key-format "$(1)/$(2)/$(3)";
        tailf:cli-suppress-table;
        tailf:cli-show-template "$(sfp-port-iter|show)";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        list sfp-port-iter {
          key "sfp-port";
          tailf:cli-drop-node-name;
          tailf:cli-table-legend
            "Rack  Card  Switch
             ------------------
             $(../rack|ljust:4)  $(../card|ljust:4)  $(../switch-id|ljust:6)
            ";
          tailf:cli-enforce-table;
          leaf sfp-port {
            type esdma_types:esdma-switch-port-type;
            description
              "Switch port";
            tailf:display-column-name "Switch Port";
          }
          leaf sfp-inserted {
            type esdma_types:esdma-switch-sfp-inserted-enum;
            tailf:cli-suppress-show-path;
            tailf:cli-suppress-show-match;
            tailf:display-column-name "SFP Inserted";
          }
          leaf sfp-controller {
            type esdma_types:esdma-switch-sfp-controller-enum;
            tailf:cli-suppress-show-path;
            tailf:cli-suppress-show-match;
            tailf:display-column-name "SFP Controller";
          }
          leaf sfp-type {
            type esdma_types:esdma-switch-sfp-type-enum;
            tailf:cli-suppress-show-path;
            tailf:cli-suppress-show-match;
            tailf:display-column-name "SFP Type";
          }
          leaf connects-to {
            type string;
            description
              "Indicates what this port connects to";
            tailf:cli-suppress-show-path;
            tailf:cli-suppress-show-match;
            tailf:cli-preformatted;
            tailf:display-column-name "Connects To";
          }
        }
      }
    }
  }

  grouping switch-sfp-detail-group {
    container detail {
      tailf:cli-incomplete-show-path;
      tailf:callpoint "esdma_switch_sfp_detail_data";
      tailf:info "Display SFP detail";
      list location {
        key "rack card switch-id";
        tailf:info "Location information for SFP information";
        tailf:cli-incomplete-show-path;
        tailf:cli-suppress-table;
        tailf:cli-key-format "$(1)/$(2)/$(3)";
        leaf rack {
          type esdma_types:esdma-rack-num-enum;
        }
        leaf card {
          type esdma_types:esdma-cpu;
        }
        leaf switch-id {
          type esdma_types:esdma-switch-type-enum;
        }
        list sfp-port-iter {
          key "sfp-port";
          tailf:cli-drop-node-name;
          tailf:cli-full-command;
          tailf:cli-suppress-table;
          tailf:cli-show-template-enter "SFP/QSFP EEPROM Data for Switch Port $(sfp-port)\n";
          tailf:cli-show-template
            "$($(sfp-inserted)==Yes?$($(sfp-type)==SFP-10G-SR?$(sfp-details|show))$($(sfp-type)==SFP-10G-LR?$(sfp-details|show))$($(sfp-type)==SFP-10G-LRM?$(sfp-details|show))$($(sfp-type)==SFP-1G-SX?$(sfp-details|show))$($(sfp-type)==SFP-1G-LX?$(sfp-details|show))$($(sfp-type)==SFP-1000Base-T?$(sfp-details|show))$($(sfp-type)==SFP-40G-SR4?$(qsfp-details|show))$($(sfp-type)==SFP-40G-LR4?$(qsfp-details|show))$($(sfp-type)==None?  Unknown SFP
             )$($(sfp-type)==Unspecified?  Unknown SFP
             ))$($(sfp-inserted)!=Yes?    No SFP inserted
             )";
          leaf sfp-port {
            type esdma_types:esdma-switch-port-type;
            description
              "Switch port";
            tailf:display-column-name "Switch Port";
            tailf:alt-name "SFP EEPROM port: ";
          }
          leaf sfp-inserted {
            type esdma_types:esdma-switch-sfp-inserted-enum;
            tailf:cli-suppress-show-path;
            tailf:cli-suppress-show-match;
          }
          leaf sfp-type {
            type esdma_types:esdma-switch-sfp-type-enum;
            tailf:cli-suppress-show-path;
            tailf:cli-suppress-show-match;
            tailf:display-column-name "SFP Type";
          }
          container sfp-details {
            tailf:cli-drop-node-name;
            tailf:cli-full-show-path;
            tailf:cli-show-template
              "$(sfp-port-detail|show:indent=4)
               SFP MSA Data
               $(sfp-msa-data|show:indent=3)
               $(sfp-diag-analog-info|show:indent=4)$(sfp-diag-data1|show:indent=3)$(sfp-diag-user-info|show)$(sfp-diag-data2|show:indent=3)
              ";
            container sfp-port-detail {
              tailf:cli-drop-node-name;
              tailf:cli-full-show-path;
              leaf sfp-tranceiver-type {
                type esdma_types:esdma-switch-sfp-tranceiver-type-enum;
                tailf:alt-name "Transceiver Type: ";
              }
              leaf sfp-tranceiver-code {
                type esdma_types:esdma-switch-sfp-type-enum;
                tailf:alt-name "Transceiver Code: ";
              }
              leaf sfp-encoding {
                type esdma_types:esdma-sfp-encoding-enum;
                tailf:alt-name "Encoding: ";
              }
              leaf sfp-bit-rate {
                type uint32;
                tailf:alt-name "Bit Rate (Mbps): ";
              }
              leaf sfp-link-reach-9u-fiber_KM {
                when "../sfp-link-reach-9u-fiber_KM != '0'";
                type uint32;
                tailf:display-when "../sfp-link-reach-9u-fiber_KM != '0'";
                tailf:alt-name "Link Reach for 9u Fiber (kilometers): ";
              }
              leaf sfp-link-reach-9u-fiber_M {
                when "../sfp-link-reach-9u-fiber_M != '0'";
                type uint32;
                tailf:display-when "../sfp-link-reach-9u-fiber_M != '0'";
                tailf:alt-name "Link Reach for 9u Fiber (meters): ";
              }
              leaf sfp-link-reach-50u-fiber_M {
                when "../sfp-link-reach-50u-fiber_M != '0'";
                type uint32;
                tailf:display-when "../sfp-link-reach-50u-fiber_M != '0'";
                tailf:alt-name "Link Reach for 50u (OM2) Fiber (meters): ";
              }
              leaf sfp-link-reach-62_5u-fiber_M {
                when "../sfp-link-reach-62_5u-fiber_M != '0'";
                type uint32;
                tailf:display-when "../sfp-link-reach-62_5u-fiber_M != '0'";
                tailf:alt-name "Link Reach for 62.5u (OM1) Fiber (meters): ";
              }
              leaf sfp-link-reach-copper_M {
                when "../sfp-link-reach-copper_M != '0'";
                type uint32;
                tailf:display-when "../sfp-link-reach-copper_M != '0'";
                tailf:alt-name "Link Reach for Copper (meters): ";
              }
              leaf sfp-vendor-name {
                type string;
                tailf:alt-name "Vendor Name: ";
                tailf:cli-preformatted;
              }
              leaf sfp-vendor-oui {
                type string;
                tailf:alt-name "Vendor OUI: ";
                tailf:cli-preformatted;
              }
              leaf sfp-vendor-part-num {
                type string;
                tailf:alt-name "Vendor Part #: ";
                tailf:cli-preformatted;
              }
              leaf sfp-laser-wavelength {
                when "../sfp-laser-wavelength != '0'";
                type uint32;
                tailf:display-when "../sfp-laser-wavelength != '0'";
                tailf:alt-name "Laser Wavelength (nano-meters): ";
              }
              leaf sfp-options {
                type bits {
                  bit LRO {
                    position 0;
                  }
                  bit PowerLvl2 {
                    position 1;
                  }
                  bit CooledXcvr {
                    position 2;
                  }
                  bit LOS {
                    position 9;
                  }
                  bit SignalDet {
                    position 10;
                  }
                  bit TxFault {
                    position 11;
                  }
                  bit TxDisable {
                    position 12;
                  }
                  bit RateSel {
                    position 13;
                  }
                }
                tailf:alt-name "Implemented Options: ";
                tailf:cli-preformatted;
              }
              leaf sfp-vendor-serial-num {
                type string;
                tailf:alt-name "Vendor Serial #: ";
                tailf:cli-preformatted;
              }
              leaf sfp-data-code {
                type string;
                tailf:alt-name "Date Code (yy/mm/dd): ";
                tailf:cli-preformatted;
              }
              leaf sfp-diag-monitoring {
                type bits {
                  bit AvePwrMon {
                    position 3;
                  }
                  bit External {
                    position 4;
                  }
                  bit Internal {
                    position 5;
                  }
                  bit DigDiagMon {
                    position 6;
                  }
                }
                tailf:alt-name "Diagnostic Monitoring: ";
                tailf:cli-preformatted;
              }
              leaf sfp-enhanced-options {
                type bits {
                  bit RateSelCtrl {
                    position 1;
                  }
                  bit ApplSelect {
                    position 2;
                  }
                  bit RateSelCtrlMon {
                    position 3;
                  }
                  bit RxLosMon {
                    position 4;
                  }
                  bit TxFaultMon {
                    position 5;
                  }
                  bit TxDisableCtrlMon {
                    position 6;
                  }
                  bit AlarmWarningFlags {
                    position 7;
                  }
                }
                tailf:cli-column-width "30";
                tailf:alt-name "Enhanced Options: ";
                tailf:cli-preformatted;
              }
            }
            container sfp-msa-data {
              tailf:cli-drop-node-name;
              tailf:cli-full-show-path;
              leaf sfp-msa-0x00 {
                type string;
                tailf:cli-drop-node-name;
                tailf:cli-preformatted;
              }
              leaf sfp-msa-0x10 {
                type string;
                tailf:cli-drop-node-name;
                tailf:cli-preformatted;
              }
              leaf sfp-msa-0x20 {
                type string;
                tailf:cli-drop-node-name;
                tailf:cli-preformatted;
              }
              leaf sfp-msa-0x30 {
                type string;
                tailf:cli-drop-node-name;
                tailf:cli-preformatted;
              }
              leaf sfp-msa-0x40 {
                type string;
                tailf:cli-drop-node-name;
                tailf:cli-preformatted;
              }
              leaf sfp-msa-0x50 {
                type string;
                tailf:cli-drop-node-name;
                tailf:cli-preformatted;
              }
            }
            container sfp-diag-analog-info {
              tailf:cli-drop-node-name;
              tailf:cli-full-show-path;
              tailf:cli-show-template
                "$($(../sfp-port-detail/sfp-tranceiver-code)!=SFP-1000Base-T?$(Thresholds|show)
                 $(Real-Time-Data|show)
                 )";
              container Thresholds {
                tailf:cli-drop-node-name;
                tailf:cli-show-template
                  "Threshold Data
                       Temperature
                   $(Temperature|show:indent=8)    Voltage
                   $(Voltage|show:indent=8)    Bias
                   $(Bias|show:indent=8)    Tx Power
                   $(Tx-Power|show:indent=8)    Rx Power
                   $(Rx-Power|show:indent=8)";
                container Temperature {
                  tailf:cli-drop-node-name;
                  leaf temp-alarm-high {
                    type string;
                    tailf:alt-name "Alarm High: ";
                    tailf:cli-preformatted;
                  }
                  leaf temp-warning-high {
                    type string;
                    tailf:alt-name "Warning High: ";
                    tailf:cli-preformatted;
                  }
                  leaf temp-warning-low {
                    type string;
                    tailf:alt-name "Warning Low: ";
                    tailf:cli-preformatted;
                  }
                  leaf temp-alarm-low {
                    type string;
                    tailf:alt-name "Alarm Low: ";
                    tailf:cli-preformatted;
                  }
                }
                container Voltage {
                  tailf:cli-drop-node-name;
                  leaf volt-alarm-high {
                    type string;
                    tailf:alt-name "Alarm High: ";
                    tailf:cli-preformatted;
                  }
                  leaf volt-warning-high {
                    type string;
                    tailf:alt-name "Warning High: ";
                    tailf:cli-preformatted;
                  }
                  leaf volt-warning-low {
                    type string;
                    tailf:alt-name "Warning Low: ";
                    tailf:cli-preformatted;
                  }
                  leaf volt-alarm-low {
                    type string;
                    tailf:alt-name "Alarm Low: ";
                    tailf:cli-preformatted;
                  }
                }
                container Bias {
                  tailf:cli-drop-node-name;
                  leaf bias-alarm-high {
                    type string;
                    tailf:alt-name "Alarm High: ";
                    tailf:cli-preformatted;
                  }
                  leaf bias-warning-high {
                    type string;
                    tailf:alt-name "Warning High: ";
                    tailf:cli-preformatted;
                  }
                  leaf bias-warning-low {
                    type string;
                    tailf:alt-name "Warning Low: ";
                    tailf:cli-preformatted;
                  }
                  leaf bias-alarm-low {
                    type string;
                    tailf:alt-name "Alarm Low: ";
                    tailf:cli-preformatted;
                  }
                }
                container Tx-Power {
                  tailf:cli-drop-node-name;
                  leaf tx-power-alarm-high {
                    type string;
                    tailf:alt-name "Alarm High: ";
                    tailf:cli-preformatted;
                  }
                  leaf tx-power-warning-high {
                    type string;
                    tailf:alt-name "Warning High: ";
                    tailf:cli-preformatted;
                  }
                  leaf tx-power-warning-low {
                    type string;
                    tailf:alt-name "Warning Low: ";
                    tailf:cli-preformatted;
                  }
                  leaf tx-power-alarm-low {
                    type string;
                    tailf:alt-name "Alarm Low: ";
                    tailf:cli-preformatted;
                  }
                }
                container Rx-Power {
                  tailf:cli-drop-node-name;
                  leaf rx-power-alarm-high {
                    type string;
                    tailf:alt-name "Alarm High: ";
                    tailf:cli-preformatted;
                  }
                  leaf rx-power-warning-high {
                    type string;
                    tailf:alt-name "Warning High: ";
                    tailf:cli-preformatted;
                  }
                  leaf rx-power-warning-low {
                    type string;
                    tailf:alt-name "Warning Low: ";
                    tailf:cli-preformatted;
                  }
                  leaf rx-power-alarm-low {
                    type string;
                    tailf:alt-name "Alarm Low: ";
                    tailf:cli-preformatted;
                  }
                }
              }
              container Real-Time-Data {
                tailf:cli-drop-node-name;
                tailf:cli-show-template
                  "Real Time Data
                   $(Current|show:indent=4)";
                container Current {
                  tailf:cli-drop-node-name;
                  leaf cur-temperature {
                    type string;
                    tailf:alt-name "Temperature: ";
                    tailf:cli-preformatted;
                  }
                  leaf cur-voltage {
                    type string;
                    tailf:alt-name "Voltage: ";
                    tailf:cli-preformatted;
                  }
                  leaf cur-bias {
                    type string;
                    tailf:alt-name "Bias: ";
                    tailf:cli-preformatted;
                  }
                  leaf cur-tx-power {
                    type string;
                    tailf:alt-name "Tx Power: ";
                    tailf:cli-preformatted;
                  }
                  leaf cur-rx-power {
                    type string;
                    tailf:alt-name "Rx Power: ";
                    tailf:cli-preformatted;
                  }
                  leaf optional-status-control {
                    type bits {
                      bit DataReadyBar {
                        position 0;
                      }
                      bit RxLOS {
                        position 1;
                      }
                      bit TxFault {
                        position 2;
                      }
                      bit SoftRateSel0Eq1 {
                        position 3;
                      }
                      bit RateSel0Eq1 {
                        position 4;
                      }
                      bit RateSel1Eq1 {
                        position 5;
                      }
                      bit SoftTxDisable {
                        position 6;
                      }
                      bit TxDisable {
                        position 7;
                      }
                    }
                    tailf:cli-column-width "30";
                    tailf:alt-name "Current Status/Control: ";
                    tailf:cli-preformatted;
                  }
                }
              }
            }
            container sfp-diag-data1 {
              tailf:cli-drop-node-name;
              tailf:cli-full-show-path;
              tailf:cli-show-template
                "$($(../sfp-port-detail/sfp-tranceiver-code)!=SFP-1000Base-T?SFP A2 Data [Lower]
                 $(optical-sfp-diag|show)
                 )";
              container optical-sfp-diag {
                tailf:cli-drop-node-name;
                leaf sfp-diag-0x00 {
                  type string;
                  tailf:cli-drop-node-name;
                  tailf:cli-preformatted;
                }
                leaf sfp-diag-0x10 {
                  type string;
                  tailf:cli-drop-node-name;
                  tailf:cli-preformatted;
                }
                leaf sfp-diag-0x20 {
                  type string;
                  tailf:cli-drop-node-name;
                  tailf:cli-preformatted;
                }
                leaf sfp-diag-0x30 {
                  type string;
                  tailf:cli-drop-node-name;
                  tailf:cli-preformatted;
                }
                leaf sfp-diag-0x40 {
                  type string;
                  tailf:cli-drop-node-name;
                  tailf:cli-preformatted;
                }
                leaf sfp-diag-0x50 {
                  type string;
                  tailf:cli-drop-node-name;
                  tailf:cli-preformatted;
                }
                leaf sfp-diag-0x60 {
                  type string;
                  tailf:cli-drop-node-name;
                  tailf:cli-preformatted;
                }
                leaf sfp-diag-0x70 {
                  type string;
                  tailf:cli-drop-node-name;
                  tailf:cli-preformatted;
                }
              }
            }
            container sfp-diag-user-info {
              tailf:cli-drop-node-name;
              tailf:cli-full-show-path;
              tailf:cli-show-template
                "$($(../sfp-port-detail/sfp-tranceiver-code)!=SFP-1000Base-T?Cisco SFP Information
                 $(cisco-data|show:indent=4)
                 )";
              container cisco-data {
                tailf:cli-drop-node-name;
                leaf cisco-clei-code {
                  type string;
                  tailf:alt-name "CLEI Code: ";
                  tailf:cli-preformatted;
                }
                leaf cisco-part-number {
                  type string;
                  tailf:alt-name "Part Number: ";
                  tailf:cli-preformatted;
                }
                leaf cisco-min-temperature {
                  type int8;
                  tailf:alt-name "Minimum Temperature (C): ";
                }
                leaf cisco-max-temperature {
                  type int8;
                  tailf:alt-name "Maximum Temperature (C): ";
                }
                leaf cisco-product-id {
                  type string;
                  tailf:alt-name "Product Id: ";
                  tailf:cli-preformatted;
                }
              }
            }
            container sfp-diag-data2 {
              tailf:cli-drop-node-name;
              tailf:cli-full-show-path;
              tailf:cli-show-template
                "$($(../sfp-port-detail/sfp-tranceiver-code)!=SFP-1000Base-T?SFP A2 Data [Upper]
                 $(optical-sfp-diag|show)
                 )";
              container optical-sfp-diag {
                tailf:cli-drop-node-name;
                leaf sfp-diag-0x80 {
                  type string;
                  tailf:cli-drop-node-name;
                  tailf:cli-preformatted;
                }
                leaf sfp-diag-0x90 {
                  type string;
                  tailf:cli-drop-node-name;
                  tailf:cli-preformatted;
                }
                leaf sfp-diag-0xA0 {
                  type string;
                  tailf:cli-drop-node-name;
                  tailf:cli-preformatted;
                }
                leaf sfp-diag-0xB0 {
                  type string;
                  tailf:cli-drop-node-name;
                  tailf:cli-preformatted;
                }
                leaf sfp-diag-0xC0 {
                  type string;
                  tailf:cli-drop-node-name;
                  tailf:cli-preformatted;
                }
                leaf sfp-diag-0xD0 {
                  type string;
                  tailf:cli-drop-node-name;
                  tailf:cli-preformatted;
                }
                leaf sfp-diag-0xE0 {
                  type string;
                  tailf:cli-drop-node-name;
                  tailf:cli-preformatted;
                }
                leaf sfp-diag-0xF0 {
                  type string;
                  tailf:cli-drop-node-name;
                  tailf:cli-preformatted;
                }
              }
            }
          }
          container qsfp-details {
            tailf:cli-drop-node-name;
            tailf:cli-full-show-path;
            tailf:cli-show-template
              "$(qsfp_page_A0_0_data|show:indent=4)
               $(qsfp_page_A0_3_data|show:indent=4)
               $(qsfp_page_A0_data|show:indent=4)";
            container qsfp_page_A0_data {
              tailf:cli-drop-node-name;
              tailf:cli-show-template
                "Real Time Data
                 $(qsfp-real-time-data|show:indent=4)
                 $(qsfp-real-time-status-flags|show:indent=4)";
              container qsfp-real-time-data {
                tailf:cli-drop-node-name;
                tailf:cli-show-template
                  "$(qsfp-temp-volt|show:indent=4)    Tx Bias
                   $(qsfp-tx-channel-bias|show:indent=8)    Tx Output Power
                   $(qsfp-tx-output-power|show:indent=8)    Rx Input Power
                   $(qsfp-rx-input-power|show:indent=8)";
                container qsfp-temp-volt {
                  tailf:cli-drop-node-name;
                  leaf module-monitor-temperature {
                    type string;
                    tailf:alt-name "Temperature: ";
                    tailf:cli-preformatted;
                  }
                  leaf module-monitor-voltage {
                    type string;
                    tailf:alt-name "Voltage: ";
                    tailf:cli-preformatted;
                  }
                }
                container qsfp-tx-channel-bias {
                  tailf:cli-drop-node-name;
                  leaf channel-monitor-Tx1-Bias {
                    type string;
                    tailf:alt-name "Channel 1: ";
                    tailf:cli-preformatted;
                  }
                  leaf channel-monitor-Tx2-Bias {
                    type string;
                    tailf:alt-name "Channel 2: ";
                    tailf:cli-preformatted;
                  }
                  leaf channel-monitor-Tx3-Bias {
                    type string;
                    tailf:alt-name "Channel 3: ";
                    tailf:cli-preformatted;
                  }
                  leaf channel-monitor-Tx4-Bias {
                    type string;
                    tailf:alt-name "Channel 4: ";
                    tailf:cli-preformatted;
                  }
                }
                container qsfp-tx-output-power {
                  tailf:cli-drop-node-name;
                  leaf channel-monitor-Tx1-Power {
                    type string;
                    tailf:alt-name "Channel 1: ";
                    tailf:cli-preformatted;
                  }
                  leaf channel-monitor-Tx2-Power {
                    type string;
                    tailf:alt-name "Channel 2: ";
                    tailf:cli-preformatted;
                  }
                  leaf channel-monitor-Tx3-Power {
                    type string;
                    tailf:alt-name "Channel 3: ";
                    tailf:cli-preformatted;
                  }
                  leaf channel-monitor-Tx4-Power {
                    type string;
                    tailf:alt-name "Channel 4: ";
                    tailf:cli-preformatted;
                  }
                }
                container qsfp-rx-input-power {
                  tailf:cli-drop-node-name;
                  leaf channel-monitor-Rx1-Power {
                    type string;
                    tailf:alt-name "Channel 1: ";
                    tailf:cli-preformatted;
                  }
                  leaf channel-monitor-Rx2-Power {
                    type string;
                    tailf:alt-name "Channel 2: ";
                    tailf:cli-preformatted;
                  }
                  leaf channel-monitor-Rx3-Power {
                    type string;
                    tailf:alt-name "Channel 3: ";
                    tailf:cli-preformatted;
                  }
                  leaf channel-monitor-Rx4-Power {
                    type string;
                    tailf:alt-name "Channel 4: ";
                    tailf:cli-preformatted;
                  }
                }
              }
              container qsfp-real-time-status-flags {
                tailf:cli-drop-node-name;
                tailf:cli-show-template
                  "    Real Time Status 
                   $(qsfp-real-time-status|show:indent=8)    Real Time Interrupt Flags
                       (Empty value displayed when no flag is set)
                   $(qsfp-real-time-interrupt-flags|show:indent=8)";
                container qsfp-real-time-status {
                  tailf:cli-drop-node-name;
                  leaf qsfp-page-select {
                    type string;
                    tailf:alt-name "Page Select: ";
                    tailf:cli-preformatted;
                  }
                  leaf qsfp-status {
                    type bits {
                      bit DataNotReady {
                        position 8;
                      }
                      bit INTL {
                        position 9;
                      }
                      bit FlatMemory {
                        position 10;
                      }
                    }
                    description
                      "Status Indicator";
                    tailf:alt-name "Status Indicator (value may be empty):";
                    tailf:cli-column-width "30";
                    tailf:cli-preformatted;
                  }
                }
                container qsfp-real-time-interrupt-flags {
                  tailf:cli-drop-node-name;
                  leaf qsfp-int-flags-LOS-Indicator {
                    type bits {
                      bit L-Rx1-LOS {
                        position 0;
                      }
                      bit L-Rx2-LOS {
                        position 1;
                      }
                      bit L-Rx3-LOS {
                        position 2;
                      }
                      bit L-Rx4-LOS {
                        position 3;
                      }
                      bit L-Tx1-LOS {
                        position 4;
                      }
                      bit L-Tx2-LOS {
                        position 5;
                      }
                      bit L-Tx3-LOS {
                        position 6;
                      }
                      bit L-Tx4-LOS {
                        position 7;
                      }
                    }
                    description
                      "Interrupt Flag for TX/RX LOS Indicator";
                    tailf:alt-name "TX/RX LOS Indicator:";
                    tailf:cli-column-width "30";
                    tailf:cli-preformatted;
                  }
                  leaf qsfp-int-flags-Fault-Indicator {
                    type bits {
                      bit L-Tx1-Fault {
                        position 0;
                      }
                      bit L-Tx2-Fault {
                        position 1;
                      }
                      bit L-Tx3-Fault {
                        position 2;
                      }
                      bit L-Tx4-Fault {
                        position 3;
                      }
                    }
                    description
                      "Interrupt Flag for TX Fault Indicator";
                    tailf:alt-name "TX Fault Indicator:";
                    tailf:cli-column-width "30";
                    tailf:cli-preformatted;
                  }
                  leaf qsfp-int-flags-Temperature-Indicator {
                    type bits {
                      bit Initialization-Complete-Flag {
                        position 0;
                      }
                      bit L-Temp-Low-Warning {
                        position 4;
                      }
                      bit L-Temp-High-Warning {
                        position 5;
                      }
                      bit L-Temp-Low-Alarm {
                        position 6;
                      }
                      bit L-Temp-High-Alarm {
                        position 7;
                      }
                    }
                    description
                      "Interrupt Flag for high/low alarm/warning temperature Indicator";
                    tailf:alt-name "Temperature Alarm/Warning Indicator:";
                    tailf:cli-column-width "30";
                    tailf:cli-preformatted;
                  }
                  leaf qsfp-int-flags-Supply-Voltage-Indicator {
                    type bits {
                      bit L-Vcc-Low-Warning {
                        position 4;
                      }
                      bit L-Vcc-High-Warning {
                        position 5;
                      }
                      bit L-Vcc-Low-Alarm {
                        position 6;
                      }
                      bit L-Vcc-High-Alarm {
                        position 7;
                      }
                    }
                    description
                      "Interrupt Flag for high/low alarm/warning Voltage Indicator";
                    tailf:alt-name "Voltage Alarm/Warning Indicator:";
                    tailf:cli-column-width "30";
                    tailf:cli-preformatted;
                  }
                  leaf qsfp-int-flags-Rx-Power-Indicator {
                    type bits {
                      bit L-Rx2-Power-Low-Warning {
                        position 0;
                      }
                      bit L-Rx2-Power-High-Warning {
                        position 1;
                      }
                      bit L-Rx2-Power-Low-Alarm {
                        position 2;
                      }
                      bit L-Rx2-Power-High-Alarm {
                        position 3;
                      }
                      bit L-Rx1-Power-Low-Warning {
                        position 4;
                      }
                      bit L-Rx1-Power-High-Warning {
                        position 5;
                      }
                      bit L-Rx1-Power-Low-Alarm {
                        position 6;
                      }
                      bit L-Rx1-Power-High-Alarm {
                        position 7;
                      }
                      bit L-Rx4-Power-Low-Warning {
                        position 8;
                      }
                      bit L-Rx4-Power-High-Warning {
                        position 9;
                      }
                      bit L-Rx4-Power-Low-Alarm {
                        position 10;
                      }
                      bit L-Rx4-Power-High-Alarm {
                        position 11;
                      }
                      bit L-Rx3-Power-Low-Warning {
                        position 12;
                      }
                      bit L-Rx3-Power-High-Warning {
                        position 13;
                      }
                      bit L-Rx3-Power-Low-Alarm {
                        position 14;
                      }
                      bit L-Rx3-Power-High-Alarm {
                        position 15;
                      }
                    }
                    description
                      "Interrupt Flag for high/low alarm/warning Rx Power in Channel 1/2/3/4 Indicator";
                    tailf:alt-name "Rx Power Alarm/Warning Indicator (Channel 1/2/3/4):";
                    tailf:cli-column-width "30";
                    tailf:cli-preformatted;
                  }
                  leaf qsfp-int-flags-Tx-Bias-Indicator {
                    type bits {
                      bit L-Tx2-Bias-Low-Warning {
                        position 0;
                      }
                      bit L-Tx2-Bias-High-Warning {
                        position 1;
                      }
                      bit L-Tx2-Bias-Low-Alarm {
                        position 2;
                      }
                      bit L-Tx2-Bias-High-Alarm {
                        position 3;
                      }
                      bit L-Tx1-Bias-Low-Warning {
                        position 4;
                      }
                      bit L-Tx1-Bias-High-Warning {
                        position 5;
                      }
                      bit L-Tx1-Bias-Low-Alarm {
                        position 6;
                      }
                      bit L-Tx1-Bias-High-Alarm {
                        position 7;
                      }
                      bit L-Tx4-Bias-Low-Warning {
                        position 8;
                      }
                      bit L-Tx4-Bias-High-Warning {
                        position 9;
                      }
                      bit L-Tx4-Bias-Low-Alarm {
                        position 10;
                      }
                      bit L-Tx4-Bias-High-Alarm {
                        position 11;
                      }
                      bit L-Tx3-Bias-Low-Warning {
                        position 12;
                      }
                      bit L-Tx3-Bias-High-Warning {
                        position 13;
                      }
                      bit L-Tx3-Bias-Low-Alarm {
                        position 14;
                      }
                      bit L-Tx3-Bias-High-Alarm {
                        position 15;
                      }
                    }
                    description
                      "Interrupt Flag for high/low alarm/warning Tx Bias in Channel 1/2/3/4 Indicator";
                    tailf:alt-name "Tx Bias Alarm/Warning Indicator (Channel 1/2/3/4):";
                    tailf:cli-column-width "30";
                    tailf:cli-preformatted;
                  }
                }
              }
            }
            container qsfp_page_A0_0_data {
              tailf:cli-drop-node-name;
              leaf qsfp-identifier {
                type esdma_types:esdma-switch-sfp-tranceiver-type-enum;
                tailf:alt-name "Transceiver Type: ";
              }
              leaf qsfp-transceiver {
                type esdma_types:esdma-qsfp-transceiver-enum;
                tailf:alt-name "Transceiver Code: ";
              }
              leaf qsfp-extended-transceiver {
                type string;
                tailf:alt-name "Extended Transceiver Type: ";
                tailf:cli-preformatted;
              }
              leaf qsfp-encoding {
                type esdma_types:esdma-sfp-encoding-enum;
                tailf:alt-name "Encoding: ";
              }
              leaf qsfp-bit-rate {
                type uint32;
                tailf:alt-name "Bit rate (Mbps): ";
              }
              leaf qsfp-link-length-standard-SM-fiber_KM {
                when "../qsfp-link-length-standard-SM-fiber_KM != '0'";
                type uint32;
                tailf:display-when "../qsfp-link-length-standard-SM-fiber_KM != '0'";
                tailf:alt-name "Link Length for standard SM Fiber (kilometers): ";
              }
              leaf qsfp-link-length-OM3-50u-fiber_M {
                when "../qsfp-link-length-OM3-50u-fiber_M != '0'";
                type uint32;
                tailf:display-when "../qsfp-link-length-OM3-50u-fiber_M != '0'";
                tailf:alt-name "Link Length for 50u (OM3) fiber (meters): ";
              }
              leaf qsfp-link-length-OM2-50u-fiber_M {
                when "../qsfp-link-length-OM2-50u-fiber_M != '0'";
                type uint32;
                tailf:display-when "../qsfp-link-length-OM2-50u-fiber_M != '0'";
                tailf:alt-name "Link Length for 50u (OM2) fiber (meters): ";
              }
              leaf qsfp-link-length-OM1-62_5u-fiber_M {
                when "../qsfp-link-length-OM1-62_5u-fiber_M != '0'";
                type uint32;
                tailf:display-when "../qsfp-link-length-OM1-62_5u-fiber_M != '0'";
                tailf:alt-name "Link Length for 62.5u (OM1) fiber (meters): ";
              }
              leaf qsfp-link-length-Copper-Cable-Assembly-fiber_M {
                when "../qsfp-link-length-Copper-Cable-Assembly-fiber_M  != '0'";
                type uint32;
                tailf:display-when "../qsfp-link-length-Copper-Cable-Assembly-fiber_M  != '0'";
                tailf:alt-name "Link Length for Copper Cable Assembly fiber (meters): ";
              }
              leaf qsfp-device-tech {
                type string;
                tailf:alt-name "Device and Transmitter Technology: ";
                tailf:cli-preformatted;
              }
              leaf qsfp-vendor-name {
                type string;
                tailf:alt-name "Vendor Name: ";
                tailf:cli-preformatted;
              }
              leaf qsfp-vendor-oui {
                type string;
                tailf:alt-name "Vendor OUI: ";
                tailf:cli-preformatted;
              }
              leaf qsfp-vendor-part-num {
                type string;
                tailf:alt-name "Vendor Part #: ";
                tailf:cli-preformatted;
              }
              leaf qsfp-laser-wavelength {
                when "../qsfp-laser-wavelength != '0'";
                type uint32;
                tailf:display-when "../qsfp-laser-wavelength != '0'";
                tailf:alt-name "Laser Wavelength (nano-meters): ";
              }
              leaf qsfp-wavelength_tolerance {
                type uint32;
                tailf:alt-name "Wavelength Tolerance (nano-meters): ";
              }
              leaf qsfp-max-case-temperature {
                type string;
                tailf:alt-name "Max Case Temperature (C): ";
                tailf:cli-preformatted;
              }
              leaf qsfp-option-value-Rx-amplitude {
                type bits {
                  bit RX-Output-Amplitude-Programming-Implemented {
                    position 0;
                  }
                }
                description
                  "Option value for Rx amplitude ";
                tailf:alt-name "Option value for Rx amplitude: ";
                tailf:cli-column-width "30";
                tailf:cli-preformatted;
              }
              leaf qsfp-option-values-Indicator {
                type bits {
                  bit TxSqlch {
                    position 0;
                  }
                  bit TxSqlchDisable {
                    position 1;
                  }
                  bit RxOutputDisable {
                    position 2;
                  }
                  bit RxSqlchDisable {
                    position 3;
                  }
                  bit TxLOS {
                    position 9;
                  }
                  bit TxSqlchReducePave {
                    position 10;
                  }
                  bit TxFaultSignal {
                    position 11;
                  }
                  bit TxDisable {
                    position 12;
                  }
                  bit RateSelect {
                    position 13;
                  }
                  bit MemPg01 {
                    position 14;
                  }
                  bit MemPg02 {
                    position 15;
                  }
                }
                description
                  "Options Implemented in the QSFP Module";
                tailf:alt-name "Implemented Options: ";
                tailf:cli-column-width "20";
              }
              leaf qsfp-vendor-serial-num {
                type string;
                tailf:alt-name "Vendor Serial #: ";
                tailf:cli-preformatted;
              }
              leaf qsfp-date-code {
                type string;
                tailf:alt-name "Date Code (yy/mm/dd): ";
                tailf:cli-preformatted;
              }
              leaf qsfp-diag-monitoring-type {
                type bits {
                  bit AvgPwrMon {
                    position 3;
                  }
                }
                tailf:alt-name "Diagnostic Monitoring Type: ";
                tailf:cli-preformatted;
              }
            }
            container qsfp_page_A0_3_data {
              tailf:cli-drop-node-name;
              tailf:cli-full-show-path;
              tailf:cli-show-template
                "Threshold Data
                     Temperature
                 $(qsfp-temperature|show:indent=8)    Voltage
                 $(qsfp-voltage|show:indent=8)    Tx Bias
                 $(qsfp-tx-bias|show:indent=8)    Tx Power
                 $(qsfp-tx-power|show:indent=8)    Rx Power
                 $(qsfp-rx-power|show:indent=8)";
              container qsfp-temperature {
                tailf:cli-drop-node-name;
                leaf qsfp-temp-alarm-high {
                  type string;
                  tailf:alt-name "Alarm High: ";
                  tailf:cli-preformatted;
                }
                leaf qsfp-temp-warning-high {
                  type string;
                  tailf:alt-name "Warning High: ";
                  tailf:cli-preformatted;
                }
                leaf qsfp-temp-warning-low {
                  type string;
                  tailf:alt-name "Warning Low: ";
                  tailf:cli-preformatted;
                }
                leaf qsfp-temp-alarm-low {
                  type string;
                  tailf:alt-name "Alarm Low: ";
                  tailf:cli-preformatted;
                }
              }
              container qsfp-voltage {
                tailf:cli-drop-node-name;
                leaf qsfp-volt-alarm-high {
                  type string;
                  tailf:alt-name "Alarm High: ";
                  tailf:cli-preformatted;
                }
                leaf qsfp-volt-warning-high {
                  type string;
                  tailf:alt-name "Warning High: ";
                  tailf:cli-preformatted;
                }
                leaf qsfp-volt-warning-low {
                  type string;
                  tailf:alt-name "Warning Low: ";
                  tailf:cli-preformatted;
                }
                leaf qsfp-volt-alarm-low {
                  type string;
                  tailf:alt-name "Alarm Low: ";
                  tailf:cli-preformatted;
                }
              }
              container qsfp-tx-bias {
                tailf:cli-drop-node-name;
                leaf qsfp-tx-bias-alarm-high {
                  type string;
                  tailf:alt-name "Alarm High: ";
                  tailf:cli-preformatted;
                }
                leaf qsfp-tx-bias-warning-high {
                  type string;
                  tailf:alt-name "Warning High: ";
                  tailf:cli-preformatted;
                }
                leaf qsfp-tx-bias-warning-low {
                  type string;
                  tailf:alt-name "Warning Low: ";
                  tailf:cli-preformatted;
                }
                leaf qsfp-tx-bias-alarm-low {
                  type string;
                  tailf:alt-name "Alarm Low: ";
                  tailf:cli-preformatted;
                }
              }
              container qsfp-tx-power {
                tailf:cli-drop-node-name;
                leaf qsfp-tx-power-alarm-high {
                  type string;
                  tailf:alt-name "Alarm High: ";
                  tailf:cli-preformatted;
                }
                leaf qsfp-tx-power-warning-high {
                  type string;
                  tailf:alt-name "Warning High: ";
                  tailf:cli-preformatted;
                }
                leaf qsfp-tx-power-warning-low {
                  type string;
                  tailf:alt-name "Warning Low: ";
                  tailf:cli-preformatted;
                }
                leaf qsfp-tx-power-alarm-low {
                  type string;
                  tailf:alt-name "Alarm Low: ";
                  tailf:cli-preformatted;
                }
              }
              container qsfp-rx-power {
                tailf:cli-drop-node-name;
                leaf qsfp-rx-power-alarm-high {
                  type string;
                  tailf:alt-name "Alarm High: ";
                  tailf:cli-preformatted;
                }
                leaf qsfp-rx-power-warning-high {
                  type string;
                  tailf:alt-name "Warning High: ";
                  tailf:cli-preformatted;
                }
                leaf qsfp-rx-power-warning-low {
                  type string;
                  tailf:alt-name "Warning Low: ";
                  tailf:cli-preformatted;
                }
                leaf qsfp-rx-power-alarm-low {
                  type string;
                  tailf:alt-name "Alarm Low: ";
                  tailf:cli-preformatted;
                }
              }
            }
          }
        }
      }
    }
  }

  grouping switch-sfp-group {
    container sfp {
      tailf:cli-incomplete-show-path;
      tailf:info "Display SFP information";
      uses switch-sfp-summary-group;
      uses switch-sfp-detail-group;
    }
  }
  tailf:id "http://cisco.com/panini/calvados/esdma/esdma_sfp";
}
