module gearbox_driver {
  namespace "http://www.cisco.com/calvados/calvados_controllers/slice_control/gearbox";
  prefix gearbox_driver;
  import gearbox_driver_types {
    prefix gearbox-driver-types;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2017 by Cisco Systems, Inc.
     All rights reserved.";

  revision "2015-08-30" {
    description "Initial version.";
  }


  grouping gearbox_lane_data {
    list gearbox_lane {
      key "gearbox_lane_id";
      leaf gearbox_lane_id {
        type gearbox-driver-types:gearbox_lane_id_type;
      }
      leaf is_data_available {
        type boolean;
        default "false";
      }
      leaf system_side_lanes {
        type string;
      }
      leaf cdr_lock_status_caui {
        type string;
      }
      leaf line_side_lanes {
        type string;
      }
      leaf lane_status_cdr {
        type string;
      }
      leaf lane_status_sig {
        type string;
      }
      leaf los_status {
        type string;
      }
      leaf system_side_loopback {
        type string;
      }
      leaf lane_side_loopback {
        type string;
      }
    }
  }

  grouping gearbox_summary_info {
    list gearbox_summary {
      key "gearbox_id";
      leaf gearbox_id {
        type gearbox-driver-types:gearbox_id_type;
      }
      leaf is_data_available {
        type boolean;
        default "false";
      }
      leaf inited {
        type boolean;
        default "false";
      }
      leaf gopaque {
        type string;
      }
      leaf gnodeid {
        type string;
      }
      leaf gslice {
        type uint32;
      }
      leaf gport {
        type uint32;
      }
      leaf gdev_addr {
        type uint8;
      }
      leaf gdev_type {
        type uint8;
      }
      leaf gctrace_err_hdl {
        type string;
      }
      leaf gctrace_evt_hdl {
        type string;
      }
      leaf gctrace_intr_hdl {
        type string;
      }
      leaf gnext {
        type string;
      }
      leaf gparent {
        type string;
      }
      leaf syslaneLOSMask {
        type string;
      }
      leaf linelaneLOSMask {
        type string;
      }
      leaf syslaneEnableMask {
        type string;
      }
      leaf linelaneEnableMask {
        type string;
      }
      leaf line_lane_cnt {
        type string;
      }
      leaf sys_lane_cnt {
        type string;
      }
      leaf verbose {
        type boolean;
        default "false";
      }
      leaf dwnld_done {
        type boolean;
        default "false";
      }
      leaf chip_version {
        type string;
      }
      leaf reversion {
        type string;
      }
      leaf firmware_version {
        type string;
      }
      leaf ucode_checksum {
        type string;
      }
      leaf chip_modesel {
        type string;
      }
      leaf chip_ref_clocksel {
        type string;
      }
      leaf line_side_tx_pll {
        type string;
      }
      leaf line_tx_vco {
        type string;
      }
      leaf line_tx_vco_state {
        type string;
      }
      leaf line_side_rx_pll {
        type string;
      }
      leaf line_rx_vco {
        type string;
      }
      leaf line_rx_vco_state {
        type string;
      }
    }
  }

  grouping gearbox_data_show {
    list gearbox {
      key "gearbox_id";
      leaf gearbox_id {
        type gearbox-driver-types:gearbox_id_type;
      }
      uses gearbox_lane_data;
    }
  }
}
