module Cisco-IOS-XR-lpts-punt-flowtrap-cfg {
  namespace "http://cisco.com/ns/yang/Cisco-IOS-XR-lpts-punt-flowtrap-cfg";
  prefix lpts-punt-flowtrap-cfg;

  import Cisco-IOS-XR-types {
    prefix xr;
  }
  import Cisco-IOS-XR-lpts-lib-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-punt-flowtrap package configuration.
     
     This YANG module augments the
       Cisco-IOS-XR-lpts-lib-cfg
     module with configuration data.
     
     Copyright (c) 2013-2017 by Cisco Systems, Inc.
     All rights reserved.";

  revision 2015-11-09 {
    description
      "IOS XR 6.0 revision.";
  }

  typedef Lpts-punt-flowtrap-proto-id {
    type enumeration {
      enum "arp" {
        value 1;
        description
          "ARP";
      }
      enum "default" {
        value 9;
        description
          "All protocols";
      }
    }
    description
      "Lpts punt flowtrap proto id";
  }

  augment "/a1:lpts" {
    description
      "This augment extends the configuration data of
       'Cisco-IOS-XR-lpts-lib-cfg'";
    container punt {
      description
        "Configure penalty timeout value";
      container flowtrap {
        description
          "excessive punt flow trap configuration commands";
        container penalty-rates {
          description
            "Configure penalty policing rate";
          list penalty-rate {
            key "protocol-name";
            description
              "none";
            leaf protocol-name {
              type Lpts-punt-flowtrap-proto-id;
              description
                "none";
            }
            leaf rate {
              type uint32 {
                range "2..100";
              }
              mandatory true;
              description
                "Penalty policer rate in packets-per-second";
            }
          }
        }
        container penalty-timeouts {
          description
            "Configure penalty timeout value";
          list penalty-timeout {
            key "protocol-name";
            description
              "none";
            leaf protocol-name {
              type Lpts-punt-flowtrap-proto-id;
              description
                "none";
            }
            leaf timeout {
              type uint32 {
                range "1..1000";
              }
              mandatory true;
              description
                "Timeout value in minutes";
            }
          }
        }
        container exclude {
          description
            "Exclude an item from all traps";
          container interface-names {
            description
              "none";
            list interface-name {
              key "ifname";
              description
                "Name of interface to exclude from all traps";
              leaf ifname {
                type xr:Interface-name;
                description
                  "Name of interface to exclude from all traps";
              }
              leaf id1 {
                type boolean;
                mandatory true;
                description
                  "Enabled or disabled";
              }
            }
          }
        }
        leaf non-subscriber-interfaces {
          type int32;
          description
            "Enable trap based on source mac on
             non-subscriber interface";
        }
        leaf subscriber-interfaces {
          type boolean;
          description
            "Enable the trap on subscriber interfaces";
        }
      }
    }
  }
}
