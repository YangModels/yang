module Cisco-IOS-XR-infra-dumper-cfg {
  namespace "http://cisco.com/ns/yang/Cisco-IOS-XR-infra-dumper-cfg";
  prefix infra-dumper-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-dumper package configuration.
     
     This module contains definitions
     for the following management objects:
       exception: Core dump configuration commands
     
     Copyright (c) 2013-2017 by Cisco Systems, Inc.
     All rights reserved.";

  revision 2017-04-28 {
    description
      "Fix the schema for config exception";
  }
  revision 2015-11-09 {
    description
      "IOS XR 6.0 revision.";
  }

  typedef Copy {
    type enumeration {
      enum "default" {
        value 0;
        description
          "copy not configured";
      }
      enum "copy" {
        value 512;
        description
          "Dump to local memory: for time critical
           processes";
      }
    }
    description
      "Copy";
  }

  typedef Context {
    type enumeration {
      enum "default" {
        value 0;
        description
          "context not configured";
      }
      enum "context" {
        value 65536;
        description
          "Dump context info only: Overrides other options
           except for 'no-core'";
      }
    }
    description
      "Context";
  }

  typedef Sharedmemory {
    type enumeration {
      enum "default" {
        value 0;
        description
          "shared memory not configured";
      }
      enum "shared-memory" {
        value 2;
        description
          "Dump shared memory of the target process";
      }
    }
    description
      "Sharedmemory";
  }

  typedef Sparse {
    type enumeration {
      enum "default" {
        value 0;
        description
          "sparse not configured";
      }
      enum "sparse" {
        value 1024;
        description
          "Dump memory relevant to stack trace only: for
           time critical processes";
      }
    }
    description
      "Sparse";
  }

  typedef Nocore {
    type enumeration {
      enum "default" {
        value 0;
        description
          "no core not configured";
      }
      enum "no-core" {
        value 131072;
        description
          "Disable core dump for the target process:
           Overrides other options";
      }
    }
    description
      "Nocore";
  }

  typedef Packetmemory {
    type enumeration {
      enum "default" {
        value 0;
        description
          "packet memory not configured";
      }
      enum "packet-memory" {
        value 8;
        description
          "Dump packet memory of the target process";
      }
    }
    description
      "Packetmemory";
  }

  typedef Skipcpuinfo {
    type enumeration {
      enum "default" {
        value 0;
        description
          "skip-cpu-info not configured";
      }
      enum "skip-cpu-info" {
        value 4096;
        description
          "Skip CPU usage snapshot: for time critical
           processes";
      }
    }
    description
      "Skipcpuinfo";
  }

  typedef Mainmemory {
    type enumeration {
      enum "default" {
        value 0;
        description
          "main memory not configured";
      }
      enum "main-memory" {
        value 1;
        description
          "Dump main memory of the target process";
      }
    }
    description
      "Mainmemory";
  }

  container exception {
    description
      "Core dump configuration commands";
    container choice1 {
      presence "enable choice1";
      description
        "Preference of the dump location";
      leaf compress {
        type boolean;
        must "../file-path";
        description
          "Specify 'true' to compress core files dumped on
           this path, 'false' to not compress";
      }
      leaf lower-limit {
        type uint32 {
          range "0..4";
        }
        must "../compress and ../file-path and ../filename and ../higher-limit";
        description
          "Lower limit.  This is required if Filename is
           specified.";
      }
      leaf higher-limit {
        type uint32 {
          range "5..64";
        }
        must "../compress and ../file-path and ../filename and ../lower-limit";
        description
          "Higher limit.  This is required if Filename is
           specified.";
      }
      leaf file-path {
        type string;
        must "../compress";
        description
          "Protocol and directory";
      }
      leaf filename {
        type string;
        must "../compress and ../file-path and ../lower-limit and ../higher-limit";
        description
          "Dump filename";
      }
    }
    container choice3 {
      presence "enable choice3";
      description
        "Preference of the dump location";
      leaf compress {
        type boolean;
        must "../file-path";
        description
          "Specify 'true' to compress core files dumped on
           this path, 'false' to not compress";
      }
      leaf lower-limit {
        type uint32 {
          range "0..4";
        }
        must "../compress and ../file-path and ../filename and ../higher-limit";
        description
          "Lower limit.  This is required if Filename is
           specified.";
      }
      leaf higher-limit {
        type uint32 {
          range "5..64";
        }
        must "../compress and ../file-path and ../filename and ../lower-limit";
        description
          "Higher limit.  This is required if Filename is
           specified.";
      }
      leaf file-path {
        type string;
        must "../compress";
        description
          "Protocol and directory";
      }
      leaf filename {
        type string;
        must "../compress and ../file-path and ../lower-limit and ../higher-limit";
        description
          "Dump filename";
      }
    }
    container process-names {
      description
        "Specify per process configuration";
      list process-name {
        key "processname";
        description
          "Specify per process configuration";
        container core-option {
          description
            "Specify per process core option";
          leaf main-memoryval {
            type Mainmemory;
            default "default";
            description
              "Dump main memory of the target process";
          }
          leaf shared-memoryval {
            type Sharedmemory;
            default "default";
            description
              "Dump shared memory of the target process";
          }
          leaf packet-memoryval {
            type Packetmemory;
            default "default";
            description
              "Dump packet memory of the target process";
          }
          leaf copyval {
            type Copy;
            default "default";
            description
              "Dump to local memory: for time critical
               processes";
          }
          leaf sparseval {
            type Sparse;
            default "default";
            description
              "Dump memory relevant to stack trace only: for
               time critical processes";
          }
          leaf skipcpuinfoval {
            type Skipcpuinfo;
            default "default";
            description
              "Skip CPU usage snapshot: for time critical
               processes";
          }
          leaf contextval {
            type Context;
            default "default";
            description
              "Dump context info only: Overrides other
               options except for 'no-core'";
          }
          leaf nocoreval {
            type Nocore;
            default "default";
            description
              "Disable core dump for the target process:
               Overrides other options";
          }
        }
        leaf processname {
          type xr:Cisco-ios-xr-string;
          description
            "Specify per process configuration";
        }
      }
    }
    container choice2 {
      presence "enable choice2";
      description
        "Preference of the dump location";
      leaf compress {
        type boolean;
        must "../file-path";
        description
          "Specify 'true' to compress core files dumped on
           this path, 'false' to not compress";
      }
      leaf lower-limit {
        type uint32 {
          range "0..4";
        }
        must "../compress and ../file-path and ../filename and ../higher-limit";
        description
          "Lower limit.  This is required if Filename is
           specified.";
      }
      leaf higher-limit {
        type uint32 {
          range "5..64";
        }
        must "../compress and ../file-path and ../filename and ../lower-limit";
        description
          "Higher limit.  This is required if Filename is
           specified.";
      }
      leaf file-path {
        type string;
        must "../compress";
        description
          "Protocol and directory";
      }
      leaf filename {
        type string;
        must "../compress and ../file-path and ../lower-limit and ../higher-limit";
        description
          "Dump filename";
      }
    }
    leaf sparse {
      type boolean;
      description
        "Specify 'true' to enable sparse core dump,
         'false' to disable sparse core dump";
    }
    leaf core-verification {
      type boolean;
      description
        "Disable core file verification";
    }
    leaf core-size {
      type uint32 {
        range "1..4095";
      }
      description
        "Only print out stack trace and create no core
         file beyond this size";
    }
    leaf kernel-debugger {
      type empty;
      description
        "Enable kernel debugger";
    }
    leaf packet-memory {
      type boolean;
      description
        "Specify 'true' to dump packet memory for all
         process, 'false' to disable dump of packet
         memory";
    }
    leaf sparse-size {
      type uint32 {
        range "1..4095";
      }
      description
        "Switch to sparse core dump at this size";
    }
    leaf memory-threshold {
      type uint32 {
        range "3..40";
      }
      units "percentage";
      description
        "Give up core dump if specified free memory can
         not be secured";
    }
  }
}
