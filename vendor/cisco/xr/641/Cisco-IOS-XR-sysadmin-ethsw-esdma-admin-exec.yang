module Cisco-IOS-XR-sysadmin-ethsw-esdma-admin-exec {
  namespace "http://www.cisco.com/ns/yang/Cisco-IOS-XR-sysadmin-ethsw-esdma-admin-exec";
  prefix esdma_admin_exec;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'controller switch port-state' command.
     
     Copyright(c) 2011-2017 by Cisco Systems, Inc.
     All rights reserved.";

  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping switch-exec-admin {
    container port-state {
      tailf:callpoint "esdma_switch_exec_admin_state";
      tailf:cli-suppress-show-path;
      tailf:info "Change switch port admin state";
      list location {
        key "rack card switch-id";
        tailf:info "Location information for switch port admin state";
        tailf:cli-suppress-table;
        tailf:cli-key-format "$(1)/$(2)/$(3)";
        tailf:cli-show-template "$(port-iter|show)";
        tailf:cli-full-command;
        leaf rack {
          type esdma_types:esdma-rack-num-enum;
        }
        leaf card {
          type esdma_types:esdma-cpu;
          description
            "Card that owns a switch of interest";
        }
        leaf switch-id {
          type esdma_types:esdma-switch-type-enum;
          description
            "Switch type";
        }
        list port-iter {
          key "port";
          tailf:cli-drop-node-name;
          leaf port {
            type esdma_types:esdma-switch-port-type;
            description
              "Switch port";
            tailf:display-column-name "Port";
          }
          tailf:action "down" {
            tailf:info "Set port admin state to down";
            tailf:actionpoint "esdma-switch-exec-admin-down";
            output {
              leaf result {
                type string;
                mandatory true;
              }
            }
          }
          tailf:action "up" {
            tailf:info "Set port admin state to up";
            tailf:actionpoint "esdma-switch-exec-admin-up";
            output {
              leaf result {
                type string;
                mandatory true;
              }
            }
          }
          tailf:action "test" {
            tailf:hidden "advanced-grp";
            tailf:info "Set port admin state to test-mode";
            tailf:actionpoint "esdma-switch-exec-admin-test";
            output {
              leaf result {
                type string;
                mandatory true;
              }
            }
          }
        }
      }
    }
  }
  tailf:id "http://cisco.com/panini/calvados/esdma/esdma_admin_exec";
}
