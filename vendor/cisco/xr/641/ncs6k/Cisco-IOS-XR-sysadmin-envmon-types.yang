module Cisco-IOS-XR-sysadmin-envmon-types {
  namespace "http://www.cisco.com/ns/Cisco-IOS-XR-sysadmin-envmon-types";
  prefix envmon-types;

  import tailf-common {
    prefix tailf;
  }

  revision 2017-05-01 {
    description
      "Namespace change to comply with Cisco guidelines on namespace";
  }

  typedef num_pm {
    type uint32 {
      range "0..12";
    }
  }

  grouping fan-speed-group {
    leaf raise-fan-speed {
      type uint32 {
        range "0..100";
      }
      config false;
      tailf:cli-drop-node-name;
    }
  }

  grouping fan-ctrl-optics-group {
    leaf fan-ctrl-optics {
      type uint32 {
        range "0..1";
      }
      config false;
      tailf:cli-drop-node-name;
    }
  }
  tailf:id "http://www.cisco.com/panini/calvados/envmon/types";
}
