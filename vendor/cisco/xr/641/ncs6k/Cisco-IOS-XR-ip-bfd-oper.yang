module Cisco-IOS-XR-ip-bfd-oper {
  namespace "http://cisco.com/ns/yang/Cisco-IOS-XR-ip-bfd-oper";
  prefix ip-bfd-oper;

  import ietf-inet-types {
    prefix inet;
  }
  import Cisco-IOS-XR-types {
    prefix xr;
  }
  include Cisco-IOS-XR-ip-bfd-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-bfd package operational data.
     
     This module contains definitions
     for the following management objects:
       bfd: Bidirectional Forwarding Detection(BFD) operational data
     
     Copyright (c) 2013-2017 by Cisco Systems, Inc.
     All rights reserved.";

  revision 2015-11-09 {
    description
      "IOS XR 6.0 revision.";
  }

  container bfd {
    config false;
    description
      "Bidirectional Forwarding Detection(BFD)
       operational data";
    container label-session-briefs {
      description
        "Table of brief information about all Label BFD
         sessions in the System";
      list label-session-brief {
        description
          "Brief information for a single Label BFD
           session";
        leaf interface-name {
          type xr:Interface-name;
          description
            "Interface Name";
        }
        leaf incoming-label {
          type int32;
          description
            "Incoming Label";
        }
        leaf location {
          type xr:Node-id;
          description
            "Location";
        }
        uses BFD-MGMT-SESSION-BRIEF;
      }
    }
    container ipv4bf-do-mplste-tail-summary {
      description
        "Summary information of IPv4 BFD over MPLS-TE
         Tail";
      uses BFD-MGMT-BFD-INFORMATION;
    }
    container ipv6-single-hop-counters {
      description
        "IPv6 single hop Counters";
      container ipv6-single-hop-packet-counters {
        description
          "Table of IPv6 single hop Packet counters";
        list ipv6-single-hop-packet-counter {
          key "interface-name";
          description
            "Interface IPv6 single hop Packet counters";
          leaf interface-name {
            type xr:Interface-name;
            description
              "Interface Name";
          }
          uses BFD-MGMT-PACKET-COUNT;
        }
      }
    }
    container counters {
      description
        "Counters";
      container packet-counters {
        description
          "Table of Packet counters";
        list packet-counter {
          key "interface-name";
          description
            "Interface Packet counters";
          leaf interface-name {
            type xr:Interface-name;
            description
              "Interface Name";
          }
          uses BFD-MGMT-PACKET-COUNT;
        }
      }
    }
    container client-details {
      description
        "Table of detailed information about BFD clients";
      list client-detail {
        key "client-name";
        description
          "Detailed information of client";
        leaf client-name {
          type xr:Cisco-ios-xr-string;
          description
            "Client Name";
        }
        uses BFD-MGMT-CLIENT-DETAIL-INFORMATION;
      }
    }
    container ipv4-single-hop-summary {
      description
        "Summary information of BFD IPv4 singlehop
         sessions";
      uses BFD-MGMT-BFD-INFORMATION;
    }
    container ipv6-single-hop-summary {
      description
        "Summary information of BFD IPv6 singlehop
         sessions";
      uses BFD-MGMT-BFD-INFORMATION;
    }
    container label-multi-paths {
      description
        "Label multipath";
      list label-multi-path {
        description
          "Label multipath table";
        leaf interface-name {
          type xr:Interface-name;
          description
            "Interface Name";
        }
        leaf incoming-label {
          type int32;
          description
            "Incoming Label";
        }
        leaf location {
          type xr:Node-id;
          description
            "Location";
        }
        uses BFD-MGMT-MULTIPLE-PATHS;
      }
    }
    container ipv4-multi-hop-session-details {
      description
        "Table of detailed information about all IPv4
         multihop BFD sessions in the System ";
      list ipv4-multi-hop-session-detail {
        description
          "Detailed information for a single IPv4 multihop
           BFD session";
        leaf source-address {
          type inet:ip-address-no-zone;
          description
            "Source Address";
        }
        leaf destination-address {
          type inet:ip-address-no-zone;
          description
            "Destination Address";
        }
        leaf location {
          type xr:Node-id;
          description
            "Location";
        }
        leaf vrf-name {
          type xr:Cisco-ios-xr-string;
          description
            "VRF name";
        }
        uses BFD-MGMT-SESSION-DETAIL;
      }
    }
    container ipv4-single-hop-session-details {
      description
        "Table of detailed information about all IPv4
         singlehop BFD sessions in the System ";
      list ipv4-single-hop-session-detail {
        description
          "Detailed information for a single IPv4
           singlehop BFD session";
        leaf interface-name {
          type xr:Interface-name;
          description
            "Interface Name";
        }
        leaf destination-address {
          type inet:ipv4-address-no-zone;
          description
            "Destination Address";
        }
        leaf location {
          type xr:Node-id;
          description
            "Location";
        }
        uses BFD-MGMT-SESSION-DETAIL;
      }
    }
    container ipv4-multi-hop-session-briefs {
      description
        "Table of brief information about all IPv4
         multihop BFD sessions in the System";
      list ipv4-multi-hop-session-brief {
        description
          "Brief information for a single IPv4 multihop
           BFD session";
        leaf source-address {
          type inet:ipv4-address-no-zone;
          description
            "Source Address";
        }
        leaf destination-address {
          type inet:ipv4-address-no-zone;
          description
            "Destination Address";
        }
        leaf location {
          type xr:Node-id;
          description
            "Location";
        }
        leaf vrf-name {
          type xr:Cisco-ios-xr-string;
          description
            "VRF name";
        }
        uses BFD-MGMT-SESSION-BRIEF;
      }
    }
    container generic-summaries {
      description
        "Generic summary information about BFD location";
      list generic-summary {
        key "location";
        description
          "Generic summary information for bfd location
           table";
        leaf location {
          type xr:Node-id;
          description
            "Location";
        }
        uses BFD-MGMT-SUMMARY;
      }
    }
    container ipv6-single-hop-multi-paths {
      description
        "IPv6 single hop multipath";
      list ipv6-single-hop-multi-path {
        description
          "IPv6 single hop multipath table";
        leaf interface-name {
          type xr:Interface-name;
          description
            "Interface name";
        }
        leaf destination-address {
          type inet:ip-address-no-zone;
          description
            "Destination address";
        }
        leaf location {
          type xr:Node-id;
          description
            "Location";
        }
        uses BFD-MGMT-MULTIPLE-PATHS;
      }
    }
    container ipv4-single-hop-node-location-summaries {
      description
        "Table of summary information about BFD IPv4
         singlehop sessions per location";
      list ipv4-single-hop-node-location-summary {
        key "location";
        description
          "Summary information for BFD IPv4 singlehop
           sessions for location";
        leaf location {
          type xr:Node-id;
          description
            "Location";
        }
        uses BFD-MGMT-BFD-LOC-INFORMATION;
      }
    }
    container label-summary {
      description
        "Summary information of Label BFD";
      uses BFD-MGMT-BFD-INFORMATION;
    }
    container ipv4bf-do-mplste-head-session-briefs {
      description
        "Table of brief information about all IPv4 BFD
         over MPLS-TE Head sessions in the System";
      list ipv4bf-do-mplste-head-session-brief {
        description
          "Brief information for a single IPv4 BFD over
           MPLS-TE Head session";
        leaf interface-name {
          type xr:Interface-name;
          description
            "Interface Name";
        }
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-SESSION-BRIEF;
      }
    }
    container ipv4bf-do-mplste-tail-session-details {
      description
        "Table of detailed information about all IPv4 BFD
         over MPLS-TE Tail sessions in the System";
      list ipv4bf-do-mplste-tail-session-detail {
        description
          "Detailed information for a single IPv4 BFD over
           MPLS-TE Tail session";
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-SESSION-DETAIL;
      }
    }
    container ipv4-multi-hop-node-location-summaries {
      description
        "Table of summary information about BFD IPv4
         multihop sessions per location";
      list ipv4-multi-hop-node-location-summary {
        key "location";
        description
          "Summary information for BFD IPv4 multihop
           sessions for location";
        leaf location {
          type xr:Node-id;
          description
            "Location";
        }
        uses BFD-MGMT-BFD-LOC-INFORMATION;
      }
    }
    container ipv4bf-do-mplste-tail-session-briefs {
      description
        "Table of brief information about all IPv4 BFD
         over MPLS-TE Tail sessions in the System";
      list ipv4bf-do-mplste-tail-session-brief {
        description
          "Brief information for a single IPv4 BFD over
           MPLS-TE session";
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-SESSION-BRIEF;
      }
    }
    container ipv6-multi-hop-node-location-summaries {
      description
        "Table of summary information about BFD IPv6
         multihop sessions per location";
      list ipv6-multi-hop-node-location-summary {
        key "location";
        description
          "Summary information for BFD IPv6 multihop
           sessions for location";
        leaf location {
          type xr:Node-id;
          description
            "Location";
        }
        uses BFD-MGMT-BFD-LOC-INFORMATION;
      }
    }
    container ipv4-multi-hop-summary {
      description
        "Summary information of BFD IPv4 multihop
         sessions";
      uses BFD-MGMT-BFD-INFORMATION;
    }
    container ipv4-single-hop-counters {
      description
        "IPv4 single hop Counters";
      container ipv4-single-hop-packet-counters {
        description
          "Table of IPv4 single hop Packet counters";
        list ipv4-single-hop-packet-counter {
          key "interface-name";
          description
            "Interface IPv4 single hop Packet counters";
          leaf interface-name {
            type xr:Interface-name;
            description
              "Interface Name";
          }
          uses BFD-MGMT-PACKET-COUNT;
        }
      }
    }
    container ipv6-multi-hop-session-details {
      description
        "Table of detailed information about all IPv6
         multihop BFD sessions in the System ";
      list ipv6-multi-hop-session-detail {
        description
          "Detailed information for a single IPv6 multihop
           BFD session";
        leaf source-address {
          type inet:ip-address-no-zone;
          description
            "Source Address";
        }
        leaf destination-address {
          type inet:ip-address-no-zone;
          description
            "Destination Address";
        }
        leaf location {
          type xr:Node-id;
          description
            "Location";
        }
        leaf vrf-name {
          type xr:Cisco-ios-xr-string;
          description
            "VRF name";
        }
        uses BFD-MGMT-SESSION-DETAIL;
      }
    }
    container ipv6-multi-hop-multi-paths {
      description
        "IPv6 multi hop multipath";
      list ipv6-multi-hop-multi-path {
        description
          "IPv6 multihop multipath table";
        leaf source-address {
          type inet:ip-address-no-zone;
          description
            "Source address";
        }
        leaf destination-address {
          type inet:ip-address-no-zone;
          description
            "Destination address";
        }
        leaf location {
          type xr:Node-id;
          description
            "Location";
        }
        leaf vrf-name {
          type xr:Cisco-ios-xr-string;
          description
            "VRF name";
        }
        uses BFD-MGMT-MULTIPLE-PATHS;
      }
    }
    container ipv4bf-do-mplste-head-counters {
      description
        "IPv4 BFD over MPLS-TE Counters";
      container ipv4bf-do-mplste-head-packet-counters {
        description
          "Table of IPv4 BFD over MPLS-TE Packet counters";
        list ipv4bf-do-mplste-head-packet-counter {
          description
            "Interface  IPv4 BFD over MPLS-TE Packet
             counters";
          leaf interface-name {
            type xr:Interface-name;
            description
              "Interface Name";
          }
          leaf location {
            type xr:Node-id;
            description
              "Location";
          }
          uses BFD-MGMT-PACKET-COUNT;
        }
      }
    }
    container session-mibs {
      description
        "BFD session MIB database";
      list session-mib {
        key "discriminator";
        description
          "Brief information for BFD session MIB";
        leaf discriminator {
          type int32;
          description
            "Sesison Discr ";
        }
        uses BFD-MGMT-MIB-DATABASE;
      }
    }
    container ipv6-multi-hop-summary {
      description
        "Summary information of BFD IPv6 multihop
         sessions";
      uses BFD-MGMT-BFD-INFORMATION;
    }
    container label-summary-nodes {
      description
        "Table of summary about Label BFD sessions for
         location";
      list label-summary-node {
        key "location-name";
        description
          "Summary of Label BFD ";
        leaf location-name {
          type xr:Cisco-ios-xr-string;
          description
            "Location name";
        }
        uses BFD-MGMT-BFD-LOC-INFORMATION;
      }
    }
    container ipv6-multi-hop-session-briefs {
      description
        "Table of brief information about all IPv6
         multihop BFD sessions in the System";
      list ipv6-multi-hop-session-brief {
        description
          "Brief information for a single IPv6 multihop
           BFD session";
        leaf source-address {
          type inet:ip-address-no-zone;
          description
            "Source Address";
        }
        leaf destination-address {
          type inet:ip-address-no-zone;
          description
            "Destination Address";
        }
        leaf location {
          type xr:Node-id;
          description
            "Location";
        }
        leaf vrf-name {
          type xr:Cisco-ios-xr-string;
          description
            "VRF name";
        }
        uses BFD-MGMT-SESSION-BRIEF;
      }
    }
    container session-briefs {
      description
        "Table of brief information about singlehop IPv4
         BFD sessions in the System";
      list session-brief {
        description
          "Brief information for a single IPv4 singlehop
           BFD session";
        leaf interface-name {
          type xr:Interface-name;
          description
            "Interface Name";
        }
        leaf destination-address {
          type inet:ipv4-address-no-zone;
          description
            "Destination Address";
        }
        leaf location {
          type xr:Node-id;
          description
            "Location";
        }
        uses BFD-MGMT-SESSION-BRIEF;
      }
    }
    container ipv6-single-hop-node-location-summaries {
      description
        "Table of summary information about BFD IPv6
         singlehop sessions per location";
      list ipv6-single-hop-node-location-summary {
        key "location";
        description
          "Summary information for BFD IPv6 singlehop
           sessions for location";
        leaf location {
          type xr:Node-id;
          description
            "Location";
        }
        uses BFD-MGMT-BFD-LOC-INFORMATION;
      }
    }
    container summary {
      description
        "Summary information of BFD IPv4 singlehop
         sessions";
      uses BFD-MGMT-BFD-INFORMATION;
    }
    container ipv4bfd-mplste-tail-node-summaries {
      description
        "Table of summary about IPv4 TE tail BFD sessions
         for location";
      list ipv4bfd-mplste-tail-node-summary {
        key "location-name";
        description
          "Summary of IPv4 BFD over MPLS-TE tail";
        leaf location-name {
          type xr:Cisco-ios-xr-string;
          description
            "Location name";
        }
        uses BFD-MGMT-BFD-LOC-INFORMATION;
      }
    }
    container ipv4-single-hop-location-summaries {
      description
        "Table of summary information about IPv4
         singlehop BFD sessions for location";
      list ipv4-single-hop-location-summary {
        key "location-name";
        description
          "Summary information for BFD IPv4 singlehop
           sessions for location";
        leaf location-name {
          type xr:Cisco-ios-xr-string;
          description
            "Location Name";
        }
        uses BFD-MGMT-BFD-LOC-INFORMATION;
      }
    }
    container ipv4bfd-mplste-head-summary-nodes {
      description
        "Table of summary about IPv4 TE head BFD sessions
         for location";
      list ipv4bfd-mplste-head-summary-node {
        key "location-name";
        description
          "Summary of IPv4 BFD over MPLS-TE head";
        leaf location-name {
          type xr:Cisco-ios-xr-string;
          description
            "Location name";
        }
        uses BFD-MGMT-BFD-LOC-INFORMATION;
      }
    }
    container label-session-details {
      description
        "Table of detailed information about all Label
         BFD sessions in the System ";
      list label-session-detail {
        description
          "Detailed information for a single BFD session";
        leaf interface-name {
          type xr:Interface-name;
          description
            "Interface Name";
        }
        leaf incoming-label {
          type int32;
          description
            "Incoming Label";
        }
        leaf location {
          type xr:Node-id;
          description
            "Location";
        }
        uses BFD-MGMT-SESSION-DETAIL;
      }
    }
    container ipv6-single-hop-session-details {
      description
        "Table of detailed information about all IPv6
         singlehop BFD sessions in the System ";
      list ipv6-single-hop-session-detail {
        description
          "Detailed information for a single IPv6
           singlehop BFD session";
        leaf interface-name {
          type xr:Interface-name;
          description
            "Interface Name";
        }
        leaf destination-address {
          type inet:ip-address-no-zone;
          description
            "Destination Address";
        }
        leaf location {
          type xr:Node-id;
          description
            "Location";
        }
        uses BFD-MGMT-SESSION-DETAIL;
      }
    }
    container ipv4-multi-hop-counters {
      description
        "IPv4 multiple hop Counters";
      container ipv4-multi-hop-packet-counters {
        description
          "Table of IPv4 multiple hop Packet counters";
        list ipv4-multi-hop-packet-counter {
          description
            "IPv4 multiple hop Packet counters";
          leaf source-address {
            type inet:ip-address-no-zone;
            description
              "Source Address";
          }
          leaf destination-address {
            type inet:ip-address-no-zone;
            description
              "Destination Address";
          }
          leaf location {
            type xr:Node-id;
            description
              "Location";
          }
          leaf vrf-name {
            type xr:Cisco-ios-xr-string;
            description
              "VRF name";
          }
          uses BFD-MGMT-PACKET-COUNT;
        }
      }
    }
    container session-details {
      description
        "Table of detailed information about IPv4
         singlehop BFD sessions in the System ";
      list session-detail {
        description
          "Detailed information for a single IPv4
           singlehop BFD session";
        leaf interface-name {
          type xr:Interface-name;
          description
            "Interface Name";
        }
        leaf destination-address {
          type inet:ipv4-address-no-zone;
          description
            "Destination Address";
        }
        leaf location {
          type xr:Node-id;
          description
            "Location";
        }
        uses BFD-MGMT-SESSION-DETAIL;
      }
    }
    container ipv4-single-hop-multi-paths {
      description
        "IPv4 single hop multipath";
      list ipv4-single-hop-multi-path {
        description
          "IPv4 single hop multipath table";
        leaf interface-name {
          type xr:Interface-name;
          description
            "Interface Name";
        }
        leaf destination-address {
          type inet:ipv4-address-no-zone;
          description
            "Destination Address";
        }
        leaf location {
          type xr:Node-id;
          description
            "Location";
        }
        uses BFD-MGMT-MULTIPLE-PATHS;
      }
    }
    container ipv4-single-hop-session-briefs {
      description
        "Table of brief information about all IPv4
         singlehop BFD sessions in the System";
      list ipv4-single-hop-session-brief {
        description
          "Brief information for a single IPv4 singlehop
           BFD session";
        leaf interface-name {
          type xr:Interface-name;
          description
            "Interface Name";
        }
        leaf destination-address {
          type inet:ipv4-address-no-zone;
          description
            "Destination Address";
        }
        leaf location {
          type xr:Node-id;
          description
            "Location";
        }
        uses BFD-MGMT-SESSION-BRIEF;
      }
    }
    container ipv6-multi-hop-counters {
      description
        "IPv6 multiple hop Counters";
      container ipv6-multi-hop-packet-counters {
        description
          "Table of IPv6 multiple hop Packet counters";
        list ipv6-multi-hop-packet-counter {
          description
            "IPv4 multiple hop Packet counters";
          leaf source-address {
            type inet:ip-address-no-zone;
            description
              "Source Address";
          }
          leaf destination-address {
            type inet:ip-address-no-zone;
            description
              "Destination Address";
          }
          leaf location {
            type xr:Node-id;
            description
              "Location";
          }
          leaf vrf-name {
            type xr:Cisco-ios-xr-string;
            description
              "VRF name";
          }
          uses BFD-MGMT-PACKET-COUNT;
        }
      }
    }
    container ipv6-single-hop-location-summaries {
      description
        "Table of summary information about BFD IPv6
         singlehop sessions per location";
      list ipv6-single-hop-location-summary {
        key "location-name";
        description
          "Summary information for BFD IPv6 singlehop
           sessions for location";
        leaf location-name {
          type xr:Cisco-ios-xr-string;
          description
            "Location Name";
        }
        uses BFD-MGMT-BFD-LOC-INFORMATION;
      }
    }
    container label-counters {
      description
        "Label Counters";
      container label-packet-counters {
        description
          "Table of Label Packet counters";
        list label-packet-counter {
          description
            "Interface Label Packet counters";
          leaf interface-name {
            type xr:Interface-name;
            description
              "Interface Name";
          }
          leaf location {
            type xr:Node-id;
            description
              "Location";
          }
          uses BFD-MGMT-PACKET-COUNT;
        }
      }
    }
    container ipv4bf-do-mplste-head-session-details {
      description
        "Table of detailed information about all IPv4 BFD
         over MPLS-TE Head sessions in the System";
      list ipv4bf-do-mplste-head-session-detail {
        description
          "Detailed information for a single IPv4 BFD over
           MPLS-TE head session";
        leaf interface-name {
          type xr:Interface-name;
          description
            "Interface Name";
        }
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-SESSION-DETAIL;
      }
    }
    container relation-briefs {
      description
        "Table of brief information about all BFD
         relations in the System";
      list relation-brief {
        description
          "Brief information for relation of a single BFD
           session";
        leaf interface-name {
          type xr:Interface-name;
          description
            "Interface Name";
        }
        leaf destination-address {
          type inet:ip-address-no-zone;
          description
            "Destination Address";
        }
        uses BFD-MGMT-RELATION-BRIEF;
      }
    }
    container client-briefs {
      description
        "Table of Brief information about BFD clients";
      list client-brief {
        key "name";
        description
          "Brief information of client";
        leaf name {
          type xr:Cisco-ios-xr-string;
          description
            "Client Name";
        }
        uses BFD-MGMT-CLIENT-BRIEF-INFORMATION;
      }
    }
    container ipv4bf-do-mplste-head-multi-paths {
      description
        "IPv4 BFD over MPLS-TE Head multipath";
      list ipv4bf-do-mplste-head-multi-path {
        description
          "Label multipath table";
        leaf interface-name {
          type xr:Interface-name;
          description
            "Interface Name";
        }
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-MULTIPLE-PATHS;
      }
    }
    container relation-details {
      description
        "Table of detail information about all BFD
         relations in the System";
      list relation-detail {
        description
          "Detail information for relation of a single BFD
           session";
        leaf interface-name {
          type xr:Interface-name;
          description
            "Interface Name";
        }
        leaf destination-address {
          type inet:ip-address-no-zone;
          description
            "Destination Address";
        }
        uses BFD-MGMT-RELATION;
      }
    }
    container ipv4bf-do-mplste-tail-counters {
      description
        "IPv4 BFD over MPLS-TE Counters";
      container ipv4bf-do-mplste-tail-packet-counters {
        description
          "Table of IPv4 BFD over MPLS-TE Packet counters";
        list ipv4bf-do-mplste-tail-packet-counter {
          description
            "Interface  IPv4 BFD over MPLS-TE Packet
             counters";
          leaf vrf-name {
            type xr:Cisco-ios-xr-string;
            description
              "VRF name";
          }
          leaf incoming-label {
            type int32;
            description
              "Incoming Label";
          }
          leaf fe-ctype {
            type int32;
            description
              "FEC Type";
          }
          leaf fec-subgroup-id {
            type int32;
            description
              "FEC Subgroup ID";
          }
          leaf feclspid {
            type int32;
            description
              "FEC LSP ID";
          }
          leaf fec-tunnel-id {
            type int32;
            description
              "FEC Tunnel ID";
          }
          leaf fec-extended-tunnel-id {
            type inet:ipv4-address-no-zone;
            description
              "FEC Extended Tunnel ID";
          }
          leaf fec-source {
            type inet:ipv4-address-no-zone;
            description
              "FEC Source";
          }
          leaf fec-destination {
            type inet:ipv4-address-no-zone;
            description
              "FEC Destination";
          }
          leaf fecp2mpid {
            type int32;
            description
              "FEC P2MP ID";
          }
          leaf fec-subgroup-originator {
            type inet:ipv4-address-no-zone;
            description
              "FEC Subgroup originator";
          }
          leaf fec-ctype {
            type int32;
            description
              "FEC C Type";
          }
          leaf location {
            type xr:Node-id;
            description
              "Location";
          }
          uses BFD-MGMT-PACKET-COUNT;
        }
      }
    }
    container ipv6-single-hop-session-briefs {
      description
        "Table of brief information about all IPv6
         singlehop BFD sessions in the System";
      list ipv6-single-hop-session-brief {
        description
          "Brief information for a single IPv6 singlehop
           BFD session";
        leaf interface-name {
          type xr:Interface-name;
          description
            "Interface Name";
        }
        leaf destination-address {
          type inet:ip-address-no-zone;
          description
            "Destination Address";
        }
        leaf location {
          type xr:Node-id;
          description
            "Location";
        }
        uses BFD-MGMT-SESSION-BRIEF;
      }
    }
    container ipv4bf-do-mplste-tail-multi-paths {
      description
        "IPv4 BFD over MPLS-TE Tail multipath";
      list ipv4bf-do-mplste-tail-multi-path {
        description
          "Label multipath table";
        leaf vrf-name {
          type xr:Cisco-ios-xr-string;
          description
            "VRF name";
        }
        leaf incoming-label {
          type int32;
          description
            "Incoming Label";
        }
        leaf fe-ctype {
          type int32;
          description
            "FEC Type";
        }
        leaf fec-subgroup-id {
          type int32;
          description
            "FEC Subgroup ID";
        }
        leaf feclspid {
          type int32;
          description
            "FEC LSP ID";
        }
        leaf fec-tunnel-id {
          type int32;
          description
            "FEC Tunnel ID";
        }
        leaf fec-extended-tunnel-id {
          type inet:ipv4-address-no-zone;
          description
            "FEC Extended Tunnel ID";
        }
        leaf fec-source {
          type inet:ipv4-address-no-zone;
          description
            "FEC Source";
        }
        leaf fec-destination {
          type inet:ipv4-address-no-zone;
          description
            "FEC Destination";
        }
        leaf fecp2mpid {
          type int32;
          description
            "FEC P2MP ID";
        }
        leaf fec-subgroup-originator {
          type inet:ipv4-address-no-zone;
          description
            "FEC Subgroup originator";
        }
        leaf fec-ctype {
          type int32;
          description
            "FEC C Type";
        }
        leaf location {
          type xr:Node-id;
          description
            "Location";
        }
        uses BFD-MGMT-MULTIPLE-PATHS;
      }
    }
    container ipv4-multi-hop-multi-paths {
      description
        "IPv4 multi-hop multipath";
      list ipv4-multi-hop-multi-path {
        description
          "IPv4 multi hop multipath table";
        leaf source-address {
          type inet:ip-address-no-zone;
          description
            "Source Address";
        }
        leaf destination-address {
          type inet:ip-address-no-zone;
          description
            "Destination Address";
        }
        leaf location {
          type xr:Node-id;
          description
            "Location";
        }
        leaf vrf-name {
          type xr:Cisco-ios-xr-string;
          description
            "VRF name";
        }
        uses BFD-MGMT-MULTIPLE-PATHS;
      }
    }
    container ipv4bf-do-mplste-head-summary {
      description
        "Summary information of IPv4 BFD over MPLS-TE
         Head";
      uses BFD-MGMT-BFD-INFORMATION;
    }
  }
}
