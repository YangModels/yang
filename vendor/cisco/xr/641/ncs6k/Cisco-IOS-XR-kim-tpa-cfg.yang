module Cisco-IOS-XR-kim-tpa-cfg {
  namespace "http://cisco.com/ns/yang/Cisco-IOS-XR-kim-tpa-cfg";
  prefix kim-tpa-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR kim-tpa package configuration.
     
     This module contains definitions
     for the following management objects:
       tpa: tpa configuration commands
     
     Copyright (c) 2013-2017 by Cisco Systems, Inc.
     All rights reserved.";

  revision 2015-11-09 {
    description
      "IOS XR 6.0 revision.";
  }

  grouping LPTS-ALLOW {
    description
      "Common node of ipv4, ipv6";
    container lpts-allow-entries {
      description
        "TPA Cli to configure LPTS entries";
      list lpts-allow-entry {
        key "interface-name remote-addr local-addr remote-port local-port protocol";
        description
          "TPA Cli to configure LPTS entry";
        leaf interface-name {
          type xr:Cisco-ios-xr-string;
          description
            "Interface name";
        }
        leaf remote-addr {
          type xr:Cisco-ios-xr-string;
          description
            "remote address";
        }
        leaf local-addr {
          type xr:Cisco-ios-xr-string;
          description
            "local address";
        }
        leaf remote-port {
          type int32;
          description
            "remote port";
        }
        leaf local-port {
          type int32;
          description
            "local port";
        }
        leaf protocol {
          type int32;
          description
            "L4 protocol";
        }
        leaf interface-name-xr {
          type xr:Interface-name;
          description
            "Interface name for allow command";
        }
        leaf remote-addr-xr {
          type string;
          description
            "IPv4/6 remote-address prefix to match";
        }
        leaf local-addr-xr {
          type string;
          description
            "IPv4/6 local-address prefix to match";
        }
        leaf remote-port-xr {
          type int32;
          description
            "remote port value";
        }
        leaf local-port-xr {
          type int32;
          description
            "local port value";
        }
        leaf protocol-xr {
          type int32;
          description
            "L4 protocol value";
        }
      }
    }
  }

  grouping UPDATE-SOURCE {
    description
      "Common node of ipv4, ipv6";
    leaf update-source {
      type xr:Interface-name;
      description
        "Interface name for source address";
    }
  }

  grouping DEFAULT-ROUTE {
    description
      "Common node of ipv4, ipv6";
    leaf default-route {
      type string;
      description
        "Default interface used for routing";
    }
  }

  container tpa {
    description
      "tpa configuration commands";
    container vrf-names {
      description
        "VRF container";
      list vrf-name {
        key "vrf-name";
        description
          "VRF name";
        container east-west-names {
          description
            "EastWest container";
          list east-west-name {
            key "east-west-name";
            description
              "East West interface";
            leaf east-west-name {
              type xr:Cisco-ios-xr-string;
              description
                "Interface";
            }
            leaf vrf {
              type string;
              description
                "VRF name";
            }
            leaf interface {
              type string;
              description
                "Interface";
            }
          }
        }
        container address-family {
          description
            "Address family";
          container ipv6 {
            description
              "IPv6 configuration";
            uses DEFAULT-ROUTE;
            uses LPTS-ALLOW;
            uses UPDATE-SOURCE;
          }
          container ipv4 {
            description
              "IPv4 configuration";
            uses DEFAULT-ROUTE;
            uses LPTS-ALLOW;
            uses UPDATE-SOURCE;
          }
        }
        leaf disable {
          type int32;
          default "1";
          description
            "Disable routes and interfaces";
        }
        leaf vrf-name {
          type xr:Cisco-ios-xr-string {
            length "1..32";
          }
          description
            "VRF name";
        }
      }
    }
    container logging {
      description
        "Third party app logging";
      container kim {
        description
          "KIM logging";
        leaf rotation-max {
          type int32;
          description
            "How many log rotation files to keep";
        }
        leaf file-size-max-kb {
          type int32;
          units "kilobyte";
          description
            "Size in Kilobytes of the log file";
        }
      }
    }
    container statistics {
      description
        "Statistics";
      leaf max-intf-events {
        type int32;
        description
          "How many interface events to record";
      }
      leaf max-lpts-events {
        type int32;
        description
          "How many LPTS events to record";
      }
      leaf statistics-update-frequency {
        type int32;
        units "second";
        description
          "Statistics update frequency into Linux";
      }
    }
  }
}
