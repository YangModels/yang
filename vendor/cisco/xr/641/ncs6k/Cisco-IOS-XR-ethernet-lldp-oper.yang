module Cisco-IOS-XR-ethernet-lldp-oper {
  namespace "http://cisco.com/ns/yang/Cisco-IOS-XR-ethernet-lldp-oper";
  prefix ethernet-lldp-oper;

  import Cisco-IOS-XR-types {
    prefix xr;
  }
  include Cisco-IOS-XR-ethernet-lldp-oper-sub2 {
    revision-date 2015-11-09;
  }
  include Cisco-IOS-XR-ethernet-lldp-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-lldp package operational data.
     
     This module contains definitions
     for the following management objects:
       lldp: Link Layer Discovery Protocol operational data
     
     Copyright (c) 2013-2017 by Cisco Systems, Inc.
     All rights reserved.";

  revision 2015-11-09 {
    description
      "IOS XR 6.0 revision.";
  }

  container lldp {
    config false;
    description
      "Link Layer Discovery Protocol operational data";
    container global-lldp {
      description
        "Global LLDP data";
      container lldp-info {
        description
          "The LLDP Global Information of this box";
        uses LLDP-MGR-GLOBAL-INFO;
      }
    }
    container nodes {
      description
        "Per node LLDP operational data";
      list node {
        key "node-name";
        description
          "The LLDP operational data for a particular node";
        container neighbors {
          description
            "The LLDP neighbor tables on this node";
          container devices {
            description
              "The detailed LLDP neighbor table on this
               device";
            list device {
              description
                "Detailed information about a LLDP neighbor
                 entry";
              leaf device-id {
                type string;
                description
                  "The neighboring device identifier";
              }
              leaf interface-name {
                type xr:Interface-name;
                description
                  "The interface name";
              }
              uses LLDP-NEIGHBOR;
            }
          }
          container details {
            description
              "The detailed LLDP neighbor table";
            list detail {
              description
                "Detailed information about a LLDP neighbor
                 entry";
              leaf interface-name {
                type xr:Interface-name;
                description
                  "The interface name";
              }
              leaf device-id {
                type string;
                description
                  "The neighboring device identifier";
              }
              uses LLDP-NEIGHBOR;
            }
          }
          container summaries {
            description
              "The LLDP neighbor summary table";
            list summary {
              description
                "Brief information about a LLDP neighbor
                 entry";
              leaf interface-name {
                type xr:Interface-name;
                description
                  "The interface name";
              }
              leaf device-id {
                type string;
                description
                  "The neighboring device identifier";
              }
              uses LLDP-NEIGHBOR;
            }
          }
        }
        container interfaces {
          description
            "The table of interfaces on which LLDP is
             running on this node";
          list interface {
            key "interface-name";
            description
              "Operational data for an interface on which
               LLDP is running";
            leaf interface-name {
              type xr:Interface-name;
              description
                "The interface name";
            }
            uses LLDP-INTERFACE;
          }
        }
        container statistics {
          description
            "The LLDP traffic statistics for this node";
          uses LLDP-STATS;
        }
        leaf node-name {
          type xr:Node-id;
          description
            "The identifier for the node";
        }
      }
    }
  }
}
