module Cisco-IOS-XR-tty-vty-cfg {
  namespace "http://cisco.com/ns/yang/Cisco-IOS-XR-tty-vty-cfg";
  prefix tty-vty-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tty-vty package configuration.
     
     This module contains definitions
     for the following management objects:
       vty: VTY Pools configuration
     
     Copyright (c) 2013-2017 by Cisco Systems, Inc.
     All rights reserved.";

  revision 2015-09-16 {
    description
      "Descriptions updated.";
  }
  revision 2015-01-07 {
    description
      "IOS XR 5.3.1 revision.";
  }

  container vty {
    description
      "VTY Pools configuration";
    container vty-pools {
      description
        "List of VTY Pools";
      list vty-pool {
        key "pool-name";
        description
          "VTY Pool";
        leaf pool-name {
          type xr:Cisco-ios-xr-string;
          description
            "For configuring range for default pool use
             'default',For configuring range for
             fault-manager pool use 'fm',For configuring
             range for any user defined pool use any other
             string";
        }
        leaf first-vty {
          type int32;
          mandatory true;
          description
            "First VTY number,For default VTY use 0,For
             user-defined use 5,For fault-manager use 100";
        }
        leaf last-vty {
          type int32;
          mandatory true;
          description
            "Last VTY number,For default configure between
             0-99,For user-defined configure between 5-99
             ,For fault-manager configure between 100-199";
        }
        leaf line-template {
          type string;
          description
            "Name of line template";
        }
        leaf none {
          type string;
          description
            "Empty Option";
        }
      }
    }
  }
}
