module Cisco-IOS-XR-manageability-object-tracking-cfg {
  namespace "http://cisco.com/ns/yang/Cisco-IOS-XR-manageability-object-tracking-cfg";
  prefix manageability-object-tracking-cfg;

  import ietf-inet-types {
    prefix inet;
  }
  import Cisco-IOS-XR-types {
    prefix xr;
  }
  import Cisco-IOS-XR-manageability-object-tracking-datatypes {
    prefix dt1;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR manageability-object-tracking package configuration.
     
     This module contains definitions
     for the following management objects:
       object-trackings: Object Tracking configuration
     
     This YANG module augments the
       Cisco-IOS-XR-ifmgr-cfg
     module with configuration data.
     
     Copyright (c) 2013-2017 by Cisco Systems, Inc.
     All rights reserved.";

  revision 2017-05-01 {
    description
      "Fixing backward compatibility error in module.";
  }
  revision 2015-11-09 {
    description
      "IOS XR 6.0 revision.";
  }

  grouping OBJECT {
    description
      "Common node of threshold-weight-object,
       threshold-percentage-object";
    list object {
      key "object";
      description
        "Track name object";
      leaf object-weight {
        type int32;
        default "1";
        description
          "Weight of object";
      }
      leaf object {
        type dt1:Object-tracking-name-string;
        description
          "Object name";
      }
    }
  }

  grouping THRESHOLD-LIMITS {
    description
      "Common node of threshold-weight,
       threshold-percentage";
    container threshold-limits {
      description
        "Threshold Limits";
      container threshold-up-values {
        description
          "Threshold limit at which track is set to UP
           state";
        list threshold-up-value {
          key "up";
          description
            "Threshold limit at which track is set to UP
             state";
          leaf threshold-down {
            type int32;
            default "0";
            description
              "Threshold limit at which track is set to Down
               state";
          }
          leaf up {
            type int32;
            description
              "Up value";
          }
        }
      }
    }
  }

  augment "/a1:interface-configurations/a1:interface-configuration" {
    description
      "This augment extends the configuration data of
       'Cisco-IOS-XR-ifmgr-cfg'";
    leaf track-name {
      type dt1:Object-tracking-name-string;
      description
        "Track Name";
    }
  }
  container object-trackings {
    description
      "Object Tracking configuration";
    list object-tracking {
      key "track-name";
      description
        "Track name - maximum 32 characters";
      container type-interface {
        description
          "Track type line-protocol";
        leaf interface {
          type xr:Interface-name;
          description
            "The name of the interface";
        }
      }
      container type-list {
        description
          "Track type boolean list";
        container threshold-weight {
          description
            "Track type threshold weight";
          uses THRESHOLD-LIMITS;
        }
        container threshold-percentage-object {
          description
            "Track type threshold percentage";
          uses OBJECT;
        }
        container threshold-percentage {
          description
            "Track type threshold percentage";
          uses THRESHOLD-LIMITS;
        }
        container threshold-weight-object {
          description
            "Track type threshold weight";
          uses OBJECT;
        }
      }
      container type-route {
        description
          "Track type route ipv4";
        container ip-address {
          presence "enable ip-address";
          description
            "set track IPv4 address";
          leaf address {
            type inet:ipv4-address-no-zone;
            description
              "IP address";
          }
          leaf mask {
            type inet:ipv4-address-no-zone;
            description
              "Mask";
          }
        }
        leaf vrf {
          type xr:Cisco-ios-xr-string {
            length "1..32";
          }
          description
            "VRF tag - use 'default' for the DEFAULT vrf";
        }
      }
      container type-boolean-list {
        description
          "Track type boolean list";
        container or-objects {
          description
            "Track type boolean or list";
          list or-object {
            key "object";
            description
              "Track name - maximum 32 characters";
            leaf object-sign {
              type dt1:Object-tracking-boolean-sign;
              description
                "Tracked Object sign (with or without not)";
            }
            leaf object {
              type dt1:Object-tracking-name-string;
              description
                "Object name";
            }
          }
        }
        container and-objects {
          description
            "Track type boolean and list";
          list and-object {
            key "object-name";
            description
              "Track name - maximum 32 characters";
            leaf object-sign {
              type dt1:Object-tracking-boolean-sign;
              description
                "Tracked Object sign (with or without not)";
            }
            leaf object-name {
              type dt1:Object-tracking-name-string;
              description
                "Object name";
            }
          }
        }
      }
      leaf delay-up {
        type dt1:Object-tracking-delay;
        units "second";
        description
          "Delay up in seconds";
      }
      leaf enable {
        type empty;
        description
          "Enable the Track";
      }
      leaf delay-down {
        type dt1:Object-tracking-delay;
        units "second";
        description
          "Track delay down time";
      }
      leaf type-interface-enable {
        type empty;
        description
          "Enable track type Interface";
      }
      leaf type-route-enable {
        type empty;
        description
          "Enable track type Route";
      }
      leaf type-boolean-list-and-enable {
        type empty;
        description
          "Enable track type boolean list and";
      }
      leaf type-boolean-list-or-enable {
        type empty;
        description
          "Enable track type boolean list or";
      }
      leaf track-name {
        type dt1:Object-tracking-name-string;
        description
          "Track name";
      }
    }
  }
}
