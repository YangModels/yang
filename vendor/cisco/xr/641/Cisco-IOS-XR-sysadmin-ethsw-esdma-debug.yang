module Cisco-IOS-XR-sysadmin-ethsw-esdma-debug {
  namespace "http://www.cisco.com/ns/yang/Cisco-IOS-XR-sysadmin-ethsw-esdma-debug";
  prefix esdma_debug;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the hidden Cisco IOS-XR SysAdmin
     'show controller switch debug counters' command.
     
     Copyright(c) 2011-2017 by Cisco Systems, Inc.
     All rights reserved.";

  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping switch-debug-data {
    container debug {
      tailf:info "Switch internal debug information";
      tailf:hidden "advanced-grp";
      container counters {
        tailf:info "Switch internal debug counters";
        tailf:callpoint "switch_debug_counters";
        list location {
          key "rack card switch-id";
          tailf:info "Location information for debug counters";
          tailf:cli-suppress-table;
          tailf:cli-key-format "$(1)/$(2)/$(3)";
          tailf:cli-full-command;
          tailf:cli-show-template "$(counters|show)";
          leaf rack {
            type esdma_types:esdma-rack-num-enum;
            tailf:display-column-name "Rack";
          }
          leaf card {
            type esdma_types:esdma-cpu;
            tailf:display-column-name "Card";
          }
          leaf switch-id {
            type esdma_types:esdma-switch-type-enum;
            tailf:display-column-name "Switch";
          }
          container counters {
            tailf:cli-drop-node-name;
            tailf:cli-suppress-show-path;
            tailf:cli-suppress-show-match;
            leaf phy-polling-enabled {
              type boolean;
              tailf:alt-name "PHY polling enabled";
            }
            leaf tx-thread-wdog-cnt {
              type uint64;
              tailf:alt-name "Tx thread watchdog count";
            }
            leaf rx-thread-wdog-cnt {
              type uint64;
              tailf:alt-name "Rx thread watchdog count";
            }
            leaf task-lock-longest-wait-time {
              type uint64;
              tailf:alt-name "Task lock longest wait time (ms)";
            }
            leaf task-lock-longest-wait-event {
              type uint32;
              tailf:alt-name "Task lock longest wait event ID";
            }
            leaf task-lock-longest-held-time {
              type uint64;
              tailf:alt-name "Task lock longest held time (ms)";
            }
            leaf task-lock-longest-held-event {
              type uint32;
              tailf:alt-name "Task lock longest held event ID";
            }
            leaf task-unlock-longest-wait-time {
              type uint64;
              tailf:alt-name "Task unlock longest wait time (ms)";
            }
            leaf task-unlock-longest-wait-event {
              type uint32;
              tailf:alt-name "Task unlock longest wait event ID";
            }
            leaf dma-max-rx-dequeued-per-int {
              type uint64;
              tailf:alt-name "DMA Rx Max packets dequeued per interrupt";
            }
            leaf dma-rx-packets-dequeued {
              type uint64;
              tailf:alt-name "DMA Rx packets dequeued";
            }
            leaf dma-rx-packet-dequeue-errors {
              type uint64;
              tailf:alt-name "DMA Rx packet dequeue errors";
            }
            leaf dma-tx-packets-queued {
              type uint64;
              tailf:alt-name "DMA Tx packets queued";
            }
            leaf dma-tx-packets-completed {
              type uint64;
              tailf:alt-name "DMA Tx packets completed";
            }
            leaf dma-tx-packet-no-msg-errors {
              type uint64;
              tailf:alt-name "DMA Tx packet no message errors";
            }
            leaf dma-tx-packet-msg-too-big-errors {
              type uint64;
              tailf:alt-name "DMA Tx packet message too big errors";
            }
            leaf dma-tx-packet-no-buffer-errors {
              type uint64;
              tailf:alt-name "DMA Tx packet no buffer errors";
            }
            leaf dma-tx-packet-queue-errors {
              type uint64;
              tailf:alt-name "DMA Tx packet queue errors";
            }
            leaf dma-tx-packet-completion-errors {
              type uint64;
              tailf:alt-name "DMA Tx packet completion errors";
            }
            leaf dma-max-tx-freed-per-int {
              type uint64;
              tailf:alt-name "DMA Tx Max packets freed per interrupt";
            }
            leaf dma-tx-buf-alloc-count {
              type uint64;
              tailf:alt-name "DMA Tx buffer allocation count";
            }
            leaf dma-tx-buf-free-count {
              type uint64;
              tailf:alt-name "DMA Tx buffer free count";
            }
            list switch-core {
              key "core";
              tailf:cli-drop-node-name;
              leaf core {
                type uint8;
                tailf:display-column-name "Switch Core";
              }
              leaf msi-count {
                type uint64;
                tailf:display-column-name "MSI Count";
              }
              leaf aer-count {
                type uint64;
                tailf:display-column-name "AER Count";
              }
              leaf hp-count {
                type uint64;
                tailf:display-column-name "HP Count";
              }
              leaf wdog-count {
                type uint64;
                tailf:display-column-name "Watchdog Count";
              }
              leaf core-task-lock-longest-wait-time {
                type uint64;
                tailf:display-column-name "Longest Lock Wait(ms)";
              }
              leaf core-task-lock-longest-held-time {
                type uint64;
                tailf:display-column-name "Longest Lock Held(ms)";
              }
              leaf core-task-unlock-longest-wait-time {
                type uint64;
                tailf:display-column-name "Longest Unlock Wait(ms)";
              }
            }
          }
        }
      }
    }
  }

  grouping switch-debug-group {
    container switch-debug-cont {
      tailf:cli-drop-node-name;
      uses switch-debug-data;
    }
  }
  tailf:id "http://cisco.com/panini/calvados/esdma/esdma_debug";
}
