module Cisco-IOS-XR-sysadmin-tacacs-show-tacacs {
  namespace "http://www.cisco.com/ns/yang/Cisco-IOS-XR-sysadmin-tacacs-show-tacacs";
  prefix show_tacacs;

  import tailf-common {
    prefix tailf;
  }
  import ietf-inet-types {
    prefix inet;
  }
  import Cisco-IOS-XR-sysadmin-tacacs-tacacs-server {
    prefix tacacs-server;
  }

  organization
    "Cisco Systems Inc.";
  contact
    "aaa-ng-tacacs-dev@cisco.com";
  description
    "This module defines yang model
     for displaying tacacs+ server host info";

  revision 2017-05-10 {
    description
      "Namespace changed from show_tacacs to Cisco-IOS-XR-sysadmin-tacacs-show-tacacs";
  }
  revision 2015-07-07 {
    description
      "Initial revision";
  }

  typedef passwdStr {
    type tailf:md5-digest-string;
    tailf:info "MD5 Digest or plain text";
  }

  augment "/tacacs-server:tacacs-server" {
    container requests {
      config false;
      tailf:callpoint "show_tacacs";
      tailf:info "Tacacs-server statistics";
      list ipv4 {
        key "addr port";
        tailf:cli-suppress-show-path;
        tailf:cli-suppress-table;
        tailf:cli-full-command;
        tailf:cli-full-show-path;
        tailf:cli-no-key-completion;
        tailf:cli-no-match-completion;
        tailf:cli-suppress-key-sort;
        tailf:cli-show-template-legend "\n";
        tailf:cli-show-template
          "Server: $(addr)/$(port) opens=$(opens) closes=$(closes) aborts=$(aborts) errors=$(errors)
                   packets in=$(packets_in) packets out=$(packets_out) family=IPv4
           
          ";
        leaf addr {
          type inet:ip-address;
          description
            "Server IPv4 address";
          tailf:cli-suppress-show-path;
        }
        leaf port {
          type inet:port-number;
          description
            "Server Port";
          tailf:cli-suppress-show-path;
        }
        leaf opens {
          type uint32;
          description
            "Socket open count";
          tailf:cli-suppress-show-path;
        }
        leaf closes {
          type uint32;
          description
            "Socket close count";
          tailf:cli-suppress-show-path;
        }
        leaf aborts {
          type uint32;
          description
            "Socket abort count";
          tailf:cli-suppress-show-path;
        }
        leaf errors {
          type uint32;
          description
            "Socket error count";
          tailf:cli-suppress-show-path;
        }
        leaf packets_in {
          type uint32;
          description
            "Packets received count";
          tailf:cli-suppress-show-path;
        }
        leaf packets_out {
          type uint32;
          description
            "Packets transmitted count";
          tailf:cli-suppress-show-path;
        }
      }
    }
  }
  tailf:id "http://www.cisco.com/calvados/show_tacacs";
}
