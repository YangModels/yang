module Cisco-IOS-XR-asr9k-ext-usb-cfg {
  namespace "http://cisco.com/ns/yang/Cisco-IOS-XR-asr9k-ext-usb-cfg";
  prefix asr9k-ext-usb-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-ext-usb package configuration.
     
     This module contains definitions
     for the following management objects:
       hardware-module-ext-usb: External USB configuration
     
     Copyright (c) 2013-2017 by Cisco Systems, Inc.
     All rights reserved.";

  revision 2015-11-09 {
    description
      "IOS XR 6.0 revision.";
  }

  container hardware-module-ext-usb {
    description
      "External USB configuration";
    leaf disable {
      type empty;
      description
        "External USB disable";
    }
  }
}
