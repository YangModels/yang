module Cisco-IOS-XR-sysadmin-fpd-infra-cli-shhwfpd {
  namespace "http://www.cisco.com/ns/yang/Cisco-IOS-XR-sysadmin-fpd-infra-cli-shhwfpd";
  prefix shhwfpd;

  import tailf-common {
    prefix tailf;
  }

  revision 2017-05-01 {
    description
      "Namespace change to comply with Cisco guidelines on namespace";
  }

  grouping hw-module-oper-group {
    container shhwfpd {
      config false;
      tailf:hidden "location";
      tailf:callpoint "show_hw_fpd";
      tailf:cli-incomplete-show-path;
      tailf:cli-drop-node-name;
      list alocation {
        key "locs";
        tailf:cli-incomplete-show-path {
          tailf:cli-min-keys "1";
        }
        tailf:cli-suppress-table;
        tailf:cli-show-template-enter "";
        tailf:cli-show-template-legend
          "                                                                   FPD Versions
                                                                           ===============
           Location  Card type         HWver FPD device       ATR Status   Run    Programd
           -------------------------------------------------------------------------------
          ";
        leaf locs {
          type string;
          tailf:display-column-name "Location";
        }
        list fpd {
          key "fpdname";
          tailf:cli-suppress-table;
          tailf:cli-show-template-enter "";
          tailf:cli-show-template-legend
            "$(.legend_shown!=true?                                                                 FPD Versions
                                                                             ===============
             Location  Card type         HWver FPD device       ATR Status   Run    Programd
             -------------------------------------------------------------------------------
             )";
          tailf:cli-show-template
            "$(.legend_shown!=true?                                                                 FPD Versions
                                                                             ==============
             Location  Card type         HWver FPD device       ATR Status   Run    Programd
             -------------------------------------------------------------------------------
             )$(../../locs|ljust:10)$(cardname|ljust:18)$(hwver|ljust:6)$(fpdname|ljust:17)$(attr|ljust:4)$(state|ljust:9)$(fpdver|ljust:8)$(fpddnld|ljust:8)
            ";
          leaf fpdname {
            type string;
            tailf:display-column-name "FPD device";
          }
          leaf state {
            type string;
            description
              "Status";
            tailf:cli-suppress-show-path;
            tailf:cli-suppress-show-match;
            tailf:display-column-name "Status";
          }
          leaf hwver {
            type string;
            description
              "HWver";
            tailf:cli-suppress-show-path;
            tailf:cli-suppress-show-match;
            tailf:display-column-name "HWver";
          }
          leaf fpdver {
            type string;
            description
              "FPD ver";
            tailf:cli-suppress-show-path;
            tailf:cli-suppress-show-match;
            tailf:display-column-name "Running FPD version";
          }
          leaf cardname {
            type string;
            description
              "Card type";
            tailf:cli-suppress-show-path;
            tailf:cli-suppress-show-match;
            tailf:display-column-name "Card type";
          }
          leaf attr {
            type string;
            description
              "Attribute";
            tailf:cli-suppress-show-path;
            tailf:cli-suppress-show-match;
            tailf:display-column-name "Attribute";
          }
          leaf fpddnld {
            type string;
            description
              "FPD Programed";
            tailf:cli-suppress-show-path;
            tailf:cli-suppress-show-match;
            tailf:display-column-name "Dlnd FPD version";
          }
        }
      }
      list fpd {
        key "fpdname";
        leaf fpdname {
          type string;
          tailf:display-column-name "FPD device";
        }
      }
    }
  }
  tailf:id "http://tail-f.com/test/shhwfpd";
}
