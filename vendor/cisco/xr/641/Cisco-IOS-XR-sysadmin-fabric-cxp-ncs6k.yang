module Cisco-IOS-XR-sysadmin-fabric-cxp-ncs6k {
  namespace "http://www.cisco.com/ns/yang/Cisco-IOS-XR-sysadmin-fabric-cxp-ncs6k";
  prefix fabric_cxp;

  import tailf-common {
    prefix tailf;
  }
  import Cisco-IOS-XR-sysadmin-fabric-types {
    prefix fabric-types;
  }
  import tailf-xsd-types {
    prefix xs;
  }

  revision 2017-08-01 {
    description
      "Updated to display cxp2 firmware and eeprom version";
  }
  revision 2017-06-19 {
    description
      "Namespace change to comply with Cisco guidelines on namespace";
  }

  grouping dom_output {
    list port {
      key "cxp_port";
      tailf:info "CXP port number";
      tailf:cli-show-template-enter "";
      tailf:cli-no-key-completion;
      tailf:cli-no-match-completion;
      tailf:cli-suppress-table;
      tailf:cli-show-template-legend
        "$(.legend_shown != true ?================================================================================
          \t\tCXP Digital Optical Monitor Information
         ================================================================================
         )";
      tailf:cli-show-template
        "$(show_port == true ?$(.legend_shown != true ?================================================================================
          \t\tCXP Digital Optical Monitor Information
         ================================================================================
         )Location\\\\: $(cur_loc_str),\t CXP port number\\\\: $(cxp_port) 
         --------------------------------------------------------------------------------
         Connector description \t   \\\\: $(dev_description)
         Vendor Name \t\t   \\\\: $(vendorname)
         Cisco Part Number \t   \\\\: $(partnumber)
         Cisco Serial Number \t   \\\\: $(serialnumber)
         Cisco VID \t\t   \\\\: $(vid)
         Cisco PID \t\t   \\\\: $(pid)
         Cisco CLEI Code \t   \\\\: $(clei_code_num)
         Vendor Part Number \t   \\\\: $(vendor_pn)
         Vendor Serial Number \t   \\\\: $(vendor_sn)
         Vendor Date Code \t   \\\\: $(ven_date_code)
         Vendor Lot Code \t   \\\\: $(ven_lot_code)
         Vendor OUI IEEE COMPANY ID \\\\: 0x$(vendor_oui_ieee_company_id |hex)
         $(cxp2_display == true ?Eeprom Revision \t   \\\\: 0x$(eeprom_rev_num |hex)
         Firmware Revision \t   \\\\: 0x$(firmware_rev_num |hex)
         )Vendor Revision Number \t   \\\\: $(vendor_rev_num)
         --------------------------------------------------------------------------------
         Tx Temperature Reading \t\\\\:$(TX_temp_rd |floatformat:2) Celsius \tTx Temperature Alarm \\\\:$(TX_temp_sts) Set
         Tx Voltage Reading \t\\\\:$(TX_volt_rd|floatformat:2)mV\tTx Voltage Alarm \\\\:$(TX_volt_sts) Set
         +-----------------------------------------------------------------------------+
         |  Channel |   Channel  |   FAULT    |       Signal       |  Optical Power    |
         |  Number. |   Status   |   Status   |      Strength      |      Alarm        |
         +-----------------------------------------------------------------------------+
         | Tx Ch 0\\\\: | $(tx_chn_sts0|ljust:10) | $(tx_fault0|ljust:11)|  $(tx_los0|ljust:18)|  $(tx_opt_pw_alm0|ljust:17)|
         | Tx Ch 1\\\\: | $(tx_chn_sts1|ljust:10) | $(tx_fault1|ljust:11)|  $(tx_los1|ljust:18)|  $(tx_opt_pw_alm1|ljust:17)|
         | Tx Ch 2\\\\: | $(tx_chn_sts2|ljust:10) | $(tx_fault2|ljust:11)|  $(tx_los2|ljust:18)|  $(tx_opt_pw_alm2|ljust:17)|
         | Tx Ch 3\\\\: | $(tx_chn_sts3|ljust:10) | $(tx_fault3|ljust:11)|  $(tx_los3|ljust:18)|  $(tx_opt_pw_alm3|ljust:17)|
         | Tx Ch 4\\\\: | $(tx_chn_sts4|ljust:10) | $(tx_fault4|ljust:11)|  $(tx_los4|ljust:18)|  $(tx_opt_pw_alm4|ljust:17)|
         | Tx Ch 5\\\\: | $(tx_chn_sts5|ljust:10) | $(tx_fault5|ljust:11)|  $(tx_los5|ljust:18)|  $(tx_opt_pw_alm5|ljust:17)|
         | Tx Ch 6\\\\: | $(tx_chn_sts6|ljust:10) | $(tx_fault6|ljust:11)|  $(tx_los6|ljust:18)|  $(tx_opt_pw_alm6|ljust:17)|
         | Tx Ch 7\\\\: | $(tx_chn_sts7|ljust:10) | $(tx_fault7|ljust:11)|  $(tx_los7|ljust:18)|  $(tx_opt_pw_alm7|ljust:17)|
         | Tx Ch 8\\\\: | $(tx_chn_sts8|ljust:10) | $(tx_fault8|ljust:11)|  $(tx_los8|ljust:18)|  $(tx_opt_pw_alm8|ljust:17)|
         | Tx Ch 9\\\\: | $(tx_chn_sts9|ljust:10) | $(tx_fault9|ljust:11)|  $(tx_los9|ljust:18)|  $(tx_opt_pw_alm9|ljust:17)|
         | Tx Ch 10\\\\:| $(tx_chn_sts10|ljust:10) | $(tx_fault10|ljust:11)|  $(tx_los10|ljust:18)|  $(tx_opt_pw_alm10|ljust:17)|
         | Tx Ch 11\\\\:| $(tx_chn_sts11|ljust:10) | $(tx_fault11|ljust:11)|  $(tx_los11|ljust:18)|  $(tx_opt_pw_alm11|ljust:17)|
         +-----------------------------------------------------------------------------+
         
         +--------------------------------------------------------------------------+
         |  Channel |       Optical Light        |     Bias .     |   Optical Bias  |
         |  Number. |          Output            |    Current     |     Alarm       |
         +--------------------------------------------------------------------------+
         | Tx Ch 0\\\\: |   $(tx_light_op_dBm0|ljust:25)|   $(tx_bias_cur0|floatformat:3) mA     | $(tx_opt_bs_alm0|ljust:15) |
         | Tx Ch 1\\\\: |   $(tx_light_op_dBm1|ljust:25)|   $(tx_bias_cur1|floatformat:3) mA     | $(tx_opt_bs_alm1|ljust:15) |
         | Tx Ch 2\\\\: |   $(tx_light_op_dBm2|ljust:25)|   $(tx_bias_cur2|floatformat:3) mA     | $(tx_opt_bs_alm2|ljust:15) |
         | Tx Ch 3\\\\: |   $(tx_light_op_dBm3|ljust:25)|   $(tx_bias_cur3|floatformat:3) mA     | $(tx_opt_bs_alm3|ljust:15) |
         | Tx Ch 4\\\\: |   $(tx_light_op_dBm4|ljust:25)|   $(tx_bias_cur4|floatformat:3) mA     | $(tx_opt_bs_alm4|ljust:15) |
         | Tx Ch 5\\\\: |   $(tx_light_op_dBm5|ljust:25)|   $(tx_bias_cur5|floatformat:3) mA     | $(tx_opt_bs_alm5|ljust:15) |
         | Tx Ch 6\\\\: |   $(tx_light_op_dBm6|ljust:25)|   $(tx_bias_cur6|floatformat:3) mA     | $(tx_opt_bs_alm6|ljust:15) |
         | Tx Ch 7\\\\: |   $(tx_light_op_dBm7|ljust:25)|   $(tx_bias_cur7|floatformat:3) mA     | $(tx_opt_bs_alm7|ljust:15) |
         | Tx Ch 8\\\\: |   $(tx_light_op_dBm8|ljust:25)|   $(tx_bias_cur8|floatformat:3) mA     | $(tx_opt_bs_alm8|ljust:15) |
         | Tx Ch 9\\\\: |   $(tx_light_op_dBm9|ljust:25)|   $(tx_bias_cur9|floatformat:3) mA     | $(tx_opt_bs_alm9|ljust:15) |
         | Tx Ch 10\\\\:|   $(tx_light_op_dBm10|ljust:25)|   $(tx_bias_cur10|floatformat:3) mA     | $(tx_opt_bs_alm10|ljust:15) |
         | Tx Ch 11\\\\:|   $(tx_light_op_dBm11|ljust:25)|   $(tx_bias_cur11|floatformat:3) mA     | $(tx_opt_bs_alm11|ljust:15) |
         +--------------------------------------------------------------------------+
         Rx Temperature Reading \t\\\\:$(RX_temp_rd|floatformat:2) Celsius\tRx Temperature Alarm \\\\:$(RX_temp_sts) Set
         Rx Voltage Reading \t\\\\:$(RX_volt_rd|floatformat:2) mV \tRx Voltage Alarm \\\\:$(RX_volt_sts) Set
         +------------------------------------------------------------------------------+
         |  Channel |   Channel  |     Signal .     |Optical Power|     Optical Light   |
         |  Number. |   Status   |    Strength      |    Alarm    |         Input       |
         +------------------------------------------------------------------------------+
         | Rx Ch 0\\\\: | $(rx_chn_sts0|ljust:11)| $(rx_los0|ljust:17)|   $(rx_opt_pw_alm0|ljust:10)| $(rx_light_in_dBm0|ljust:19) |
         | Rx Ch 1\\\\: | $(rx_chn_sts1|ljust:11)| $(rx_los1|ljust:17)|   $(rx_opt_pw_alm1|ljust:10)| $(rx_light_in_dBm1|ljust:19) |
         | Rx Ch 2\\\\: | $(rx_chn_sts2|ljust:11)| $(rx_los2|ljust:17)|   $(rx_opt_pw_alm2|ljust:10)| $(rx_light_in_dBm2|ljust:19) |
         | Rx Ch 3\\\\: | $(rx_chn_sts3|ljust:11)| $(rx_los3|ljust:17)|   $(rx_opt_pw_alm3|ljust:10)| $(rx_light_in_dBm3|ljust:19) |
         | Rx Ch 4\\\\: | $(rx_chn_sts4|ljust:11)| $(rx_los4|ljust:17)|   $(rx_opt_pw_alm4|ljust:10)| $(rx_light_in_dBm4|ljust:19) |
         | Rx Ch 5\\\\: | $(rx_chn_sts5|ljust:11)| $(rx_los5|ljust:17)|   $(rx_opt_pw_alm5|ljust:10)| $(rx_light_in_dBm5|ljust:19) |
         | Rx Ch 6\\\\: | $(rx_chn_sts6|ljust:11)| $(rx_los6|ljust:17)|   $(rx_opt_pw_alm6|ljust:10)| $(rx_light_in_dBm6|ljust:19) |
         | Rx Ch 7\\\\: | $(rx_chn_sts7|ljust:11)| $(rx_los7|ljust:17)|   $(rx_opt_pw_alm7|ljust:10)| $(rx_light_in_dBm7|ljust:19) |
         | Rx Ch 8\\\\: | $(rx_chn_sts8|ljust:11)| $(rx_los8|ljust:17)|   $(rx_opt_pw_alm8|ljust:10)| $(rx_light_in_dBm8|ljust:19) |
         | Rx Ch 9\\\\: | $(rx_chn_sts9|ljust:11)| $(rx_los9|ljust:17)|   $(rx_opt_pw_alm9|ljust:10)| $(rx_light_in_dBm9|ljust:19) |
         | Rx Ch 10\\\\:| $(rx_chn_sts10|ljust:11)| $(rx_los10|ljust:17)|   $(rx_opt_pw_alm10|ljust:10)| $(rx_light_in_dBm10|ljust:19) |
         | Rx Ch 11\\\\:| $(rx_chn_sts11|ljust:11)| $(rx_los11|ljust:17)|   $(rx_opt_pw_alm11|ljust:10)| $(rx_light_in_dBm11|ljust:19) |
         +------------------------------------------------------------------------------+
         
         :CXP not present. 
         )";
      leaf show_port {
        type boolean;
        tailf:hidden "internal";
      }
      leaf cxp2_display {
        type boolean;
        tailf:hidden "internal";
      }
      leaf rack_num {
        type uint32;
        tailf:hidden "internal";
      }
      leaf slot_num {
        type uint32;
        tailf:hidden "internal";
      }
      leaf cxp_port {
        type fabric-types:cxp_port_type;
      }
      leaf cur_loc_str {
        type string;
        tailf:hidden "internal";
      }
      leaf vendorname {
        type string;
        tailf:hidden "internal";
      }
      leaf partnumber {
        type string;
        tailf:hidden "internal";
      }
      leaf serialnumber {
        type string;
        tailf:hidden "internal";
      }
      leaf vid {
        type string;
        tailf:hidden "internal";
      }
      leaf pid {
        type string;
        tailf:hidden "internal";
      }
      leaf vendor_rev_num {
        type uint32;
        tailf:hidden "internal";
      }
      leaf vendor_pn {
        type string;
        tailf:hidden "internal";
      }
      leaf vendor_sn {
        type string;
        tailf:hidden "internal";
      }
      leaf dev_description {
        type string;
        tailf:hidden "internal";
      }
      leaf clei_code_num {
        type string;
        tailf:hidden "internal";
      }
      leaf ven_date_code {
        type string;
        tailf:hidden "internal";
      }
      leaf ven_lot_code {
        type string;
        tailf:hidden "internal";
      }
      leaf vendor_oui_ieee_company_id {
        type uint32;
        tailf:hidden "internal";
      }
      leaf eeprom_rev_num {
        type uint32;
        tailf:hidden "internal";
      }
      leaf firmware_rev_num {
        type uint32;
        tailf:hidden "internal";
      }
      leaf TX_temp_rd {
        type xs:float;
        tailf:hidden "internal";
      }
      leaf TX_temp_sts {
        type string;
        tailf:hidden "internal";
      }
      leaf TX_volt_sts {
        type string;
        tailf:hidden "internal";
      }
      leaf TX_volt_rd {
        type xs:float;
        tailf:hidden "internal";
      }
      leaf tx_chn_sts0 {
        type string;
        tailf:hidden "internal";
      }
      leaf tx_chn_sts1 {
        type string;
        tailf:hidden "internal";
      }
      leaf tx_chn_sts2 {
        type string;
        tailf:hidden "internal";
      }
      leaf tx_chn_sts3 {
        type string;
        tailf:hidden "internal";
      }
      leaf tx_chn_sts4 {
        type string;
        tailf:hidden "internal";
      }
      leaf tx_chn_sts5 {
        type string;
        tailf:hidden "internal";
      }
      leaf tx_chn_sts6 {
        type string;
        tailf:hidden "internal";
      }
      leaf tx_chn_sts7 {
        type string;
        tailf:hidden "internal";
      }
      leaf tx_chn_sts8 {
        type string;
        tailf:hidden "internal";
      }
      leaf tx_chn_sts9 {
        type string;
        tailf:hidden "internal";
      }
      leaf tx_chn_sts10 {
        type string;
        tailf:hidden "internal";
      }
      leaf tx_chn_sts11 {
        type string;
        tailf:hidden "internal";
      }
      leaf tx_fault0 {
        type string;
        tailf:hidden "internal";
      }
      leaf tx_fault1 {
        type string;
        tailf:hidden "internal";
      }
      leaf tx_fault2 {
        type string;
        tailf:hidden "internal";
      }
      leaf tx_fault3 {
        type string;
        tailf:hidden "internal";
      }
      leaf tx_fault4 {
        type string;
        tailf:hidden "internal";
      }
      leaf tx_fault5 {
        type string;
        tailf:hidden "internal";
      }
      leaf tx_fault6 {
        type string;
        tailf:hidden "internal";
      }
      leaf tx_fault7 {
        type string;
        tailf:hidden "internal";
      }
      leaf tx_fault8 {
        type string;
        tailf:hidden "internal";
      }
      leaf tx_fault9 {
        type string;
        tailf:hidden "internal";
      }
      leaf tx_fault10 {
        type string;
        tailf:hidden "internal";
      }
      leaf tx_fault11 {
        type string;
        tailf:hidden "internal";
      }
      leaf tx_bias_cur0 {
        type xs:float;
        tailf:hidden "internal";
      }
      leaf tx_bias_cur1 {
        type xs:float;
        tailf:hidden "internal";
      }
      leaf tx_bias_cur2 {
        type xs:float;
        tailf:hidden "internal";
      }
      leaf tx_bias_cur3 {
        type xs:float;
        tailf:hidden "internal";
      }
      leaf tx_bias_cur4 {
        type xs:float;
        tailf:hidden "internal";
      }
      leaf tx_bias_cur5 {
        type xs:float;
        tailf:hidden "internal";
      }
      leaf tx_bias_cur6 {
        type xs:float;
        tailf:hidden "internal";
      }
      leaf tx_bias_cur7 {
        type xs:float;
        tailf:hidden "internal";
      }
      leaf tx_bias_cur8 {
        type xs:float;
        tailf:hidden "internal";
      }
      leaf tx_bias_cur9 {
        type xs:float;
        tailf:hidden "internal";
      }
      leaf tx_bias_cur10 {
        type xs:float;
        tailf:hidden "internal";
      }
      leaf tx_bias_cur11 {
        type xs:float;
        tailf:hidden "internal";
      }
      leaf tx_los0 {
        type string;
        tailf:hidden "internal";
      }
      leaf tx_los1 {
        type string;
        tailf:hidden "internal";
      }
      leaf tx_los2 {
        type string;
        tailf:hidden "internal";
      }
      leaf tx_los3 {
        type string;
        tailf:hidden "internal";
      }
      leaf tx_los4 {
        type string;
        tailf:hidden "internal";
      }
      leaf tx_los5 {
        type string;
        tailf:hidden "internal";
      }
      leaf tx_los6 {
        type string;
        tailf:hidden "internal";
      }
      leaf tx_los7 {
        type string;
        tailf:hidden "internal";
      }
      leaf tx_los8 {
        type string;
        tailf:hidden "internal";
      }
      leaf tx_los9 {
        type string;
        tailf:hidden "internal";
      }
      leaf tx_los10 {
        type string;
        tailf:hidden "internal";
      }
      leaf tx_los11 {
        type string;
        tailf:hidden "internal";
      }
      leaf tx_opt_pw_alm0 {
        type string;
        tailf:hidden "internal";
      }
      leaf tx_opt_pw_alm1 {
        type string;
        tailf:hidden "internal";
      }
      leaf tx_opt_pw_alm2 {
        type string;
        tailf:hidden "internal";
      }
      leaf tx_opt_pw_alm3 {
        type string;
        tailf:hidden "internal";
      }
      leaf tx_opt_pw_alm4 {
        type string;
        tailf:hidden "internal";
      }
      leaf tx_opt_pw_alm5 {
        type string;
        tailf:hidden "internal";
      }
      leaf tx_opt_pw_alm6 {
        type string;
        tailf:hidden "internal";
      }
      leaf tx_opt_pw_alm7 {
        type string;
        tailf:hidden "internal";
      }
      leaf tx_opt_pw_alm8 {
        type string;
        tailf:hidden "internal";
      }
      leaf tx_opt_pw_alm9 {
        type string;
        tailf:hidden "internal";
      }
      leaf tx_opt_pw_alm10 {
        type string;
        tailf:hidden "internal";
      }
      leaf tx_opt_pw_alm11 {
        type string;
        tailf:hidden "internal";
      }
      leaf tx_opt_bs_alm0 {
        type string;
        tailf:hidden "internal";
      }
      leaf tx_opt_bs_alm1 {
        type string;
        tailf:hidden "internal";
      }
      leaf tx_opt_bs_alm2 {
        type string;
        tailf:hidden "internal";
      }
      leaf tx_opt_bs_alm3 {
        type string;
        tailf:hidden "internal";
      }
      leaf tx_opt_bs_alm4 {
        type string;
        tailf:hidden "internal";
      }
      leaf tx_opt_bs_alm5 {
        type string;
        tailf:hidden "internal";
      }
      leaf tx_opt_bs_alm6 {
        type string;
        tailf:hidden "internal";
      }
      leaf tx_opt_bs_alm7 {
        type string;
        tailf:hidden "internal";
      }
      leaf tx_opt_bs_alm8 {
        type string;
        tailf:hidden "internal";
      }
      leaf tx_opt_bs_alm9 {
        type string;
        tailf:hidden "internal";
      }
      leaf tx_opt_bs_alm10 {
        type string;
        tailf:hidden "internal";
      }
      leaf tx_opt_bs_alm11 {
        type string;
        tailf:hidden "internal";
      }
      leaf tx_light_op_dBm0 {
        type string;
        tailf:hidden "internal";
      }
      leaf tx_light_op_dBm1 {
        type string;
        tailf:hidden "internal";
      }
      leaf tx_light_op_dBm2 {
        type string;
        tailf:hidden "internal";
      }
      leaf tx_light_op_dBm3 {
        type string;
        tailf:hidden "internal";
      }
      leaf tx_light_op_dBm4 {
        type string;
        tailf:hidden "internal";
      }
      leaf tx_light_op_dBm5 {
        type string;
        tailf:hidden "internal";
      }
      leaf tx_light_op_dBm6 {
        type string;
        tailf:hidden "internal";
      }
      leaf tx_light_op_dBm7 {
        type string;
        tailf:hidden "internal";
      }
      leaf tx_light_op_dBm8 {
        type string;
        tailf:hidden "internal";
      }
      leaf tx_light_op_dBm9 {
        type string;
        tailf:hidden "internal";
      }
      leaf tx_light_op_dBm10 {
        type string;
        tailf:hidden "internal";
      }
      leaf tx_light_op_dBm11 {
        type string;
        tailf:hidden "internal";
      }
      leaf RX_temp_rd {
        type xs:float;
        tailf:hidden "internal";
      }
      leaf RX_temp_sts {
        type string;
        tailf:hidden "internal";
      }
      leaf RX_volt_sts {
        type string;
        tailf:hidden "internal";
      }
      leaf RX_volt_rd {
        type xs:float;
        tailf:hidden "internal";
      }
      leaf rx_chn_sts0 {
        type string;
        tailf:hidden "internal";
      }
      leaf rx_chn_sts1 {
        type string;
        tailf:hidden "internal";
      }
      leaf rx_chn_sts2 {
        type string;
        tailf:hidden "internal";
      }
      leaf rx_chn_sts3 {
        type string;
        tailf:hidden "internal";
      }
      leaf rx_chn_sts4 {
        type string;
        tailf:hidden "internal";
      }
      leaf rx_chn_sts5 {
        type string;
        tailf:hidden "internal";
      }
      leaf rx_chn_sts6 {
        type string;
        tailf:hidden "internal";
      }
      leaf rx_chn_sts7 {
        type string;
        tailf:hidden "internal";
      }
      leaf rx_chn_sts8 {
        type string;
        tailf:hidden "internal";
      }
      leaf rx_chn_sts9 {
        type string;
        tailf:hidden "internal";
      }
      leaf rx_chn_sts10 {
        type string;
        tailf:hidden "internal";
      }
      leaf rx_chn_sts11 {
        type string;
        tailf:hidden "internal";
      }
      leaf rx_los0 {
        type string;
        tailf:hidden "internal";
      }
      leaf rx_los1 {
        type string;
        tailf:hidden "internal";
      }
      leaf rx_los2 {
        type string;
        tailf:hidden "internal";
      }
      leaf rx_los3 {
        type string;
        tailf:hidden "internal";
      }
      leaf rx_los4 {
        type string;
        tailf:hidden "internal";
      }
      leaf rx_los5 {
        type string;
        tailf:hidden "internal";
      }
      leaf rx_los6 {
        type string;
        tailf:hidden "internal";
      }
      leaf rx_los7 {
        type string;
        tailf:hidden "internal";
      }
      leaf rx_los8 {
        type string;
        tailf:hidden "internal";
      }
      leaf rx_los9 {
        type string;
        tailf:hidden "internal";
      }
      leaf rx_los10 {
        type string;
        tailf:hidden "internal";
      }
      leaf rx_los11 {
        type string;
        tailf:hidden "internal";
      }
      leaf rx_opt_pw_alm0 {
        type string;
        tailf:hidden "internal";
      }
      leaf rx_opt_pw_alm1 {
        type string;
        tailf:hidden "internal";
      }
      leaf rx_opt_pw_alm2 {
        type string;
        tailf:hidden "internal";
      }
      leaf rx_opt_pw_alm3 {
        type string;
        tailf:hidden "internal";
      }
      leaf rx_opt_pw_alm4 {
        type string;
        tailf:hidden "internal";
      }
      leaf rx_opt_pw_alm5 {
        type string;
        tailf:hidden "internal";
      }
      leaf rx_opt_pw_alm6 {
        type string;
        tailf:hidden "internal";
      }
      leaf rx_opt_pw_alm7 {
        type string;
        tailf:hidden "internal";
      }
      leaf rx_opt_pw_alm8 {
        type string;
        tailf:hidden "internal";
      }
      leaf rx_opt_pw_alm9 {
        type string;
        tailf:hidden "internal";
      }
      leaf rx_opt_pw_alm10 {
        type string;
        tailf:hidden "internal";
      }
      leaf rx_opt_pw_alm11 {
        type string;
        tailf:hidden "internal";
      }
      leaf rx_light_in_dBm0 {
        type string;
        tailf:hidden "internal";
      }
      leaf rx_light_in_dBm1 {
        type string;
        tailf:hidden "internal";
      }
      leaf rx_light_in_dBm2 {
        type string;
        tailf:hidden "internal";
      }
      leaf rx_light_in_dBm3 {
        type string;
        tailf:hidden "internal";
      }
      leaf rx_light_in_dBm4 {
        type string;
        tailf:hidden "internal";
      }
      leaf rx_light_in_dBm5 {
        type string;
        tailf:hidden "internal";
      }
      leaf rx_light_in_dBm6 {
        type string;
        tailf:hidden "internal";
      }
      leaf rx_light_in_dBm7 {
        type string;
        tailf:hidden "internal";
      }
      leaf rx_light_in_dBm8 {
        type string;
        tailf:hidden "internal";
      }
      leaf rx_light_in_dBm9 {
        type string;
        tailf:hidden "internal";
      }
      leaf rx_light_in_dBm10 {
        type string;
        tailf:hidden "internal";
      }
      leaf rx_light_in_dBm11 {
        type string;
        tailf:hidden "internal";
      }
    }
  }

  grouping fc_cxp_port_rack_summary {
    list split_tbl_flag {
      key "tbl_splt";
      tailf:cli-suppress-table;
      tailf:cli-show-template-enter "";
      tailf:cli-show-template-legend
        "$(.legend_shown != true ?==========================================================================
          \t     Fabric side CXP Port Initialization Status Summary
         ==========================================================================
         )";
      leaf tbl_splt {
        type uint32;
      }
      list smry_per_slot {
        key "slot_no";
        tailf:cli-show-template-enter "";
        tailf:cli-suppress-table;
        tailf:cli-show-template
          "$(row_cxp_1 == true ?Active functional role of the Rack [R/S] \\\\: $(func_rack_name) 
            \t. - CXP is not present
            \tp - CXP is not powered
            \tI - CXP is not Initialized
            \tU - CXP is not Supported
            \tT - One or more Tx channel is disabled on the CXP
            \tR - One or more Rx channel is disabled on the CXP
            \tG - CXP is Initialized properly
           
            \t  Maximum CXP port number [0-$(max_cxp)] per slot
           +--------+---+---+---+---+---+---+---+---+---+---+---+---+---+---+---+---+
           | Slot   | 0 | 1 | 2 | 3 | 4 | 5 | 6 | 7 | 8 | 9 |10 |11 |12 |13 |14 |15 |
           +--------+---+---+---+---+---+---+---+---+---+---+---+---+---+---+---+---+
           )$(tbl_splt_flag == false ?| $(fc_loc_str|ljust:7)|$(cxp_sts_0|ljust:3)|$(cxp_sts_1|ljust:3)|$(cxp_sts_2|ljust:3)|$(cxp_sts_3|ljust:3)|$(cxp_sts_4|ljust:3)|$(cxp_sts_5|ljust:3)|$(cxp_sts_6|ljust:3)|$(cxp_sts_7|ljust:3)|$(cxp_sts_8|ljust:3)|$(cxp_sts_9|ljust:3)|$(cxp_sts_10|ljust:3)|$(cxp_sts_11|ljust:3)|$(cxp_sts_12|ljust:3)|$(cxp_sts_13|ljust:3)|$(cxp_sts_14|ljust:3)|$(cxp_sts_15|ljust:3)|
           +--------+---+---+---+---+---+---+---+---+---+---+---+---+---+---+---+---+
           :$(row_cxp_2 == true ?+--------+---+---+---+---+---+---+---+---+---+---+---+---+---+---+---+---+
           | Slot   |16 |17 |18 |19 |20 |21 |22 |23 |24 |25 |26 |27 |28 |29 |30 |31 |
           +--------+---+---+---+---+---+---+---+---+---+---+---+---+---+---+---+---+
           )| $(fc_loc_str|ljust:7)|$(cxp_sts_0|ljust:3)|$(cxp_sts_1|ljust:3)|$(cxp_sts_2|ljust:3)|$(cxp_sts_3|ljust:3)|$(cxp_sts_4|ljust:3)|$(cxp_sts_5|ljust:3)|$(cxp_sts_6|ljust:3)|$(cxp_sts_7|ljust:3)|$(cxp_sts_8|ljust:3)|$(cxp_sts_9|ljust:3)|$(cxp_sts_10|ljust:3)|$(cxp_sts_11|ljust:3)|$(cxp_sts_12|ljust:3)|$(cxp_sts_13|ljust:3)|$(cxp_sts_14|ljust:3)|$(cxp_sts_15|ljust:3)|
           +--------+---+---+---+---+---+---+---+---+---+---+---+---+---+---+---+---+
           )";
        leaf func_rack_name {
          type string;
          tailf:hidden "internal";
        }
        leaf max_cxp {
          type uint32;
          tailf:hidden "internal";
        }
        leaf row_cxp_1 {
          type boolean;
          default "false";
          tailf:hidden "internal";
        }
        leaf row_cxp_2 {
          type boolean;
          default "false";
          tailf:hidden "internal";
        }
        leaf slot_row {
          type boolean;
          default "false";
          tailf:hidden "internal";
        }
        leaf tbl_splt_flag {
          type boolean;
          tailf:hidden "internal";
        }
        leaf slot_no {
          type uint32;
        }
        leaf cxp_port_no {
          type uint32;
          tailf:hidden "internal";
        }
        leaf fc_loc_str {
          type string;
          tailf:hidden "internal";
        }
        leaf cxp_sts_0 {
          type string;
          tailf:hidden "internal";
        }
        leaf cxp_sts_1 {
          type string;
          tailf:hidden "internal";
        }
        leaf cxp_sts_2 {
          type string;
          tailf:hidden "internal";
        }
        leaf cxp_sts_3 {
          type string;
          tailf:hidden "internal";
        }
        leaf cxp_sts_4 {
          type string;
          tailf:hidden "internal";
        }
        leaf cxp_sts_5 {
          type string;
          tailf:hidden "internal";
        }
        leaf cxp_sts_6 {
          type string;
          tailf:hidden "internal";
        }
        leaf cxp_sts_7 {
          type string;
          tailf:hidden "internal";
        }
        leaf cxp_sts_8 {
          type string;
          tailf:hidden "internal";
        }
        leaf cxp_sts_9 {
          type string;
          tailf:hidden "internal";
        }
        leaf cxp_sts_10 {
          type string;
          tailf:hidden "internal";
        }
        leaf cxp_sts_11 {
          type string;
          tailf:hidden "internal";
        }
        leaf cxp_sts_12 {
          type string;
          tailf:hidden "internal";
        }
        leaf cxp_sts_13 {
          type string;
          tailf:hidden "internal";
        }
        leaf cxp_sts_14 {
          type string;
          tailf:hidden "internal";
        }
        leaf cxp_sts_15 {
          type string;
          tailf:hidden "internal";
        }
      }
    }
  }

  grouping fc_cxp_dom {
    container cxp {
      tailf:info "Fabric card CXP optics information";
      tailf:cli-incomplete-show-path;
      container dom {
        tailf:callpoint "fc_cxp_optics_dom_cp";
        tailf:info "CXP optic DOM data";
        tailf:cli-incomplete-show-path;
        list location {
          key "loc_str";
          tailf:cli-incomplete-show-path;
          tailf:cli-suppress-table;
          leaf loc_str {
            type string;
          }
          leaf description {
            type string;
            default "location (R/S)";
          }
          uses dom_output;
        }
      }
      container summary {
        tailf:callpoint "fc_cxp_port_summary_cp";
        tailf:cli-incomplete-show-path;
        tailf:hidden "internal-command";
        tailf:info "CXP Port Status Summary";
        list rack {
          key "rack_str";
          tailf:cli-suppress-table;
          leaf rack_str {
            type string;
          }
          leaf description {
            type string;
            default "Rack No.";
          }
          uses fc_cxp_port_rack_summary;
        }
      }
    }
  }
  tailf:id "http://www.cisco.com/panini/calvados/fabric/cxp";
}
