module Cisco-IOS-XR-sysadmin-asic-errors-ael {
  namespace "http://www.cisco.com/ns/yang/Cisco-IOS-XR-sysadmin-asic-errors-ael";
  prefix ael;

  import tailf-common {
    prefix tailf;
  }
  import Cisco-IOS-XR-sysadmin-types {
    prefix calvados;
  }

  revision 2017-07-05 {
    description
      "Namespace change to fix comply with Cisco guidelines on namespace";
  }
  revision 2017-05-01 {
    description
      "Namespace change to comply with Cisco guidelines on namespace";
  }

  grouping clear-asic-errors {
    tailf:action "counter" {
      tailf:actionpoint "ael-clear-stats";
    }
  }

  grouping ael-history-ap-grp {
    container history {
      tailf:info "show history before last node reload/shutdown";
      tailf:cli-incomplete-show-path;
      list location {
        key "location-name";
        tailf:info "Location to display";
        tailf:callpoint "ael_location";
        leaf location-name {
          type calvados:location-id;
        }
        uses clear-asic-errors;
      }
    }
  }

  grouping ael-history-grp {
    container history {
      tailf:info "show history before last node reload/shutdown";
      tailf:cli-incomplete-show-path;
      list location {
        key "location-name";
        tailf:info "Location to display";
        tailf:callpoint "ael_location";
        leaf location-name {
          type calvados:location-id;
        }
        list log-lst {
          tailf:cli-drop-node-name;
          tailf:cli-suppress-mode;
          tailf:cli-suppress-table;
          tailf:callpoint "ael_get_errors";
          tailf:cli-suppress-show-path;
          tailf:cli-table-legend "";
          tailf:cli-show-template "$(log-line)\n";
          leaf log-line {
            type string;
          }
        }
      }
    }
  }

  grouping ael-non-history-grp {
    list location {
      key "location-name";
      tailf:info "Location to display";
      tailf:callpoint "ael_location";
      leaf location-name {
        type calvados:location-id;
      }
      list log-lst {
        tailf:cli-drop-node-name;
        tailf:cli-suppress-mode;
        tailf:cli-suppress-table;
        tailf:callpoint "ael_get_errors";
        tailf:cli-suppress-show-path;
        tailf:cli-table-legend "";
        tailf:cli-show-template "$(log-line)\n";
        leaf log-line {
          type string;
        }
      }
    }
  }

  grouping ael-non-history-ap-grp {
    list location {
      key "location-name";
      tailf:info "Location to display";
      tailf:callpoint "ael_location";
      leaf location-name {
        type calvados:location-id;
      }
      uses clear-asic-errors;
    }
  }

  grouping ael-all-error-types-grp {
    container sbe {
      tailf:info "Single bit error information";
      tailf:cli-incomplete-show-path;
      uses ael-non-history-grp;
    }
    container mbe {
      tailf:info "Multi bit error information";
      tailf:cli-incomplete-show-path;
      uses ael-non-history-grp;
    }
    container parity {
      tailf:info "Parity error information";
      tailf:cli-incomplete-show-path;
      uses ael-non-history-grp;
    }
    container generic {
      tailf:info "Generic error information";
      tailf:cli-incomplete-show-path;
      uses ael-non-history-grp;
    }
    container crc {
      tailf:info "CRC error information";
      tailf:cli-incomplete-show-path;
      uses ael-non-history-grp;
    }
    container reset {
      tailf:info "ASIC reset information";
      tailf:cli-incomplete-show-path;
      uses ael-non-history-grp;
    }
    container barrier {
      tailf:info "barrier errors";
      tailf:cli-incomplete-show-path;
      uses ael-non-history-grp;
    }
    container unexpected {
      tailf:info "unexpected errors";
      tailf:cli-incomplete-show-path;
      uses ael-non-history-grp;
    }
    container link {
      tailf:info "physical link level errors";
      tailf:cli-incomplete-show-path;
      uses ael-non-history-grp;
    }
    container oor-thresh {
      tailf:info "oor threshold";
      tailf:cli-incomplete-show-path;
      uses ael-non-history-grp;
    }
    container bp {
      tailf:info "error related for Fabric Backpressure";
      tailf:cli-incomplete-show-path;
      uses ael-non-history-grp;
    }
    container io {
      tailf:info "IO operation error";
      tailf:cli-incomplete-show-path;
      uses ael-non-history-grp;
    }
    container ucode {
      tailf:info "ucode errors";
      tailf:cli-incomplete-show-path;
      uses ael-non-history-grp;
    }
    container config {
      tailf:info "config error";
      tailf:cli-incomplete-show-path;
      uses ael-non-history-grp;
    }
    container indirect {
      tailf:info "indirect error";
      tailf:cli-incomplete-show-path;
      uses ael-non-history-grp;
    }
    container nonerr {
      tailf:info "non-error";
      tailf:cli-incomplete-show-path;
      uses ael-non-history-grp;
    }
    container summary {
      tailf:info "Errors summary information";
      tailf:cli-incomplete-show-path;
      uses ael-non-history-grp;
    }
    container all {
      tailf:info "All error information";
      tailf:cli-incomplete-show-path;
      uses ael-history-grp;
      uses ael-non-history-grp;
    }
  }

  grouping ael-all-error-types-wo-history-grp {
    container sbe {
      tailf:info "Single bit error information";
      tailf:cli-incomplete-show-path;
      uses ael-non-history-grp;
    }
    container mbe {
      tailf:info "Multi bit error information";
      tailf:cli-incomplete-show-path;
      uses ael-non-history-grp;
    }
    container parity {
      tailf:info "Parity error information";
      tailf:cli-incomplete-show-path;
      uses ael-non-history-grp;
    }
    container generic {
      tailf:info "Generic error information";
      tailf:cli-incomplete-show-path;
      uses ael-non-history-grp;
    }
    container crc {
      tailf:info "CRC error information";
      tailf:cli-incomplete-show-path;
      uses ael-non-history-grp;
    }
    container reset {
      tailf:info "ASIC reset information";
      tailf:cli-incomplete-show-path;
      uses ael-non-history-grp;
    }
    container barrier {
      tailf:info "barrier errors";
      tailf:cli-incomplete-show-path;
      uses ael-non-history-grp;
    }
    container unexpected {
      tailf:info "unexpected errors";
      tailf:cli-incomplete-show-path;
      uses ael-non-history-grp;
    }
    container link {
      tailf:info "physical link level errors";
      tailf:cli-incomplete-show-path;
      uses ael-non-history-grp;
    }
    container oor-thresh {
      tailf:info "oor threshold";
      tailf:cli-incomplete-show-path;
      uses ael-non-history-grp;
    }
    container bp {
      tailf:info "error related for Fabric Backpressure";
      tailf:cli-incomplete-show-path;
      uses ael-non-history-grp;
    }
    container io {
      tailf:info "IO operation error";
      tailf:cli-incomplete-show-path;
      uses ael-non-history-grp;
    }
    container ucode {
      tailf:info "ucode errors";
      tailf:cli-incomplete-show-path;
      uses ael-non-history-grp;
    }
    container config {
      tailf:info "config error";
      tailf:cli-incomplete-show-path;
      uses ael-non-history-grp;
    }
    container indirect {
      tailf:info "indirect error";
      tailf:cli-incomplete-show-path;
      uses ael-non-history-grp;
    }
    container nonerr {
      tailf:info "non-error";
      tailf:cli-incomplete-show-path;
      uses ael-non-history-grp;
    }
    container summary {
      tailf:info "Errors summary information";
      tailf:cli-incomplete-show-path;
      uses ael-non-history-grp;
    }
    container all {
      tailf:info "All error information";
      tailf:cli-incomplete-show-path;
      uses ael-non-history-grp;
    }
  }

  grouping ael-all-error-types-ap-grp {
    container sbe {
      tailf:info "Single bit error information";
      tailf:cli-incomplete-show-path;
      uses ael-non-history-ap-grp;
    }
    container mbe {
      tailf:info "Multi bit error information";
      tailf:cli-incomplete-show-path;
      uses ael-non-history-ap-grp;
    }
    container parity {
      tailf:info "Parity error information";
      tailf:cli-incomplete-show-path;
      uses ael-non-history-ap-grp;
    }
    container generic {
      tailf:info "Generic error information";
      tailf:cli-incomplete-show-path;
      uses ael-non-history-ap-grp;
    }
    container crc {
      tailf:info "CRC error information";
      tailf:cli-incomplete-show-path;
      uses ael-non-history-ap-grp;
    }
    container reset {
      tailf:info "ASIC reset information";
      tailf:cli-incomplete-show-path;
      uses ael-non-history-ap-grp;
    }
    container barrier {
      tailf:info "barrier errors";
      tailf:cli-incomplete-show-path;
      uses ael-non-history-ap-grp;
    }
    container unexpected {
      tailf:info "unexpected errors";
      tailf:cli-incomplete-show-path;
      uses ael-non-history-ap-grp;
    }
    container link {
      tailf:info "physical link level errors";
      tailf:cli-incomplete-show-path;
      uses ael-non-history-ap-grp;
    }
    container oor-thresh {
      tailf:info "oor threshold";
      tailf:cli-incomplete-show-path;
      uses ael-non-history-ap-grp;
    }
    container bp {
      tailf:info "error related for Fabric Backpressure";
      tailf:cli-incomplete-show-path;
      uses ael-non-history-ap-grp;
    }
    container io {
      tailf:info "IO operation error";
      tailf:cli-incomplete-show-path;
      uses ael-non-history-ap-grp;
    }
    container ucode {
      tailf:info "ucode errors";
      tailf:cli-incomplete-show-path;
      uses ael-non-history-ap-grp;
    }
    container config {
      tailf:info "config error";
      tailf:cli-incomplete-show-path;
      uses ael-non-history-ap-grp;
    }
    container indirect {
      tailf:info "indirect error";
      tailf:cli-incomplete-show-path;
      uses ael-non-history-ap-grp;
    }
    container nonerr {
      tailf:info "non-error";
      tailf:cli-incomplete-show-path;
      uses ael-non-history-ap-grp;
    }
    container summary {
      tailf:info "Errors summary information";
      tailf:cli-incomplete-show-path;
      uses ael-non-history-ap-grp;
    }
    container all {
      tailf:info "All error information";
      tailf:cli-incomplete-show-path;
      uses ael-history-ap-grp;
      uses ael-non-history-ap-grp;
    }
  }

  grouping ael-show-asic-errors-grp {
    list asic-errors {
      key "device-name";
      config false;
      tailf:info "Display ASIC related device errors";
      tailf:cli-incomplete-show-path;
      tailf:callpoint "ael_devices";
      leaf device-name {
        type string;
      }
      list instance {
        key "instance-num";
        tailf:info "ASIC instance number";
        tailf:cli-incomplete-show-path;
        tailf:cli-drop-node-name;
        tailf:callpoint "ael_instances";
        leaf instance-num {
          type uint32;
        }
        uses ael-all-error-types-grp;
      }
      container show-all-instances {
        tailf:alt-name "all";
        tailf:cli-incomplete-show-path;
        uses ael-all-error-types-wo-history-grp;
      }
    }
  }

  grouping ael-clear-asic-errors-grp {
    container clear-asic-errors-grp {
      tailf:alt-name "asic-errors";
      tailf:info "Clear ASIC related device errors";
      tailf:cli-incomplete-show-path;
      list clear-device {
        key "device-name";
        config false;
        tailf:cli-drop-node-name;
        tailf:cli-incomplete-show-path;
        tailf:callpoint "ael_devices";
        leaf device-name {
          type string;
        }
        list instance {
          key "instance-num";
          tailf:cli-incomplete-show-path;
          tailf:cli-drop-node-name;
          tailf:callpoint "ael_instances";
          leaf instance-num {
            type uint32;
          }
          uses ael-all-error-types-ap-grp;
        }
        container all-instances {
          tailf:alt-name "all";
          tailf:cli-incomplete-show-path;
          uses ael-all-error-types-ap-grp;
        }
      }
    }
  }
  tailf:id "http://cisco.com/panini/calvados/asic-errors";

  uses ael-show-asic-errors-grp;
}
