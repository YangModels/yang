module Cisco-IOS-XR-sysadmin-aaa-aaa-show {
  namespace "http://www.cisco.com/ns/yang/Cisco-IOS-XR-sysadmin-aaa-aaa-show";
  prefix aaa_show;

  import tailf-common {
    prefix tailf;
  }
  import tailf-aaa {
    prefix aaa;
  }

  organization
    "Cisco Systems Inc.";
  contact
    "clos-mgbl@cisco.com";
  description
    "This module defines yang model
     for logging user/date who accessed
     shell last time";

  revision 2017-05-10 {
    description
      "Namespace changed from aaa_show to Cisco-IOS-XR-sysadmin-aaa-aaa-show";
  }
  revision 2011-06-20 {
    description
      "Initial revision";
  }

  augment "/aaa:aaa" {
    container privileged-access {
      config false;
      tailf:cli-incomplete-command;
      tailf:callpoint "show_aaa";
      tailf:info
        "
         Privileged-user, shell access and disaster-recovery user information";
      tailf:cli-show-template
        "
         Privileged-user, shell access and disaster-recovery user information 
           Last access to shell via disaster-recovery account : $(shell-access)
           Privileged-user                                    : $(first-user)
           Privileged-user attributes changed via admin CLI   : $(first-user-change)
           Current disaster-recovery user                     : $(current-disaster-recovery-user)
         
        ";
      leaf shell-access {
        type string;
        mandatory false;
        tailf:cli-suppress-show-path;
        tailf:info
          "
           User and Time who accessed the shell last time";
      }
      leaf first-user {
        type string;
        mandatory false;
        tailf:cli-suppress-show-path;
        tailf:info
          "
           first user configured name";
      }
      leaf first-user-change {
        type string;
        mandatory false;
        tailf:cli-suppress-show-path;
        tailf:info
          "
           Indicate whether first user is changed from admin CLI or not";
      }
      leaf current-disaster-recovery-user {
        type string;
        mandatory false;
        tailf:cli-suppress-show-path;
        tailf:info
          "
           Current disaster-recovery user name";
      }
    }
    container accounting {
      config false;
      tailf:cli-incomplete-command;
      tailf:callpoint "show_audit";
      tailf:info
        "
         Detail audit log information";
      tailf:cli-show-template
        "
         Detail audit log information 
           Time                     Username          Session-ID     Node-Information     Command
         ---------------------------------------------------------------------------------------------------
         $(log-data)
        ";
      leaf log-data {
        type string;
        mandatory false;
        tailf:cli-suppress-show-path;
        tailf:info
          "
           logging details";
      }
    }
    container user-group {
      config false;
      tailf:cli-incomplete-command;
      tailf:callpoint "show_group";
      tailf:info
        "
         Detail Current user grp information";
      tailf:cli-show-template
        "
         User group : $(grp-data)
        ";
      leaf grp-data {
        type string;
        mandatory false;
        tailf:cli-suppress-show-path;
        tailf:info
          "
           group details";
      }
    }
  }
  tailf:id "http://www.cisco.com/calvados/aaa_show";
}
