module Cisco-IOS-XR-isis-act {

    namespace "http://cisco.com/ns/yang/Cisco-IOS-XR-isis-act";
    
    prefix "isis-act";
    
    import Cisco-IOS-XR-types { prefix "xr"; }
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR ISIS action package configuration.

     Copyright (c) 2016-2017 by Cisco Systems, Inc.
     All rights reserved.";
    
    revision "2016-06-30" {
        description
            "IOS XR 6.2.1 revision.";
    } 
    
    rpc clear-isis-process {
        description "Clear all IS-IS data structures";
        input {
            container instance {
                description "Clear data from single IS-IS instance";
                leaf instance-identifier {
                    description "IS-IS process instance identifier";
                    type string;
                }
            }
            leaf process {
                description "Clear all IS-IS data structures";
                type empty;
            }
        }
    }

    rpc clear-isis-route {
        description "Clear IS-IS routes";
        input {
            container instance {
                description "Clear data from single IS-IS instance";
                leaf instance-identifier {
                    description "IS-IS process instance identifier";
                    type string;
                }
            }
            leaf route {
                description "Clear IS-IS routes";
                type empty;
            }
        }
    }

    rpc clear-isis-stat {
        description "Clear IS-IS protocol statistics";
        input {
            container instance {
                description "Clear data from single IS-IS instance";
                leaf instance-identifier {
                    description "IS-IS process instance identifier";
                    type string;
                }
            }
            container statistics {
                description "Clear IS-IS protocol statistics";   
                leaf interface-name {
                    mandatory true;
                    description "Interface name";
                    type xr:Interface-name;
                }
            }
        }
    }

    rpc clear-isis-dist {
        description "Reset BGP-LS topology distribution";
        input {
            container instance {
                description "Reset BGP-LS topology from single IS-IS instance";
                leaf instance-identifier {
                    description "IS-IS process instance identifier";
                    type string;
                }
            }
            leaf distribution {
                description "Reset BGP-LS topology distribution";
                type empty;
            }
        }
    }

    rpc clear-isis-local-lsp {
        description "Clean and regenerate local LSPs";
        input {
            container instance {
                description "Clean and regenerate local LSPs from single IS-IS instance";
                leaf instance-identifier {
                    description "IS-IS process instance identifier";
                    type string;
                }
            }
            leaf local-lsp {
                description "Clean and regenerate local LSPs";
                type empty;
            }
        }
    }

    rpc clear-isis {
        description "Clear IS-IS data structures";
        input {
            container instance {
                description "Clear data from single IS-IS instance";
                leaf instance-identifier {
                    description "IS-IS process instance identifier";
                    type string;
                }
            }
            leaf rt-type {
                description "Clear data for these route types";
                type enumeration {
                    enum AFI-ALL-MULTICAST {
                        value 0;
                    }
                    enum AFI-ALL-SAFI-ALL {
                        value 1;
                    }
                    enum AFI-ALL-UNICAST {
                        value 2;
                    }
                    enum IPv4-MULTICAST {
                        value 3;
                    }
                    enum IPv4-SAFI-ALL {
                        value 4;
                    }
                    enum IPv4-UNICAST {
                        value 5;
                    }
                    enum IPv6-MULTICAST {
                        value 6;
                    }
                    enum IPv6-SAFI-ALL {
                        value 7;
                    }
                    enum IPv6-UNICAST {
                        value 8;
                    }
                }
            }
            leaf route {
                description "Clear IS-IS routes";
                when "../topology = ''";
                type empty;
            }
            leaf topology {
                description "Topology table information";
                when "../route = 'empty'";
                type string;
            }
        } 
    }
}
