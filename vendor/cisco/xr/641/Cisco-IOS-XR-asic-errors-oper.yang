module Cisco-IOS-XR-asic-errors-oper {
  namespace "http://cisco.com/ns/yang/Cisco-IOS-XR-asic-errors-oper";
  prefix asic-errors-oper;

  import Cisco-IOS-XR-types {
    prefix xr;
  }
  include Cisco-IOS-XR-asic-errors-oper-sub2 {
    revision-date 2017-09-07;
  }
  include Cisco-IOS-XR-asic-errors-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asic-errors package operational data.
     
     This module contains definitions
     for the following management objects:
       asic-errors: Error summary of all asics
     
     Copyright (c) 2013-2017 by Cisco Systems, Inc.
     All rights reserved.";

  revision 2017-09-07 {
    description
      "Fixed type translation error.";
  }
  revision 2015-11-09 {
    description
      "IOS XR 6.0 revision.";
  }

  container asic-errors {
    config false;
    description
      "Error summary of all asics";
    container nodes {
      description
        "Asic errors for each available nodes";
      list node {
        key "node-name";
        description
          "Asic error for a particular node";
        leaf node-name {
          type xr:Node-id;
          description
            "Node ID";
        }
        list asic-information {
          key "asic";
          description
            "Asic on the node";
          container all-instances {
            description
              "All asic instance on the node";
            container all-error-path {
              description
                "Error path of all instances";
              container summary {
                description
                  "Summary of all instances errors";
                uses ASIC-SUMMARY-BG;
              }
            }
          }
          container instances {
            description
              "All asic errors  on the node";
            list instance {
              key "asic-instance";
              description
                "Particular asic instance on the node";
              container error-path {
                description
                  "Error path of the instances";
                container multiple-bit-soft-errors {
                  description
                    "Multiple bit soft error information";
                  uses CIHERR-NODES-BG;
                }
                container asic-error-generic-soft {
                  description
                    "Indirect hard error information";
                  uses CIHERR-NODES-BG;
                }
                container crc-hard-errors {
                  description
                    "CRC hard error information";
                  uses CIHERR-NODES-BG;
                }
                container asic-error-sbe-soft {
                  description
                    "Indirect hard error information";
                  uses CIHERR-NODES-BG;
                }
                container hardware-soft-errors {
                  description
                    "Hardware soft error information";
                  uses CIHERR-NODES-BG;
                }
                container asic-error-crc-soft {
                  description
                    "Indirect hard error information";
                  uses CIHERR-NODES-BG;
                }
                container asic-error-parity-soft {
                  description
                    "Indirect hard error information";
                  uses CIHERR-NODES-BG;
                }
                container io-soft-errors {
                  description
                    "IO soft error information";
                  uses CIHERR-NODES-BG;
                }
                container reset-soft-errors {
                  description
                    "Reset soft error information";
                  uses CIHERR-NODES-BG;
                }
                container barrier-hard-errors {
                  description
                    "Barrier hard error information";
                  uses CIHERR-NODES-BG;
                }
                container ucode-soft-errors {
                  description
                    "Ucode soft error information";
                  uses CIHERR-NODES-BG;
                }
                container asic-error-reset-hard {
                  description
                    "Indirect hard error information";
                  uses CIHERR-NODES-BG;
                }
                container single-bit-hard-errors {
                  description
                    "Single bit hard error information";
                  uses CIHERR-NODES-BG;
                }
                container indirect-hard-errors {
                  description
                    "Indirect hard error information";
                  uses CIHERR-NODES-BG;
                }
                container outof-resource-soft {
                  description
                    "OOR thresh information";
                  uses CIHERR-NODES-BG;
                }
                container crc-soft-errors {
                  description
                    "CRC soft error information";
                  uses CIHERR-NODES-BG;
                }
                container time-out-hard-errors {
                  description
                    "Time out hard error information";
                  uses CIHERR-NODES-BG;
                }
                container barrier-soft-errors {
                  description
                    "Barrier soft error information";
                  uses CIHERR-NODES-BG;
                }
                container asic-error-mbe-soft {
                  description
                    "Indirect hard error information";
                  uses CIHERR-NODES-BG;
                }
                container back-pressure-hard-errors {
                  description
                    "BP hard error information";
                  uses CIHERR-NODES-BG;
                }
                container single-bit-soft-errors {
                  description
                    "Single bit soft error information";
                  uses CIHERR-NODES-BG;
                }
                container indirect-soft-errors {
                  description
                    "Indirect soft error information";
                  uses CIHERR-NODES-BG;
                }
                container generic-hard-errors {
                  description
                    "Generic hard error information";
                  uses CIHERR-NODES-BG;
                }
                container link-hard-errors {
                  description
                    "Link hard error information";
                  uses CIHERR-NODES-BG;
                }
                container configuration-hard-errors {
                  description
                    "Configuration hard error information";
                  uses CIHERR-NODES-BG;
                }
                container instance-summary {
                  description
                    "Summary for a specific instance";
                  uses ASIC-SUMMARY-BG;
                }
                container unexpected-hard-errors {
                  description
                    "Unexpected hard error information";
                  uses CIHERR-NODES-BG;
                }
                container time-out-soft-errors {
                  description
                    "Time out soft error information";
                  uses CIHERR-NODES-BG;
                }
                container asic-error-generic-hard {
                  description
                    "Indirect hard error information";
                  uses CIHERR-NODES-BG;
                }
                container parity-hard-errors {
                  description
                    "Parity hard error information";
                  uses CIHERR-NODES-BG;
                }
                container descriptor-hard-errors {
                  description
                    "Descriptor hard error information";
                  uses CIHERR-NODES-BG;
                }
                container interface-hard-errors {
                  description
                    "Interface hard error information";
                  uses CIHERR-NODES-BG;
                }
                container asic-error-sbe-hard {
                  description
                    "Indirect hard error information";
                  uses CIHERR-NODES-BG;
                }
                container asic-error-crc-hard {
                  description
                    "Indirect hard error information";
                  uses CIHERR-NODES-BG;
                }
                container asic-error-parity-hard {
                  description
                    "Indirect hard error information";
                  uses CIHERR-NODES-BG;
                }
                container asic-error-reset-soft {
                  description
                    "Indirect hard error information";
                  uses CIHERR-NODES-BG;
                }
                container back-pressure-soft-errors {
                  description
                    "BP soft error information";
                  uses CIHERR-NODES-BG;
                }
                container generic-soft-errors {
                  description
                    "Generic soft error information";
                  uses CIHERR-NODES-BG;
                }
                container link-soft-errors {
                  description
                    "Link soft error information";
                  uses CIHERR-NODES-BG;
                }
                container configuration-soft-errors {
                  description
                    "Configuration soft error information";
                  uses CIHERR-NODES-BG;
                }
                container multiple-bit-hard-errors {
                  description
                    "Multiple bit hard error information";
                  uses CIHERR-NODES-BG;
                }
                container unexpected-soft-errors {
                  description
                    "Unexpected soft error information";
                  uses CIHERR-NODES-BG;
                }
                container outof-resource-hard {
                  description
                    "OOR thresh information";
                  uses CIHERR-NODES-BG;
                }
                container hardware-hard-errors {
                  description
                    "Hardware hard error information";
                  uses CIHERR-NODES-BG;
                }
                container parity-soft-errors {
                  description
                    "Parity soft error information";
                  uses CIHERR-NODES-BG;
                }
                container descriptor-soft-errors {
                  description
                    "Descriptor soft error information";
                  uses CIHERR-NODES-BG;
                }
                container interface-soft-errors {
                  description
                    "Interface soft error information";
                  uses CIHERR-NODES-BG;
                }
                container io-hard-errors {
                  description
                    "IO hard error information";
                  uses CIHERR-NODES-BG;
                }
                container reset-hard-errors {
                  description
                    "Reset hard error information";
                  uses CIHERR-NODES-BG;
                }
                container ucode-hard-errors {
                  description
                    "UCode hard error information";
                  uses CIHERR-NODES-BG;
                }
                container asic-error-mbe-hard {
                  description
                    "Indirect hard error information";
                  uses CIHERR-NODES-BG;
                }
              }
              leaf asic-instance {
                type uint32;
                description
                  "asic instance";
              }
            }
          }
          leaf asic {
            type xr:Cisco-ios-xr-string;
            description
              "Asic string";
          }
        }
      }
    }
  }
}
