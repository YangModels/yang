submodule Cisco-IOS-XR-ip-ntp-oper-sub1 {
  belongs-to Cisco-IOS-XR-ip-ntp-oper {
    prefix Cisco-IOS-XR-ip-ntp-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-ntp package operational data.
     
     Copyright (c) 2013-2017 by Cisco Systems, Inc.
     All rights reserved.";

  revision 2015-11-09 {
    description
      "IOS XR 6.0 revision.";
  }

  typedef Clock-update-node {
    type enumeration {
      enum "clk-never-updated" {
        value 0;
        description
          " clock is never updated";
      }
      enum "clk-updated" {
        value 1;
        description
          " clock is updated";
      }
      enum "clk-no-update-info" {
        value 2;
        description
          " clock has no update info";
      }
    }
    description
      "Mode of Clock Update";
  }

  typedef Ntp-loop-filter-state {
    type enumeration {
      enum "ntp-loop-flt-n-set" {
        value 0;
        description
          " never set";
      }
      enum "ntp-loop-flt-f-set" {
        value 1;
        description
          " drift set from file";
      }
      enum "ntp-loop-flt-spik" {
        value 2;
        description
          " spike";
      }
      enum "ntp-loop-flt-freq" {
        value 3;
        description
          " drift being measured";
      }
      enum "ntp-loop-flt-sync" {
        value 4;
        description
          " normal controlled loop";
      }
      enum "ntp-loop-flt-unkn" {
        value 5;
        description
          " unknown";
      }
    }
    description
      "Loop filter state";
  }

  typedef Ntp-peer-status {
    type enumeration {
      enum "ntp-ctl-pst-sel-reject" {
        description
          "   reject";
      }
      enum "ntp-ctl-pst-sel-sane" {
        description
          " x falsetick";
      }
      enum "ntp-ctl-pst-sel-correct" {
        description
          " . excess ";
      }
      enum "ntp-ctl-pst-sel-selcand" {
        description
          " - outlyer";
      }
      enum "ntp-ctl-pst-sel-sync-cand" {
        description
          " + candidate";
      }
      enum "ntp-ctl-pst-sel-distsys-peer" {
        description
          " # selected";
      }
      enum "ntp-ctl-pst-sel-sys-peer" {
        description
          " * sys peer";
      }
      enum "ntp-ctl-pst-sel-pps" {
        description
          " o pps peer";
      }
    }
    description
      "Type of peer status";
  }

  typedef Ntp-mode {
    type enumeration {
      enum "ntp-mode-unspec" {
        description
          "Unspecified probably old NTP version";
      }
      enum "ntp-mode-symetric-active" {
        description
          "Symmetric active";
      }
      enum "ntp-mode-symetric-passive" {
        description
          "Symmetric passive";
      }
      enum "ntp-mode-client" {
        description
          "Client mode";
      }
      enum "ntp-mode-server" {
        description
          "Server mode";
      }
      enum "ntp-mode-xcast-server" {
        description
          "Broadcast mode";
      }
      enum "ntp-mode-control" {
        description
          "Control mode packet";
      }
      enum "ntp-mode-private" {
        description
          "Implementation defined function";
      }
      enum "ntp-mode-xcast-client" {
        description
          "A broadcast client mode";
      }
    }
    description
      "Type of mode";
  }

  typedef Ntp-leap {
    type enumeration {
      enum "ntp-leap-no-warning" {
        description
          "Normal, no leap second warning";
      }
      enum "ntp-leap-addse-cond" {
        description
          "Last minute of day has 61 seconds";
      }
      enum "ntp-leap-delse-cond" {
        description
          "Last minute of day has 59 seconds";
      }
      enum "ntp-leap-not-in-sync" {
        description
          "Overload, clock is free running";
      }
    }
    description
      "Type of leap";
  }

  grouping NTP-EDM-PEER-SUMMARY-INFO {
    description
      "Peer summary info";
    container peer-info-common {
      description
        "Common peer info";
      uses NTP-EDM-PEER-INFO-COMMON;
    }
    leaf time-since {
      type int32;
      description
        "Time since last frame received (-1=none)";
    }
  }

  grouping NTP-EDM-ASSOC-SUMMARY-RESULT {
    description
      "The NTP association result";
    leaf is-ntp-enabled {
      type boolean;
      description
        "Is NTP enabled";
    }
    leaf sys-leap {
      type Ntp-leap;
      description
        "Leap";
    }
    list peer-summary-info {
      description
        "Peer info";
      uses NTP-EDM-PEER-SUMMARY-INFO;
    }
  }

  grouping NTP-EDM-STATUS-RESULT {
    description
      "The NTP status result";
    container sys-ref-time {
      description
        "Reference time";
      uses EDM-L-FP;
    }
    container sys-drift {
      description
        "System Drift";
      uses EDM-L-FP;
    }
    leaf is-ntp-enabled {
      type boolean;
      description
        "Is NTP enabled";
    }
    leaf sys-dispersion {
      type string;
      description
        "Peer dispersion";
    }
    leaf sys-offset {
      type string;
      description
        "Clock offset";
    }
    leaf clock-period {
      type uint32;
      units "nanosecond";
      description
        "Clock period in nanosecs";
    }
    leaf sys-leap {
      type Ntp-leap;
      description
        "leap";
    }
    leaf sys-precision {
      type int8;
      description
        "Precision";
    }
    leaf sys-stratum {
      type uint8;
      description
        "Stratum";
    }
    leaf sys-ref-id {
      type inet:ipv4-address;
      description
        "Reference clock ID";
    }
    leaf sys-root-delay {
      type string;
      description
        "Root delay";
    }
    leaf sys-root-dispersion {
      type string;
      description
        "Root dispersion";
    }
    leaf loop-filter-state {
      type Ntp-loop-filter-state;
      description
        "Loop Filter State";
    }
    leaf poll-interval {
      type uint8;
      description
        "Peer poll interval";
    }
    leaf is-updated {
      type Clock-update-node;
      description
        "Is clock updated";
    }
    leaf last-update {
      type int32;
      description
        "Last Update";
    }
    leaf is-auth-enabled {
      type boolean;
      description
        "Is NTP Authenticate enabled";
    }
  }

  grouping FILTER-DETAILS {
    description
      "Sub part of peer info";
    leaf filter-delay {
      type string;
      description
        "filter delay";
    }
    leaf filter-offset {
      type string;
      description
        "filter offset";
    }
    leaf filter-disp {
      type string;
      description
        "filter disp";
    }
  }

  grouping EDM-UL-F {
    description
      "EDM UL F";
    leaf frac {
      type uint32;
      description
        "Fractional format in NTP reference code";
    }
  }

  grouping EDM-UL-I {
    description
      "EDM UL I";
    leaf int {
      type uint32;
      description
        "Integer format in NTP reference code";
    }
  }

  grouping EDM-L-FP {
    description
      "EDM L FP";
    container sec {
      description
        "Second part in 64-bit NTP timestamp";
      uses EDM-UL-I;
    }
    container frac-secs {
      description
        "Fractional part in 64-bit NTP timestamp";
      uses EDM-UL-F;
    }
  }

  grouping NTP-EDM-PEER-INFO-COMMON {
    description
      "Peer common info";
    leaf host-mode {
      type Ntp-mode;
      description
        "Association mode with this peer";
    }
    leaf is-configured {
      type boolean;
      description
        "Is configured";
    }
    leaf address {
      type string;
      description
        "Peer Address";
    }
    leaf reference-id {
      type inet:ipv4-address;
      description
        "Peer reference ID";
    }
    leaf host-poll {
      type uint8;
      description
        "Host poll";
    }
    leaf reachability {
      type uint8;
      description
        "Reachability";
    }
    leaf stratum {
      type uint8;
      description
        "Peer stratum";
    }
    leaf status {
      type Ntp-peer-status;
      description
        "Peer status";
    }
    leaf delay {
      type string;
      description
        "Peer delay";
    }
    leaf offset {
      type string;
      description
        "Peer offset";
    }
    leaf dispersion {
      type string;
      description
        "Peer dispersion";
    }
    leaf is-sys-peer {
      type boolean;
      description
        "Indicates whether this is syspeer";
    }
  }

  grouping NTP-EDM-PEER-DETAIL-INFO {
    description
      "Peer Detail Information";
    container peer-info-common {
      description
        "Common peer info";
      uses NTP-EDM-PEER-INFO-COMMON;
    }
    container ref-time {
      description
        "Reference time";
      uses EDM-L-FP;
    }
    container originate-time {
      description
        "Originate timestamp";
      uses EDM-L-FP;
    }
    container receive-time {
      description
        "Receive timestamp";
      uses EDM-L-FP;
    }
    container transmit-time {
      description
        "Transmit timestamp";
      uses EDM-L-FP;
    }
    leaf leap {
      type Ntp-leap;
      description
        "Leap";
    }
    leaf peer-mode {
      type Ntp-mode;
      description
        "Peer's association mode";
    }
    leaf poll-interval {
      type uint8;
      description
        "Peer poll interval";
    }
    leaf is-ref-clock {
      type boolean;
      description
        "Is refclock";
    }
    leaf is-authenticated {
      type boolean;
      description
        "Is authenticated";
    }
    leaf root-delay {
      type string;
      description
        "Root delay";
    }
    leaf root-dispersion {
      type string;
      description
        "Root dispersion";
    }
    leaf synch-distance {
      type string;
      description
        "Synch distance";
    }
    leaf precision {
      type int8;
      description
        "Precision";
    }
    leaf version {
      type uint8;
      description
        "NTP version";
    }
    leaf filter-index {
      type uint32;
      description
        "Index into filter shift register";
    }
    list filter-detail {
      max-elements "8";
      description
        "Filter Details";
      uses FILTER-DETAILS;
    }
  }

  grouping NTP-EDM-ASSOC-DETAIL-RESULT {
    description
      "The NTP association detail result";
    leaf is-ntp-enabled {
      type boolean;
      description
        "Is NTP enabled";
    }
    leaf sys-leap {
      type Ntp-leap;
      description
        "Leap";
    }
    list peer-detail-info {
      description
        "Peer info";
      uses NTP-EDM-PEER-DETAIL-INFO;
    }
  }
}
