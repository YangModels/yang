module Cisco-IOS-XR-sysadmin-fpd-infra-cli-fpd-service {
  namespace "http://www.cisco.com/ns/yang/Cisco-IOS-XR-sysadmin-fpd-infra-cli-fpd-service";
  prefix upgrade;

  import tailf-common {
    prefix tailf;
  }

  revision 2017-05-01 {
    description
      "Namespace change to comply with Cisco guidelines on namespace";
  }
  tailf:id "http://cisco.com/calvados/hwfpd";

  list location {
    key "loc";
    config false;
    tailf:cli-suppress-show-path;
    tailf:callpoint "fpd_cp1";
    leaf loc {
      type string;
    }
    list fpd2 {
      key "name";
      config false;
      tailf:callpoint "fpd_cp2";
      leaf name {
        type string;
      }
    }
  }
}
