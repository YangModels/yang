module Cisco-IOS-XR-sysadmin-fabric-types {
  namespace "http://www.cisco.com/ns/yang/Cisco-IOS-XR-sysadmin-fabric-types";
  prefix fabric-types;

  import tailf-common {
    prefix tailf;
  }

  revision 2017-05-01 {
    description
      "Namespace change to comply with Cisco guidelines on namespace";
  }
  revision 2017-04-07 {
    description
      "Fabric types for NCS4k platforms";
  }

  typedef instance_type {
    type string {
      pattern "[0-2]|all";
    }
    tailf:info "0-2|all;;Asic instance number.";
  }

  typedef sfe_instance_type {
    type string {
      pattern "[0-2]|all";
    }
    tailf:info "0-2;;Asic instance number";
  }

  typedef sfe_link_type {
    type int32 {
      range "0 .. 143";
    }
  }

  typedef sfe_start_link_type {
    type int32 {
      range "0 .. 143";
    }
    tailf:info "0-143;;Start link number";
  }

  typedef sfe_end_link_type {
    type int32 {
      range "0 .. 143";
    }
    tailf:info "0-143;;End link number";
  }

  typedef plane_type {
    type string {
      pattern "all|[0-3]";
    }
    tailf:info "0-3;;Fabric plane number.";
  }

  typedef plane_zermatt_type {
    type string {
      pattern "all|0";
    }
    tailf:info "0;;Fabric plane number.";
  }

  typedef conf_plane_type {
    type string {
      pattern "[0-3]";
    }
    tailf:info "0-3;;Fabric plane number.";
  }

  typedef conf_plane_zermatt_type {
    type string {
      pattern "0";
    }
    tailf:info "0;;Fabric plane number.";
  }

  typedef conf_instance_type {
    type int32 {
      range "0..7";
    }
    tailf:info "Instance number under plane config <0-7>";
  }

  typedef conf_folded_instance_type {
    type int32;
    default "0";
    tailf:info "Folded: Instance number under plane config";
  }

  typedef conf_location_type {
    type string {
      pattern "(0?F[0-3])/[F|f][C|c](0?[0-9]|1[0-1])";
    }
    tailf:info "S2 card location for instance config <[F0-3]/FC[0-11]>";
  }

  typedef link_port_type {
    type string {
      pattern "fia|s1|s2|s3";
    }
    tailf:info "fia | s1 | s2 | s3;;Link ports";
  }

  typedef asic_stage_type {
    type string {
      pattern "fia|s123|s13|s2|b2b";
    }
    tailf:info "fia | s123 | s13 | s2 | b2b;;Switching Fabric Element";
  }

  typedef sfe_stage_type {
    type string {
      pattern "s1|s2|s3|s123";
    }
    tailf:info "s1 | s2 | s3 | s123 ;;Switching Fabric Element Stage";
  }

  typedef asic_location_type {
    type string {
      pattern "((0?[0-9]|1[0-5])/([F|f][C|c](0?[0-3]))/(0?[0-2]))|((0?[0-9]|1[0-5])/(0?[0-9]|1[0-5])/(0?[0-0]))|(([F|f][0-3])/([F|f][C|c](0?[0-9]|1[0-1]))/(0?[0-2]))";
    }
    tailf:info
      "R/S/A;;Asic location -
       rack(0-15 or F0-F3)
       slot(0-15 or FC0-FC11)
       asic(0-2)";
  }

  typedef asic_location_zermatt_type {
    type string {
      pattern "((0)/([R|r][P|p](0))/(0?[0-1]))|((0)/(0)/(0?[0-7]))";
    }
    tailf:info
      "R/S/A;;Asic location -
       rack(0)
       slot(0 or RP0)
       asic(0-7)";
  }

  typedef link_port_location_type {
    type string {
      pattern "((0?[0-9]|1[0-5])/([F|f][C|c](0?[0-3]))/(0?[0-2])/(0?[0-9]|[1-9][0-9]|1[0-3][0-9]|14[0-3]))|((0?[0-9]|1[0-5])/(0?[0-9]|1[0-5])/(0?[0-0])/(0?[0-9]|[1-2][0-9]|3[0-5]))|(([F|f][0-3])/([F|f][C|c](0?[0-9]|1[0-1]))/(0?[0-2])/(0?[0-9]|[1-9][0-9]|1[0-3][0-9]|14[0-3]))";
    }
    tailf:info
      "R/S/A/L;;Link port -
       rack(0-15 or F0-F3)
       slot(0-15 or FC0-FC11)
       asic(0-2)
       link(0-143)";
  }

  typedef link_port_location_zermatt_type_for_yang {
    type string {
      pattern "((0)/([R|r][P|p](0))/(0?[0-1])/(0?[0-9]|[1-9][0-9]|1[0-3][0-9]|14[0-3]))|((0)/(0)/(0?[0-7])/(0?[0-9]|[1-3][0-9]|4[0-7]))";
    }
    tailf:info
      "R/S/A/L;;Link port -
       rack(0)
       slot(0 or RP0)
       asic(0-7)
       link(0-143)";
  }

  typedef link_port_location_zermatt_type {
    type string {
      pattern "((0)/([R|r][P|p](0))/(0?[0-1])/(0?[0-9]|[1-9][0-9]|1[0-3][0-9]|14[0-3]))|((0)/(0)/(0?[0-7])/(0?[0-9]|[1-2][0-9]|3[0-5]))";
    }
    tailf:info
      "R/S/A/L;;Link port -
       rack(0)
       slot(0 or RP0)
       asic(0-7)
       link(0-143)";
  }

  typedef link_port_location_oldcastle_type {
    type string {
      pattern "((0)/([R|r][P|p](0))/(0)/(0?[0-9]|[1-9][0-9]|1[0-3][0-9]|14[0-3]))|((0)/(0)/(0?[0-3])/(0?[0-9]|[1-3][0-9]|4[0-7]))";
    }
    tailf:info
      "R/S/A/L;;Link port -
       rack(0)
       slot(0 or RP0)
       asic(0-3)
       link(0-143)";
  }

  typedef bundle_location_type {
    type string {
      pattern "((0?[0-9]|1[0-5])/([F|f][C|c](0?[0-3]))/((0?[0-9])|(1[0-5])))|(([F|f][0-3])/([F|f][C|c](0?[0-9]|1[0-1]))/((0?[0-9])|([1-2][0-9])|(3[0-1])))";
    }
    tailf:info
      "R/S/P;;Bundle port location -
       rack(0-15    or F0-F3)
       slot(FC0-FC3 or FC0-FC11)
       port(0-15    or 0-31)";
  }

  typedef fabric_fgid_id_type {
    type int32 {
      range "0..524287";
    }
    tailf:info "0-524287;;fgid id";
  }

  typedef fabric_fgid_elements_type {
    type int32 {
      range "0..524288";
    }
    tailf:info "0-524288;;Number of fgid ids";
  }

  typedef fabric_fgid_start_id_type {
    type int32 {
      range "0..524287";
    }
    tailf:info "0-524287;;Start fgid id";
  }

  typedef fabric_fgid_end_id_type {
    type int32 {
      range "0..524287";
    }
    tailf:info "0-524287;;End fgid id";
  }

  typedef fabric_nc55_fixed_fgid_id_type {
    type int32 {
      range "0..524287";
    }
    tailf:info "0-524287;;fgid id";
  }

  typedef fabric_nc55_fixed_fgid_elements_type {
    type int32 {
      range "0..524288";
    }
    tailf:info "0-524288;;Number of fgid ids";
  }

  typedef fabric_nc55_fixed_fgid_start_id_type {
    type int32 {
      range "0..524287";
    }
    tailf:info "0-524287;;Start fgid id";
  }

  typedef fabric_nc55_fixed_fgid_end_id_type {
    type int32 {
      range "0..524287";
    }
    tailf:info "0-524287;;End fgid id";
  }

  typedef fabric_dump_file_name_type {
    type string;
    tailf:info "file name string";
  }

  typedef fabric_diag_shell_cmd_type {
    type string;
    tailf:info "STRING;;diag shell command string - double quote enclosed";
  }

  typedef fabric_diag_shell_instance_num_type {
    type int32 {
      range "0..2";
    }
    tailf:info "0-2;;Asic instance number.";
  }

  typedef fabric_rack_num_type {
    type string {
      pattern "(0?[0-9])|(1[0-5])|([F|f][0-3])";
    }
    tailf:info "0-15 or F0-F3;;Rack number";
  }

  typedef fabric_fabid_type {
    type string {
      pattern "(0?[0-9]|1[0-5])/(0?[0-9]|1[0-5])/(0?[0-0])|([0-9]|[1-9][0-9]|[1-9][0-9][0-9]|10[0-1][0-9]|102[0-3])";
    }
    tailf:info "[0-1023] or R/S/A;;Amba id";
  }

  typedef sfe_location_type {
    type string {
      pattern "((0?[0-9]|1[0-5])/([F|f][C|c](0?[0-3])))|(([F|f][0-3])/([F|f][C|c](0?[0-9]|1[0-1])))";
    }
    tailf:info "WORD;;sfe location - R/S";
  }

  typedef sfe_location_zermatt_type {
    type string {
      pattern "((0?[0-9]|1[0-5])/([F|f][C|c](0?[0-5])))|(0/([R|r][P|p]0))";
    }
    tailf:info
      "R/S;;sfe location -
       rack(0)
       slot(RP0)";
  }

  typedef cxp_port_type {
    type uint32 {
      range "0..31";
    }
    tailf:info "0-31;;CXP port number.";
  }
  tailf:id "http://www.cisco.com/panini/calvados/fabric/types";
}
