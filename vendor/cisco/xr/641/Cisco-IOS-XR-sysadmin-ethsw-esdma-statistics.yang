module Cisco-IOS-XR-sysadmin-ethsw-esdma-statistics {
  namespace "http://www.cisco.com/ns/yang/Cisco-IOS-XR-sysadmin-ethsw-esdma-statistics";
  prefix esdma_statistics;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch statistics' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-statistics-group {
    container statistics {
      tailf:info "Show switch statistics";
      tailf:cli-incomplete-show-path;
      container summary-statistics {
        tailf:cli-drop-node-name;
        tailf:callpoint "esdma_switch_statistics_summary_data";
        list location {
          key "rack card switch-id";
          tailf:info "Location information for switch statistics";
          tailf:cli-full-command;
          tailf:cli-suppress-table;
          tailf:cli-key-format "$(1)/$(2)/$(3)";
          tailf:cli-show-template "$(port-iter|show)";
          leaf rack {
            type esdma_types:esdma-rack-num-enum;
          }
          leaf card {
            type esdma_types:esdma-cpu;
            description
              "Card that owns a switch of interest";
          }
          leaf switch-id {
            type esdma_types:esdma-switch-type-enum;
            description
              "Switch type";
          }
          leaf serial-num {
            type string;
            description
              "Rack serial number";
            tailf:cli-suppress-show-path;
            tailf:cli-suppress-show-match;
          }
          list port-iter {
            key "port";
            tailf:cli-drop-node-name;
            tailf:cli-table-legend
              "Rack  Card  Switch  Rack Serial Number
               --------------------------------------
               $(../rack|ljust:4)  $(../card|ljust:4)  $(../switch-id|ljust:6)  $(../serial-num|ljust:18)
              ";
            tailf:cli-enforce-table;
            leaf port {
              type esdma_types:esdma-switch-port-type;
              description
                "Switch port";
              tailf:display-column-name "Port";
            }
            leaf phys-state {
              type esdma_types:esdma-switch-port-state;
              description
                "Physical port state";
              tailf:cli-suppress-show-path;
              tailf:cli-suppress-show-match;
              tailf:display-column-name "Phys State";
              tailf:alt-name "Physical port state:";
            }
            leaf state-changes {
              type uint32;
              description
                "Physical port state changes";
              tailf:cli-suppress-show-path;
              tailf:cli-suppress-show-match;
              tailf:display-column-name "State Changes";
            }
            leaf sw-sum-tx-packets {
              type uint64;
              description
                "Packets transmitted on this switch port";
              tailf:cli-suppress-show-path;
              tailf:cli-suppress-show-match;
              tailf:display-column-name "Tx Packets";
            }
            leaf sw-sum-rx-packets {
              type uint64;
              description
                "Indicates the port speed in bits per second";
              tailf:cli-suppress-show-path;
              tailf:cli-suppress-show-match;
              tailf:display-column-name "Rx Packets";
            }
            leaf sw-sum-tx-drops-errors {
              type uint64;
              description
                "Indicates the number of transmitted packets that had an error or were dropped by the policer";
              tailf:cli-suppress-show-path;
              tailf:cli-suppress-show-match;
              tailf:display-column-name "Tx Drops/ Errors";
            }
            leaf sw-sum-rx-drops-errors {
              type uint64;
              description
                "Indicates the number of received packets that had an error or were dropped by the policer";
              tailf:cli-suppress-show-path;
              tailf:cli-suppress-show-match;
              tailf:display-column-name "Rx Drops/ Errors";
            }
            leaf connects-to {
              type string;
              description
                "Indicates what this port connects to";
              tailf:cli-suppress-show-path;
              tailf:cli-suppress-show-match;
              tailf:cli-preformatted;
              tailf:display-column-name "Connects To";
            }
          }
        }
      }
      container detail {
        tailf:info "Detailed switch port statistics";
        tailf:callpoint "esdma_switch_statistics_detail_data";
        list location {
          key "rack card switch-id";
          tailf:info "Location for detailed switch port statistics";
          tailf:cli-incomplete-command;
          tailf:cli-incomplete-show-path;
          tailf:cli-suppress-table;
          tailf:cli-key-format "$(1)/$(2)/$(3)";
          leaf rack {
            type esdma_types:esdma-rack-num-enum;
          }
          leaf card {
            type esdma_types:esdma-cpu;
            description
              "Card that owns a switch of interest";
          }
          leaf switch-id {
            type esdma_types:esdma-switch-type-enum;
            description
              "Switch type";
          }
          list port-iter {
            key "port";
            tailf:cli-drop-node-name;
            tailf:cli-full-command;
            tailf:cli-suppress-table;
            tailf:info "Switch port";
            tailf:cli-show-template
              "                          Phys   Port
               Rack  Card  Switch  Port  State  Speed    Connects To
               -----------------------------------------------------
               $(../../rack|ljust:4)  $(../../card|ljust:4)  $(../../switch-id|ljust:6)  $(port|ljust:4)  $(phys-state|ljust:5)  $(port-speed|ljust:7)  $(connects-to|ljust:20)
               
               $(counters|show)";
            leaf port {
              type esdma_types:esdma-switch-port-type;
              description
                "Switch port";
            }
            leaf phys-state {
              type esdma_types:esdma-switch-port-state;
              description
                "Physical port state";
              tailf:cli-suppress-show-path;
              tailf:cli-suppress-show-match;
            }
            leaf port-speed {
              type string;
              description
                "Indicates the port speed in bits per second";
              tailf:cli-suppress-show-path;
              tailf:cli-suppress-show-match;
            }
            leaf connects-to {
              type string;
              description
                "Indicates what this port connects to";
              tailf:cli-suppress-show-path;
              tailf:cli-suppress-show-match;
              tailf:cli-preformatted;
            }
            container counters {
              tailf:cli-drop-node-name;
              leaf sw-det-rx-ucast-packets {
                type uint64;
                tailf:cli-suppress-show-path;
                tailf:cli-suppress-show-match;
                tailf:alt-name "Rx Unicast Packets:";
              }
              leaf sw-det-rx-mcast-packets {
                type uint64;
                tailf:cli-suppress-show-path;
                tailf:cli-suppress-show-match;
                tailf:alt-name "Rx Multicast Packets:";
              }
              leaf sw-det-rx-bcast-packets {
                type uint64;
                tailf:cli-suppress-show-path;
                tailf:cli-suppress-show-match;
                tailf:alt-name "Rx Broadcast Packets:";
              }
              leaf sw-det-rx-flow-control {
                type uint64;
                tailf:cli-suppress-show-path;
                tailf:cli-suppress-show-match;
                tailf:alt-name "Rx Flow Control:";
              }
              leaf sw-det-rx-good-octets {
                type uint64;
                tailf:cli-suppress-show-path;
                tailf:cli-suppress-show-match;
                tailf:alt-name "Rx Good Octets:";
              }
              leaf sw-det-rx-bad-octets {
                type uint64;
                tailf:cli-suppress-show-path;
                tailf:cli-suppress-show-match;
                tailf:alt-name "Rx Bad Octets:";
              }
              leaf sw-det-rx-fifo-overrun {
                type uint64;
                tailf:cli-suppress-show-path;
                tailf:cli-suppress-show-match;
                tailf:alt-name "Rx FIFO Overrun:";
              }
              leaf sw-det-rx-undersize {
                type uint64;
                tailf:cli-suppress-show-path;
                tailf:cli-suppress-show-match;
                tailf:alt-name "Rx Undersize:";
              }
              leaf sw-det-rx-fragments {
                type uint64;
                tailf:cli-suppress-show-path;
                tailf:cli-suppress-show-match;
                tailf:alt-name "Rx Fragments:";
              }
              leaf sw-det-rx-oversize {
                type uint64;
                tailf:cli-suppress-show-path;
                tailf:cli-suppress-show-match;
                tailf:alt-name "Rx Oversize:";
              }
              leaf sw-det-rx-jabber {
                type uint64;
                tailf:cli-suppress-show-path;
                tailf:cli-suppress-show-match;
                tailf:alt-name "Rx Jabber: ";
              }
              leaf sw-det-rx-errors {
                type uint64;
                tailf:cli-suppress-show-path;
                tailf:cli-suppress-show-match;
                tailf:alt-name "Rx Errors:";
              }
              leaf sw-det-rx-bad-crc {
                type uint64;
                tailf:cli-suppress-show-path;
                tailf:cli-suppress-show-match;
                tailf:alt-name "Rx Bad CRC:";
              }
              leaf sw-det-rx-collisions {
                type uint64;
                tailf:cli-suppress-show-path;
                tailf:cli-suppress-show-match;
                tailf:alt-name "Rx Collisions:";
              }
              leaf sw-det-rx-policing-drops {
                type uint64;
                tailf:cli-suppress-show-path;
                tailf:cli-suppress-show-match;
                tailf:alt-name "Rx Policing Drops:";
              }
              leaf sw-det-tx-ucast-packets {
                type uint64;
                tailf:cli-suppress-show-path;
                tailf:cli-suppress-show-match;
                tailf:alt-name "Tx Unicast Packets:";
              }
              leaf sw-det-tx-mcast-packets {
                type uint64;
                tailf:cli-suppress-show-path;
                tailf:cli-suppress-show-match;
                tailf:alt-name "Tx Multicast Packets:";
              }
              leaf sw-det-tx-bcast-packets {
                type uint64;
                tailf:cli-suppress-show-path;
                tailf:cli-suppress-show-match;
                tailf:alt-name "Tx Broadcast Packets:";
              }
              leaf sw-det-tx-flow-control {
                type uint64;
                tailf:cli-suppress-show-path;
                tailf:cli-suppress-show-match;
                tailf:alt-name "Tx Flow Control:";
              }
              leaf sw-det-tx-good-octets {
                type uint64;
                tailf:cli-suppress-show-path;
                tailf:cli-suppress-show-match;
                tailf:alt-name "Tx Good Octets:";
              }
              leaf sw-det-tx-deferred {
                type uint64;
                tailf:cli-suppress-show-path;
                tailf:cli-suppress-show-match;
                tailf:alt-name "Tx Deferred Packets:";
              }
              leaf sw-det-tx-fifo-unrun {
                type uint64;
                tailf:cli-suppress-show-path;
                tailf:cli-suppress-show-match;
                tailf:alt-name "Tx FIFO Underrun/CRC:";
              }
              leaf sw-det-tx-mult-collision {
                type uint64;
                tailf:cli-suppress-show-path;
                tailf:cli-suppress-show-match;
                tailf:alt-name "Tx Multiple Collisions:";
              }
              leaf sw-det-tx-excess-collision {
                type uint64;
                tailf:cli-suppress-show-path;
                tailf:cli-suppress-show-match;
                tailf:alt-name "Tx Excess Collisions:";
              }
              leaf sw-det-tx-late-collisions {
                type uint64;
                tailf:cli-suppress-show-path;
                tailf:cli-suppress-show-match;
                tailf:alt-name "Tx Late Collisions:";
              }
              leaf sw-det-tx-policing-drops {
                type uint64;
                tailf:cli-suppress-show-path;
                tailf:cli-suppress-show-match;
                tailf:alt-name "Tx Policing Drops:";
              }
              leaf sw-det-txq-drops {
                type uint64;
                tailf:cli-suppress-show-path;
                tailf:cli-suppress-show-match;
                tailf:alt-name "Tx Queueing Drops:";
              }
              leaf sw-det-rxtx-packets-64 {
                type uint64;
                tailf:cli-suppress-show-path;
                tailf:cli-suppress-show-match;
                tailf:alt-name "RxTx Packets 64:";
              }
              leaf sw-det-rxtx-packets-65-127 {
                type uint64;
                tailf:cli-suppress-show-path;
                tailf:cli-suppress-show-match;
                tailf:alt-name "RxTx Packets 65-127:";
              }
              leaf sw-det-rxtx-packets-128-255 {
                type uint64;
                tailf:cli-suppress-show-path;
                tailf:cli-suppress-show-match;
                tailf:alt-name "RxTx Packets 128-255:";
              }
              leaf sw-det-rxtx-packets-256-511 {
                type uint64;
                tailf:cli-suppress-show-path;
                tailf:cli-suppress-show-match;
                tailf:alt-name "RxTx Packets 256-511: ";
              }
              leaf sw-det-rxtx-packets-512-1023 {
                type uint64;
                tailf:cli-suppress-show-path;
                tailf:cli-suppress-show-match;
                tailf:alt-name "RxTx Packets 512-1023";
              }
              leaf sw-det-rxtx-packets-1024-max {
                type uint64;
                tailf:cli-suppress-show-path;
                tailf:cli-suppress-show-match;
                tailf:alt-name "RxTx Packets 1024-Max:";
              }
            }
          }
        }
      }
    }
  }
  tailf:id "http://cisco.com/panini/calvados/esdma/esdma_statistics";
}
