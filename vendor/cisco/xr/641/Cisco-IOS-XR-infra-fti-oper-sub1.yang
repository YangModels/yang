submodule Cisco-IOS-XR-infra-fti-oper-sub1 {
  belongs-to Cisco-IOS-XR-infra-fti-oper {
    prefix Cisco-IOS-XR-infra-fti-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-fti package operational data.
     
     Copyright (c) 2013-2017 by Cisco Systems, Inc.
     All rights reserved.";

  revision 2015-11-09 {
    description
      "IOS XR 6.0 revision.";
  }

  typedef Fti-bag-fabric-peer-state {
    type enumeration {
      enum "fti-bag-fabric-peer-status-disconnected" {
        value 0;
        description
          "Disconnected";
      }
      enum "fti-bag-fabric-peer-status-connecting" {
        value 1;
        description
          "Connecting";
      }
      enum "fti-bag-fabric-peer-status-connected" {
        value 2;
        description
          "Connected";
      }
      enum "fti-bag-fabric-peer-status-ready" {
        value 3;
        description
          "Ready";
      }
      enum "fti-bag-fabric-peer-status-closing" {
        value 4;
        description
          "Closing";
      }
    }
    description
      "FTI Fabric Peer States";
  }

  typedef Fti-bag-fabric-state {
    type enumeration {
      enum "fti-bag-fabric-state-active-down" {
        value 0;
        description
          "Active (Down)";
      }
      enum "fti-bag-fabric-state-active-degraded" {
        value 1;
        description
          "Active (Degraded)";
      }
      enum "fti-bag-fabric-state-active-healthy" {
        value 2;
        description
          "Active (Healthy)";
      }
      enum "fti-bag-fabric-state-inactive" {
        value 3;
        description
          "Inactive";
      }
    }
    description
      "FTI Fabric States";
  }

  typedef Fti-bag-fabric-config-state {
    type enumeration {
      enum "fti-bag-config-complete" {
        value 0;
        description
          "Config Complete";
      }
      enum "fti-bag-config-incomplete" {
        value 1;
        description
          "Config Incomplete";
      }
    }
    description
      "FTI Fabric Config States";
  }

  grouping FTI-ACP {
    description
      "FTI ACP";
    leaf vni-min {
      type uint32;
      description
        "VNI MIN VALUE";
    }
    leaf vni-max {
      type uint32;
      description
        "VNI MAX VALUE";
    }
    leaf vni-bits {
      type uint32;
      description
        "Num of VNI used bits";
    }
    leaf bvi-min {
      type uint32;
      description
        "BVI MIN VALUE";
    }
    leaf bvi-max {
      type uint32;
      description
        "BVI MAX VALUE";
    }
    leaf bvi-bits {
      type uint32;
      description
        "Num of BVI used bits";
    }
    leaf bd-min {
      type uint32;
      description
        "BD MIN VALUE";
    }
    leaf bd-max {
      type uint32;
      description
        "BD MAX VALUE";
    }
    leaf bd-bits {
      type uint32;
      description
        "Num of BD used bits";
    }
    leaf vniused-range {
      type string;
      description
        "Used VNI Range";
    }
    leaf bviused-range {
      type string;
      description
        "Used BVI Range";
    }
    leaf bdused-range {
      type string;
      description
        "Used BD Range";
    }
  }

  grouping FTI-DCI-VRF-INFO {
    description
      "FTI DCI VRF INFO";
    leaf dci-vrf {
      type string;
      description
        "DCI VRF";
    }
    leaf num-fabric-vrf {
      type uint32;
      description
        "Number of Fabric VRFs";
    }
    leaf faric-vrfs-id-name {
      type string;
      description
        "Associated Fabric Vrfs Info";
    }
    leaf vni-id {
      type uint32;
      description
        "VNI Id";
    }
    leaf bd-name {
      type string;
      description
        "BD Name";
    }
    leaf bvi-id {
      type uint32;
      description
        "BVI Id";
    }
    leaf bvi-ip {
      type string;
      description
        "BVI Override IP";
    }
    leaf bvi-ip-v6 {
      type boolean;
      description
        "BVI IPV6. False is disabled, True is enabled";
    }
    leaf dci-vrf-flags {
      type string;
      description
        "DCI VRF Flags";
    }
    list v4-import-rt {
      description
        "V4 Import Route Targets";
      uses VRF-RT;
    }
    list v4-export-rt {
      description
        "V4 Export Route Targets";
      uses VRF-RT;
    }
    list v6-import-rt {
      description
        "V6 Import Route Targets";
      uses VRF-RT;
    }
    list v6-export-rt {
      description
        "V6 Export Route Targets";
      uses VRF-RT;
    }
  }

  grouping VRF-RT {
    description
      "VRF RT";
    leaf rt-value {
      type string;
      description
        "RT Value";
    }
    leaf rt-flags {
      type string;
      description
        "RT Flags";
    }
  }

  grouping FABRIC-VRF {
    description
      "FABRIC VRF";
    leaf fabric-vrf {
      type string;
      description
        "Fabric VRF";
    }
    leaf dci-vrf {
      type string;
      description
        "Dci VRF";
    }
    leaf fabric-vrf-flags {
      type string;
      description
        "Fabric VRF Flags";
    }
    list v4-import-rt {
      description
        "V4 Import Route Targets";
      uses VRF-RT;
    }
    list v4-export-rt {
      description
        "V4 Export Route Targets";
      uses VRF-RT;
    }
    list v6-import-rt {
      description
        "V6 Import Route Targets";
      uses VRF-RT;
    }
    list v6-export-rt {
      description
        "V6 Export Route Targets";
      uses VRF-RT;
    }
  }

  grouping FTI-FABRIC-VRF-INFO {
    description
      "FTI FABRIC VRF INFO";
    leaf fabric-id {
      type uint32;
      description
        "Fabric Id";
    }
    list fabric-vrf {
      description
        "Fabric VRFs";
      uses FABRIC-VRF;
    }
  }

  grouping FTI-FABRIC-PEER-INFO {
    description
      "FTI FABRIC PEER INFO";
    leaf peer-ip {
      type inet:ipv4-address;
      description
        "Peer IP";
    }
    leaf peer-port {
      type uint32;
      description
        "Peer Port";
    }
    leaf peer-state {
      type Fti-bag-fabric-peer-state;
      description
        "Peer State";
    }
    leaf last-upd-ts-peer-status {
      type uint64;
      description
        "Peer Status Last Update Timestamp";
    }
  }

  grouping FTI-FABRIC-SESSION-INFO {
    description
      "FTI FABRIC SESSION INFO";
    leaf fabric-id {
      type uint32;
      description
        "Fabric Id";
    }
    leaf config-state {
      type Fti-bag-fabric-config-state;
      description
        "Config State";
    }
    leaf last-upd-ts-config {
      type uint64;
      description
        "Config Last Update Timestamp";
    }
    leaf fabric-state {
      type Fti-bag-fabric-state;
      description
        "Fabric State";
    }
    leaf last-upd-ts-fabric {
      type uint64;
      description
        "Fabric Last Update Timestamp";
    }
    list peer-info {
      description
        "Fabric Per Peer Info";
      uses FTI-FABRIC-PEER-INFO;
    }
  }
}
