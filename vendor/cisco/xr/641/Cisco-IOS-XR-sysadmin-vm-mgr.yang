module Cisco-IOS-XR-sysadmin-vm-mgr {
  namespace "http://www.cisco.com/ns/yang/Cisco-IOS-XR-sysadmin-vm-mgr";
  prefix vmmh;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2012-2017 by Cisco Systems, Inc.
     All rights reserved.";

  revision 2017-04-12 {
    description
      "Changed the namespace and module name";
  }
  revision 2016-05-12 {
    description
      "Initial Version";
  }
  tailf:id "http://cisco.com/calvados/vmm";

  container VM {
    config false;
    description
      "VM Info";
    tailf:info "Show VM Manager information";
    tailf:callpoint "vmm_show_location";
    list all-locations {
      key "location";
      tailf:cli-drop-node-name;
      tailf:cli-suppress-table;
      tailf:cli-show-template-enter
        "
         Location: $(location)
         Id                Status        IP Address       HB Sent/Recv
         -------------------------------------------------------------
        ";
      leaf location {
        type string;
        tailf:cli-expose-key-name;
      }
      list all-uiids {
        key "uiid";
        tailf:cli-show-template-enter "";
        tailf:cli-suppress-table;
        tailf:cli-suppress-show-path;
        tailf:cli-suppress-show-match;
        tailf:cli-show-template "$(id|ljust:16)  $(status|ljust:12)  $(ipaddr|ljust:15)  $(last_hb_sent|ljust)/$(last_hb_rec|ljust)\n";
        leaf uiid {
          type string;
          description
            "Unique Immutable ID";
        }
        leaf id {
          type string;
          description
            "ID of the VM";
        }
        leaf status {
          type string;
          description
            "Status of the VM";
        }
        leaf ipaddr {
          type string;
          description
            "CE IP address";
        }
        leaf hb_interval_s {
          type string;
          description
            "Heartbeat interval sec";
        }
        leaf hb_interval_ns {
          type string;
          description
            "Heartbeat interval nsec";
        }
        leaf last_hb_sent {
          type string;
          description
            "Last heartbeat sent";
        }
        leaf last_hb_rec {
          type string;
          description
            "Last heartbeat received";
        }
        leaf role {
          type string;
          description
            "ISSU role";
          tailf:cli-suppress-show-path;
          tailf:cli-suppress-show-match;
        }
      }
    }
  }
}
