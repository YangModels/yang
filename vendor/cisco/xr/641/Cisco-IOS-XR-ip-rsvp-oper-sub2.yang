submodule Cisco-IOS-XR-ip-rsvp-oper-sub2 {
  belongs-to Cisco-IOS-XR-ip-rsvp-oper {
    prefix Cisco-IOS-XR-ip-rsvp-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-rsvp package operational data.
     
     Copyright (c) 2013-2017 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  grouping MPLS-RSVP-INTERFACE-COUNTERS {
    description
      "MPLS RSVP interface counters";
    leaf interface-name-xr {
      type string;
      description
        "Interface name";
    }
    leaf in-path-messages {
      type uint64;
      description
        "Per interface count of path messages received";
    }
    leaf in-path-error-messages {
      type uint64;
      description
        "Per interface count of path error messages
         received";
    }
    leaf in-path-tear-messages {
      type uint64;
      description
        "Per interface count of path tear messages
         received";
    }
    leaf in-reservation-messages {
      type uint64;
      description
        "Per interface count of reservation messages
         received";
    }
    leaf in-reservation-error-messages {
      type uint64;
      description
        "Per interface count of reservation error
         messages received";
    }
    leaf in-reservation-tear-messages {
      type uint64;
      description
        "Per interface count of reservation tear messages
         received";
    }
    leaf in-hello-messages {
      type uint64;
      description
        "Per interface count of hello messages received";
    }
    leaf in-srefresh-messages {
      type uint64;
      description
        "Per interface count of srefresh messages
         received";
    }
    leaf in-ack-messages {
      type uint64;
      description
        "Per interface count of ack messages received";
    }
    leaf out-path-messages {
      type uint64;
      description
        "Per interface count of path messages send";
    }
    leaf out-path-error-messages {
      type uint64;
      description
        "Per interface count of path error messages send";
    }
    leaf out-path-tear-messages {
      type uint64;
      description
        "Per interface count of path tear messages send";
    }
    leaf out-reservation-messages {
      type uint64;
      description
        "Per interface count of reservation messages send";
    }
    leaf out-reservation-error-messages {
      type uint64;
      description
        "Per interface count of reservation error
         messages send";
    }
    leaf out-reservation-tear-messages {
      type uint64;
      description
        "Per interface count of reservation tear messages
         send";
    }
    leaf out-hello-messages {
      type uint64;
      description
        "Per interface count of hello messages send";
    }
    leaf out-srefresh-messages {
      type uint64;
      description
        "Per interface count of srefresh messages send";
    }
    leaf out-ack-messages {
      type uint64;
      description
        "Per interface count of ack messages send";
    }
  }

  grouping MPLS-RSVP-GLOBAL-COUNTERS {
    description
      "MPLS RSVP global counters";
    leaf path-timeouts {
      type uint64;
      description
        "Global count of Path Timeouts";
    }
    leaf reservation-timeouts {
      type uint64;
      description
        "Global count of reservation timeouts";
    }
    leaf rate-limited-messages {
      type uint64;
      description
        "Global count of rate limited messages";
    }
    leaf in-path-messages {
      type uint64;
      description
        "Global count of path messages received";
    }
    leaf in-path-error-messages {
      type uint64;
      description
        "Global count of path error messages received";
    }
    leaf in-path-tear-messages {
      type uint64;
      description
        "Global count of path tear messages received";
    }
    leaf in-reservation-messages {
      type uint64;
      description
        "Global count of reservation messages received";
    }
    leaf in-reservation-error-messages {
      type uint64;
      description
        "Global count of reservation error messages
         received";
    }
    leaf in-reservation-tear-messages {
      type uint64;
      description
        "Global count of reservation tear messages
         received";
    }
    leaf in-hello-messages {
      type uint64;
      description
        "Global count of hello messages received";
    }
    leaf in-srefresh-messages {
      type uint64;
      description
        "Global count of srefresh messages received";
    }
    leaf in-ack-messages {
      type uint64;
      description
        "Global count of ack messages received";
    }
    leaf out-path-messages {
      type uint64;
      description
        "Global count of path messages send";
    }
    leaf out-path-error-messages {
      type uint64;
      description
        "Global count of path error messages send";
    }
    leaf out-path-tear-messages {
      type uint64;
      description
        "Global count of path tear messages send";
    }
    leaf out-reservation-messages {
      type uint64;
      description
        "Global count of reservation messages send";
    }
    leaf out-reservation-error-messages {
      type uint64;
      description
        "Global count of reservation error messages send";
    }
    leaf out-reservation-tear-messages {
      type uint64;
      description
        "Global count of reservation tear messages send";
    }
    leaf out-hello-messages {
      type uint64;
      description
        "Global count of hello messages send";
    }
    leaf out-srefresh-messages {
      type uint64;
      description
        "Global count of srefresh messages send";
    }
    leaf out-ack-messages {
      type uint64;
      description
        "Global count of ack messages send";
    }
  }
}
