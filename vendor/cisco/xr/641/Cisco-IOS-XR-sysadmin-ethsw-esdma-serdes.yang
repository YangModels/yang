module Cisco-IOS-XR-sysadmin-ethsw-esdma-serdes {
  namespace "http://www.cisco.com/ns/yang/Cisco-IOS-XR-sysadmin-ethsw-esdma-serdes";
  prefix esdma_serdes;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch serdes' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-serdes-group {
    container serdes {
      tailf:info "Display serdes information";
      container serdes-statistics {
        tailf:cli-drop-node-name;
        tailf:callpoint "esdma_switch_serdes_data";
        list location {
          key "rack card switch-id";
          tailf:info "Location information for switch Serdes information";
          tailf:cli-full-command;
          tailf:cli-suppress-table;
          tailf:cli-key-format "$(1)/$(2)/$(3)";
          tailf:cli-show-template "$(port-iter|show)";
          leaf rack {
            type esdma_types:esdma-rack-num-enum;
          }
          leaf card {
            type esdma_types:esdma-cpu;
            description
              "Card to list the switch Serdes information for";
          }
          leaf switch-id {
            type esdma_types:esdma-switch-type-enum;
            description
              "Switch type";
          }
          list port-iter {
            key "port";
            tailf:cli-drop-node-name;
            tailf:cli-table-legend
              "Rack  Card  Switch
               ------------------
               $(../rack|ljust:4)  $(../card|ljust:4)  $(../switch-id|ljust:6)
              ";
            tailf:cli-enforce-table;
            leaf port {
              type esdma_types:esdma-switch-port-type;
              description
                "Switch port";
              tailf:display-column-name "Switch Port";
            }
            list serdes-entry {
              key "id";
              tailf:cli-drop-node-name;
              leaf id {
                type uint32;
                tailf:cli-drop-node-name;
                tailf:cli-suppress-show-path;
                tailf:cli-suppress-show-match;
                tailf:display-column-name "Serdes ID";
              }
              leaf base-reg {
                type string;
                tailf:cli-suppress-show-path;
                tailf:cli-suppress-show-match;
                tailf:display-column-name "Base Reg";
              }
              leaf desc {
                type string;
                tailf:cli-suppress-show-path;
                tailf:cli-suppress-show-match;
                tailf:display-column-name "Description";
              }
              leaf lane-0 {
                type string;
                tailf:cli-suppress-show-path;
                tailf:cli-suppress-show-match;
                tailf:display-column-name "Lane 0";
              }
              leaf lane-1 {
                type string;
                tailf:cli-suppress-show-path;
                tailf:cli-suppress-show-match;
                tailf:display-column-name "Lane 1";
              }
              leaf lane-2 {
                type string;
                tailf:cli-suppress-show-path;
                tailf:cli-suppress-show-match;
                tailf:display-column-name "Lane 2";
              }
              leaf lane-3 {
                type string;
                tailf:cli-suppress-show-path;
                tailf:cli-suppress-show-match;
                tailf:display-column-name "Lane 3";
              }
            }
          }
        }
      }
    }
  }
  tailf:id "http://cisco.com/panini/calvados/esdma/esdma_serdes";
}
