module Cisco-IOS-XR-atm-common-datatypes {
  namespace "http://cisco.com/ns/yang/Cisco-IOS-XR-atm-common-datatypes";
  prefix atm-common-datatypes;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2017 by Cisco Systems, Inc.
     All rights reserved.";

  revision 2015-11-09 {
    description
      "IOS XR 6.0 revision.";
  }

  typedef Atm-vp-shaping {
    type enumeration {
      enum "cbr" {
        value 1;
        description
          "Constant Bit Rate";
      }
      enum "vbr-nrt" {
        value 2;
        description
          "Variable Bit Rate-non real time";
      }
      enum "vbr-rt" {
        value 3;
        description
          "Variable Bit Rate-real time";
      }
      enum "ubr" {
        value 6;
        description
          "Unspecified Bit Rate";
      }
    }
    description
      "Atm vp shaping";
  }

  typedef Atm-pvc-shaping {
    type enumeration {
      enum "cbr" {
        value 1;
        description
          "Constant Bit Rate";
      }
      enum "vbr-nrt" {
        value 2;
        description
          "Variable Bit Rate-non real time";
      }
      enum "vbr-rt" {
        value 3;
        description
          "Variable Bit Rate-real time";
      }
      enum "ubr" {
        value 6;
        description
          "Unspecified Bit Rate";
      }
    }
    description
      "Atm pvc shaping";
  }

  typedef Atm-pvc-data {
    type enumeration {
      enum "data" {
        value 0;
        description
          "Data";
      }
      enum "ilmi" {
        value 2;
        description
          "ILMI";
      }
      enum "layer2" {
        value 3;
        description
          "Layer2";
      }
    }
    description
      "Atm pvc data";
  }

  typedef Atm-pvc-encapsulation {
    type enumeration {
      enum "snap" {
        value 3;
        description
          "SNAP";
      }
      enum "vc-mux" {
        value 4;
        description
          "VC MUX";
      }
      enum "nlpid" {
        value 5;
        description
          "NLPID";
      }
      enum "aal0" {
        value 7;
        description
          "AAL0";
      }
      enum "aal5" {
        value 8;
        description
          "AAL5";
      }
    }
    description
      "Atm pvc encapsulation";
  }

  typedef Atm-vc-class-name {
    type xr:Cisco-ios-xr-string {
      length "1..30";
    }
    description
      "Atm vc class name";
  }
}
