module Cisco-IOS-XR-invmgr-cfg {
  namespace "http://cisco.com/ns/yang/Cisco-IOS-XR-invmgr-cfg";
  prefix invmgr-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR invmgr package configuration.
     
     This module contains definitions
     for the following management objects:
       inventory-configurations: Configuration for inventory entities
     
     Copyright (c) 2013-2017 by Cisco Systems, Inc.
     All rights reserved.";

  revision 2015-11-09 {
    description
      "IOS XR 6.0 revision.";
  }

  container inventory-configurations {
    description
      "Configuration for inventory entities";
    list entity {
      key "name";
      description
        "Entity name";
      leaf name {
        type string;
        description
          "Entity name";
      }
      leaf name-xr {
        type string;
        mandatory true;
        description
          "Entity name";
      }
    }
  }
}
