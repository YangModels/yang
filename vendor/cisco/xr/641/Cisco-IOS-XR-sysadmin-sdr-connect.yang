module Cisco-IOS-XR-sysadmin-sdr-connect {
  namespace "http://www.cisco.com/ns/yang/Cisco-IOS-XR-sysadmin-sdr-connect";
  prefix inter_sdr_connect;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module implements entities for inter sdr connect
     feature";

  revision 2017-10-09 {
    description
      "Initial version";
  }
  tailf:id "http://www.cisco.com/panini/calvados/sdr_mgr/inter_sdr_connect";

  container sdr-connect {
    tailf:cli-drop-node-name;
    tailf:validate "sdr_connect_validate" {
      tailf:dependency ".";
    }
    container connect {
      description
        "Connect two Secure Domain Routers";
      tailf:info "Secure Domain Router connect config command";
      list sdr {
        key "sdr-name remote-sdr-name csi-id";
        description
          "Secure Domain Router connect config";
        tailf:cli-suppress-mode;
        tailf:info "Secure Domain Router connect config commands";
        tailf:cli-suppress-key-sort;
        leaf sdr-name {
          type string {
            pattern "[a-zA-Z0-9_-]{1,30}";
          }
          mandatory true;
          description
            "Name of the Secure Domain Router , 30 max characters";
          tailf:info "sdr name (1 to 30 characters(0-9,a-z,A-Z,-,_))";
        }
        leaf remote-sdr-name {
          type string {
            pattern "[a-zA-Z0-9_-]{1,30}";
          }
          mandatory true;
          description
            "Name of the Remote Secure Domain Router , 30 max characters";
          tailf:info "remote sdr name (1 to 30 characters(0-9,a-z,A-Z,-,_))";
        }
        leaf csi-id {
          type uint32 {
            range "1 .. 15";
          }
          mandatory true;
          description
            "Index unique for each SDR connection pair";
          tailf:cli-expose-key-name;
          tailf:info "Index unique for each SDR connection pair";
        }
      }
    }
  }
}
