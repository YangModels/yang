module Cisco-IOS-XR-sysadmin-ethsw-esdma-types {
  namespace "http://www.cisco.com/ns/yang/Cisco-IOS-XR-sysadmin-ethsw-esdma-types";
  prefix esdma_types;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG enumerated type
     definitions used by the Cisco IOS-XR SysAdmin
     Control Ethernet commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  typedef esdma-rack-type-enum {
    type enumeration {
      enum "Unknown" {
        tailf:code-name "esdma-rack-type-unknown";
      }
      enum "FCC" {
        tailf:code-name "esdma-rack-type-fcc";
      }
      enum "LCC" {
        tailf:code-name "esdma-rack-type-lcc";
      }
      enum "BSC" {
        tailf:code-name "esdma-rack-type-bsc";
      }
      enum "COMPUTE" {
        tailf:code-name "esdma-rack-type-compute";
      }
    }
    description
      "The valid chassis types supported supported in Sysadmin.";
  }

  typedef esdma-rack-num-enum {
    type enumeration {
      enum "0" {
        tailf:code-name "esdma-rack-num-L0";
      }
      enum "1" {
        tailf:code-name "esdma-rack-num-L1";
      }
      enum "2" {
        tailf:code-name "esdma-rack-num-L2";
      }
      enum "3" {
        tailf:code-name "esdma-rack-num-L3";
      }
      enum "4" {
        tailf:code-name "esdma-rack-num-L4";
      }
      enum "5" {
        tailf:code-name "esdma-rack-num-L5";
      }
      enum "6" {
        tailf:code-name "esdma-rack-num-L6";
      }
      enum "7" {
        tailf:code-name "esdma-rack-num-L7";
      }
      enum "8" {
        tailf:code-name "esdma-rack-num-L8";
      }
      enum "9" {
        tailf:code-name "esdma-rack-num-L9";
      }
      enum "10" {
        tailf:code-name "esdma-rack-num-L10";
      }
      enum "11" {
        tailf:code-name "esdma-rack-num-L11";
      }
      enum "12" {
        tailf:code-name "esdma-rack-num-L12";
      }
      enum "13" {
        tailf:code-name "esdma-rack-num-L13";
      }
      enum "14" {
        tailf:code-name "esdma-rack-num-L14";
      }
      enum "15" {
        tailf:code-name "esdma-rack-num-L15";
      }
      enum "F0" {
        tailf:code-name "esdma-rack-num-F0";
      }
      enum "F1" {
        tailf:code-name "esdma-rack-num-F1";
      }
      enum "F2" {
        tailf:code-name "esdma-rack-num-F2";
      }
      enum "F3" {
        tailf:code-name "esdma-rack-num-F3";
      }
      enum "B0" {
        tailf:code-name "esdma-rack-num-B0";
      }
      enum "B1" {
        tailf:code-name "esdma-rack-num-B1";
      }
    }
    description
      "The valid rack numbers supported in Sysadmin.";
  }

  typedef esdma-cpu {
    type enumeration {
      enum "Unknown" {
        tailf:code-name "esdma-cpu-unknown";
      }
      enum "RP0" {
        tailf:code-name "esdma-cpu-rp0";
      }
      enum "RP1" {
        tailf:code-name "esdma-cpu-rp1";
      }
      enum "SC0" {
        tailf:code-name "esdma-cpu-sc0";
      }
      enum "SC1" {
        tailf:code-name "esdma-cpu-sc1";
      }
      enum "LC0" {
        tailf:code-name "esdma-cpu-lc0";
      }
      enum "LC1" {
        tailf:code-name "esdma-cpu-lc1";
      }
      enum "LC2" {
        tailf:code-name "esdma-cpu-lc2";
      }
      enum "LC3" {
        tailf:code-name "esdma-cpu-lc3";
      }
      enum "LC4" {
        tailf:code-name "esdma-cpu-lc4";
      }
      enum "LC5" {
        tailf:code-name "esdma-cpu-lc5";
      }
      enum "LC6" {
        tailf:code-name "esdma-cpu-lc6";
      }
      enum "LC7" {
        tailf:code-name "esdma-cpu-lc7";
      }
      enum "LC8" {
        tailf:code-name "esdma-cpu-lc8";
      }
      enum "LC9" {
        tailf:code-name "esdma-cpu-lc9";
      }
      enum "LC10" {
        tailf:code-name "esdma-cpu-lc10";
      }
      enum "LC11" {
        tailf:code-name "esdma-cpu-lc11";
      }
      enum "LC12" {
        tailf:code-name "esdma-cpu-lc12";
      }
      enum "LC13" {
        tailf:code-name "esdma-cpu-lc13";
      }
      enum "LC14" {
        tailf:code-name "esdma-cpu-lc14";
      }
      enum "LC15" {
        tailf:code-name "esdma-cpu-lc15";
      }
      enum "LC16" {
        tailf:code-name "esdma-cpu-lc16";
      }
      enum "LC17" {
        tailf:code-name "esdma-cpu-lc17";
      }
      enum "LC18" {
        tailf:code-name "esdma-cpu-lc18";
      }
      enum "LC19" {
        tailf:code-name "esdma-cpu-lc19";
      }
      enum "FC0" {
        tailf:code-name "esdma-cpu-fc0";
      }
      enum "FC1" {
        tailf:code-name "esdma-cpu-fc1";
      }
      enum "FC2" {
        tailf:code-name "esdma-cpu-fc2";
      }
      enum "FC3" {
        tailf:code-name "esdma-cpu-fc3";
      }
      enum "FC4" {
        tailf:code-name "esdma-cpu-fc4";
      }
      enum "FC5" {
        tailf:code-name "esdma-cpu-fc5";
      }
      enum "CB0" {
        tailf:code-name "esdma-cpu-cb0";
      }
    }
    description
      "The set of CPU enumerations that have control plane Ethernet switches or run the MLAP protocol.";
  }

  typedef esdma-switch-type-enum {
    type enumeration {
      enum "RP-SW" {
        tailf:code-name "esdma-switch_type-rp-sw";
      }
      enum "SC-SW" {
        tailf:code-name "esdma-switch_type-sc-sw";
      }
      enum "LC-SW" {
        tailf:code-name "esdma-switch_type-lc-sw";
      }
      enum "F-SW0" {
        tailf:code-name "esdma-switch_type-f-sw0";
      }
      enum "F-SW1" {
        tailf:code-name "esdma-switch_type-f-sw1";
      }
      enum "FC-SW" {
        tailf:code-name "esdma-switch_type-fc-sw";
      }
      enum "EOBC-SW" {
        tailf:code-name "esdma-switch_type-eobc-sw";
      }
      enum "EPC-SW" {
        tailf:code-name "esdma-switch_type-epc-sw";
      }
      enum "CB-SW" {
        tailf:code-name "esdma-switch_type-cb-sw";
      }
      enum "Unknown" {
        tailf:code-name "esdma-switch_type-unknown";
      }
    }
    description
      "The list of Ethernet switch types";
  }

  typedef esdma-switch-yes-no-enum {
    type enumeration {
      enum "Yes" {
        tailf:code-name "esdma-switch-yes";
      }
      enum "No" {
        tailf:code-name "esdma-switch-no";
      }
    }
  }

  typedef esdma-switch-sfp-inserted-enum {
    type enumeration {
      enum "Unknown" {
        tailf:code-name "esdma-switch-sfp-inserted-unknown";
      }
      enum "Yes" {
        tailf:code-name "esdma-switch-sfp-inserted-yes";
      }
      enum "No" {
        tailf:code-name "esdma-switch-sfp-inserted-no";
      }
      enum "Failed" {
        tailf:code-name "esdma-switch-sfp-inserted-failed";
      }
    }
  }

  typedef esdma-switch-sfp-controller-enum {
    type enumeration {
      enum "Unknown" {
        tailf:code-name "esdma-sfp-ctrlr-unknown";
      }
      enum "Switch" {
        tailf:code-name "esdma-sfp-ctrlr-switch";
      }
      enum "PHY" {
        tailf:code-name "esdma-sfp-ctrlr-phy";
      }
    }
  }

  typedef esdma-switch-sfp-tranceiver-type-enum {
    type enumeration {
      enum "Unspecified" {
        tailf:code-name "esdma-sfp-xceiver-type-unspecified";
      }
      enum "SFP" {
        tailf:code-name "esdma-sfp-xceiver-type-sfp";
      }
      enum "QSFP" {
        tailf:code-name "esdma-sfp-xceiver-type-qsfp";
      }
      enum "Unknown" {
        tailf:code-name "esdma-sfp-xceiver-type-unknown";
      }
    }
  }

  typedef esdma-sfp-encoding-enum {
    type enumeration {
      enum "Unspecified" {
        tailf:code-name "esdma-sfp-encoding-unspecified";
      }
      enum "8B/10B" {
        tailf:code-name "esdma-sfp-encoding-8b10b";
      }
      enum "4B/5B" {
        tailf:code-name "esdma-sfp-encoding-4b5b";
      }
      enum "NRZ" {
        tailf:code-name "esdma-sfp-encoding-nrz";
      }
      enum "Manchester" {
        tailf:code-name "esdma-sfp-encoding-manchester";
      }
      enum "SONET Scrambled" {
        tailf:code-name "esdma-sfp-encoding-sonet-scram";
      }
      enum "64B/66B" {
        tailf:code-name "esdma-sfp-encoding-64b66b";
      }
      enum "Unknown" {
        tailf:code-name "esdma-sfp-encoding-unknown";
      }
    }
  }

  typedef esdma-qsfp-transceiver-enum {
    type enumeration {
      enum "QSFP-40G-LR4" {
        tailf:code-name "esdma-qsfp-transceiver-40g-lr4";
      }
      enum "QSFP-40G-SR4" {
        tailf:code-name "esdma-qsfp-transceiver-40g-sr4";
      }
      enum "QSFP-40G-CR4-Active" {
        tailf:code-name "esdma-qsfp-transceiver-40g-cr4-active";
      }
      enum "QSFP-40G-CR4-Passive" {
        tailf:code-name "esdma-qsfp-transceiver-40g-cr4-passive";
      }
      enum "Unknown" {
        tailf:code-name "esdma-qsfp-transceiver-unknown";
      }
    }
  }

  typedef esdma-switch-sfp-type-enum {
    type enumeration {
      enum "None" {
        tailf:code-name "esdma-sfp-type-none";
      }
      enum "SFP-10G-SR" {
        tailf:code-name "esdma-sfp-type-10g-sr";
      }
      enum "SFP-10G-LR" {
        tailf:code-name "esdma-sfp-type-10g-lr";
      }
      enum "SFP-10G-LRM" {
        tailf:code-name "esdma-sfp-type-10g-lrm";
      }
      enum "SFP-1G-SX" {
        tailf:code-name "esdma-sfp-type-1g-sx";
      }
      enum "SFP-1G-LX" {
        tailf:code-name "esdma-sfp-type-1g-lx";
      }
      enum "SFP-1000Base-T" {
        tailf:code-name "esdma-sfp-type-1000b-t";
      }
      enum "SFP-40G-SR4" {
        tailf:code-name "esdma-sfp-type-40g-sr4";
      }
      enum "SFP-40G-LR4" {
        tailf:code-name "esdma-sfp-type-40g-lr4";
      }
      enum "Unsupported" {
        tailf:code-name "esdma-sfp-type-unsupported";
      }
    }
  }

  typedef esdma-switch-port-type {
    type int32 {
      range "0..127";
    }
    description
      "A type defining the allowable switch port numbers";
  }

  typedef esdma-switch-port-state {
    type enumeration {
      enum "Unknown" {
        tailf:code-name "esdma-switch-port-state-unknown";
      }
      enum "Test" {
        tailf:code-name "esdma-switch-port-state-test";
      }
      enum "Down" {
        tailf:code-name "esdma-switch-port-state-down";
      }
      enum "Up" {
        tailf:code-name "esdma-switch-port-state-up";
      }
    }
    description
      "The switch port up and down states";
  }

  typedef switch-forwarding-state {
    type enumeration {
      enum "Unknown" {
        tailf:code-name "switch-forwarding-state-unknown";
      }
      enum "-" {
        tailf:code-name "switch-forwarding-state-not-applic";
      }
      enum "Disabled" {
        tailf:code-name "switch-forwarding-state-disabled";
      }
      enum "Blocking" {
        tailf:code-name "switch-forwarding-state-listen-block";
      }
      enum "Learning" {
        tailf:code-name "switch-forwarding-state-learning";
      }
      enum "Forwarding" {
        tailf:code-name "switch-forwarding-state-forwarding";
      }
    }
    description
      "The set of switch port forwarding states";
  }

  typedef switch-traffic-class-enum {
    type int8 {
      range "-1..7";
    }
  }

  typedef esdma-sdr-id {
    type uint8;
  }

  typedef esd-cir-eir-type {
    type enumeration {
      enum "CIR" {
        tailf:code-name "switch-cir";
      }
      enum "PIR" {
        tailf:code-name "switch-pir";
      }
    }
  }

  typedef esd-percentage {
    type uint8 {
      range "0..100";
    }
  }

  typedef mlap-ep-type {
    type enumeration {
      enum "Unknown" {
        tailf:code-name "mlap-ep-type-unknown";
      }
      enum "RP" {
        tailf:code-name "mlap-ep-type-rp";
      }
      enum "SC" {
        tailf:code-name "mlap-ep-type-sc";
      }
      enum "FC" {
        tailf:code-name "mlap-ep-type-fc";
      }
      enum "LC" {
        tailf:code-name "mlap-ep-type-lc";
      }
      enum "F-SW" {
        tailf:code-name "mlap-ep-type-f-sw";
      }
      enum "CB" {
        tailf:code-name "mlap-ep-type-cb";
      }
    }
  }

  typedef mlap-state-enum {
    type enumeration {
      enum "-" {
        tailf:code-name "mlap-state-enum-not-applic";
      }
      enum "Down" {
        tailf:code-name "mlap-state-enum-down";
      }
      enum "Up" {
        tailf:code-name "mlap-state-enum-up";
      }
      enum "Admin Down" {
        tailf:code-name "mlap-state-enum-admin-down";
      }
      enum "Do Not Use" {
        tailf:code-name "mlap-state-enum-do-not-use";
      }
      enum "Invalid" {
        tailf:code-name "mlap-state-enum-invalid";
      }
      enum "Active" {
        tailf:code-name "mlap-state-enum-active";
      }
      enum "Standby" {
        tailf:code-name "mlap-state-enum-standby";
      }
      enum "Rem Managed" {
        tailf:code-name "mlap-state-enum-rem-manage";
      }
    }
    description
      "The set of enumerated values that MLAP uses to manage a port's protocol state";
  }

  typedef mlap-protocol-enum {
    type enumeration {
      enum "Internal" {
        tailf:code-name "mlap-protocol-enum-internal";
      }
      enum "External" {
        tailf:code-name "mlap-protocol-enum-external";
      }
    }
    description
      "The types of MLAP protocol";
  }

  typedef mlap-trace-verbosity {
    type enumeration {
      enum "Off" {
        tailf:code-name "mlap-trace-verbosity-off";
      }
      enum "Low" {
        tailf:code-name "mlap-trace-verbosity-low";
      }
      enum "Medium" {
        tailf:code-name "mlap-trace-verbosity-medium";
      }
      enum "High" {
        tailf:code-name "mlap-trace-verbosity-high";
      }
    }
  }

  typedef vlan-id-type {
    type uint16 {
      range "0..4095";
    }
  }

  typedef switch-data-direction-enum {
    type enumeration {
      enum "-" {
        tailf:code-name "switch-data-direction-none";
      }
      enum "Both" {
        tailf:code-name "switch-data-direction-both";
      }
      enum "Rx" {
        tailf:code-name "switch-data-direction-rx";
      }
      enum "Tx" {
        tailf:code-name "switch-data-direction-tx";
      }
      enum "Unknown" {
        tailf:code-name "switch-data-direction-unknown";
      }
      enum "Invalid" {
        tailf:code-name "switch-data-direction-max";
      }
    }
    description
      "Switch data direction";
  }

  typedef switch-table-type-enum {
    type enumeration {
      enum "-" {
        tailf:code-name "switch-table-type-none";
      }
      enum "Port" {
        tailf:code-name "switch-table-type-port";
      }
      enum "VLAN" {
        tailf:code-name "switch-table-type-vlan";
      }
      enum "TCAM" {
        tailf:code-name "switch-table-type-tcam";
      }
      enum "Unknown" {
        tailf:code-name "switch-table-type-unknown";
      }
    }
  }

  typedef switch-match-type-enum {
    type enumeration {
      enum "-" {
        tailf:code-name "switch-match-type-none";
      }
      enum "Any" {
        tailf:code-name "switch-match-type-any";
      }
      enum "Tagged" {
        tailf:code-name "switch-match-type-tagged";
      }
      enum "Untagged" {
        tailf:code-name "switch-match-type-untagged";
      }
      enum "Unknown" {
        tailf:code-name "switch-match-type-unknown";
      }
    }
  }

  typedef switch-action-type-enum {
    type enumeration {
      enum "-" {
        tailf:code-name "switch-action-type-none";
      }
      enum "Translate" {
        tailf:code-name "switch-action-type-translate";
      }
      enum "Remove Outer" {
        tailf:code-name "switch-action-type-remove-outer";
      }
      enum "Add Outer" {
        tailf:code-name "switch-action-type-add-outer";
      }
      enum "Drop" {
        tailf:code-name "switch-action-type-drop";
      }
      enum "Forward" {
        tailf:code-name "switch-action-type-forward";
      }
      enum "Unknown" {
        tailf:code-name "switch-action-type-unknown";
      }
    }
  }

  typedef esdma-sdr-traffic-type {
    type enumeration {
      enum "Unknown" {
        tailf:code-name "esdma-traffic-type-unknown";
      }
      enum "IPC" {
        tailf:code-name "esdma-traffic-type-ipc";
      }
      enum "MgmtEth" {
        tailf:code-name "esdma-traffic-type-mgmt";
      }
      enum "All" {
        tailf:code-name "esdma-traffic-type-all";
      }
      enum "Invalid" {
        tailf:code-name "esdma-traffic-type-max";
      }
    }
  }

  typedef esdma-trunk-member-status {
    type enumeration {
      enum "Disabled" {
        tailf:code-name "esdma-trunk-member-status-disabled";
      }
      enum "Enabled" {
        tailf:code-name "esdma-trunk-member-status-enabled";
      }
      enum "-" {
        tailf:code-name "esdma-trunk-member-status-not-present";
      }
    }
  }
  tailf:id "http://cisco.com/panini/calvados/esdma/esdma_types";
}
