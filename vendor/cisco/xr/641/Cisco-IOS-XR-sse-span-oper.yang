module Cisco-IOS-XR-sse-span-oper {
  namespace "http://cisco.com/ns/yang/Cisco-IOS-XR-sse-span-oper";
  prefix sse-span-oper;

  import Cisco-IOS-XR-types {
    prefix xr;
  }
  include Cisco-IOS-XR-sse-span-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sse-span package operational data.
     
     This module contains definitions
     for the following management objects:
       ssespan: SSE SPAN operational data
     
     Copyright (c) 2013-2017 by Cisco Systems, Inc.
     All rights reserved.";

  revision 2017-09-07 {
    description
      "Fixed type translation error.";
  }
  revision 2015-11-09 {
    description
      "IOS XR 6.0 revision.";
  }

  container ssespan {
    config false;
    description
      "SSE SPAN operational data";
    container nodes {
      description
        "Node table for node-specific operational data";
      list node {
        key "node";
        description
          "Node-specific data for a particular node";
        container span-mirr-infos {
          description
            "SPAN SFT entry";
          list span-mirr-info {
            key "intf-name";
            description
              "Mirror info ";
            leaf intf-name {
              type xr:Interface-name;
              description
                "interface name";
            }
            uses SSE-SPAN-EA-SFT-BAG;
          }
        }
        container spanudf {
          description
            "udf info";
          uses SSE-SPAN-EA-UDF-BAG;
        }
        container span-sess-infos {
          description
            "SPAN SDT entry";
          list span-sess-info {
            key "session-id session-class";
            description
              "Session info ";
            leaf session-id {
              type uint32;
              description
                "Session Id";
            }
            leaf session-class {
              type uint32;
              description
                "Session class";
            }
            uses SSE-SPAN-EA-SDT-BAG;
          }
        }
        leaf node {
          type xr:Node-id;
          description
            "Node";
        }
      }
    }
  }
}
