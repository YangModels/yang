module cisco-xr-ietf-netconf-acm-deviations {
  namespace "http://cisco.com/ns/yang/cisco-xr-ietf-netconf-acm-deviations";
  prefix nacmdevs;

  import ietf-netconf-acm {
    prefix nacm;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for 
      
     ietf-netconf-acm.yang@2012-02-22 
     
     on Cisco IOS-XR devices.
     
     Copyright (c) 2016-2017 by Cisco Systems, Inc.
     All rights reserved.";

  revision 2017-08-02 {
    description
      "Initial revision applicable to IOS-XR 6.2.1";
  }

  deviation "/nacm:nacm/nacm:enable-nacm" {
    deviate not-supported;
  }
  deviation "/nacm:nacm/nacm:denied-notifications" {
    deviate not-supported;
  }
}
