module modena_driver_types {
  namespace "http://www.cisco.com/panini/calvados/slice_control/modena/types";
  prefix modena_driver_type;

  import tailf-common {
    prefix tailf;
  }

  typedef modena_lane_id_type {
    type string {
      pattern "all|[0-3]";
    }
    tailf:info "0-3;;Modena system lane number.";
  }

  typedef modena_id_type {
    type string {
      pattern "all|[0-19]";
    }
    tailf:info "0-19;;Modena number.";
  }
}
