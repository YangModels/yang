module Cisco-IOS-XR-sysadmin-ship {
  namespace "http://www.cisco.com/ns/yang/Cisco-IOS-XR-sysadmin-ship";
  prefix ship;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin operational.
     
     This module defines operational data for
     sysadmin ship process.
     
     Copyright(c) 2010-2016 by Cisco Systems, Inc.
     All rights reserved.";

  revision 2017-05-09 {
    description
      "Namespace change to comply with Cisco guidelines";
  }
  revision 2016-05-30 {
    description
      "Initial version.";
  }
  tailf:id "http://cisco.com/calvados/ship";

  container stat {
    config false;
    description
      "SHIP Info";
    tailf:alt-name "System-statistics";
    tailf:callpoint "ship_show_comp";
    list ship_comp {
      key "comp-name";
      description
        "Select ship client component";
      tailf:alt-name "Component-name";
      tailf:info "Select ship component name";
      tailf:cli-suppress-table;
      tailf:cli-show-template-enter "Component name: $(comp-name)";
      leaf comp-name {
        type string;
        description
          "Name of component";
        tailf:info "Name of component";
      }
      list process {
        key "process-name";
        tailf:callpoint "ship_show_comp_proc";
        tailf:info "Select ship process name";
        tailf:cli-suppress-table;
        tailf:cli-show-template-enter "Process name: $(process-name)";
        leaf process-name {
          type string;
          tailf:info "Name of process";
        }
        list client {
          key "client-name";
          tailf:callpoint "ship_show_comp_cl";
          tailf:info "Select ship client name";
          tailf:cli-suppress-table;
          tailf:cli-show-template-enter "Client name: $(client-name)";
          leaf client-name {
            type string;
            tailf:info "Name of client";
          }
          list cat {
            key "cat-name";
            tailf:callpoint "ship_show_comp_cat";
            tailf:info "Select ship cat name";
            tailf:cli-suppress-table;
            tailf:cli-show-template-enter "Category name: $(cat-name)";
            leaf cat-name {
              type enumeration {
                enum "SHIP_TRANSPORT_COUNTERS" {
                  value 0;
                }
                enum "SHIP_SERVER_COUNTERS" {
                  value 1;
                }
                enum "SHIP_CLIENT_LIB_COUNTERS" {
                  value 2;
                }
                enum "SHIP_REPLICATION_COUNTERS" {
                  value 3;
                }
                enum "SHIP_READER_REPLICA_COUNTERS" {
                  value 4;
                }
                enum "SHIP_WRITER_REPLICA_COUNTERS" {
                  value 5;
                }
                enum "SHIP_TRANSPORT_COUNTERS_FAILOVER" {
                  value 6;
                }
                enum "SHIP_SERVER_COUNTERS_FAILOVER" {
                  value 7;
                }
                enum "SHIP_CLIENT_LIB_COUNTERS_FAILOVER" {
                  value 8;
                }
                enum "SHIP_REPLICATION_COUNTERS_FAILOVER" {
                  value 9;
                }
                enum "SHIP_TRANSPORT_ERRORS" {
                  value 10;
                }
                enum "SHIP_SERVER_ERRORS" {
                  value 11;
                }
                enum "SHIP_CLIENT_LIB_ERRORS" {
                  value 12;
                }
                enum "SHIP_REPLICATION_ERRORS" {
                  value 13;
                }
                enum "SHIP_READER_REPLICA_ERRORS" {
                  value 14;
                }
                enum "SHIP_WRITER_REPLICA_ERRORS" {
                  value 15;
                }
                enum "SHIP_TRANSPORT_ERRORS_FAILOVER" {
                  value 16;
                }
                enum "SHIP_SERVER_ERRORS_FAILOVER" {
                  value 17;
                }
                enum "SHIP_CLIENT_LIB_ERRORS_FAILOVER" {
                  value 18;
                }
                enum "SHIP_REPLICATION_ERRORS_FAILOVER" {
                  value 19;
                }
                enum "FEATURE_MA_COUNTERS" {
                  value 20;
                }
                enum "FEATURE_MA_COUNTERS_ERRORS" {
                  value 21;
                }
                enum "FEATURE_MA_COUNTERS_FAILOVER" {
                  value 22;
                }
                enum "VIRTUAL_INTERFACE_MA_COUNTERS" {
                  value 23;
                }
                enum "VIRTUAL_INTERFACE_MA_COUNTERS_ERRORS" {
                  value 24;
                }
                enum "VIRTUAL_INTERFACE_MA_COUNTERS_FAILOVER" {
                  value 25;
                }
                enum "FEATURE_EA_COUNTERS" {
                  value 26;
                }
                enum "FEATURE_EA_COUNTERS_ERRORS" {
                  value 27;
                }
                enum "VIRTUAL_INTERFACE_EA_COUNTERS" {
                  value 28;
                }
                enum "VIRTUAL_INTERFACE_EA_COUNTERS_ERRORS" {
                  value 29;
                }
                enum "VIRTUAL_INTERFACE_EA_COUNTERS_FAILOVER" {
                  value 30;
                }
                enum "SHIP_HISTOGRAM_COUNTERS" {
                  value 31;
                }
                enum "SHIP_WATERMARK_COUNTERS" {
                  value 32;
                }
                enum "SHIP_NODE_COUNTERS" {
                  value 33;
                }
              }
              tailf:info "Name of cat";
            }
            list counter-32b {
              key "counter-name";
              tailf:alt-name "Counter-List";
              tailf:callpoint "ship_show_comp_counter";
              tailf:info "Select ship counter name";
              tailf:cli-suppress-table;
              tailf:cli-show-template-enter "Counter name: $(counter-name)\t";
              leaf counter-name {
                type string;
                tailf:alt-name "\t Counter-API Name";
                tailf:info "Counter name or API name";
              }
              leaf counter-value {
                type uint32;
                tailf:alt-name "  Counter Value :";
                tailf:cli-suppress-show-path;
                tailf:cli-suppress-show-match;
              }
              leaf watermark {
                type uint32;
                tailf:cli-suppress-show-path;
                tailf:cli-suppress-show-match;
              }
              leaf time-stamp {
                type uint64;
                tailf:cli-suppress-show-path;
                tailf:cli-suppress-show-match;
              }
              leaf hist-info1 {
                type uint32;
                tailf:alt-name
                  "
                   \t 10us :";
                tailf:cli-suppress-show-path;
                tailf:cli-suppress-show-match;
              }
              leaf hist-info2 {
                type uint32;
                tailf:alt-name "\t 100us :";
                tailf:cli-suppress-show-path;
                tailf:cli-suppress-show-match;
              }
              leaf hist-info3 {
                type uint32;
                tailf:alt-name "\t 1ms :";
                tailf:cli-suppress-show-path;
                tailf:cli-suppress-show-match;
              }
              leaf hist-info4 {
                type uint32;
                tailf:alt-name "\t 10ms :";
                tailf:cli-suppress-show-path;
                tailf:cli-suppress-show-match;
              }
              leaf hist-info5 {
                type uint32;
                tailf:alt-name "\t 100ms :";
                tailf:cli-suppress-show-path;
                tailf:cli-suppress-show-match;
              }
              leaf hist-info6 {
                type uint32;
                tailf:alt-name "\t 1s :";
                tailf:cli-suppress-show-path;
                tailf:cli-suppress-show-match;
              }
              leaf hist-info7 {
                type uint32;
                tailf:alt-name "\t 10s :";
                tailf:cli-suppress-show-path;
                tailf:cli-suppress-show-match;
              }
              leaf hist-info8 {
                type uint32;
                tailf:alt-name "\t 100s :";
                tailf:cli-suppress-show-path;
                tailf:cli-suppress-show-match;
              }
            }
          }
        }
      }
    }
  }
}
