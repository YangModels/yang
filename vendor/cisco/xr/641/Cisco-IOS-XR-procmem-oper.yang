module Cisco-IOS-XR-procmem-oper {
  namespace "http://cisco.com/ns/yang/Cisco-IOS-XR-procmem-oper";
  prefix procmem-oper;

  import Cisco-IOS-XR-types {
    prefix xr;
  }
  include Cisco-IOS-XR-procmem-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR procmem package operational data.
     
     This module contains definitions
     for the following management objects:
       processes-memory: Process statistics
     
     Copyright (c) 2013-2017 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }
  revision 2015-07-30 {
    description
      "IOS XR 6.0.0 revision.";
  }

  container processes-memory {
    config false;
    description
      "Process statistics";
    container nodes {
      description
        "List of nodes";
      list node {
        key "node-name";
        description
          "Node ID";
        container process-ids {
          description
            "List of jobs";
          list process-id {
            key "process-id";
            description
              "Process Id";
            leaf process-id {
              type uint32;
              description
                "Process Id";
            }
            uses PROCESSESMEMORY-ENTRY;
          }
        }
        leaf node-name {
          type xr:Node-id;
          description
            "Node name";
        }
      }
    }
  }
}
