module Cisco-IOS-XR-subscriber-accounting-oper {
  namespace "http://cisco.com/ns/yang/Cisco-IOS-XR-subscriber-accounting-oper";
  prefix subscriber-accounting-oper;

  import Cisco-IOS-XR-types {
    prefix xr;
  }
  include Cisco-IOS-XR-subscriber-accounting-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-accounting package operational data.
     
     This module contains definitions
     for the following management objects:
       subscriber-accounting: Subscriber accounting operational data
     
     Copyright (c) 2013-2017 by Cisco Systems, Inc.
     All rights reserved.";

  revision 2015-11-09 {
    description
      "IOS XR 6.0 revision.";
  }

  container subscriber-accounting {
    config false;
    description
      "Subscriber accounting operational data";
    container nodes {
      description
        "Subscriber accounting operational data for a
         particular location";
      list node {
        key "node-id";
        description
          "Location. For example, 0/1/CPU0";
        container subscriber-accounting-session-features {
          description
            "Subscriber accounting session feature data";
          list subscriber-accounting-session-feature {
            key "sub-label";
            description
              "Display accounting session features by unique
               subscriber label";
            leaf sub-label {
              type int32;
              description
                "Unique subscriber label";
            }
            uses ACCT-MA-SESSION-FEATURES;
          }
        }
        container subscriber-accounting-summary {
          description
            "Display subscriber accounting summary data";
          uses ACCT-MA-FEATURE-SUMMARY;
        }
        container subscriber-accounting-flow-features {
          description
            "Subscriber accounting flow feature data";
          list subscriber-accounting-flow-feature {
            key "class-label";
            description
              "Display accounting flow features by unique
               subscriber label";
            leaf class-label {
              type int32;
              description
                "Unique subscriber class label";
            }
            uses ACCT-MA-FLOW-FEATURES;
          }
        }
        leaf node-id {
          type xr:Node-id;
          description
            "The node id to filter on. For example,
             0/1/CPU0";
        }
      }
    }
  }
}
