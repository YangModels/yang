module Cisco-IOS-XR-sysadmin-sdr-console {
  namespace "http://www.cisco.com/ns/yang/Cisco-IOS-XR-sysadmin-sdr-console";
  prefix sdr_console;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     Copyright(c) 2015-2017 by Cisco Systems, Inc.
     All rights reserved.
     
     Copyright (c) 2012-2017 by Cisco Systems, Inc.
     All rights reserved.";

  revision 2017-12-05 {
    description
      "Removed cli-incomplete-command statement";
  }

  grouping console-attach-config-group {
    container attach-sdr {
      container runtime {
        list location {
          key "location-rp";
          leaf location-rp {
            type string {
              pattern "((0?[0-9]|1[1-5]|[bB]\\d)/(([rR][pP]|[cC][bB])\\d{1,2}))(/[cC][pP][uU]0)?";
            }
          }
          list tty-name {
            key "ttyname";
            leaf ttyname {
              type string {
                length "1..30";
                pattern "console1|console2";
              }
            }
            leaf sdr-name {
              type string {
                length "1..30";
                pattern "[a-zA-Z0-9_.{}+-]+";
              }
            }
          }
        }
      }
      container boot {
        list location {
          key "location-rp";
          leaf location-rp {
            type string {
              pattern "((0?[0-9]|1[1-5]|[bB]\\d)/(([rR][pP]|[cC][bB])\\d{1,2}))(/[cC][pP][uU]0)?";
            }
          }
          leaf sdr-name {
            type string {
              length "1..30";
              pattern "[a-zA-Z0-9_.{}+-]+";
            }
          }
        }
      }
    }
  }
}
