module Cisco-IOS-XR-sysadmin-ethsw-esdma-mgmt-agent {
  namespace "http://www.cisco.com/ns/yang/Cisco-IOS-XR-sysadmin-ethsw-esdma-mgmt-agent";
  prefix esdma_mgmt_agent;

  import tailf-common {
    prefix tailf;
  }
  import ietf-inet-types {
    prefix inet;
  }
  import Cisco-IOS-XR-sysadmin-ethsw-esdma-types {
    prefix esdma_types;
  }
  import Cisco-IOS-XR-sysadmin-ethsw-esdma-trace {
    prefix esdma_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch mgmt-agent' commands.
     
     Copyright(c) 2011-2017 by Cisco Systems, Inc.
     All rights reserved.";

  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping esdma-debug {
    container connections {
      tailf:hidden "advanced-grp";
      tailf:info "Display ESD Management Agent connectivity";
      tailf:cli-full-show-path;
      tailf:cli-full-command;
      tailf:callpoint "esdma_connections";
      tailf:cli-show-template
        "$(esdma-info|show)
         $(sdr-nm-client-id|show)$(esd-client-id|show)$(mlap-client-id|show)";
      container esdma-info {
        tailf:cli-drop-node-name;
        tailf:cli-suppress-show-path;
        tailf:cli-show-template
          "Active ESD Management Agent IP Address: $(active-esdma-address)
           
          ";
        leaf active-esdma-address {
          type inet:ip-address;
        }
      }
      list sdr-nm-client-id {
        tailf:cli-table-legend "ESDMA-SDR Clients:";
        tailf:cli-table-footer
          "
           Total table entries: $(../sdr-nm-num-clients)";
        leaf sdr-nm-ip-address {
          type inet:ip-address;
          tailf:display-column-name "IP Address";
          tailf:cli-column-width "15";
        }
        leaf sdr-nm-port-num {
          type inet:port-number;
          tailf:display-column-name "Port Number";
          tailf:cli-column-width "11";
        }
      }
      leaf sdr-nm-num-clients {
        type uint32;
        tailf:cli-suppress-show-path;
      }
      list esd-client-id {
        tailf:cli-table-legend "ETHSW-MGMT Clients:";
        tailf:cli-table-footer
          "
           Total table entries: $(../esd-client-num-clients)";
        leaf esd-client-ip-address {
          type inet:ip-address;
          tailf:display-column-name "IP Address";
          tailf:cli-column-width "15";
        }
        leaf esd-client-port-num {
          type inet:port-number;
          tailf:display-column-name "Port Number";
          tailf:cli-column-width "11";
        }
        leaf esd-client-location {
          type string;
          tailf:display-column-name "Location";
        }
        leaf esd-client-switch-info-cached {
          type esdma_types:esdma-switch-yes-no-enum;
          tailf:display-column-name "Switch Info";
        }
        leaf esd-client-sdr-info-cached {
          type esdma_types:esdma-switch-yes-no-enum;
          tailf:display-column-name "SDR Info";
        }
      }
      leaf esd-client-num-clients {
        type uint32;
        tailf:cli-suppress-show-path;
      }
      list mlap-client-id {
        tailf:cli-table-legend "MLAP-MGMT Clients:";
        tailf:cli-table-footer
          "
           Total table entries: $(../mlap-client-num-clients)";
        leaf mlap-client-ip-address {
          type inet:ip-address;
          tailf:display-column-name "IP Address";
          tailf:cli-column-width "15";
        }
        leaf mlap-client-port-num {
          type inet:port-number;
          tailf:display-column-name "Port Number";
          tailf:cli-column-width "11";
        }
        leaf mlap-client-location {
          type string;
          tailf:display-column-name "Location";
        }
        leaf mlap-client-switch-info-cached {
          type esdma_types:esdma-switch-yes-no-enum;
          tailf:display-column-name "Switch Info";
        }
      }
      leaf mlap-client-num-clients {
        type uint32;
        tailf:cli-suppress-show-path;
      }
    }
  }

  grouping esdma-mgmt-group {
    container mgmt-agent {
      tailf:info "Switch and MLAP management agent";
      uses esdma_trace:esdma-ctrace;
      uses esdma-debug;
    }
  }
  tailf:id "http://cisco.com/panini/calvados/esdma/esdma_mgmt_agent";
}
