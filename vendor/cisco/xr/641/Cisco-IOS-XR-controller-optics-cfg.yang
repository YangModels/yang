module Cisco-IOS-XR-controller-optics-cfg {
  namespace "http://cisco.com/ns/yang/Cisco-IOS-XR-controller-optics-cfg";
  prefix controller-optics-cfg;

  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-optics package configuration.
     
     This YANG module augments the
       Cisco-IOS-XR-ifmgr-cfg
     module with configuration data.
     
     Copyright (c) 2013-2017 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  typedef Optics-fec {
    type enumeration {
      enum "fec-none" {
        value 0;
        description
          "No Fec";
      }
      enum "fec-h15" {
        value 1;
        description
          "Enhanced H15";
      }
      enum "fec-h25" {
        value 2;
        description
          "Enhanced H25";
      }
      enum "fec-h15-de" {
        value 4;
        description
          "Enhanced H15 DE";
      }
      enum "fec-h25-de" {
        value 8;
        description
          "Enhanced H25 DE";
      }
    }
    description
      "Optics fec";
  }

  typedef Optics-ots-ampli-control-mode {
    type enumeration {
      enum "automatic" {
        value 1;
        description
          "Automatic Amplifier Mode";
      }
      enum "manual" {
        value 2;
        description
          "Manual Amplifier Mode";
      }
    }
    description
      "Optics ots ampli control mode";
  }

  typedef Threshold {
    type enumeration {
      enum "low" {
        value 1;
        description
          "Low Threshold";
      }
      enum "high" {
        value 2;
        description
          "High Threshold";
      }
    }
    description
      "Threshold";
  }

  typedef Optics-dwdm-carrier-param {
    type enumeration {
      enum "itu-ch" {
        value 0;
        description
          "ITU Wave Channel Number";
      }
      enum "wavelength" {
        value 1;
        description
          "Wavelength in nm";
      }
      enum "frequency" {
        value 2;
        description
          "Frequency in Hertz";
      }
    }
    description
      "Optics dwdm carrier param";
  }

  typedef Optics-ots-safety-control-mode {
    type enumeration {
      enum "auto" {
        value 1;
        description
          "Automatic Safety Control Mode";
      }
      enum "disabled" {
        value 2;
        description
          "Disable Safety Control Mode";
      }
    }
    description
      "Optics ots safety control mode";
  }

  typedef Optics-ots-ampli-gain-range {
    type enumeration {
      enum "normal" {
        value 1;
        description
          "Normal Amplifier Gain Range";
      }
      enum "extended" {
        value 2;
        description
          "Extended Amplifier Gain Range";
      }
    }
    description
      "Optics ots ampli gain range";
  }

  typedef Optics-dwdm-carrier-grid {
    type enumeration {
      enum "50g-hz-grid" {
        value 0;
        description
          "50GHz Grid";
      }
      enum "100mhz-grid" {
        value 1;
        description
          "100MHz Grid";
      }
    }
    description
      "Optics dwdm carrier grid";
  }

  typedef Optics-loopback {
    type enumeration {
      enum "none" {
        value 0;
        description
          "No Loopback";
      }
      enum "internal" {
        value 1;
        description
          "Internal Loopback";
      }
      enum "line" {
        value 2;
        description
          "Line Loopback";
      }
    }
    description
      "Optics loopback";
  }

  augment "/a1:interface-configurations/a1:interface-configuration" {
    description
      "This augment extends the configuration data of
       'Cisco-IOS-XR-ifmgr-cfg'";
    container optics {
      description
        "Optics controller configuration";
      container rx-thresholds {
        description
          "Configure Rx threshold";
        list rx-threshold {
          key "rx-threshold-type";
          description
            "Optics RX Low or high threshold configuration";
          leaf rx-threshold-type {
            type Threshold;
            description
              "Low or high rx threshold";
          }
          leaf rx-threshold {
            type int32 {
              range "-400..300";
            }
            mandatory true;
            description
              "Select power level (in units of 0.1dBm)";
          }
        }
      }
      container optics-network-srlgs {
        description
          "Configure Network srlgs";
        list optics-network-srlg {
          key "set-id";
          description
            "Configure network srlg sets";
          leaf set-id {
            type uint32 {
              range "1..17";
            }
            description
              "Set index";
          }
          leaf srlg1 {
            type uint32 {
              range "0..4294967294";
            }
            description
              "none";
          }
          leaf srlg2 {
            type uint32 {
              range "0..4294967294";
            }
            description
              "none";
          }
          leaf srlg3 {
            type uint32 {
              range "0..4294967294";
            }
            description
              "none";
          }
          leaf srlg4 {
            type uint32 {
              range "0..4294967294";
            }
            description
              "none";
          }
          leaf srlg5 {
            type uint32 {
              range "0..4294967294";
            }
            description
              "none";
          }
          leaf srlg6 {
            type uint32 {
              range "0..4294967294";
            }
            description
              "none";
          }
        }
      }
      container optics-dwdm-carrier {
        presence "Indicates a optics-dwdm-carrier node is configured.";
        description
          "Configure optics DWDM Carrier";
        leaf grid-type {
          type Optics-dwdm-carrier-grid;
          mandatory true;
          description
            "DWDM Channel Grid Type";
        }
        leaf param-type {
          type Optics-dwdm-carrier-param;
          mandatory true;
          description
            "DWDM Channel Parameter Type ITU-Channel or
             Frequency or Wavelength";
        }
        leaf param-value {
          type uint32 {
            range "1..1961000";
          }
          mandatory true;
          description
            "Type ITU-Channel Range 1-100, Frequency Range
             19115-19610, Wavelength Range 1528773-1568362,
             100MHz Frequency Range 1911500-1961000";
        }
      }
      container optics-lanes {
        description
          "Optics lanes";
        list optics-lane {
          key "index";
          description
            "Lane";
          leaf description {
            type string {
              length "1..255";
            }
            description
              "Configure description for this Lane";
          }
          leaf index {
            type uint32;
            description
              "Lane Number";
          }
        }
      }
      container tx-thresholds {
        description
          "Configure Tx threshold";
        list tx-threshold {
          key "tx-threshold-type";
          description
            "Optics TX Low or high threshold configuration";
          leaf tx-threshold-type {
            type Threshold;
            description
              "Low or high tx threshold";
          }
          leaf tx-threshold {
            type int32 {
              range "-400..300";
            }
            mandatory true;
            description
              "Select power level (in units of 0.1dBm)";
          }
        }
      }
      leaf optics-transmit-power {
        type int32 {
          range "-190..20";
        }
        description
          "Select power level (in units of 0.1dBm)";
      }
      leaf optics-ots-channel-power-max-delta {
        type int32 {
          range "-500..300";
        }
        description
          "Configure max delta among all measured channel
           powers ";
      }
      leaf optics-loopback {
        type Optics-loopback;
        default "none";
        description
          "Configure optics loopback mode ";
      }
      leaf optics-ots-osri {
        type boolean;
        description
          "Configure Optical safety remote interlock
           (OSRI)";
      }
      leaf optics-ots-amplifier-gain-degrade-high-threshold {
        type int32 {
          range "0..500";
        }
        description
          "Select Amplifier Gain Degrade High Threshold(in
           units of 0.1dBm)";
      }
      leaf optics-ots-rx-voa-attenuation {
        type int32 {
          range "0..200";
        }
        description
          "Select RX Voa Attenuation Setpoint(in units of
           0.1dBm)";
      }
      leaf optics-fec {
        type Optics-fec;
        default "fec-none";
        description
          "Configure optics fec ";
      }
      leaf optics-dgd-high-threshold {
        type int32 {
          range "0..18000";
        }
        description
          "Select DGD high threshold(in units of 0.1ps)";
      }
      leaf optics-ots-amplifier-channel-power {
        type int32 {
          range "-500..300";
        }
        description
          "Select Amplifier Channel Power(in units of 0
           .1dBm)";
      }
      leaf optics-ots-amplifier-control-mode {
        type Optics-ots-ampli-control-mode;
        description
          "Configure amplifier working mode";
      }
      leaf optics-ots-amplifier-gain {
        type int32 {
          range "0..500";
        }
        description
          "Select Amplifier Gain value(in units of 0.1dBm)";
      }
      leaf optics-ots-amplifier-gain-range {
        type Optics-ots-ampli-gain-range;
        description
          "Normal or extended Ampli Gain Range";
      }
      leaf optics-ots-safety-control-mode {
        type Optics-ots-safety-control-mode;
        description
          "Configure safety Control Mode";
      }
      leaf optics-cd-min {
        type int32 {
          range "-280000..280000";
        }
        description
          "Select min chromatic dispersion (in units of
           ps/nm)";
      }
      leaf optics-ots-tx-voa-attenuation {
        type int32 {
          range "0..200";
        }
        description
          "Select TX Voa Attenuation Setpoint(in units of
           0.1dBm)";
      }
      leaf optics-ots-amplifier-tilt {
        type int32 {
          range "-50..50";
        }
        description
          "Select Amplifier Tilt value(in units of 0.1dB)";
      }
      leaf optics-transmit-shutdown {
        type boolean;
        description
          "Configure optics transmit laser shutdown ";
      }
      leaf optics-description {
        type string {
          length "1..255";
        }
        description
          "Configure optics port description ";
      }
      leaf optics-performance-monitoring {
        type boolean;
        default "true";
        description
          "Select Performance Monitoring as Enable or
           Disable";
      }
      leaf optics-cd-max {
        type int32 {
          range "-280000..280000";
        }
        description
          "Select max chromatic dispersion (in units of
           ps/nm)";
      }
      leaf optics-lbc-high-threshold {
        type int32 {
          range "0..100";
        }
        description
          "Select power level (in units of percentage)";
      }
      leaf optics-cd-high-threshold {
        type int32 {
          range "-280000..280000";
        }
        description
          "Select chromatic dispersion high threshold(in
           units of ps/nm)";
      }
      leaf optics-osnr-low-threshold {
        type int32 {
          range "0..4000";
        }
        description
          "Select OSNR low threshold(in units of 0.01db)";
      }
      leaf optics-ots-amplifier-gain-degrade-low-threshold {
        type int32 {
          range "0..500";
        }
        description
          "Select Amplifier Gain Degrade Low Threshold(in
           units of 0.1dBm)";
      }
      leaf optics-cd-low-threshold {
        type int32 {
          range "-280000..280000";
        }
        description
          "Select chromatic dispersion low threshold(in
           units of ps/nm)";
      }
    }
  }
}
