module Cisco-IOS-XR-sysadmin-ethsw-esdma-sdr {
  namespace "http://www.cisco.com/ns/yang/Cisco-IOS-XR-sysadmin-ethsw-esdma-sdr";
  prefix esdma_sdr;

  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains the YANG definitions
     for the Cisco IOS-XR SysAdmin
     'show controller switch sdr' commands.
     
     Copyright(c) 2011-2017 by Cisco Systems, Inc.
     All rights reserved.
     
     Copyright (c) 2012-2017 by Cisco Systems, Inc.
     All rights reserved.";

  revision 2017-05-01 {
    description
      "Namespace change to comply with Cisco guidelines on namespace";
  }

  grouping sdr-detail-group {
    container sdr-detail {
      list sdr-id {
        key "sdr";
        leaf sdr {
          type esdma_types:esdma-sdr-id;
        }
        container port-statistics {
          list location {
            key "rack card switch-id";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              leaf port {
                type esdma_types:esdma-switch-port-type;
                description
                  "Switch port";
              }
              list traffic-type-id {
                key "traffic-type";
                leaf traffic-type {
                  type esdma_types:esdma-sdr-traffic-type;
                }
                list direction-id {
                  key "direction";
                  leaf direction {
                    type esdma_types:switch-data-direction-enum;
                    description
                      "Packet direction this rule applies to";
                  }
                  list traffic-class-id {
                    key "tc";
                    leaf tc {
                      type esdma_types:switch-traffic-class-enum;
                      description
                        "Traffic class (0->7) for these statistics.";
                    }
                    leaf green-packets {
                      type uint64;
                      description
                        "Counts packets within the committed information rate for a traffic class on this VLAN.";
                    }
                    leaf yellow-packets {
                      type uint64;
                      description
                        "Counts packets above the committed information rate, but within the excess information rate for a traffic class on this VLAN.";
                    }
                    leaf red-packets {
                      type uint64;
                      description
                        "Counts packets above the excess information rate for a traffic class on this VLAN. Generally, these packets are dropped.";
                    }
                  }
                }
              }
            }
          }
        }
      }
    }
  }

  grouping sdr-summary-port-stats {
    container port-statistics {
      list location {
        key "rack card switch-id";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list port-iter {
          key "port";
          leaf port {
            type esdma_types:esdma-switch-port-type;
            description
              "Switch port";
          }
          list sdr-id {
            key "sdr";
            leaf sdr {
              type esdma_types:esdma-sdr-id;
            }
            leaf esd-sdr-name {
              type string;
            }
            list traffic-type-id {
              key "traffic-type";
              leaf traffic-type {
                type esdma_types:esdma-sdr-traffic-type;
              }
              list direction-id {
                key "direction";
                leaf direction {
                  type esdma_types:switch-data-direction-enum;
                  description
                    "Packet direction this rule applies to";
                }
                leaf green-packets {
                  type uint64;
                  description
                    "Counts packets within the committed information rate for all traffic classes on this SDR.";
                }
                leaf yellow-packets {
                  type uint64;
                  description
                    "Counts packets above the committed information rate, but within the excess information rate for all traffic classes on this SDR.";
                }
                leaf red-packets {
                  type uint64;
                  description
                    "Counts packets above the excess information rate for all traffic classes on this SDR. Generally, these packets are dropped.";
                }
              }
            }
          }
        }
      }
    }
  }

  grouping sdr-summary-global-stats {
    container global-statistics {
      list location {
        key "rack card switch-id";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list sdr-id {
          key "sdr";
          leaf sdr {
            type esdma_types:esdma-sdr-id;
          }
          leaf esd-sdr-name {
            type string;
          }
          list traffic-type-id {
            key "traffic-type";
            leaf traffic-type {
              type esdma_types:esdma-sdr-traffic-type;
            }
            list traffic-class-id {
              key "tc";
              leaf tc {
                type esdma_types:switch-traffic-class-enum;
                description
                  "Traffic class (0->7) for these statistics.";
              }
              leaf green-packets {
                type uint64;
                description
                  "Counts packets within the committed information rate for a traffic class on this VLAN.";
              }
              leaf yellow-packets {
                type uint64;
                description
                  "Counts packets above the committed information rate, but within the excess information rate for a traffic class on this VLAN.";
              }
              leaf red-packets {
                type uint64;
                description
                  "Counts packets above the excess information rate for a traffic class on this VLAN. Generally, these packets are dropped.";
              }
            }
          }
        }
      }
    }
  }

  grouping sdr-summary-policers {
    container policers {
      list location {
        key "rack card switch-id";
        leaf rack {
          type esdma_types:esdma-rack-num-enum;
        }
        leaf card {
          type esdma_types:esdma-cpu;
        }
        leaf switch-id {
          type esdma_types:esdma-switch-type-enum;
        }
        container esd-policer-status {
          container indent-group {
            leaf esd-port-policing-enabled {
              type esdma_types:esdma-switch-yes-no-enum;
            }
            leaf esd-port-committed-burst-size {
              type uint32;
            }
            leaf esd-port-peak-burst-size {
              type uint32;
            }
            leaf esd-port-policer-mru {
              type uint32;
            }
            leaf esd-global-policing-enabled {
              type esdma_types:esdma-switch-yes-no-enum;
            }
            leaf esd-global-committed-burst-size {
              type uint32;
            }
            leaf esd-global-peak-burst-size {
              type uint32;
            }
            leaf esd-global-policer-mru {
              type uint32;
            }
          }
        }
        list sdr-id {
          key "sdr";
          leaf sdr {
            type esdma_types:esdma-sdr-id;
          }
          leaf esd-sdr-name {
            type string;
          }
          leaf esd-sdr-cir {
            type esdma_types:esd-percentage;
          }
          leaf esd-sdr-pir {
            type esdma_types:esd-percentage;
          }
          list esd-sdr-cos-type-iter {
            key "esd-sdr-cos-type";
            leaf esd-sdr-cos-type {
              type esdma_types:esd-cir-eir-type;
            }
            leaf esd-sdr-cos-0 {
              type esdma_types:esd-percentage;
            }
            leaf esd-sdr-cos-1 {
              type esdma_types:esd-percentage;
            }
            leaf esd-sdr-cos-2 {
              type esdma_types:esd-percentage;
            }
            leaf esd-sdr-cos-3 {
              type esdma_types:esd-percentage;
            }
            leaf esd-sdr-cos-4 {
              type esdma_types:esd-percentage;
            }
            leaf esd-sdr-cos-5 {
              type esdma_types:esd-percentage;
            }
            leaf esd-sdr-cos-6 {
              type esdma_types:esd-percentage;
            }
            leaf esd-sdr-cos-7 {
              type esdma_types:esd-percentage;
            }
          }
        }
      }
    }
  }

  grouping sdr-summary-group {
    uses sdr-summary-port-stats;
    uses sdr-summary-global-stats;
    uses sdr-summary-policers;
  }

  grouping switch-sdr-group {
    container sdr {
      uses sdr-summary-group;
      uses sdr-detail-group;
    }
  }
}
