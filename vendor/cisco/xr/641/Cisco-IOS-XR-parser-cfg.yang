module Cisco-IOS-XR-parser-cfg {
  namespace "http://cisco.com/ns/yang/Cisco-IOS-XR-parser-cfg";
  prefix parser-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR parser package configuration.
     
     This module contains definitions
     for the following management objects:
       parser: Parser configuration
     
     Copyright (c) 2013-2017 by Cisco Systems, Inc.
     All rights reserved.";

  revision 2017-05-09 {
    description
      "IOS XR 6.3.1 revision.";
  }
  revision 2015-01-07 {
    description
      "IOS XR 5.3.1 revision.";
  }

  container parser {
    description
      "Parser configuration";
    container indentation {
      description
        "indentation tracking";
      leaf indentation-disable {
        type boolean;
        description
          "disable the indentation";
      }
    }
    container alias {
      description
        "Alias for command mapping";
      container execs {
        description
          "Exec command alias";
        list exec {
          key "identifier";
          description
            "Exec alias name";
          leaf identifier {
            type string {
              length "1..30";
            }
            description
              "Exec Alias name";
          }
          leaf identifier-xr {
            type string;
            mandatory true;
            description
              "Aliased exec command";
          }
        }
      }
      container configurations {
        description
          "Configuration command alias";
        list configuration {
          key "identifier";
          description
            "Configuration Alias name";
          leaf identifier {
            type string {
              length "1..30";
            }
            description
              "Configuration alias name";
          }
          leaf identifier-xr {
            type string;
            mandatory true;
            description
              "Aliased config command";
          }
        }
      }
      container alls {
        description
          "Table of all aliases configured";
        list all {
          key "identifier";
          description
            "Alias name to command mapping";
          leaf identifier {
            type string {
              length "1..30";
            }
            description
              "Alias name";
          }
          leaf identifier-xr {
            type string;
            mandatory true;
            description
              "The actual command";
          }
        }
      }
    }
    container history {
      description
        "cli commands history";
      leaf size {
        type uint32 {
          range "1000..5000";
        }
        description
          "maximum number of commands in history";
      }
    }
    container interactive {
      description
        "interactive mode";
      leaf interactive-disable {
        type boolean;
        description
          "disable interactive mode";
      }
    }
    container commit-optimized {
      description
        "Enable optimization for regular commit";
      leaf commit-optimized-enable {
        type boolean;
        description
          "Enable the feature";
      }
    }
    container sysadmin-login-banner {
      description
        "Configuration to disable sysadmin login banner";
      leaf sysadmin-login-banner-disable {
        type boolean;
        description
          "Disable sysadmin login banner";
      }
    }
    container interface-display {
      description
        "Configure the Interface display order";
      leaf slot-order {
        type boolean;
        description
          "Configure Interface display order as slot order";
      }
    }
    container netmask-format {
      description
        "Ipv4 netmask-format to be configured";
      leaf bit-count {
        type boolean;
        description
          "Enable ipv4 netmask-format as bit-count";
      }
    }
    container configuration {
      description
        "cli configuration services";
      container disable {
        description
          "disable for read-only access users";
        leaf usergroup {
          type string;
          description
            "Disable config mode for usergroup";
        }
      }
    }
    container submode-exit {
      description
        "Exit submode when only '!' seen in interactive
         mode";
      leaf enable {
        type boolean;
        description
          "Enable the feature";
      }
    }
  }
}
