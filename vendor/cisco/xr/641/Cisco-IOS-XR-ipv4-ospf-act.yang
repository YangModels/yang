module Cisco-IOS-XR-ipv4-ospf-act {

    namespace "http://cisco.com/ns/yang/Cisco-IOS-XR-ipv4-ospf-act";
   
    prefix "ospf-act";

    import Cisco-IOS-XR-types { prefix "xr"; }

    import ietf-inet-types { prefix "inet"; }
   
    organization "Cisco Systems, Inc.";
   
    contact
    "Cisco Systems, Inc.
     Customer Service

     Postal: 170 West Tasman Drive
     San Jose, CA 95134

     Tel: +1 800 553-NETS

     E-mail: cs-yang@cisco.com";
   
    description
    "This module contains a collection of YANG definitions
     for Cisco IOS-XR OSPF action package configuration.

     Copyright (c) 2016-2017 by Cisco Systems, Inc.
     All rights reserved.";
   
    revision "2016-09-14" {
        description
            "IOS XR 6.2.1 revision.";
    }

    rpc clear-ospf-routes {
        description "Clear OSPF route table";
        input {
            container instance {
                description "Clear data from OSPF instance";
                leaf instance-identifier {
                    description "OSPF process instance identifier";
                    type string;
                }
            }
            leaf route {
                description "Clear OSPF route table";
                mandatory true;
                type empty;
            }
        }
    }

    rpc clear-ospf-redistribution {
        description "Clear OSPF route redistribution";
        input {
            container instance {
                description "Clear data from OSPF instance";
                leaf instance-identifier {
                    description "OSPF process instance identifier";
                    type string;
                }
            }
            leaf redistribution {
                description "Clear OSPF route redistribution";
                mandatory true;
                type empty;
            }
        }
    }

    rpc clear-ospf-statistics {
        description "Clear OSPF counters and statistics";
        input {
            container instance {
                description "Clear data from OSPF instance";
                leaf instance-identifier {
                    description "OSPF process instance identifier";
                    type string;
                }
            }
            leaf all {
                description "All OSPF counters and statistics";
                type empty;
            }
            leaf message-queue {
                description "Message-queue statistics";
                type empty;
            }
            leaf spf {
                description "SPF statistics";
                type empty;
            }
            leaf neighbor {
                description "Neighbor statistics per neighbor id";
                type empty;
            }
            leaf interface-name {
                description "OSPF interface statistics";
                type empty;
            }
        }
    }

    rpc clear-ospf-statistics-neighbor {
        description "Clear OSPF neighbor statistics per interface or neighbor id";
        input {
            container instance {
                description "Clear data from OSPF instance";
                leaf instance-identifier {
                    description "OSPF process instance identifier";
                    type string;
                }
            }
            container neighbor {
                leaf neighbor-id {
                    description "Neighbor ID";
                    type inet:ipv4-address;
                }
                leaf interface-name {
                    description "Interface";
                    type xr:Interface-name;
                }
            }
        }
    }

    rpc clear-ospf-statistics-interface {
        description "Clear OSPF interface statistics";
        input {
            container instance {
                description "Clear data from OSPF instance";
                leaf instance-identifier {
                    description "OSPF process instance identifier";
                    type string;
                }
             }
             container interface {
                 leaf interface-name {
                     description "OSPF interface statistics";
                     type xr:Interface-name;
                 }
             }
        }
    }

    rpc clear-ospf-process {
        description "Clear (reset) OSPF process";
        input {
            container instance {
                description "Clear data from OSPF instance";
                leaf instance-identifier {
                    description "OSPF process instance identifier";
                    type string;
                }
            }
            leaf process {
                description "Reset OSPF process";
                mandatory true;
                type empty;
            }
        }
    }

    grouping OSPF-STAT-ATTRIBUTES {
        leaf process {
            description "Reset OSPF process";
            type empty;
        }
        leaf redistribution {
            description "Clear OSPF route redistrbution";
            type empty;
        }
        leaf route {
            description "Clear OSPF route table";
            type empty;
        }
        container stats {
            description "OSPF counters and statistics";
            leaf spf {
                description "SPF statistics";
                type empty; 
            } 
            leaf message-queue {
                description "Message-queue statistics";
                type empty; 
            } 
            container interface {
                description "OSPF interface statistics";
                leaf interface-name {
                    type xr:Interface-name;
                }
            }
            container neighbor {
                description "Neighbor statistics per interface or neighbor id";
                leaf neighbor-id {
                    description "Neighbor ID";
                    type inet:ipv4-address;
                }
                container interface {
                    leaf interface-name {
                        description "OSPF interface statistics";
                        type xr:Interface-name;
                    }
                }
            } 
        }
    }

    rpc clear-ospf-instance-vrf {
        description "Clear one or more non-default OSPF VRFs in process";
        input {
            container instance {
                description "OSPF instance name";
                leaf instance-identifier {
                    description "OSPF process instance identifier";
                    mandatory true;
                    type string;
                }

                container vrf {
                    description "Clear one or more non-default OSPF VRFs in process";
                    leaf vrf-name {
                        description "OSPF VRF name";
                        type string;
                    }
                    uses OSPF-STAT-ATTRIBUTES;
                }

                container all {
                    description "Clear all non-default OSPF VRFs";
                    uses OSPF-STAT-ATTRIBUTES;
                }

                container all-inclusive {
                    description "Clear all non-default and default OSPF VRFs";
                    uses OSPF-STAT-ATTRIBUTES;
                }
            }
        }
    }
}
