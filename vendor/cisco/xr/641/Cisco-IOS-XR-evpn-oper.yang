module Cisco-IOS-XR-evpn-oper {
  namespace "http://cisco.com/ns/yang/Cisco-IOS-XR-evpn-oper";
  prefix evpn-oper;

  import ietf-inet-types {
    prefix inet;
  }
  import ietf-yang-types {
    prefix yang;
  }
  import Cisco-IOS-XR-types {
    prefix xr;
  }
  include Cisco-IOS-XR-evpn-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR evpn package operational data.
     
     This module contains definitions
     for the following management objects:
       evpn: EVPN Operational Table
     
     Copyright (c) 2013-2017 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  typedef Rd-addr-index {
    type uint32 {
      range "0..65535";
    }
    description
      "Rd addr index";
  }

  typedef Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef Bgp-route-target {
    type enumeration {
      enum "no-stitching" {
        value 0;
        description
          "RT is default type";
      }
      enum "stitching" {
        value 1;
        description
          "RT is for stitching (Golf-L2)";
      }
    }
    description
      "Bgp route target";
  }

  typedef Rdas-index {
    type uint32 {
      range "0..4294967295";
    }
    description
      "Rdas index";
  }

  typedef Rdas-range {
    type uint32 {
      range "1..4294967295";
    }
    description
      "Rdas range";
  }

  typedef Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  grouping EVI-TABLE {
    description
      "Common node of active, standby, node";
    container evis {
      description
        "L2VPN EVPN EVI Table";
      list evi {
        key "evi";
        description
          "L2VPN EVPN EVI Entry";
        leaf evi {
          type uint32;
          description
            "EVPN id";
        }
        uses L2VPN-EVPN-EVI-SUMMARY;
      }
    }
  }

  grouping AC-ID-TABLE {
    description
      "Common node of active, standby, node";
    container ac-ids {
      description
        "EVPN AC ID table";
      list ac-id {
        description
          "EVPN AC ID table";
        leaf evi {
          type uint32;
          description
            "EVPN id";
        }
        leaf ac-id {
          type uint32;
          description
            "AC ID";
        }
        uses L2VPN-EVPN-NEIGHBOR;
      }
    }
  }

  grouping EVI-DETAIL {
    description
      "Common node of active, standby, node";
    container evi-detail {
      description
        "L2VPN EVI Detail Table";
      container elements {
        description
          "EVI BGP RT Detail Info Elements";
        list element {
          key "evi";
          description
            "EVI BGP RT Detail Info";
          leaf evi {
            type uint32;
            description
              "EVPN id";
          }
          uses L2VPN-EVPN-EVI-DETAIL;
        }
      }
      container evi-children {
        description
          "Container for all EVI detail info";
        container neighbors {
          description
            "EVPN Neighbor table";
          list neighbor {
            description
              "EVPN Neighbor table";
            leaf evi {
              type uint32;
              description
                "EVPN id";
            }
            leaf neighbor-ip {
              type inet:ip-address-no-zone;
              description
                "Neighbor IP";
            }
            uses L2VPN-EVPN-NEIGHBOR;
          }
        }
        container ethernet-auto-discoveries {
          description
            "EVPN Ethernet Auto-Discovery table";
          list ethernet-auto-discovery {
            description
              "EVPN Ethernet Auto-Discovery Entry";
            leaf evi {
              type uint32;
              description
                "EVPN id";
            }
            leaf esi1 {
              type xr:Hex-integer;
              description
                "ES id (part 1/5)";
            }
            leaf esi2 {
              type xr:Hex-integer;
              description
                "ES id (part 2/5)";
            }
            leaf esi3 {
              type xr:Hex-integer;
              description
                "ES id (part 3/5)";
            }
            leaf esi4 {
              type xr:Hex-integer;
              description
                "ES id (part 4/5)";
            }
            leaf esi5 {
              type xr:Hex-integer;
              description
                "ES id (part 5/5)";
            }
            leaf ethernet-tag {
              type uint32;
              description
                "Ethernet Tag ID";
            }
            uses L2VPN-EVPN-EAD;
          }
        }
        container inclusive-multicasts {
          description
            "L2VPN EVPN IMCAST table";
          list inclusive-multicast {
            description
              "L2VPN EVPN IMCAST table";
            leaf evi {
              type uint32;
              description
                "EVPN id";
            }
            leaf ethernet-tag {
              type uint32;
              description
                "Ethernet Tag";
            }
            leaf originating-ip {
              type inet:ip-address-no-zone;
              description
                "Originating IP";
            }
            uses L2VPN-EVPN-IMCAST;
          }
        }
        container route-targets {
          description
            "L2VPN EVPN EVI RT Child Table";
          list route-target {
            description
              "L2VPN EVPN EVI RT Table";
            leaf evi {
              type uint32;
              description
                "EVPN id";
            }
            leaf role {
              type Bgp-route-target-role;
              description
                "Role of the route target";
            }
            leaf type {
              type Bgp-route-target;
              description
                "Type of the route target";
            }
            leaf format {
              type Bgp-route-target-format;
              description
                "Format of the route target";
            }
            leaf as {
              type Rdas-range;
              description
                "Two or Four byte AS Number";
            }
            leaf as-index {
              type Rdas-index;
              description
                "RT AS Index";
            }
            leaf addr-index {
              type Rd-addr-index;
              description
                "RT IP Index";
            }
            leaf address {
              type inet:ipv4-address-no-zone;
              description
                "RT IPv4 Address";
            }
            uses L2VPN-EVPN-EVI-BGP-RT;
          }
        }
        container macs {
          description
            "L2VPN EVPN EVI MAC table";
          list mac {
            description
              "L2VPN EVPN MAC table";
            leaf evi {
              type uint32;
              description
                "EVPN id";
            }
            leaf ethernet-tag {
              type uint32;
              description
                "Ethernet Tag ID";
            }
            leaf mac-address {
              type yang:mac-address;
              description
                "MAC address";
            }
            leaf ip-address {
              type inet:ip-address-no-zone;
              description
                "IP Address";
            }
            uses L2VPN-EVPN-MAC;
          }
        }
      }
    }
  }

  grouping ETHERNET-SEGMENT-TABLE {
    description
      "Common node of active, standby, node";
    container ethernet-segments {
      description
        "EVPN Ethernet-Segment Table";
      list ethernet-segment {
        description
          "EVPN Ethernet-Segment Entry";
        leaf interface-name {
          type xr:Interface-name;
          description
            "Interface";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        uses L2VPN-EVPN-ES;
      }
    }
  }

  grouping CLIENT {
    description
      "Common node of active, standby, node";
    container client {
      description
        "L2VPN EVPN Client";
      uses L2VPN-EVPN-CLIENT;
    }
  }

  grouping SUMMARY {
    description
      "Common node of active, standby, node";
    container summary {
      description
        "L2VPN EVPN Summary";
      uses L2VPN-EVPN-SUMMARY;
    }
  }

  grouping EVPN-GROUP-TABLE {
    description
      "Common node of active, standby, node";
    container evpn-groups {
      description
        "EVPN Group Table";
      list evpn-group {
        key "group-number";
        description
          "EVPN Group information";
        leaf group-number {
          type uint32 {
            range "1..4294967295";
          }
          description
            "EVPN group number";
        }
        uses EVPN-GRP-INFO;
      }
    }
  }

  grouping INTERNAL-LABEL-TABLE {
    description
      "Common node of active, standby, node";
    container internal-labels {
      description
        "EVPN Internal Label Table";
      list internal-label {
        description
          "L2VPN EVPN Internal Label";
        leaf evi {
          type uint32;
          description
            "EVPN id";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        leaf ethernet-tag {
          type uint32;
          description
            "Ethernet Tag ID";
        }
        uses L2VPN-EVPN-LABEL;
      }
    }
  }

  container evpn {
    config false;
    description
      "EVPN Operational Table";
    container nodes {
      description
        "Table of EVPN operational data for a particular
         node";
      list node {
        key "node-id";
        description
          "EVPN operational data for a particular node";
        leaf node-id {
          type xr:Node-id;
          description
            "Location";
        }
        uses EVPN-GROUP-TABLE;
        uses CLIENT;
        uses EVI-TABLE;
        uses SUMMARY;
        uses EVI-DETAIL;
        uses INTERNAL-LABEL-TABLE;
        uses ETHERNET-SEGMENT-TABLE;
        uses AC-ID-TABLE;
      }
    }
    container active {
      description
        "Active EVPN operational data";
      uses EVPN-GROUP-TABLE;
      uses CLIENT;
      uses EVI-TABLE;
      uses SUMMARY;
      uses EVI-DETAIL;
      uses INTERNAL-LABEL-TABLE;
      uses ETHERNET-SEGMENT-TABLE;
      uses AC-ID-TABLE;
    }
    container standby {
      description
        "Standby EVPN operational data";
      uses EVPN-GROUP-TABLE;
      uses CLIENT;
      uses EVI-TABLE;
      uses SUMMARY;
      uses EVI-DETAIL;
      uses INTERNAL-LABEL-TABLE;
      uses ETHERNET-SEGMENT-TABLE;
      uses AC-ID-TABLE;
    }
  }
}
