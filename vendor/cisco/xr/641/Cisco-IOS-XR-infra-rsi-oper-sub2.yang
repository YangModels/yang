submodule Cisco-IOS-XR-infra-rsi-oper-sub2 {
  belongs-to Cisco-IOS-XR-infra-rsi-oper {
    prefix Cisco-IOS-XR-infra-rsi-oper;
  }

  include Cisco-IOS-XR-infra-rsi-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-rsi package operational data.
     
     Copyright (c) 2013-2017 by Cisco Systems, Inc.
     All rights reserved.";

  revision 2017-09-07 {
    description
      "Fixed type translation error.";
  }
  revision 2017-05-01 {
    description
      "Fixing backward compatibility error in module.";
  }
  revision 2015-01-07 {
    description
      "IOS XR 5.3.1 revision.";
  }

  typedef Source {
    type enumeration {
      enum "configured" {
        value 1;
        description
          "Configured";
      }
      enum "from-group" {
        value 2;
        description
          "From group";
      }
      enum "inherited" {
        value 4;
        description
          "Inherited";
      }
      enum "from-optical" {
        value 8;
        description
          "From optical";
      }
      enum "configured-and-notified" {
        value 17;
        description
          "Configured and notified";
      }
      enum "from-group-and-notified" {
        value 18;
        description
          "From group and notified";
      }
      enum "inherited-and-notified" {
        value 20;
        description
          "Inherited and notified";
      }
      enum "from-optical-and-notified" {
        value 24;
        description
          "From optical and notified";
      }
    }
    description
      "Source";
  }

  typedef Priority {
    type enumeration {
      enum "critical" {
        value 0;
        description
          "Critical";
      }
      enum "high" {
        value 1;
        description
          "High";
      }
      enum "medium" {
        value 2;
        description
          "Medium";
      }
      enum "low" {
        value 3;
        description
          "Low";
      }
      enum "very-low" {
        value 4;
        description
          "Very low";
      }
      enum "invald" {
        value 5;
        description
          "Invalid";
      }
    }
    description
      "Priority";
  }

  grouping RSI-SRLG-NAME-INTF-SHOW {
    description
      "RSI SRLG NAME INTF SHOW";
    container interfaces {
      description
        "Interfaces information";
      uses RSI-SRLG-INTF-SHOW;
    }
    leaf srlg-name-xr {
      type string;
      description
        "SRLG name";
    }
    leaf srlg-value {
      type uint32;
      description
        "SRLG value";
    }
  }

  grouping RSI-SRLG-INTF-SHOW {
    description
      "RSI SRLG INTF SHOW";
    leaf-list interface-name {
      type String1;
      description
        "Interface name";
    }
  }

  grouping RSI-SRLG-ATTR-DETAIL {
    description
      "RSI SRLG ATTR DETAIL";
    leaf srlg-value {
      type uint32;
      description
        "SRLG value";
    }
    leaf priority {
      type Priority;
      description
        "Priority";
    }
    leaf source {
      type Source;
      description
        "Source";
    }
    leaf source-name {
      type string;
      description
        "Source name";
    }
    leaf srlg-index {
      type uint16;
      description
        "Index";
    }
  }

  grouping RSI-SRLG-INTF-DETAIL-SHOW {
    description
      "RSI SRLG INTF DETAIL SHOW";
    leaf groups {
      type uint32;
      description
        "Groups";
    }
    leaf nodes {
      type uint32;
      description
        "Nodes";
    }
    list srlg-attribute {
      description
        "SRLG attributes";
      uses RSI-SRLG-ATTR-DETAIL;
    }
  }

  grouping RSI-SRLG-INHLOC-SHOW {
    description
      "RSI SRLG INHLOC SHOW";
    leaf node-name {
      type string;
      description
        "Inherit node name";
    }
    leaf node-values {
      type uint32;
      description
        "Node values";
    }
    list srlg-attribute {
      description
        "SRLG attribute";
      uses RSI-SRLG-ATTR-BRIEF;
    }
  }

  grouping RSI-SRLG-NAME-VALUE-SHOW {
    description
      "RSI SRLG NAME VALUE SHOW";
    leaf srlg-value {
      type uint32;
      description
        "SRLG value";
    }
    leaf srlg-name-xr {
      type string;
      description
        "SRLG name";
    }
  }

  grouping RSI-SRLG-RSIP-SHOW {
    description
      "RSI SRLG RSIP SHOW";
    leaf optical-layer-interface-name {
      type string;
      description
        "Optical layer interface name";
    }
    leaf registrations {
      type uint32;
      description
        "Registrations";
    }
    leaf interface-values {
      type uint32;
      description
        "Interface values";
    }
    list srlg-attribute {
      description
        "SRLG attribute";
      uses RSI-SRLG-ATTR-BRIEF;
    }
  }

  grouping RSI-SRLG-INTF-BRIEF-SHOW {
    description
      "RSI SRLG INTF BRIEF SHOW";
    leaf interface-name-xr {
      type string;
      description
        "Interface name";
    }
    leaf value-count {
      type uint32;
      description
        "Values";
    }
    leaf registrations {
      type uint32;
      description
        "Registrations";
    }
    leaf-list srlg-value {
      type uint32;
      description
        "SRLG values";
    }
  }

  grouping RSI-SRLG-ATTR-BRIEF {
    description
      "RSI SRLG ATTR BRIEF";
    leaf srlg-value {
      type uint32;
      description
        "SRLG value";
    }
    leaf priority {
      type Priority;
      description
        "Priority";
    }
    leaf srlg-index {
      type uint16;
      description
        "Index";
    }
  }

  grouping RSI-SRLG-GROUP-SHOW {
    description
      "RSI SRLG GROUP SHOW";
    leaf group-name-xr {
      type string;
      description
        "Group name";
    }
    leaf group-values {
      type uint32;
      description
        "Group values";
    }
    list srlg-attribute {
      description
        "SRLG attribute";
      uses RSI-SRLG-ATTR-BRIEF;
    }
  }

  grouping RSI-VRFGROUP-ATTR-BRIEF {
    description
      "RSI VRFGROUP ATTR BRIEF";
    leaf vrf-name {
      type string;
      description
        "VRF name";
    }
  }

  grouping RSI-VRFGROUP-GROUP-SHOW {
    description
      "RSI VRFGROUP GROUP SHOW";
    leaf vr-fs {
      type uint32;
      description
        "Number of VRFs in this VRF group";
    }
    leaf forward-reference {
      type boolean;
      description
        "VRF group not present but used";
    }
    list vrf {
      description
        "VRF group's VRF";
      uses RSI-VRFGROUP-ATTR-BRIEF;
    }
  }
}
