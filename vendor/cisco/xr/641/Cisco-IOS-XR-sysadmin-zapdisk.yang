module Cisco-IOS-XR-sysadmin-zapdisk {
  namespace "http://www.cisco.com/ns/yang/Cisco-IOS-XR-sysadmin-zapdisk";
  prefix zapdisk;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR Zapdisk module.
     
     This module zapdisk is for factory card reset feature.
     
     Copyright(c) 2016-2017 by Cisco Systems, Inc.
     All rights reserved.
     
     Copyright (c) 2012-2017 by Cisco Systems, Inc.
     All rights reserved.";

  revision 2017-05-23 {
    description
      "Changed namespace and module name";
  }

  rpc zapdisk {
    input {
      choice zapdisk-input {
        mandatory true;
        case target-set {
          leaf set {
            type empty;
            mandatory false;
          }
        }
        case target-unset {
          container czapdisk-unset {
            leaf unset {
              type empty;
              mandatory false;
            }
          }
        }
      }
    }
    output {
      leaf result {
        type string;
        mandatory true;
      }
    }
    tailf:actionpoint "zapdisk";
  }
}
