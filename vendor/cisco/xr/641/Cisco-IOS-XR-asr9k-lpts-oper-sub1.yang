submodule Cisco-IOS-XR-asr9k-lpts-oper-sub1 {
  belongs-to Cisco-IOS-XR-asr9k-lpts-oper {
    prefix Cisco-IOS-XR-asr9k-lpts-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-lpts package operational data.
     
     Copyright (c) 2013-2017 by Cisco Systems, Inc.
     All rights reserved.";

  revision 2015-11-09 {
    description
      "IOS XR 6.0 revision.";
  }

  grouping PL-PIFIB-POLICE-INFO {
    description
      "PL PIFIB POLICE INFO";
    leaf avgrate {
      type uint32;
      description
        "avgrate";
    }
    leaf burst {
      type uint32;
      description
        "burst";
    }
    leaf static-avgrate {
      type uint32;
      description
        "static avgrate";
    }
    leaf avgrate-type {
      type string {
        length "0..50";
      }
      description
        "avgrate type";
    }
    leaf flow-type {
      type string {
        length "0..50";
      }
      description
        "flow type";
    }
    leaf accepted-stats {
      type uint64;
      description
        "accepted stats";
    }
    leaf dropped-stats {
      type uint64;
      description
        "dropped stats";
    }
    leaf policer {
      type uint32;
      description
        "policer";
    }
    leaf str-iptos-val {
      type string {
        length "0..8";
      }
      description
        "str iptos val";
    }
    leaf change-type {
      type uint8;
      description
        "change type";
    }
    leaf acl-config {
      type uint8;
      description
        "acl config";
    }
    leaf acl-str {
      type string {
        length "0..50";
      }
      description
        "acl str";
    }
  }

  grouping PL-PIFIB-SHOW-POLICE {
    description
      "Pre-IFIB platform specific police data structure";
    list police-info {
      description
        "Per flow type police info";
      uses PL-PIFIB-POLICE-INFO;
    }
  }

  grouping PL-PIFIB-SHOW-STATS {
    description
      "Pre-IFIB global statistics";
    leaf accepted {
      type uint64;
      description
        "Deleted-entry accepted packets counter";
    }
    leaf dropped {
      type uint64;
      description
        "Deleted-entry dropped packets counter";
    }
    leaf clear-ts {
      type uint64;
      description
        "Statistics clear timestamp";
    }
    leaf no-stats-mem-err {
      type uint64;
      description
        "No statistics memory error";
    }
  }

  grouping PL-PIFIB-SHOW-STATIC-POLICE-INFO {
    description
      "PL PIFIB SHOW STATIC POLICE INFO";
    leaf punt-reason {
      type uint32;
      description
        "punt reason";
    }
    leaf sid {
      type uint32;
      description
        "sid";
    }
    leaf flow-rate {
      type uint32;
      description
        "flow rate";
    }
    leaf burst-rate {
      type uint32;
      description
        "burst rate";
    }
    leaf accepted {
      type uint64;
      description
        "accepted";
    }
    leaf dropped {
      type uint64;
      description
        "dropped";
    }
    leaf punt-reason-string {
      type string {
        length "0..50";
      }
      description
        "punt reason string";
    }
    leaf change-type {
      type uint8;
      description
        "change type";
    }
  }

  grouping PL-PIFIB-SHOW-STATIC-POLICE {
    description
      "Pre-IFIB platform specific punt reason data
       structure";
    list static-info {
      description
        "Per punt reason info";
      uses PL-PIFIB-SHOW-STATIC-POLICE-INFO;
    }
  }
}
