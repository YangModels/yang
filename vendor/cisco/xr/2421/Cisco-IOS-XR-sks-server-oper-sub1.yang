submodule Cisco-IOS-XR-sks-server-oper-sub1 {
  belongs-to Cisco-IOS-XR-sks-server-oper {
    prefix Cisco-IOS-XR-sks-server-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR sks-server package operational data.
     
     Copyright (c) 2013-2022 by Cisco Systems, Inc.
     All rights reserved.";

  revision 2021-08-11 {
    description
      "Added string bound check.";
    semver:module-version "1.0.0";
  }
  revision 2020-10-14 {
    description
      "Initial yang support for sks oper.";
  }
  revision 2019-04-05 {
    description
      "Establish semantic version baseline.";
  }
  revision 2015-11-09 {
    description
      "IOS XR 6.0 revision.";
  }

  grouping SKS-MCELIECE-PUBKEY-INFO {
    description
      "Info for a sks pubkey";
    leaf key-label {
      type string;
      description
        "Label for pubkey";
    }
    leaf key-type {
      type string;
      description
        "Type of pubkey";
    }
    leaf key-size {
      type uint32;
      description
        "Size of pubkey";
    }
    leaf key-hash {
      type string;
      description
        "SHA1 hash of pubkey";
    }
  }

  grouping SKS-PEER-INFO {
    description
      "Info for a sks peer";
    leaf peer-name-xr {
      type string;
      description
        "Peer identifier";
    }
    leaf profile-name {
      type string;
      description
        "Profile Name for the peer";
    }
    leaf seed-done {
      type boolean;
      description
        "Seed done for this peer";
    }
    leaf pubkey-imp-done {
      type boolean;
      description
        "Pubkey import done for this peer";
    }
    leaf master {
      type boolean;
      description
        "This peer is master";
    }
  }

  grouping SKS-PROFILE-INFO {
    description
      "Info for a sks profile";
    leaf profile-name-xr {
      type string;
      description
        "Profile Name";
    }
    leaf my-identifier {
      type string;
      description
        "My identifier";
    }
    leaf live-keys {
      type uint32;
      description
        "Live keys for this profile";
    }
    leaf single-pool {
      type boolean;
      description
        "Single/Double pool for this profile";
    }
    leaf prf-done {
      type boolean;
      description
        "PRF done for this profile";
    }
    leaf reg-client-count {
      type uint32;
      description
        "Number of clients registered for change in this
         profile";
    }
    list peer {
      description
        "Peers configured in this profile";
      uses SKS-PEER-INFO;
    }
  }
}
