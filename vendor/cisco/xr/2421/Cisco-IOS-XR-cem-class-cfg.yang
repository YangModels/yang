module Cisco-IOS-XR-cem-class-cfg {
  namespace "http://cisco.com/ns/yang/Cisco-IOS-XR-cem-class-cfg";
  prefix cem-class-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cem-class package configuration.
     
     This module contains definitions
     for the following management objects:
       cem: Configure CEM
     
     Copyright (c) 2013-2022 by Cisco Systems, Inc.
     All rights reserved.";

  revision 2021-08-18 {
    description
      "Replaced default option with best-match option in payload and dejitter command under cem class configuration.
       2021-07-20
         CEM class payload and dejitter command modified.
       2021-03-29
         CEM class profile config command added.";
    semver:module-version "2.0.0";
  }
  revision 2019-04-05 {
    description
      "Establish semantic version baseline.";
    semver:module-version "1.0.0";
  }
  revision 2015-11-09 {
    description
      "IOS XR 6.0 revision.";
  }

  typedef Cem-class-dummy-mode {
    type enumeration {
      enum "last-frame" {
        value 0;
        description
          "Last frame";
      }
      enum "user-defined" {
        value 1;
        description
          "User defined";
      }
    }
    description
      "Cem class dummy mode";
  }

  container cem {
    description
      "Configure CEM";
    container classes {
      description
        "Configure a CEM class";
      list class {
        key "class-name";
        description
          "CEM class name";
        container idle {
          description
            "Configure idle pattern";
          leaf pattern {
            type xr:Hex-integer;
            description
              "Idle pattern from 0x0 to 0xff";
          }
        }
        container dummy {
          description
            "Configure bit-pattern for filling in lost or
             corrupted frames";
          leaf pattern {
            type xr:Hex-integer;
            description
              "User defined bit pattern from 0x0 to 0xff for
               CEM frame";
          }
          leaf mode {
            type Cem-class-dummy-mode;
            description
              "Configure mode";
          }
        }
        container payload-dejitter {
          description
            "Configure payload size and dejitter buffer
             length";
          leaf payload {
            type uint32 {
              range "0..1472";
            }
            must "not(../dejitter)";
            description
              "32-1472 is valid range, '0' value indicates
               to choose best suitable payload value for the
               given dejitter buffer length";
          }
          leaf dejitter {
            type uint32 {
              range "0..500000";
            }
            must "not(../payload)";
            description
              "1-500000 is valid range, '0' value indicates
               to choose best suitable dejitter buffer
               length value for the given payload";
          }
        }
        leaf class-name {
          type xr:Cisco-ios-xr-string {
            length "1..80";
          }
          description
            "CEM class name";
        }
      }
    }
  }
}
