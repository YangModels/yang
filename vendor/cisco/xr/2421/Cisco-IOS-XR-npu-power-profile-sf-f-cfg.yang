module Cisco-IOS-XR-npu-power-profile-sf-f-cfg {
  namespace "http://cisco.com/ns/yang/Cisco-IOS-XR-npu-power-profile-sf-f-cfg";
  prefix npu-power-profile-sf-f-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR npu-power-profile-sf-f package configuration.
     
     This module contains definitions
     for the following management objects:
       npu-hw-module-profile-config: none
     
     Copyright (c) 2013-2022 by Cisco Systems, Inc.
     All rights reserved.";

  revision 2021-03-22 {
    description
      "Yang Schema updated to handle power mode as enum instead of uint32_t.";
    semver:module-version "2.0.0";
  }
  revision 2020-11-13 {
    description
      "Yang Schema added for SF-F NPU power profile in hw-module config.";
    semver:module-version "1.0.0";
  }
  revision 2019-04-05 {
    description
      "Establish semantic version baseline.";
  }
  revision 2015-11-09 {
    description
      "IOS XR 6.0 revision.";
  }

  typedef Power-mode-enum {
    type enumeration {
      enum "low" {
        value 1;
        description
          "Low";
      }
      enum "medium" {
        value 2;
        description
          "Medium";
      }
      enum "high" {
        value 3;
        description
          "High";
      }
    }
    description
      "Power mode enum";
  }

  container npu-hw-module-profile-config {
    description
      "none";
    container profile {
      description
        "Configure profile.";
      container npu-power-profile {
        description
          "Configure asic power usage.";
        container card-type {
          description
            "Card Type";
          container fixed-board {
            description
              "Fixed board systems";
            leaf power-mode {
              type Power-mode-enum;
              description
                "Power Mode";
            }
          }
        }
      }
    }
  }
}
