module Cisco-IOS-XR-fabric-fgid-stats-8000-oper {
  namespace "http://cisco.com/ns/yang/Cisco-IOS-XR-fabric-fgid-stats-8000-oper";
  prefix fabric-fgid-stats-8000-oper;

  import Cisco-IOS-XR-types {
    prefix xr;
  }
  import cisco-semver {
    prefix semver;
  }
  include Cisco-IOS-XR-fabric-fgid-stats-8000-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fabric-fgid-stats-8000 package operational data.
     
     This module contains definitions
     for the following management objects:
       fabric-fgid: Fabric Fgid Data
     
     Copyright (c) 2013-2019, 2022 by Cisco Systems, Inc.
     All rights reserved.";

  revision 2019-04-05 {
    description
      "Establish semantic version baseline.";
    semver:module-version "1.0.0";
  }
  revision 2015-11-09 {
    description
      "IOS XR 6.0 revision.";
  }

  typedef Fgid-info-elem-max {
    type uint32 {
      range "1..262144";
    }
    description
      "Fgid info elem max";
  }

  typedef Fgid-info-start-max {
    type uint32 {
      range "0..262143";
    }
    description
      "Fgid info start max";
  }

  container fabric-fgid {
    config false;
    description
      "Fabric Fgid Data";
    container statistics {
      description
        "Fabric Fgid Statistics";
      container all {
        description
          "Statistics Data";
        uses FGID-ALL-STATS-INFO;
      }
      container system {
        description
          "Statistics Data";
        uses FGID-SYS-STATS-INFO;
      }
    }
    container display-opts {
      description
        "Fabric Fgid System";
      list display-opt {
        key "displayopt";
        description
          "Display Option";
        leaf displayopt {
          type xr:Cisco-ios-xr-string;
          description
            "brief/detail/diag";
        }
        list start-fgid-id {
          key "fgid-id";
          description
            "Start FGID Number";
          leaf fgid-id {
            type Fgid-info-start-max;
            description
              "Fabric FGID";
          }
          list element {
            key "num-fgids";
            description
              "Number of Fgids";
            leaf num-fgids {
              type Fgid-info-elem-max;
              description
                "Number of Fabric FGIDs";
            }
            list fgid-id {
              key "fgid-id";
              description
                "Single Fgid information";
              leaf fgid-id {
                type Fgid-info-start-max;
                description
                  "Single Fgid";
              }
              uses FGID-INFO;
            }
          }
        }
      }
    }
  }
}
