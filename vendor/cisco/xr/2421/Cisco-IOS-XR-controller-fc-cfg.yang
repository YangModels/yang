module Cisco-IOS-XR-controller-fc-cfg {
  namespace "http://cisco.com/ns/yang/Cisco-IOS-XR-controller-fc-cfg";
  prefix controller-fc-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-fc package configuration.
     
     This YANG module augments the
       Cisco-IOS-XR-ifmgr-cfg
     module with configuration data.
     
     Copyright (c) 2013-2022 by Cisco Systems, Inc.
     All rights reserved.";

  revision 2021-06-20 {
    description
      "sf-ber-threshold and sd-ber-threshold config support added";
    semver:module-version "1.0.0";
  }
  revision 2020-03-22 {
    description
      "Fibre Channel controller configurations added";
  }
  revision 2019-04-05 {
    description
      "Establish semantic version baseline.";
  }
  revision 2015-11-09 {
    description
      "IOS XR 6.0 revision.";
  }

  typedef Fibre-chan-prbs-mode {
    type enumeration {
      enum "source" {
        value 1;
        description
          "PRBS source mode";
      }
      enum "sink" {
        value 2;
        description
          "PRBS sink mode";
      }
      enum "source-sink" {
        value 3;
        description
          "PRBS source-sink mode";
      }
    }
    description
      "Fibre chan prbs mode";
  }

  typedef Fibre-chan-prbs-pattern {
    type enumeration {
      enum "pn31" {
        value 1;
        description
          "PRBS pattern pn31";
      }
      enum "pn23" {
        value 2;
        description
          "PRBS pattern pn23";
      }
      enum "pn15" {
        value 3;
        description
          "PRBS pattern pn15";
      }
      enum "pn11" {
        value 4;
        description
          "PRBS pattern pn11";
      }
      enum "pn9" {
        value 5;
        description
          "PRBS pattern pn9";
      }
      enum "pn7" {
        value 6;
        description
          "PRBS pattern pn7";
      }
    }
    description
      "Fibre chan prbs pattern";
  }

  typedef Fibre-channel-fec {
    type enumeration {
      enum "none" {
        value 1;
        description
          "Disable any FEC enabled on the interface";
      }
      enum "standard" {
        value 2;
        description
          "Enable standard FEC";
      }
    }
    description
      "Fibre channel fec";
  }

  typedef Fibre-channel-loopback {
    type enumeration {
      enum "line" {
        value 1;
        description
          "Line loopback";
      }
      enum "internal" {
        value 2;
        description
          "Internal loopback";
      }
    }
    description
      "Fibre channel loopback";
  }

  augment "/a1:interface-configurations/a1:interface-configuration" {
    description
      "This augment extends the configuration data of
       'Cisco-IOS-XR-ifmgr-cfg'";
    container fibre-channel {
      description
        "Fibre Channel specific controller configuration";
      container prbs {
        presence "Indicates a prbs node is configured.";
        description
          "Configure Pseudo Random Binary Sequence";
        leaf prbs-mode {
          type Fibre-chan-prbs-mode;
          mandatory true;
          description
            "PRBS Mode";
        }
        leaf prbs-pattern {
          type Fibre-chan-prbs-pattern;
          mandatory true;
          description
            "PRBS Pattern";
        }
      }
      leaf forward-error-correction {
        type Fibre-channel-fec;
        description
          "Forward Error Correction";
      }
      leaf perf-mon-disable {
        type empty;
        description
          "Configure Performance Monitoring ";
      }
      leaf holdoff-time {
        type uint32 {
          range "0..3000";
        }
        description
          "Configure Holdoff Time";
      }
      leaf signal-failure-ber-threshold {
        type uint32 {
          range "3..9";
        }
        description
          "Configure Signal Failure BER threshold";
      }
      leaf signal-degrade-ber-threshold {
        type uint32 {
          range "6..12";
        }
        description
          "Configure Signal Degrade BER threshold";
      }
      leaf laser-squelch {
        type empty;
        description
          "Configure Laser-Squelch";
      }
      leaf loopback {
        type Fibre-channel-loopback;
        description
          "Configure loopback mode";
      }
    }
  }
}
