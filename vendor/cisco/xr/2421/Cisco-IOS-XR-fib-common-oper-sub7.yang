submodule Cisco-IOS-XR-fib-common-oper-sub7 {
  belongs-to Cisco-IOS-XR-fib-common-oper {
    prefix Cisco-IOS-XR-fib-common-oper;
  }

  import ietf-yang-types {
    prefix yang;
  }
  import cisco-semver {
    prefix semver;
  }
  include Cisco-IOS-XR-fib-common-oper-sub5 {
    revision-date 2024-01-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2024 by Cisco Systems, Inc.
     All rights reserved.";

  revision 2024-01-25 {
    description
      "Increased ECMP/UCMP capability
       2024-01-12
         Add back error/oor state for telemetry in oc-aft-l3 model
       2023-12-01
         Add platform-pbtsv6-support to platform capabilities
       2023-11-29
         Added Nexthop group ID information
       2023-11-27
         Optimized schema for linklocal. Added is-non-recursive field to IP prefixes.
       2023-10-25
         Added GIL ID in PWHE information and Interface List attribute
       2023-10-24
         Consolidated nh-info tables by type
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  grouping FIB-SH-COFO-TBL-ID-PER-SDR {
    description
      "FIB SH COFO TBL ID PER SDR";
    leaf sdrid {
      type uint32;
      description
        "SDR ID";
    }
    leaf num-ofipv4-tables {
      type uint16;
      description
        "Number of Tables for IPv4";
    }
    leaf num-ofipv6-tables {
      type uint16;
      description
        "Number of Tables for IPv6";
    }
    leaf num-ofmpls-tables {
      type uint16;
      description
        "Number of Tables for MPLS";
    }
  }

  grouping FIB-SH-COFO-TBL-ID-DB-SUM {
    description
      "FIB cofo table id summary information";
    leaf number-of-tbl-id-allocated {
      type uint32;
      description
        "Number of Table Id Allocated";
    }
    leaf tbl-id-minimum {
      type uint32;
      description
        "Minimum Table Id in Range";
    }
    leaf tbl-id-maximum {
      type uint32;
      description
        "Maximum Table Id in Range";
    }
    leaf tbl-id-last-allocated {
      type uint32;
      description
        "Last Table Id Allocated";
    }
    leaf tbl-id-default-v4 {
      type uint32;
      description
        "COFO default V4 Table Id";
    }
    leaf tbl-id-default-v6 {
      type uint32;
      description
        "COFO default V6 Table Id";
    }
    leaf number-of-tbl-id-in-gc {
      type uint32;
      description
        "Number of Table Id in Garbage Collection List";
    }
    list per-sdr-stat {
      description
        "Per SDR statistics";
      uses FIB-SH-COFO-TBL-ID-PER-SDR;
    }
  }

  grouping FIB-SH-COFO-TBL-ID-ENTRY-INFO {
    description
      "FIB cofo table id information";
    container object-base {
      description
        "FIB Object Base information";
      uses FIB-SH-FIB-OBJ-BASE;
    }
    leaf sdrid {
      type uint32;
      description
        "SDR ID";
    }
    leaf protocol-type {
      type uint32;
      description
        "FIB Cofo Protocol";
    }
    leaf route-distinguisher {
      type yang:hex-string;
      description
        "Route Distinguisher";
    }
    leaf table-id {
      type uint32;
      description
        "Table ID";
    }
    leaf vrf-name {
      type string;
      description
        "VRF Name";
    }
    leaf table-pointer {
      type uint64;
      description
        "Table Pointer";
    }
  }

  grouping FIB-SH-COFO-IDB-BUNDLE-MEMBER-INFO {
    description
      "FIB SH COFO IDB BUNDLE MEMBER INFO";
    leaf intf-index {
      type uint32;
      description
        "Interface Index";
    }
    leaf unique-id {
      type uint8;
      description
        "Unique Identifier";
    }
    leaf order-num {
      type uint8;
      description
        "Link Order Number";
    }
    leaf weight {
      type uint8;
      description
        "Member Weight";
    }
    leaf pic {
      type uint64;
      description
        "Port Information Context";
    }
  }

  grouping FIB-SH-COFO-IDB-TBL-ENTRY-INFO {
    description
      "FIB cofo idb entry information";
    container object-base {
      description
        "FIB Object Base information";
      uses FIB-SH-FIB-OBJ-BASE;
    }
    leaf sdrid {
      type uint32;
      description
        "SDR ID";
    }
    leaf intf-type {
      type uint32;
      description
        "Interface Type";
    }
    leaf intf-index {
      type uint32;
      description
        "Interface Index";
    }
    leaf intf-state {
      type uint32;
      description
        "Interface State";
    }
    leaf parent-intf-index {
      type uint32;
      description
        "Parent Interface Index";
    }
    leaf parent-intf-type {
      type uint32;
      description
        "Parent Interface Type";
    }
    leaf bundle-member-total-weight {
      type uint16;
      description
        "Bundle Member Interface Total Weight";
    }
    leaf main-pointer {
      type uint64;
      description
        "Main Interface Pointer";
    }
    leaf table-pointer {
      type uint64;
      description
        "Table Pointer";
    }
    leaf hardware-handle {
      type uint64;
      description
        "FIB Cofo Hardware Handle";
    }
    leaf intf-name {
      type string;
      description
        "Interface Name";
    }
    leaf-list pic {
      type uint64;
      description
        "Port Information Context";
    }
    list bundle-member-info {
      description
        "Bundle Member Info";
      uses FIB-SH-COFO-IDB-BUNDLE-MEMBER-INFO;
    }
  }
}
