module Cisco-IOS-XR-sch-types {
  namespace "http://cisco.com/ns/yang/cisco-xr-sch-types";
  prefix sch;

  import cisco-semver {
    prefix semver;
  }

  organization
    "Cisco Systems, Inc.";
  contact
    "Cisco Systems, Inc.
     Postal: 170 W Tasman Drive
     San Jose, CA 95134-1706
     USA
     
     E-mail: terastream-yang-dev@cisco.com";
  description
    "XR CDL specific definitions.
     
     Copyright (c) 2013-2016, 2018-2021, 2023-2024 by Cisco Systems, Inc.
     All rights reserved.";

  revision 2020-05-15 {
    description
      "Added support for NCS5700.";
    semver:module-version "1.0.0";
  }
  revision 2019-04-05 {
    description
      "Establish semantic version baseline.";
    semver:module-version "1.0.0";
  }
  revision 2015-08-06 {
    description
      "Added extenstion for identity str-values and int-values.";
  }
  revision 2013-07-22 {
    description
      "Initial revision.";
  }

  extension bag {
    argument file_name;
    description
      "BAG file name.";
  }

  extension bag-dll {
    argument file_name;
    description
      "BAG DLL file name.";
  }

  extension bag-encoder {
    argument encoder;
    description
      "";
  }

  extension bag-grp-name {
    argument name;
    description
      "";
  }

  extension bag-key {
    description
      "";
  }

  extension bag-list-next {
    argument next;
    description
      "";
  }

  extension bag-name {
    argument name;
    description
      "BAG name.";
  }

  extension bag-path {
    argument path;
    description
      "";
  }

  extension bag-primitive-type {
    argument type;
    description
      "";
  }

  extension bag-version {
    argument version;
    description
      "BAG version.";
  }

  extension bind {
    argument bind;
    description
      "";
  }

  extension compatibility {
    argument version;
    description
      "";
  }

  extension delete-dependent {
    argument dep;
    description
      "";
  }

  extension dependent {
    argument dep;
    description
      "";
  }

  extension exact {
    description
      "";
  }

  extension filterlist {
    argument filter;
    description
      "";
  }

  extension internal-key {
    argument key;
    description
      "";
  }

  extension item {
    description
      "";
  }

  extension pack-elem-size {
    argument size;
    description
      "Size of PACK element (in bytes).";
  }

  extension pack-format {
    argument format;
    description
      "Format string specifying format for each PACK
       element.";
  }

  extension pack-order {
    argument position;
    description
      "Position of element in PACK (in bytes).";
  }

  extension pathformat {
    argument format;
    description
      "Format string specifying format of naming
       attributes of element's SysDB path section.";
  }

  extension scope {
    argument scope;
    description
      "";
  }

  extension struct {
    argument file_name;
    description
      "";
  }

  extension verifier-bgen {
    argument verifier;
    description
      "";
  }

  extension verifier-namespace {
    argument verifier;
    description
      "";
  }

  extension verifyfns-apply {
    argument verifyfns;
    description
      "";
  }

  extension verifyfns-verify {
    argument verifyfns;
    description
      "";
  }

  extension identity-int-value {
    argument identity-int-value;
    description
      "Integer value for identity representation";
  }

  extension identity-str-value {
    argument identity-str-value;
    description
      "String value for identity representation";
  }

  extension xr-cfg-pathname {
    argument pathname;
    description
      "";
  }

  extension xr-oper-pathname {
    argument pathname;
    description
      "";
  }

  extension xr-primitive-type {
    argument type;
    description
      "";
  }

  extension xr-sch-arg-name {
    argument name;
    description
      "";
  }

  extension xr-sch-pathname {
    argument pathname;
    description
      "SysDB path of element.";
  }

  extension xr-sch-type {
    argument type;
    description
      "MDA schema type name.";
  }

  extension xr-task {
    argument task;
    description
      "";
  }

  extension xr-create-item-relative-path {
    argument path;
    description
      "Notion to create / delete enter element on specified
       path.";
  }

  extension xr-presence-packed {
    description
      "Presence container is SysDB packed tuple.";
  }

  extension rpl-func {
    argument function;
    description
      "Function name from lib_rpl.dll.";
  }

  extension xr-default-set {
    description
      "Notion to create / delete default values implicitly";
  }

  extension xr-exec {
    argument exec;
    description
      "Exec API for action yang models";
  }

  extension xr-yang-naming {
    description
      "Indicates that MDA syntax ':yang-naming' is specified.";
  }

  extension non-empty {
    description
      "Indicates that MDA syntax ':yang-naming' is specified.";
  }

  extension xr-create-item-value {
    argument value;
    description
      "Notion to create / delete element with specified value";
  }

  extension xr-create-item-relative-path2 {
    argument path;
    description
      "Notion to create / delete enter element on specified
       path.";
  }

  extension xr-create-item-value2 {
    argument value;
    description
      "Notion to create / delete element with specified value";
  }

  extension xr-create-item-relative-path3 {
    argument path;
    description
      "Notion to create / delete enter element on specified
       path.";
  }

  extension xr-create-item-value3 {
    argument value;
    description
      "Notion to create / delete element with specified value";
  }

  extension xr-create-item-relative-path4 {
    argument path;
    description
      "Notion to create / delete enter element on specified
       path.";
  }

  extension xr-create-item-value4 {
    argument value;
    description
      "Notion to create / delete element with specified value";
  }

  extension xr-create-item-relative-path5 {
    argument path;
    description
      "Notion to create / delete enter element on specified
       path.";
  }

  extension xr-create-item-value5 {
    argument value;
    description
      "Notion to create / delete element with specified value";
  }

  extension xr-create-item-relative-path6 {
    argument path;
    description
      "Notion to create / delete enter element on specified
       path.";
  }

  extension xr-create-item-value6 {
    argument value;
    description
      "Notion to create / delete element with specified value";
  }

  extension xr-create-item-relative-path7 {
    argument path;
    description
      "Notion to create / delete enter element on specified
       path.";
  }

  extension xr-create-item-value7 {
    argument value;
    description
      "Notion to create / delete element with specified value";
  }

  extension xr-create-item-relative-path8 {
    argument path;
    description
      "Notion to create / delete enter element on specified
       path.";
  }

  extension xr-create-item-value8 {
    argument value;
    description
      "Notion to create / delete element with specified value";
  }

  extension xr-create-item-value9 {
    argument value;
    description
      "Notion to create / delete element with specified value";
  }

  extension xr-create-item-relative-path9 {
    argument path;
    description
      "Notion to create / delete enter element on specified
       path.";
  }

  extension xr-create-item-value10 {
    argument value;
    description
      "Notion to create / delete element with specified value";
  }

  extension xr-create-item-relative-path10 {
    argument path;
    description
      "Notion to create / delete enter element on specified
       path.";
  }

  extension xr-create-item-value11 {
    argument value;
    description
      "Notion to create / delete element with specified value";
  }

  extension xr-create-item-relative-path11 {
    argument path;
    description
      "Notion to create / delete enter element on specified
       path.";
  }

  extension xr-create-item-value12 {
    argument value;
    description
      "Notion to create / delete element with specified value";
  }

  extension xr-create-item-relative-path12 {
    argument path;
    description
      "Notion to create / delete enter element on specified
       path.";
  }

  extension xr-create-item-value13 {
    argument value;
    description
      "Notion to create / delete element with specified value";
  }

  extension xr-create-item-relative-path13 {
    argument path;
    description
      "Notion to create / delete enter element on specified
       path.";
  }

  extension xr-create-item-value14 {
    argument value;
    description
      "Notion to create / delete element with specified value";
  }

  extension xr-create-item-relative-path14 {
    argument path;
    description
      "Notion to create / delete enter element on specified
       path.";
  }

  extension xr-create-item-value15 {
    argument value;
    description
      "Notion to create / delete element with specified value";
  }

  extension xr-create-item-relative-path15 {
    argument path;
    description
      "Notion to create / delete enter element on specified
       path.";
  }

  extension xr-create-item-value16 {
    argument value;
    description
      "Notion to create / delete element with specified value";
  }

  extension xr-create-item-relative-path16 {
    argument path;
    description
      "Notion to create / delete enter element on specified
       path.";
  }

  extension xr-create-item-value17 {
    argument value;
    description
      "Notion to create / delete element with specified value";
  }

  extension xr-create-item-relative-path17 {
    argument path;
    description
      "Notion to create / delete enter element on specified
       path.";
  }

  extension xr-create-item-value18 {
    argument value;
    description
      "Notion to create / delete element with specified value";
  }

  extension xr-create-item-relative-path18 {
    argument path;
    description
      "Notion to create / delete enter element on specified
       path.";
  }

  extension xr-create-item-value19 {
    argument value;
    description
      "Notion to create / delete element with specified value";
  }

  extension xr-create-item-relative-path19 {
    argument path;
    description
      "Notion to create / delete enter element on specified
       path.";
  }

  extension xr-create-item-value20 {
    argument value;
    description
      "Notion to create / delete element with specified value";
  }

  extension xr-create-item-relative-path20 {
    argument path;
    description
      "Notion to create / delete enter element on specified
       path.";
  }

  extension xr-create-item-value21 {
    argument value;
    description
      "Notion to create / delete element with specified value";
  }

  extension xr-create-item-relative-path21 {
    argument path;
    description
      "Notion to create / delete enter element on specified
       path.";
  }

  extension xr-default-value {
    argument value;
    description
      "Notion to set the specified value when deleting this node";
  }

  extension xr-platforms {
    argument value;
    description
      "Used within 'feature' statement. A space separated list of platforms that support the feature. Currently these names are recognized: ncs1k, ncs1004, ncs5k, ncs5500, xrv9000, zermatt, ncs540l, ncs5700, ncs1001, ncs560, asr9000, ncs1010, enxr, 8000, xrd-vrouter, xrd-control-plane, other";
  }
}
