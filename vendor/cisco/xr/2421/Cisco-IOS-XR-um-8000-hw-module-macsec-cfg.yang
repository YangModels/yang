module Cisco-IOS-XR-um-8000-hw-module-macsec-cfg {
  namespace "http://cisco.com/ns/yang/Cisco-IOS-XR-um-8000-hw-module-macsec-cfg";
  prefix um-8000-hw-module-macsec-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-hw-module-macsec package configuration.
     
     This YANG module augments the
     modules with configuration data.
     
     Copyright (c) 2023 by Cisco Systems, Inc.
     All rights reserved.";

  revision 2023-09-26 {
    description
      "Initial release";
  }

  container hw-module {
    description
      "Configure h/w module";
    container macsec-mode {
      description
        "Enable macsec-mode";
      container location {
        description
          "Specify a location";
        container all {
          presence "Indicates an all node is configured.";
          description
            "all locations";
        }
        list location-list {
          key "location-name";
          description
            "Location on which this config applies";
          leaf location-name {
            type xr:Node-id;
            description
              "Fully qualified location specification";
          }
        }
      }
    }
    container macsec-fips-post {
      description
        "Enable macsec-fips-post";
      container location {
        description
          "Specify a location";
        container all {
          presence "Indicates an all node is configured.";
          description
            "all locations";
        }
        list location-list {
          key "location-name";
          description
            "Location on which this config applies";
          leaf location-name {
            type xr:Node-id;
            description
              "Fully qualified location specification";
          }
        }
      }
    }
  }
}
