module Cisco-IOS-XR-um-local-mac-cfg {
  namespace "http://cisco.com/ns/yang/Cisco-IOS-XR-um-local-mac-cfg";
  prefix um-local-mac-cfg;

  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR local-mac package configuration.
     
     This YANG module augments the
     modules with configuration data.
     
     Copyright (c) 2022-2023 by Cisco Systems, Inc.
     All rights reserved.";

  revision 2022-05-08 {
    description
      "Initial release";
  }

  feature routing_macaddr_supported {
    description
      "Function to determine if a system wide configurable routing mac address is supported on the platform";
  }

  container hw-module {
    description
      "Configure h/w module";
    container local-mac {
      description
        "Configure local station MAC address";
      leaf address {
        if-feature "routing_macaddr_supported";
        type yang:mac-address;
        description
          "Ethernet MAC address";
      }
    }
  }
}
