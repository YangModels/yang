module Cisco-IOS-XR-l2vpn-oper {
  namespace "http://cisco.com/ns/yang/Cisco-IOS-XR-l2vpn-oper";
  prefix l2vpn-oper;

  import ietf-inet-types {
    prefix inet;
  }
  import ietf-yang-types {
    prefix yang;
  }
  import Cisco-IOS-XR-types {
    prefix xr;
  }
  import cisco-semver {
    prefix semver;
  }
  include Cisco-IOS-XR-l2vpn-oper-sub4 {
    revision-date 2024-03-01;
  }
  include Cisco-IOS-XR-l2vpn-oper-sub3 {
    revision-date 2024-03-01;
  }
  include Cisco-IOS-XR-l2vpn-oper-sub2 {
    revision-date 2024-03-01;
  }
  include Cisco-IOS-XR-l2vpn-oper-sub1 {
    revision-date 2024-03-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2vpn package operational data.
     
     This module contains definitions
     for the following management objects:
       l2vpn-forwarding: Show L2VPN forwarding
       l2vpnv2: L2VPN operational data to support active and standby.
         L2VPN has been deprecated
       ea-pwhe: EA PWHE operational data
     
     Copyright (c) 2013-2024 by Cisco Systems, Inc.
     All rights reserved.";

  revision 2024-03-01 {
    description
      "- Add IPMAC Learning is-immutable, is-nd-override and is-nd-router
       2024-01-25
         - Added evi-bd-count to summary
       2024-01-11
         - Add EVPN IPMAC is-immutable, is-nd-override and is-nd-router
       2023-11-10
         - Add support for pseudowires with XCID as PW ID
       2023-11-08
         - Added PD mac-address details
       2023-10-31
         - Add reroute-label to EVPN ports in l2vpn-forwarding
       2023-10-11
         - Add EVPN IPMAC is-best and is-latest
       2023-10-07
         - Add EVPN IPMAC bp-interface and xcid
       2023-10-02
         - Add replication-type to l2fib-evpn-incl-mcast-leaf-info
       2023-10-01
         - Added new internal service group app enum entry to l2vpn_id_mgr_app_bag_type
       2023-09-30
         - Add dynamic flow-label to EVPN Instance
       2023-06-17
         - Renamed master-context to primary-context - Renamed slave-context to secondary-context - Renamed master-time to primary-time
       2023-06-16
         - Added to stale-xid-modified to l2fib-mroute-summary.
       2023-06-01
         - Added modules-registered-for-issu-phase to nsr and proc-fsm information
       2023-05-09
         - Added no-child-vc and no-child-vc-up EVPN Down reasons - Increased the value of evpn-down-reason-max
       2023-04-28
         - Updated l2vpn-pw to hold vlan-aware-vc-up-count and vlan-aware-vc-down-count
       2023-04-26
         - Restructure EVPN path lists into an l2vpn-label-path-buffer container
       2023-03-27
         - Remove reference-count from mstp-port and main-interface-info
       2023-03-10
         - Remove iflist related items.
       2023-02-28
         - Remove pw-oam-refresh-transmit-time from l2vpn-globals
       2023-02-10
         - Add more states to l2fib-evpn-ip4mac and l2fib-evpn-ip6mac, remove arp-nd-delete-pending.
       2023-02-02
         - Change generic-interface-list to conform to new model.
       2023-02-01
         - Added EMOI ipv6-mapping-key and is-sh - Updated EMOI moi-type enum names
       2022-12-22
         - Added Promoted Backup EVPN DF Role.
       2022-12-09
         - Added pseudowire-headend under standby and node containers.
       2022-12-06
         - Added static L2 service vni mode.
       2022-11-29
         - Restructured remote-split-horizon-group-labels with an esi-id specific to encap-type.
       2022-11-19
         - Added LTEP NHOP support.
       2022-10-19
         - Deprecated logging NSR config
       2022-09-28
         - Added Global ID for PWHE IDBs.
       2022-09-14
         - Added evpn-esi-id for bridge port.
       2022-09-12
         - Added Attachment-Circuit to IP Tunnel cross-connect type.
       2022-09-07
         - Added ac-extra-id to attachment-circuit
       2022-09-07
         - Added IPv6 fields to VNI info - Added EVPN Peer ES down - Added internal-id to EVPN MOI context
       2022-09-01
         - Added internal-id to pseudowire-headend detail-interface
       2022-08-30
         - l2fib-summary: Added VXLAN nexthop information
       2022-08-09
         - Added L2VPN-VXLAN-TUNNEL grouping. - Added vxlan-tunnel container to L2VPN-SEGMENT grouping.
       2022-08-08
         - Added ESI ID for used in ESI filtering
       2022-07-06
         - Added new ID MGR App type for Auto RD per EVI
       2022-06-24
         - Update format of l2fib-message-summary
       2022-06-06
         - l2fib-evpn-incl-mcast-ole: Removed SRv6 SID format and added VNI ID to naming
       2022-05-30
         - Added a new leaf mac-limit-enabled to L2VPN-BRIDGE-SEC-PARAM.
       2022-05-26
         Refactored ES Service Carving Arrays
       2022-05-03
         - Added mac-limit-enabled - Removed duplicate fields
       2022-04-14
         - Add new APP type in IDMGR
       2022-03-21
         - Removed legacy and override ESI types
       2022-03-14
         - Added new members to main-interface-info protect-type
       2022-03-09
         - l2fib-mroute-port: Added hardware-information leaf.
       2022-03-08
         - Add EVPN unicast-label and multicast-label.
       2022-02-24
         - l2fib-mroute-port: Added pin-down-interface-name leaf.
       2022-02-09
         - Added l2fib-l3-sync-interfaces - Update keys of l2fib-mroute-port - Add l2fib-evpn-etree-remote - Update keys of l2fib-evpn-incl-mcast-ole - Add l2fib-mroute-ipv6-summary - Only expose valid keys and members of l2fib-mac-learning-mac, l2fib-mac-learning-mac-ipv4, and l2fib-mac-learning-mac-ipv6";
    semver:module-version "6.0.0";
  }
  revision 2021-09-07 {
    description
      "- Added SRv6 nhop
       2021-08-24
          Updated l2vpn forwarding adjacencies to expose both interface and address information.
       2021-08-13
          - Changed flag-extension to 32bit
       2021-07-20
          - Added support for MAC is-cfm flag";
    semver:module-version "5.0.0";
  }
  revision 2020-05-05 {
    description
      "changes related to treat SRv6 and SID as well-known when parsing XML for yang";
    semver:module-version "4.0.0";
  }
  revision 2020-04-28 {
    description
      "- AC Backup related changes
       2020-01-22
       - PWGROUP related changes
       2019-12-20
       - EVPN-VPWS related changes - SR-TE policy related changes";
    semver:module-version "3.0.0";
  }
  revision 2019-04-05 {
    description
      "Establish semantic version baseline.";
    semver:module-version "2.0.0";
  }
  revision 2019-03-30 {
    description
      "- Rename l2fib-mac-learning-mac* interface-handle to interface-name - Rename l2fib-pw-group tunnel-if-handle to tunnel-interface-name - Convert several array from leaf-list to list syntax. - Implement range datatypes for all L2FIB integers.";
  }
  revision 2018-08-01 {
    description
      "Removed empty groupings.";
  }
  revision 2017-09-07 {
    description
      "Fixed type translation error.";
  }
  revision 2017-06-26 {
    description
      "Change identifiers to be more readable.";
  }
  revision 2017-05-01 {
    description
      "Fixing backward compatibility error in module.";
  }
  revision 2015-11-09 {
    description
      "IOS XR 6.0 revision.";
  }

  typedef L2tpv2-session-id-range {
    type uint32 {
      range "0..65535";
    }
    description
      "L2tpv2 session id range";
  }

  typedef Msti-range {
    type uint32 {
      range "0..1004";
    }
    description
      "Msti range";
  }

  typedef G8032-ring-instance-range {
    type uint32 {
      range "0..4294967295";
    }
    description
      "G8032 ring instance range";
  }

  typedef Main-interface-id-range {
    type uint32 {
      range "0..4294967295";
    }
    description
      "Main interface id range";
  }

  typedef L2vpn-service {
    type enumeration {
      enum "vpws" {
        value 0;
        description
          "VPWS service";
      }
      enum "vpls" {
        value 1;
        description
          "VPLS service";
      }
    }
    description
      "L2vpn service";
  }

  typedef Bridge-id-range {
    type uint32 {
      range "0..262144";
    }
    description
      "Bridge id range";
  }

  typedef L2fib-evpn-xid {
    type enumeration {
      enum "none" {
        value 0;
        description
          "Not an EVPN XID";
      }
      enum "evpn-xid" {
        value 16384;
        description
          "EVPN XID BUM MOI ID type";
      }
      enum "evpn-moi-id" {
        value 32768;
        description
          "EVPN XID to MOI ID type";
      }
    }
    description
      "L2fib evpn xid";
  }

  typedef Lsm-id-range {
    type uint32 {
      range "1..1048574";
    }
    description
      "Lsm id range";
  }

  typedef P2mp-id-range {
    type uint32 {
      range "0..4294967295";
    }
    description
      "P2mp id range";
  }

  typedef Tunnel-id-range {
    type uint32 {
      range "0..65535";
    }
    description
      "Tunnel id range";
  }

  typedef L2tpv3-session-id-range {
    type uint32 {
      range "0..4294967295";
    }
    description
      "L2tpv3 session id range";
  }

  typedef Preferred-path-option {
    type enumeration {
      enum "te-tunnel" {
        value 2;
        description
          "TE Tunnel";
      }
      enum "ip-tunnel" {
        value 3;
        description
          "IP Tunnel";
      }
      enum "tp-tunnel" {
        value 4;
        description
          "Deprecated in 7.10.1";
      }
      enum "sr-te-policy" {
        value 5;
        description
          "SR TE Policy";
      }
      enum "mldp-tunnel" {
        value 6;
        description
          "mLDP Tunnel";
      }
      enum "mte-tunnel" {
        value 7;
        description
          "mTE Tunnel";
      }
      enum "named-te-tunnel" {
        value 8;
        description
          "Named TE Tunnel";
      }
    }
    description
      "Preferred path option";
  }

  typedef Evpn-main-interface {
    type enumeration {
      enum "evpn-main-interface-ac" {
        value 1;
        description
          "EVPN main interface type AC";
      }
      enum "evpn-main-interface-nve" {
        value 2;
        description
          "EVPN main interface type NVE";
      }
      enum "evpn-main-interface-ac-vfi" {
        value 3;
        description
          "EVPN main interface type AC VFI";
      }
      enum "evpn-main-interface-ac-pw" {
        value 4;
        description
          "EVPN main interface type AC PW";
      }
    }
    description
      "Evpn main interface";
  }

  typedef L2fib-evpn-incl-mcast-ole-key {
    type enumeration {
      enum "label" {
        value 0;
        description
          "Label key type";
      }
      enum "srv6" {
        value 1;
        description
          "SRv6 key type";
      }
      enum "vni" {
        value 2;
        description
          "VNI key type";
      }
    }
    description
      "L2fib evpn incl mcast ole key";
  }

  typedef L2fib-next-hop-key {
    type enumeration {
      enum "nexthop-ipv4" {
        value 1;
        description
          "IPv4 Nexthop type";
      }
      enum "nexthop-mpls-internal-label" {
        value 2;
        description
          "MPLS Internal-Label Nexthop type";
      }
      enum "nexthop-ipv6" {
        value 3;
        description
          "IPv6 Nexthop type";
      }
      enum "nexthop-vx-lan-internal-label" {
        value 4;
        description
          "Vxlan Internal-Label Nexthop type";
      }
      enum "nexthop-sr-te-bsid" {
        value 5;
        description
          "SR-TE BindingSID Nexthop type";
      }
      enum "nexthop-te-tunnel" {
        value 6;
        description
          "TE Tunnel Nexthop type";
      }
      enum "nexthop-lsm-id" {
        value 7;
        description
          "LSM ID Nexthop type";
      }
      enum "nexthop-iid" {
        value 8;
        description
          "Internal-ID Nexthop type";
      }
    }
    description
      "L2fib next hop key";
  }

  typedef Pw-group-id-range {
    type uint32 {
      range "0..4294967295";
    }
    description
      "Pw group id range";
  }

  typedef L2vpnp2mp-ptree {
    type enumeration {
      enum "rsvp-te" {
        value 1;
        description
          "RSVPTE Type";
      }
      enum "mldp" {
        value 2;
        description
          "MLDP Type";
      }
    }
    description
      "L2vpnp2mp ptree";
  }

  typedef Rib-iid-range {
    type uint32 {
      range "0..4294967295";
    }
    description
      "Rib iid range";
  }

  typedef L2vpnpw {
    type enumeration {
      enum "manual" {
        value 1;
        description
          "Manual pseudowire";
      }
      enum "vpls-autodiscovered" {
        value 2;
        description
          "VPLS autodiscovered pseudowire";
      }
      enum "vpws-autodiscovered" {
        value 3;
        description
          "VPWS autodiscovered pseudowire";
      }
      enum "vpls-autodiscovered-ldp" {
        value 4;
        description
          "VPLS autodiscovered pseudowire with LDP
           signaling";
      }
    }
    description
      "L2vpnpw";
  }

  grouping SRTE-POLICY-TABLE {
    description
      "Common node of active, standby, node";
    container srte-policies {
      description
        "SRTE Policy Table";
      list srte-policy {
        description
          "SRTE Policy information";
        leaf color {
          type uint32;
          description
            "Policy Color";
        }
        leaf endpoint {
          type inet:ip-address-no-zone;
          description
            "Policy Endpoint IP Address";
        }
        uses L2VPN-SRTE-POLICY;
      }
    }
  }

  grouping FLEXIBLE-XCONNECT-SERVICE-TABLE {
    description
      "Common node of active, standby, node";
    container flexible-xconnect-services {
      description
        "Flexible XConnect Service Table";
      list flexible-xconnect-service {
        key "name";
        description
          "Flexible XConnect Service Information";
        container flexible-xconnect-service-acs {
          description
            "Flexible XConnect Service Attachment Circuit
             Table";
          list flexible-xconnect-service-ac {
            key "interface-name";
            description
              "Flexible XConnect Service Attachment Circuit";
            leaf interface-name {
              type xr:Interface-name;
              description
                "Interface Name";
            }
            uses L2VPN-FXC-AC;
          }
        }
        container flexible-xconnect-service-info {
          description
            "Flexible XConnect Service Information";
          uses L2VPN-FXC;
        }
        leaf name {
          type xr:Cisco-ios-xr-string {
            length "1..23";
          }
          description
            "Flexible XConnect Service Name";
        }
      }
    }
  }

  grouping XCONNECT-MP2MP-TABLE {
    description
      "Common node of active, standby, node";
    container xconnect-mp2mps {
      description
        "XConnect MP2MP Table";
      list xconnect-mp2mp {
        key "group-name mp2-mp-name";
        description
          "XConnect MP2MP information";
        leaf group-name {
          type xr:Cisco-ios-xr-string {
            length "1..32";
          }
          description
            "XConnect Group";
        }
        leaf mp2-mp-name {
          type xr:Cisco-ios-xr-string {
            length "1..26";
          }
          description
            "Mp2Mp Name";
        }
        uses L2VPN-MP2MP-XC;
      }
    }
  }

  grouping FLEXIBLE-XCONNECT-SERVICE-SUMMARY {
    description
      "Common node of active, standby, node";
    container flexible-xconnect-service-summary {
      description
        "Flexible XConnect Service summary information";
      uses L2VPN-FXC-SUMMARY;
    }
  }

  grouping DISCOVERY-SUMMARY {
    description
      "Common node of active, standby, node";
    container discovery-summary {
      description
        "Discovery summary information";
      uses L2VPN-DISCO-SUMMARY;
    }
  }

  grouping XCONNECT-GROUP-TABLE {
    description
      "Common node of active, standby, node";
    container xconnect-groups {
      description
        "XConnect group Table";
      list xconnect-group {
        key "group-name";
        description
          "XConnect group information";
        leaf group-name {
          type xr:Cisco-ios-xr-string {
            length "1..32";
          }
          description
            "XConnect Group";
        }
        uses L2VPN-GROUP;
      }
    }
  }

  grouping MSTP-PORT-TABLE {
    description
      "Common node of active, standby, node";
    container mstp-ports {
      description
        "L2VPN MSTP Port Table";
      list mstp-port {
        key "interface";
        description
          "MSTP Port information";
        leaf interface {
          type xr:Interface-name;
          description
            "Interface";
        }
        uses L2VPN-MSTP-PORT;
      }
    }
  }

  grouping PWR {
    description
      "Common node of active, standby, node";
    container pwr {
      description
        "Pseudowire Routing Table";
      container summary {
        description
          "L2VPN Pseudowire Routing Summary";
        uses L2VPN-ATOM-PWR-SUMMARY;
      }
    }
  }

  grouping MAIN-INTERFACE-TABLE {
    description
      "Common node of active, standby, node";
    container main-interfaces {
      description
        "Main Interface";
      list main-interface {
        key "interface-name";
        description
          "Main Interface Table";
        container main-interface-instances {
          description
            "Main Interface Instance table";
          list main-interface-instance {
            key "instance";
            description
              "Main Interface Instance";
            container main-interface-instance-info {
              description
                "Main Interface Instance info";
              uses L2VPN-MAIN-INTERFACE-INSTANCE;
            }
            container main-interface-instance-bridge-ports {
              description
                "Main Interface Instance Bridge Port table";
              list main-interface-instance-bridge-port {
                key "bridge-port";
                description
                  "Main Interface Bridge Port info";
                leaf bridge-port {
                  type xr:Interface-name;
                  description
                    "Bridge Port";
                }
                uses L2VPN-MAIN-INTERFACE-INSTANCE-BPORT;
              }
            }
            leaf instance {
              type Msti-range;
              description
                "Instance";
            }
          }
        }
        container main-interface-info {
          description
            "Main Interface info";
          uses L2VPN-MAIN-INTERFACE;
        }
        leaf interface-name {
          type xr:Interface-name;
          description
            "Main interface";
        }
      }
    }
  }

  grouping PREFERRED-PATH-TABLE {
    description
      "Common node of active, standby, node";
    container preferred-paths {
      description
        "Preferred path Table";
      list preferred-path {
        description
          "Preferred path information";
        leaf preferred-type {
          type Preferred-path-option;
          description
            "Preferred type";
        }
        leaf interface-name {
          type xr:Interface-name;
          description
            "Main interface";
        }
        uses L2VPN-PREFERRED-PATH;
      }
    }
  }

  grouping DISCOVERY-TABLE {
    description
      "Common node of active, standby, node";
    container discoveries {
      description
        "Discovery Table";
      list discovery {
        description
          "VPLS Discovery information";
        leaf service-name {
          type L2vpn-service;
          description
            "Service type";
        }
        leaf group-name {
          type xr:Cisco-ios-xr-string {
            length "1..32";
          }
          description
            "Group Name";
        }
        leaf vpn-name {
          type xr:Cisco-ios-xr-string {
            length "1..27";
          }
          description
            "VPN Name";
        }
        uses L2VPN-DISCO;
      }
    }
  }

  grouping XCONNECT-BRIEF {
    description
      "Common node of active, standby, node";
    container xconnect-brief {
      description
        "XConnect brief information";
      uses L2VPN-XC-BRIEF;
    }
  }

  grouping L2FIB-EVPN-INCL-MCAST-LEAF-INFO {
    description
      "Common node of l2fib-evpn-incl-mcast-leaf,
       l2fib-evpn-incl-mcast-leaf-hardware-ingress,
       l2fib-evpn-incl-mcast-leaf-hardware-egress";
    container l2fib-evpn-incl-mcast-leaf-info {
      description
        "L2FIB EVPN inclusive multicast leaf information";
      uses L2FIB-EVPN-MCAST-LEAF-INFO;
    }
  }

  grouping G8032 {
    description
      "Common node of active, standby, node";
    container g8032 {
      description
        "G8032 information";
      container g8032-rings {
        description
          "G8032 Ring table";
        list g8032-ring {
          key "ring-name";
          description
            "G8032 Ring";
          container g8032-ring-detail {
            description
              "G8032 Ring detailed information";
            uses L2VPN-G8032-RING-DETAIL-INFO;
          }
          container g8032-ring-instance-summaries {
            description
              "G8032 Ring Instance summary table";
            list g8032-ring-instance-summary {
              key "instance";
              description
                "G8032 Ring Instance summary information";
              leaf instance {
                type uint32;
                description
                  "Instance";
              }
              uses L2VPN-G8032-RING-INSTANCE-SUMMARY-INFO;
            }
          }
          container g8032-ring-summary {
            description
              "G8032 Ring summary information";
            uses L2VPN-G8032-RING-SUMMARY-INFO;
          }
          container g8032-ring-instance-details {
            description
              "G8032 Ring Instance detail table";
            list g8032-ring-instance-detail {
              key "instance";
              description
                "G8032 Ring Instance detailed information";
              leaf instance {
                type G8032-ring-instance-range;
                description
                  "Instance";
              }
              uses L2VPN-G8032-RING-INSTANCE-DETAIL-INFO;
            }
          }
          leaf ring-name {
            type xr:Cisco-ios-xr-string {
              length "1..32";
            }
            description
              "Ring Name";
          }
        }
      }
    }
  }

  grouping XCONNECT-SUMMARY {
    description
      "Common node of active, standby, node";
    container xconnect-summary {
      description
        "XConnect summary information";
      uses L2VPN-XC-SUMMARY;
    }
  }

  grouping L2VPN-COLLABORATORS {
    description
      "Common node of active, standby, node";
    container l2vpn-collaborators {
      description
        "L2VPN collaborator information";
      uses L2VPN-GLOBAL-INFO;
    }
  }

  grouping L2VPN-CACDB {
    description
      "Common node of active, standby, node";
    container policy-names {
      description
        "L2VPN CAC-DB";
      list policy-name {
        key "policy-name";
        description
          "Policy Name";
        leaf policy-name {
          type xr:Cisco-ios-xr-string;
          description
            "Name of the policy";
        }
        uses L2VPN-CAC-DB;
      }
    }
  }

  grouping PROC-FSM {
    description
      "Common node of active, standby, nodeCommon node
       of active, standby, node";
    container proc-fsm {
      description
        "L2VPN Process FSM information";
      uses L2VPN-MGMT-PROC-FSM;
    }
  }

  grouping BRIDGE-PW-TABLE {
    description
      "Common node of bridge-core-vfi-table,
       bridge-access-vfi-table";
    container bridge-pws {
      description
        "Bridge Domain Access/Core Pseudowire Table";
      list bridge-pw {
        description
          "Bridge Domain Pseudowire";
        leaf neighbor {
          type inet:ipv4-address-no-zone;
          description
            "Neighbor IPv4 address";
        }
        leaf pw-type {
          type L2vpnpw;
          description
            "PW Type";
        }
        leaf pseudowire-id {
          type uint32 {
            range "1..4294967295";
          }
          description
            "Pseudowire ID";
        }
        leaf ve-id-vpls-id-0-3 {
          type uint32 {
            range "0..4294967295";
          }
          description
            "Zero or concatenation of local and remote
             VE-ID or first 4 bytes of VPLS-ID";
        }
        leaf vpls-id-4-7 {
          type uint32 {
            range "0..4294967295";
          }
          description
            "Zero or Last 4 bytes of VPLS-ID";
        }
        uses L2VPN-BD-PW;
      }
    }
  }

  grouping GLOBAL-SETTINGS {
    description
      "Common node of active, standby, node";
    container global-settings {
      description
        "L2VPN global settings";
      uses L2VPN-GLOBALS;
    }
  }

  grouping L2FIB-EVPN-INCL-MCAST-OLE-TABLE {
    description
      "Common node of l2fib-evpn-incl-mcast-leaf,
       l2fib-evpn-incl-mcast-leaf-hardware-ingress,
       l2fib-evpn-incl-mcast-leaf-hardware-egress";
    container l2fib-evpn-incl-mcast-oles {
      description
        "L2FIB EVPN inclusive multicast output list
         element table";
      list l2fib-evpn-incl-mcast-ole {
        description
          "L2FIB EVPN inclusive multicast output list
           element";
        leaf key-type {
          type L2fib-evpn-incl-mcast-ole-key;
          description
            "Key type";
        }
        leaf moi-id {
          type uint32;
          description
            "MOI ID";
        }
        leaf srv6-sid {
          type inet:ip-address-no-zone;
          description
            "SRv6 SID";
        }
        leaf label {
          type uint32 {
            range "0..1048575";
          }
          description
            "Label";
        }
        leaf vniid {
          type xr:Hex-integer;
          description
            "VNI ID";
        }
        uses L2FIB-EVPN-MCAST-OLE-INFO;
      }
    }
  }

  grouping BRIDGE-SUMMARY {
    description
      "Common node of active, standby, node";
    container bridge-summary {
      description
        "Bridge Domain summary information";
      uses L2VPN-BRIDGE-SUMMARY;
    }
  }

  grouping XCONNECT-MP2MP-CE2CE-TABLE {
    description
      "Common node of active, standby, node";
    container xconnect-mp2mp-ce2ces {
      description
        "XConnect MP2MP CE2CE Table";
      list xconnect-mp2mp-ce2ce {
        description
          "XConnect MP2MP CE2CE information";
        leaf group-name {
          type xr:Cisco-ios-xr-string {
            length "1..32";
          }
          description
            "XConnect Group";
        }
        leaf mp2-mp-name {
          type xr:Cisco-ios-xr-string {
            length "1..26";
          }
          description
            "Mp2Mp Name";
        }
        leaf local-ceid {
          type uint32 {
            range "1..4294967295";
          }
          description
            "Local CE ID";
        }
        leaf remote-ceid {
          type uint32 {
            range "1..4294967295";
          }
          description
            "Remote CE ID";
        }
        uses L2VPN-XC;
      }
    }
  }

  grouping L2VPN-OPER-L2VPN-RESOURCE-STATE-MP {
    description
      "Common node of active, standby, node";
    container l2vpn-resource-state {
      description
        "L2VPN resource state information";
      uses L2VPN-RESOURCE-STATE;
    }
  }

  grouping MSTP-VLAN-TABLE {
    description
      "Common node of active, standby, node";
    container mstp-vlans {
      description
        "L2VPN MSTP VLAN Table";
      list mstp-vlan {
        key "vlan-id";
        description
          "L2VPN MSTP VLAN information";
        leaf vlan-id {
          type uint32 {
            range "0..4098";
          }
          description
            "vlan id";
        }
        uses L2VPN-MSTP-VLAN;
      }
    }
  }

  grouping XCONNECT-TABLE {
    description
      "Common node of active, standby, node";
    container xconnects {
      description
        "XConnect Table";
      list xconnect {
        key "group-name xconnect-name";
        description
          "XConnect information";
        leaf group-name {
          type xr:Cisco-ios-xr-string {
            length "1..32";
          }
          description
            "XConnect Group";
        }
        leaf xconnect-name {
          type string {
            length "1..38";
          }
          description
            "XConnect Name";
        }
        uses L2VPN-XC;
      }
    }
  }

  grouping L2VPN-PBB-BSA {
    description
      "Common node of active, standby, node";
    container l2vpn-pbb-bsa {
      description
        "L2VPN PBB Backbone Source MAC information";
      uses L2VPN-PBB-BMAC-SA;
    }
  }

  grouping BRIDGE-DOMAIN-TABLE {
    description
      "Common node of active, standby, node";
    container bridge-domains {
      description
        "Bridge Domain Information";
      list bridge-domain {
        key "bridge-domain-group-name bridge-domain-name";
        description
          "Bridge Domain Information";
        container bridge-access-vfi-table {
          description
            "Bridge Domain Access VFI Table";
          uses BRIDGE-PW-TABLE;
        }
        container bridge-core-vfi-table {
          description
            "Bridge Domain Core VFI Table";
          uses BRIDGE-PW-TABLE;
        }
        container bridge-acs {
          description
            "Bridge Domain Attachment Circuit Table";
          list bridge-ac {
            key "interface-name";
            description
              "Bridge Domain Attachment Circuit";
            leaf interface-name {
              type xr:Interface-name;
              description
                "Interface Name";
            }
            uses L2VPN-BD-AC;
          }
        }
        container bridge-access-pws {
          description
            "Bridge Domain Access Pseudowire Table";
          list bridge-access-pw {
            description
              "Bridge Domain Access Pseudowire";
            leaf neighbor {
              type inet:ipv4-address-no-zone;
              description
                "Neighbor IPv4 address";
            }
            leaf pw-type {
              type L2vpnpw;
              description
                "PW Type";
            }
            leaf pseudowire-id {
              type uint32 {
                range "1..4294967295";
              }
              description
                "Pseudowire ID";
            }
            leaf ve-id-vpls-id-0-3 {
              type uint32 {
                range "0..4294967295";
              }
              description
                "Zero or concatenation of local and remote
                 VE-ID or first 4 bytes of VPLS-ID";
            }
            leaf vpls-id-4-7 {
              type uint32 {
                range "0..4294967295";
              }
              description
                "Zero or Last 4 bytes of VPLS-ID";
            }
            uses L2VPN-BD-PW;
          }
        }
        container bridge-domain-info {
          description
            "Bridge Domain Information";
          uses L2VPN-BRIDGE;
        }
        leaf bridge-domain-group-name {
          type xr:Cisco-ios-xr-string {
            length "1..32";
          }
          description
            "Bridge Domain Group Name";
        }
        leaf bridge-domain-name {
          type xr:Cisco-ios-xr-string {
            length "1..27";
          }
          description
            "Bridge Domain Name";
        }
      }
    }
  }

  grouping ICCP-SM {
    description
      "Common node of active, standby, node";
    container iccp-sm {
      description
        "ICCP-based Service Multi-homing operational data";
      container iccp-sm-summary {
        description
          "ICCP-based Service Multi-homing database
           summary";
        uses ICCP-SM-SUMMARY;
      }
      container iccp-groups {
        description
          "ICCP Group Table";
        list iccp-group {
          key "group-id";
          description
            "ICCP Group";
          container iccp-group-info {
            description
              "ICCP Group Information";
            uses ICCP-SM-GROUP;
          }
          container iccp-ports {
            description
              "ICCP Port Table";
            list iccp-port {
              key "interface";
              description
                "ICCP Port";
              leaf interface {
                type xr:Interface-name;
                description
                  "Interface";
              }
              uses ICCP-SM-PORT;
            }
          }
          leaf group-id {
            type uint32 {
              range "1..4294967295";
            }
            description
              "Group ID";
          }
        }
      }
    }
  }

  grouping INDEX-TABLE {
    description
      "Common node of active, standby, node";
    container indexes {
      description
        "ID Manager Index Table";
      list index {
        key "pool-id";
        description
          "ID Manager Index Pool";
        leaf pool-id {
          type xr:Hex-integer;
          description
            "Pool ID";
        }
        uses L2VPN-INDEX-INFO;
      }
    }
  }

  grouping NSR {
    description
      "Common node of active, standby, node";
    container nsr {
      description
        "L2VPN NSR information";
      uses L2VPN-MGMT-PROC-FSM;
    }
  }

  grouping PSEUDOWIRE-CLASS-TABLE {
    description
      "Common node of active, standby, node";
    container pseudowire-classes {
      description
        "List of pseudowire classes";
      list pseudowire-class {
        key "pseudowire-class-name";
        description
          "Pseudowire class information";
        leaf pseudowire-class-name {
          type xr:Cisco-ios-xr-string {
            length "1..32";
          }
          description
            "Pseudowire Class Name";
        }
        uses L2VPN-PW-CLASS;
      }
    }
  }

  grouping PSEUDOWIRE-HEADEND {
    description
      "Common node of active, standby, node";
    container pseudowire-headend {
      description
        "Pseudowire Headend related operational data";
      container detail-interfaces {
        description
          "PW-HE Interfaces";
        list detail-interface {
          key "interface-name";
          description
            "PW-HE Interface detail";
          leaf interface-name {
            type xr:Interface-name;
            description
              "PWHE Interface name";
          }
          uses L2VPN-PWHE-DETAIL;
        }
      }
      container summary {
        description
          "PW-HE interface summary";
        uses L2VPN-PWHE-SUMMARY;
      }
    }
  }

  grouping MVRP {
    description
      "Common node of active, standby, node";
    container mvrp {
      description
        "MVRP";
      container mvrp-main-ports {
        description
          "MVRP Main Port Table";
        list mvrp-main-port {
          key "main-port-interface-name";
          description
            "MVRP Main Port";
          container mvrp-main-port-info {
            description
              "MVRP Main Port Information";
            uses L2VPN-MVRP;
          }
          container mvrp-bridge-ports {
            description
              "MVRP Bridge Port Table";
            list mvrp-bridge-port {
              key "interface-name";
              description
                "MVRP Bridge Port Information";
              leaf interface-name {
                type xr:Interface-name;
                description
                  "Bridge Port Interface Name";
              }
              uses L2VPN-MVRP-BP;
            }
          }
          leaf main-port-interface-name {
            type xr:Interface-name;
            description
              "Main Port interface";
          }
        }
      }
    }
  }

  container l2vpn-forwarding {
    config false;
    description
      "Show L2VPN forwarding";
    container nodes {
      description
        "Per node L2VPN forwarding Operational data";
      list node {
        key "node-id";
        description
          "The L2VPN forwarding Operational data for a
           particular node";
        container l2fibx-con-locals {
          description
            "The L2VPN forwarding Local LC XConnect Detail
             Table";
          list l2fibx-con-local {
            description
              "Specify Sub Ifh";
            leaf interface-name {
              type xr:Interface-name;
              description
                "Interface Name";
            }
            leaf vsp-vlan-id {
              type uint32 {
                range "0..4094";
              }
              description
                "VLAN-Switched Port VLAN ID";
            }
            uses L2FIB-XCON-INFO;
          }
        }
        container l2fib-evpn-e-tree-remotes {
          description
            "EVPN ETREE Remote Information Table";
          list l2fib-evpn-e-tree-remote {
            key "next-hop-address";
            description
              "EVPN ETREE Remote Information";
            leaf next-hop-address {
              type inet:ip-address-no-zone;
              description
                "NHOP Address";
            }
            uses L2FIB-EVPN-REMOTE-SHG-INFO;
          }
        }
        container l2fib-mroute-summaries {
          description
            "Mroute Summary Table";
          list l2fib-mroute-summary {
            description
              "Multicast Summary Information";
            leaf bd-group-name {
              type xr:Cisco-ios-xr-string {
                length "1..32";
              }
              description
                "Bridge Group Name";
            }
            leaf bd-name {
              type xr:Cisco-ios-xr-string {
                length "1..65";
              }
              description
                "Bridge Domain Name";
            }
            uses L2FIB-MCAST-SUMMARY-INFO;
          }
        }
        container l2fib-message-summary {
          description
            "L2FIB Message Summary information";
          uses L2FIB-EXT-MSG-SUMMARY-INFO;
        }
        container l2fib-mroutes {
          description
            "multicast information";
          list l2fib-mroute {
            description
              "Bridge Domain Multicast Information";
            leaf bd-name {
              type xr:Cisco-ios-xr-string {
                length "1..65";
              }
              description
                "Bridge Domain Name";
            }
            leaf source {
              type inet:ipv4-address-no-zone;
              description
                "Source IP Address";
            }
            leaf group {
              type inet:ipv4-address-no-zone;
              description
                "Group IP Address";
            }
            uses L2FIB-MCAST-LEAF-INFO;
          }
        }
        container pbb-bmac-sa {
          description
            "PBB Backbone Source MAC information";
          uses L2FIB-PBB-BMAC-SA-INFO;
        }
        container l2fib-mac-learning {
          description
            "The L2VPN forwarding Mac Learning Data";
          container l2fib-mac-learning-macs {
            description
              "The L2VPN forwarding All Mac Learning Table";
            list l2fib-mac-learning-mac {
              description
                "The attributes for a particular learned Mac
                 Route";
              leaf bdid {
                type Bridge-id-range;
                description
                  "BD ID";
              }
              leaf mac-address {
                type yang:mac-address;
                description
                  "MAC Address";
              }
              uses L2FIB-MAC-DB-INFO;
            }
          }
          container l2fib-mac-learning-mac-ipv4s {
            description
              "The L2VPN forwarding Mac IPV4 Learning Table";
            list l2fib-mac-learning-mac-ipv4 {
              description
                "The attributes for a particular learned IPV4
                 Mac Route";
              leaf interface-name {
                type xr:Interface-name;
                description
                  "Interface Name";
              }
              leaf address {
                type inet:ip-address-no-zone;
                description
                  "IP Address";
              }
              uses L2FIB-MAC-DB-INFO;
            }
          }
          container l2fib-mac-learning-mac-ipv6s {
            description
              "The L2VPN forwarding Mac IPV6 Learning Table";
            list l2fib-mac-learning-mac-ipv6 {
              description
                "The attributes for a particular learned IPV6
                 Mac Route";
              leaf interface-name {
                type xr:Interface-name;
                description
                  "Interface Name";
              }
              leaf address {
                type inet:ip-address-no-zone;
                description
                  "IP Address";
              }
              uses L2FIB-MAC-DB-INFO;
            }
          }
        }
        container l2fib-p2mp {
          description
            "p2mp information";
          container ptrees {
            description
              "ptree information";
            list ptree {
              description
                "P2MP PTree Information";
              leaf ptree-type {
                type L2vpnp2mp-ptree;
                description
                  "PTree Type";
              }
              leaf lsm-id {
                type Lsm-id-range;
                description
                  "LSM Id";
              }
              leaf tunnel-id {
                type Tunnel-id-range;
                description
                  "Tunnel Id";
              }
              leaf p2mp-id {
                type P2mp-id-range;
                description
                  "P2MP Id";
              }
              leaf extended-tunnel-id {
                type inet:ipv4-address-no-zone;
                description
                  "Extended Tunnel Id";
              }
              uses L2FIB-P2MP-PTREE-INFO;
            }
          }
        }
        container l2fibmac-hardware-ingresses {
          description
            "Bridge Hardware Ingress information";
          list l2fibmac-hardware-ingress {
            description
              "MAC Hardware Ingress information";
            leaf address {
              type yang:mac-address;
              description
                "Static MAC address";
            }
            leaf group-name {
              type xr:Cisco-ios-xr-string {
                length "1..32";
              }
              description
                "Bridge Group Name";
            }
            leaf name {
              type xr:Cisco-ios-xr-string {
                length "1..27";
              }
              description
                "Bridge Domain Name";
            }
            uses L2FIB-BRIDGE-MAC-INFO;
          }
        }
        container l2fib-evpn-ip4macs {
          description
            "EVPN IPv4-MAC Table";
          list l2fib-evpn-ip4mac {
            description
              "The attributes for a particular EVPN IPv4-MAC
               Entry";
            leaf bdid {
              type Bridge-id-range;
              description
                "BD ID";
            }
            leaf ip-address {
              type inet:ip-address-no-zone;
              description
                "IP Address";
            }
            leaf is-local {
              type boolean;
              description
                "Entry is locally learned";
            }
            leaf mac-address {
              type yang:mac-address;
              description
                "MAC Address";
            }
            uses L2FIB-EVPN-IPMAC-INFO;
          }
        }
        container l2fib-pwhe-main-ports {
          description
            "PWHE Main-port table";
          list l2fib-pwhe-main-port {
            key "interface-name";
            description
              "PWHE Main-port";
            leaf interface-name {
              type xr:Interface-name;
              description
                "PWHE Main-port";
            }
            uses L2FIB-PWHE-MP-SHOW-INFO;
          }
        }
        container l2fib-dhcp-binding-count {
          description
            "DHCP binding forwarding total count";
          uses L2FIB-DHCP-BINDING-COUNT-INFO;
        }
        container l2fib-bridge-domains {
          description
            "Bridge Domain forwarding detail";
          list l2fib-bridge-domain {
            description
              "Specify Bridge Domain Name";
            leaf bd-group-name {
              type xr:Cisco-ios-xr-string {
                length "1..32";
              }
              description
                "Name of the Bridge group";
            }
            leaf bd-name {
              type xr:Cisco-ios-xr-string {
                length "1..65";
              }
              description
                "Bridge Domain Name";
            }
            uses L2FIB-BRIDGE-INFO;
          }
        }
        container l2fib-mstp-summaries {
          description
            "MSTP Summary Table";
          list l2fib-mstp-summary {
            description
              "MSTP Summary information";
            leaf parent-interface {
              type xr:Interface-name;
              description
                "Parent interface context";
            }
            leaf main-interface-type {
              type Evpn-main-interface;
              description
                "Main port interface type";
            }
            leaf msti {
              type Msti-range;
              description
                "MSTI context";
            }
            uses L2FIB-MAIN-PORT-MSTP-SUMMARY-INFO;
          }
        }
        container l2fib-resource-availability {
          description
            "Resource availability information";
          uses L2FIB-RSRC-INFO;
        }
        container l2fibmac-hardware-egresses {
          description
            "Bridge Hardware Egress information";
          list l2fibmac-hardware-egress {
            description
              "MAC Hardware Egress information";
            leaf address {
              type yang:mac-address;
              description
                "Static MAC address";
            }
            leaf group-name {
              type xr:Cisco-ios-xr-string {
                length "1..32";
              }
              description
                "Bridge Group Name";
            }
            leaf name {
              type xr:Cisco-ios-xr-string {
                length "1..27";
              }
              description
                "Bridge Domain Name";
            }
            uses L2FIB-BRIDGE-MAC-INFO;
          }
        }
        container l2fib-evpn-incl-mcast-leaf-hardware-ingresses {
          description
            "L2FIB hardware egress EVPN inclusive multicast
             leaf table";
          list l2fib-evpn-incl-mcast-leaf-hardware-ingress {
            description
              "L2FIB hardware ingress EVPN inclusive
               multicast leaf";
            leaf bd-group-name {
              type xr:Cisco-ios-xr-string {
                length "1..32";
              }
              description
                "Name of the Bridge group";
            }
            leaf name {
              type xr:Cisco-ios-xr-string {
                length "1..65";
              }
              description
                "Bridge Domain Name";
            }
            leaf xcid {
              type xr:Hex-integer;
              description
                "XC ID";
            }
            uses L2FIB-EVPN-INCL-MCAST-OLE-TABLE;
            uses L2FIB-EVPN-INCL-MCAST-LEAF-INFO;
          }
        }
        container l2fib-l3-sync-interfaces {
          description
            "L3-Sync interface table";
          list l2fib-l3-sync-interface {
            key "interface-name";
            description
              "L3-Sync interface";
            leaf interface-name {
              type xr:Interface-name;
              description
                "Interface name";
            }
            uses L2FIB-L3-SYNC-INTF-INFO;
          }
        }
        container l2fibx-con-l2tpv2s {
          description
            "The L2VPN forwarding XConnect L2TPv2 Detail
             Table";
          list l2fibx-con-l2tpv2 {
            description
              "Specify Sub Ifh";
            leaf interface-name {
              type xr:Interface-name;
              description
                "Interface Name";
            }
            leaf vsp-vlan-id {
              type uint32 {
                range "0..4094";
              }
              description
                "VLAN-Switched Port VLAN ID";
            }
            uses L2FIB-XCON-INFO;
          }
        }
        container l2fib-mroute-ipv6s {
          description
            "multicast information";
          list l2fib-mroute-ipv6 {
            description
              "Bridge Domain Multicast Information";
            leaf bd-name {
              type xr:Cisco-ios-xr-string {
                length "1..65";
              }
              description
                "Bridge Domain Name";
            }
            leaf source {
              type inet:ip-address-no-zone;
              description
                "Source IPv6 Address";
            }
            leaf group {
              type inet:ip-address-no-zone;
              description
                "Group IPv6 Address";
            }
            uses L2FIB-MCAST-LEAF-INFO;
          }
        }
        container l2fib-mon-sess-x-cons {
          description
            "The L2VPN forwarding Monitor Session XConnect
             Information";
          list l2fib-mon-sess-x-con {
            key "monitor-session-name";
            description
              "Specify Monitor Session Name";
            leaf monitor-session-name {
              type xr:Cisco-ios-xr-string {
                length "1..64";
              }
              description
                "Monitor Session Name";
            }
            uses L2FIB-XCON-INFO;
          }
        }
        container l2fib-mmrp-summaries {
          description
            "Mmrp Summary Table";
          list l2fib-mmrp-summary {
            description
              "Mmrp Summary Information";
            leaf bd-group-name {
              type xr:Cisco-ios-xr-string {
                length "1..32";
              }
              description
                "Bridge Group Name";
            }
            leaf bd-name {
              type xr:Cisco-ios-xr-string {
                length "1..65";
              }
              description
                "Bridge Domain Name";
            }
            uses L2FIB-MCAST-SUMMARY-INFO;
          }
        }
        container l2fib-pw-groups {
          description
            "PW Group Table Information";
          list l2fib-pw-group {
            description
              "PW Group Information";
            leaf next-hop-type {
              type L2fib-next-hop-key;
              description
                "NHOP Type";
            }
            leaf peer-address {
              type inet:ipv4-address-no-zone;
              description
                "Peer IP Address";
            }
            leaf group-id {
              type Pw-group-id-range;
              description
                "Group Id";
            }
            leaf next-hop-address {
              type inet:ipv4-address-no-zone;
              description
                "NHOP Address";
            }
            leaf next-hop-te-interface-name {
              type xr:Interface-name;
              description
                "NHOP (SR-)TE Interface";
            }
            leaf next-hop-lsm-id {
              type Lsm-id-range;
              description
                "NHOP LSM ID";
            }
            leaf next-hop-address-v6 {
              type inet:ip-address-no-zone;
              description
                "NHOP Address V6";
            }
            leaf next-hop-internal-label {
              type uint32 {
                range "0..1048575";
              }
              description
                "NHOP Internal Label";
            }
            leaf next-hop-sr-te-bsid {
              type uint32 {
                range "0..1048575";
              }
              description
                "NHOP SR-TE Binding Label (BSID)";
            }
            leaf next-hop-internal-id {
              type Rib-iid-range;
              description
                "NHOP Internal ID";
            }
            uses L2FIB-PWGROUP-INFO;
          }
        }
        container l2fib-dhcp-binding-details {
          description
            "DHCP binding forwarding detail";
          list l2fib-dhcp-binding-detail {
            description
              "Specify DHCP binding detail";
            leaf xcid {
              type xr:Hex-integer;
              description
                "XConnect ID";
            }
            leaf neighbor-address {
              type inet:ipv4-address-no-zone;
              description
                "Neighbor IPv4 address";
            }
            leaf address {
              type yang:mac-address;
              description
                "MAC address";
            }
            uses L2FIB-DHCP-BINDING-DETAIL-INFO;
          }
        }
        container l2fibx-cons {
          description
            "The L2VPN forwarding XConnect Detail Table";
          list l2fibx-con {
            key "xcid";
            description
              "Specify XConnect ID";
            leaf xcid {
              type xr:Hex-integer;
              description
                "XC ID";
            }
            uses L2FIB-XCON-INFO;
          }
        }
        container l2fib-main-interfaces {
          description
            "Main Interface";
          list l2fib-main-interface {
            description
              "Main Interface Table";
            container l2fib-main-interface-hardware-egress-detail-info {
              description
                "Main Interface hardware egress detail info";
              uses L2FIB-MAIN-INTERFACE-DETAIL-INFO;
            }
            container l2fib-main-interface-hardware-egress-info {
              description
                "Main Interface hardware egress info";
              uses L2FIB-MAIN-INTERFACE-SUMMARY-INFO;
            }
            container l2fib-main-interface-instances {
              description
                "Main Interface Instance table";
              list l2fib-main-interface-instance {
                key "instance";
                description
                  "Main Interface Instance";
                container l2fib-main-interface-instance-detail-info {
                  description
                    "Main Interface Instance detail info";
                  uses L2FIB-MAIN-INTERFACE-INSTANCE-DETAIL-INFO;
                }
                container l2fib-main-interface-instance-bridge-port-details {
                  description
                    "Main Interface Instance Bridge Port detail
                     table";
                  list l2fib-main-interface-instance-bridge-port-detail {
                    key "xcid";
                    description
                      "Main Interface Bridge Port detail info";
                    leaf xcid {
                      type xr:Hex-integer;
                      description
                        "Bridge Port";
                    }
                    uses L2FIB-MAIN-INTERFACE-INSTANCE-BPORT-DETAIL-INFO;
                  }
                }
                container l2fib-main-interface-instance-info {
                  description
                    "Main Interface Instance info";
                  uses L2FIB-MAIN-INTERFACE-INSTANCE-SUMMARY-INFO;
                }
                container l2fib-main-interface-instance-hardware-ingress-detail-info {
                  description
                    "Main Interface Instance hardware ingress
                     detail info";
                  uses L2FIB-MAIN-INTERFACE-INSTANCE-DETAIL-INFO;
                }
                container l2fib-main-interface-instance-hardware-egress-info {
                  description
                    "Main Interface Instance hardware egress
                     info";
                  uses L2FIB-MAIN-INTERFACE-INSTANCE-SUMMARY-INFO;
                }
                container l2fib-main-interface-instance-hardware-ingress-info {
                  description
                    "Main Interface Instance hardware ingress
                     info";
                  uses L2FIB-MAIN-INTERFACE-INSTANCE-SUMMARY-INFO;
                }
                container l2fib-main-interface-instance-bridge-ports {
                  description
                    "Main Interface Instance Bridge Port table";
                  list l2fib-main-interface-instance-bridge-port {
                    key "xcid";
                    description
                      "Main Interface Bridge Port info";
                    leaf xcid {
                      type xr:Hex-integer;
                      description
                        "Bridge Port";
                    }
                    uses L2FIB-MAIN-INTERFACE-INSTANCE-BPORT-SUMMARY-INFO;
                  }
                }
                container l2fib-main-interface-instance-hardware-egress-detail-info {
                  description
                    "Main Interface Instance hardware egress
                     detail info";
                  uses L2FIB-MAIN-INTERFACE-INSTANCE-DETAIL-INFO;
                }
                leaf instance {
                  type Msti-range;
                  description
                    "Instance";
                }
              }
            }
            container l2fib-main-interface-info {
              description
                "Main Interface info";
              uses L2FIB-MAIN-INTERFACE-SUMMARY-INFO;
            }
            container l2fib-main-interface-detail-info {
              description
                "Main Interface detail info";
              uses L2FIB-MAIN-INTERFACE-DETAIL-INFO;
            }
            container l2fib-main-interface-hardware-ingress-detail-info {
              description
                "Main Interface hardware ingress detail info";
              uses L2FIB-MAIN-INTERFACE-DETAIL-INFO;
            }
            container l2fib-main-interface-hardware-ingress-info {
              description
                "Main Interface hardware ingress info";
              uses L2FIB-MAIN-INTERFACE-SUMMARY-INFO;
            }
            leaf main-interface-id {
              type Main-interface-id-range;
              description
                "Main interface id";
            }
            leaf main-interface-type {
              type Evpn-main-interface;
              description
                "Main interface type";
            }
          }
        }
        container l2fib-mroute-ipv6-summaries {
          description
            "Mroute IPv6 Summary Table";
          list l2fib-mroute-ipv6-summary {
            description
              "Multicast IPv6 Summary Information";
            leaf bd-group-name {
              type xr:Cisco-ios-xr-string {
                length "1..32";
              }
              description
                "Bridge Group Name";
            }
            leaf bd-name {
              type xr:Cisco-ios-xr-string {
                length "1..65";
              }
              description
                "Bridge Domain Name";
            }
            uses L2FIB-MCAST-SUMMARY-INFO;
          }
        }
        container l2fib-message-hardware-summary {
          description
            "L2FIB Message Summary information from
             hardware";
          uses L2FIB-HW-INFO;
        }
        container l2fib-mstp-details {
          description
            "MSTP Detail Table";
          list l2fib-mstp-detail {
            description
              "MSTP Detail information";
            leaf parent-interface {
              type xr:Interface-name;
              description
                "Parent interface context";
            }
            leaf main-interface-type {
              type Evpn-main-interface;
              description
                "Main port interface type";
            }
            leaf msti {
              type Msti-range;
              description
                "MSTI context";
            }
            uses L2FIB-MAIN-PORT-MSTP-DETAIL-INFO;
          }
        }
        container l2fib-l2tp {
          description
            "L2TP";
          container l2tpv3-sessions {
            description
              "L2TPV3 Session table";
            list l2tpv3-session {
              key "session-id";
              description
                "L2TPV3 Session";
              leaf session-id {
                type L2tpv3-session-id-range;
                description
                  "SessionID";
              }
              uses L2FIB-L2TP-DISP-INFO;
            }
          }
          container l2tpv2-sessions {
            description
              "L2TPV2 Session table";
            list l2tpv2-session {
              description
                "L2TPV2 Session";
              leaf session-id {
                type L2tpv2-session-id-range;
                description
                  "SessionID";
              }
              leaf tunnel-id {
                type Tunnel-id-range;
                description
                  "TunnelID";
              }
              uses L2FIB-L2TP-DISP-INFO;
            }
          }
        }
        container l2fib-g8032 {
          description
            "G8032 information";
          container l2fib-g8032-rings {
            description
              "G8032 Ring table";
            list l2fib-g8032-ring {
              key "ring-name";
              description
                "G8032 Ring";
              container l2fib-g8032-ring-detail {
                description
                  "G8032 Ring detailed information";
                uses L2FIB-G8032-RING-DETAIL-INFO;
              }
              container l2fib-g8032-ring-summary {
                description
                  "G8032 Ring summary information";
                uses L2FIB-G8032-RING-SUMMARY-INFO;
              }
              container l2fib-g8032-ring-instance-summaries {
                description
                  "G8032 Ring Instance summary table";
                list l2fib-g8032-ring-instance-summary {
                  key "instance";
                  description
                    "G8032 Ring Instance summary information";
                  leaf instance {
                    type G8032-ring-instance-range;
                    description
                      "Instance";
                  }
                  uses L2FIB-G8032-RING-INSTANCE-SUMMARY-INFO;
                }
              }
              container l2fib-g8032-ring-instance-details {
                description
                  "G8032 Ring Instance detail table";
                list l2fib-g8032-ring-instance-detail {
                  key "instance";
                  description
                    "G8032 Ring Instance detailed information";
                  leaf instance {
                    type G8032-ring-instance-range;
                    description
                      "Instance";
                  }
                  uses L2FIB-G8032-RING-INSTANCE-DETAIL-INFO;
                }
              }
              leaf ring-name {
                type xr:Cisco-ios-xr-string {
                  length "1..32";
                }
                description
                  "Ring Name";
              }
            }
          }
        }
        container l2fib-bridge-ports {
          description
            "Bridge Port forwarding detail";
          list l2fib-bridge-port {
            description
              "Specify Bridge Domain Name and XC ID";
            leaf group-name {
              type xr:Cisco-ios-xr-string {
                length "1..32";
              }
              description
                "Bridge Group Name";
            }
            leaf bd-name {
              type xr:Cisco-ios-xr-string {
                length "1..65";
              }
              description
                "Bridge Domain Name";
            }
            leaf xc-uint-id {
              type xr:Hex-integer;
              description
                "XC ID";
            }
            uses L2FIB-BRIDGE-PORT-DETAIL-INFO;
          }
        }
        container l2fibmac-details {
          description
            "Bridge MAC detail information";
          list l2fibmac-detail {
            description
              "MAC Detail information";
            leaf address {
              type yang:mac-address;
              description
                "Static MAC address";
            }
            leaf group-name {
              type xr:Cisco-ios-xr-string {
                length "1..32";
              }
              description
                "Bridge Group Name";
            }
            leaf name {
              type xr:Cisco-ios-xr-string {
                length "1..65";
              }
              description
                "Bridge Domain Name";
            }
            uses L2FIB-BRIDGE-MAC-INFO;
          }
        }
        container l2fib-bridge-domain-names {
          description
            "Bridge Domain forwarding detail";
          list l2fib-bridge-domain-name {
            description
              "Specify Bridge Domain Name";
            leaf bd-group-name {
              type xr:Cisco-ios-xr-string {
                length "1..32";
              }
              description
                "Name of the Bridge group";
            }
            leaf name {
              type xr:Cisco-ios-xr-string {
                length "1..65";
              }
              description
                "Bridge Domain Name";
            }
            uses L2FIB-BRIDGE-SUMMARY-INFO;
          }
        }
        container l2fib-evpn-incl-mcast-leafs {
          description
            "L2FIB EVPN inclusive multicast leaf table";
          list l2fib-evpn-incl-mcast-leaf {
            description
              "L2FIB EVPN inclusive multicast leaf";
            leaf bd-group-name {
              type xr:Cisco-ios-xr-string {
                length "1..32";
              }
              description
                "Name of the Bridge group";
            }
            leaf name {
              type xr:Cisco-ios-xr-string {
                length "1..65";
              }
              description
                "Bridge Domain Name";
            }
            leaf xcid {
              type xr:Hex-integer;
              description
                "XC ID";
            }
            uses L2FIB-EVPN-INCL-MCAST-OLE-TABLE;
            uses L2FIB-EVPN-INCL-MCAST-LEAF-INFO;
          }
        }
        container l2fib-mroute-ports {
          description
            "multicast bridge port information ";
          list l2fib-mroute-port {
            description
              "Multicast Port Information";
            leaf bd-name {
              type xr:Cisco-ios-xr-string {
                length "1..65";
              }
              description
                "Bridge Domain Name";
            }
            leaf xcid {
              type xr:Hex-integer;
              description
                "XConnect ID";
            }
            leaf xid-type {
              type L2fib-evpn-xid;
              description
                "XID Type";
            }
            leaf moi-id {
              type uint32;
              description
                "MOI ID";
            }
            leaf label {
              type uint32 {
                range "0..1048575";
              }
              description
                "NextHop Label";
            }
            leaf source {
              type inet:ipv4-address-no-zone;
              description
                "Source IP Address";
            }
            leaf group {
              type inet:ipv4-address-no-zone;
              description
                "Group IP Address";
            }
            uses L2FIB-MCAST-XID-INFO;
          }
        }
        container l2fib-summary {
          description
            "L2FIB Summary information";
          uses L2FIB-SUMMARY-INFO;
        }
        container l2fib-nve-peers {
          description
            "NVE Peer Table";
          list l2fib-nve-peer {
            description
              "The attributes for a particular NVE Peer";
            leaf xc-uint-id {
              type xr:Hex-integer;
              description
                "XC ID";
            }
            leaf vniid {
              type xr:Hex-integer;
              description
                "VNI ID";
            }
            leaf vtep-address {
              type inet:ipv4-address-no-zone;
              description
                "VTEP IP Address";
            }
            uses L2FIB-VTEP-INFO;
          }
        }
        container l2fib-mmrps {
          description
            "mmrp information";
          list l2fib-mmrp {
            description
              "Bridge Domain Mmrp Information";
            leaf bd-name {
              type xr:Cisco-ios-xr-string {
                length "1..65";
              }
              description
                "Bridge Domain Name";
            }
            leaf source {
              type yang:mac-address;
              description
                "Source Mac Address";
            }
            leaf group {
              type yang:mac-address;
              description
                "Group Mac Address";
            }
            uses L2FIB-MCAST-LEAF-INFO;
          }
        }
        container l2fib-evpn-ip6macs {
          description
            "EVPN IPv6-MAC Table";
          list l2fib-evpn-ip6mac {
            description
              "The attributes for a particular EVPN IPv6-MAC
               Entry";
            leaf bdid {
              type Bridge-id-range;
              description
                "BD ID";
            }
            leaf ip-address {
              type inet:ip-address-no-zone;
              description
                "IP Address";
            }
            leaf is-local {
              type boolean;
              description
                "Entry is locally learned";
            }
            leaf mac-address {
              type yang:mac-address;
              description
                "MAC Address";
            }
            uses L2FIB-EVPN-IPMAC-INFO;
          }
        }
        container l2fib-pwhe-main-port-hardware-egresses {
          description
            "PWHE Main-port Hardware Egress Table";
          list l2fib-pwhe-main-port-hardware-egress {
            key "interface-name";
            description
              "PWHE Main-port H/W Egress Info";
            leaf interface-name {
              type xr:Interface-name;
              description
                "PWHE Main-port";
            }
            uses L2FIB-PWHE-MP-SHOW-INFO;
          }
        }
        container l2fib-evpn-incl-mcast-leaf-hardware-egresses {
          description
            "L2FIB hardware ingress EVPN inclusive
             multicast leaf table";
          list l2fib-evpn-incl-mcast-leaf-hardware-egress {
            description
              "L2FIB hardware egress EVPN inclusive
               multicast leaf";
            leaf bd-group-name {
              type xr:Cisco-ios-xr-string {
                length "1..32";
              }
              description
                "Name of the Bridge group";
            }
            leaf name {
              type xr:Cisco-ios-xr-string {
                length "1..65";
              }
              description
                "Bridge Domain Name";
            }
            leaf xcid {
              type xr:Hex-integer;
              description
                "XC ID";
            }
            uses L2FIB-EVPN-INCL-MCAST-OLE-TABLE;
            uses L2FIB-EVPN-INCL-MCAST-LEAF-INFO;
          }
        }
        container l2fib-dhcp-binding-summaries {
          description
            "DHCP binding forwarding summary";
          list l2fib-dhcp-binding-summary {
            key "xcid";
            description
              "Specify DHCP binding summary";
            leaf xcid {
              type xr:Hex-integer;
              description
                "XConnect ID";
            }
            uses L2FIB-DHCP-BINDING-SUMMARY-INFO;
          }
        }
        container l2fib-pwhe-main-port-hardware-ingresses {
          description
            "PWHE Main-port Hardware Ingress Table";
          list l2fib-pwhe-main-port-hardware-ingress {
            key "interface-name";
            description
              "PWHE Main-port H/W Ingress Info";
            leaf interface-name {
              type xr:Interface-name;
              description
                "PWHE Main-port";
            }
            uses L2FIB-PWHE-MP-SHOW-INFO;
          }
        }
        leaf node-id {
          type xr:Node-id;
          description
            "The identifier for the node";
        }
      }
    }
  }
  container l2vpnv2 {
    config false;
    description
      "L2VPN operational data to support active and
       standby. L2VPN has been deprecated";
    container standby {
      description
        "Standby L2VPN operational data";
      uses DISCOVERY-TABLE;
      uses FLEXIBLE-XCONNECT-SERVICE-SUMMARY;
      uses MAIN-INTERFACE-TABLE;
      uses ICCP-SM;
      uses BRIDGE-SUMMARY;
      uses NSR;
      uses PREFERRED-PATH-TABLE;
      uses PSEUDOWIRE-HEADEND;
      uses GLOBAL-SETTINGS;
      uses L2VPN-CACDB;
      uses PWR;
      uses XCONNECT-MP2MP-CE2CE-TABLE;
      uses XCONNECT-TABLE;
      uses XCONNECT-GROUP-TABLE;
      uses XCONNECT-MP2MP-TABLE;
      uses SRTE-POLICY-TABLE;
      uses INDEX-TABLE;
      uses XCONNECT-SUMMARY;
      uses PROC-FSM;
      uses MSTP-PORT-TABLE;
      uses L2VPN-OPER-L2VPN-RESOURCE-STATE-MP;
      uses BRIDGE-DOMAIN-TABLE;
      uses DISCOVERY-SUMMARY;
      uses G8032;
      uses PSEUDOWIRE-CLASS-TABLE;
      uses L2VPN-COLLABORATORS;
      uses MVRP;
      uses MSTP-VLAN-TABLE;
      uses L2VPN-PBB-BSA;
      uses FLEXIBLE-XCONNECT-SERVICE-TABLE;
      uses XCONNECT-BRIEF;
    }
    container active {
      description
        "Active L2VPN operational data";
      uses DISCOVERY-TABLE;
      uses FLEXIBLE-XCONNECT-SERVICE-SUMMARY;
      uses MAIN-INTERFACE-TABLE;
      uses ICCP-SM;
      uses BRIDGE-SUMMARY;
      uses NSR;
      uses PREFERRED-PATH-TABLE;
      uses PSEUDOWIRE-HEADEND;
      uses GLOBAL-SETTINGS;
      uses L2VPN-CACDB;
      uses PWR;
      uses XCONNECT-MP2MP-CE2CE-TABLE;
      uses XCONNECT-TABLE;
      uses XCONNECT-GROUP-TABLE;
      uses XCONNECT-MP2MP-TABLE;
      uses SRTE-POLICY-TABLE;
      uses INDEX-TABLE;
      uses XCONNECT-SUMMARY;
      uses PROC-FSM;
      uses MSTP-PORT-TABLE;
      uses L2VPN-OPER-L2VPN-RESOURCE-STATE-MP;
      uses BRIDGE-DOMAIN-TABLE;
      uses DISCOVERY-SUMMARY;
      uses G8032;
      uses PSEUDOWIRE-CLASS-TABLE;
      uses L2VPN-COLLABORATORS;
      uses MVRP;
      uses MSTP-VLAN-TABLE;
      uses L2VPN-PBB-BSA;
      uses FLEXIBLE-XCONNECT-SERVICE-TABLE;
      uses XCONNECT-BRIEF;
    }
    container nodes {
      description
        "Table of L2VPN operational data for a particular
         node";
      list node {
        key "node-id";
        description
          "L2VPN operational data for a particular node";
        leaf node-id {
          type xr:Node-id;
          description
            "Location";
        }
        uses DISCOVERY-TABLE;
        uses FLEXIBLE-XCONNECT-SERVICE-SUMMARY;
        uses MAIN-INTERFACE-TABLE;
        uses ICCP-SM;
        uses BRIDGE-SUMMARY;
        uses NSR;
        uses PREFERRED-PATH-TABLE;
        uses PSEUDOWIRE-HEADEND;
        uses GLOBAL-SETTINGS;
        uses L2VPN-CACDB;
        uses PWR;
        uses XCONNECT-MP2MP-CE2CE-TABLE;
        uses XCONNECT-TABLE;
        uses XCONNECT-GROUP-TABLE;
        uses XCONNECT-MP2MP-TABLE;
        uses SRTE-POLICY-TABLE;
        uses INDEX-TABLE;
        uses XCONNECT-SUMMARY;
        uses PROC-FSM;
        uses MSTP-PORT-TABLE;
        uses L2VPN-OPER-L2VPN-RESOURCE-STATE-MP;
        uses BRIDGE-DOMAIN-TABLE;
        uses DISCOVERY-SUMMARY;
        uses G8032;
        uses PSEUDOWIRE-CLASS-TABLE;
        uses L2VPN-COLLABORATORS;
        uses MVRP;
        uses MSTP-VLAN-TABLE;
        uses L2VPN-PBB-BSA;
        uses FLEXIBLE-XCONNECT-SERVICE-TABLE;
        uses XCONNECT-BRIEF;
      }
    }
  }
  container ea-pwhe {
    config false;
    description
      "EA PWHE operational data";
    container nodes {
      description
        "Table of EA PWHE operational data for a
         particular node";
      list node {
        key "node-id";
        description
          "EA PWHE operational data for a particular node";
        container ea-pwhe-idbs {
          description
            "Generic interface list table";
          list ea-pwhe-idb {
            key "if-h";
            description
              "EA PWHE Interface Database";
            leaf if-h {
              type xr:Hex-integer;
              description
                "Interface Handle";
            }
            uses PWHE-EA-IDB;
          }
        }
        container ea-pwhe-summary {
          description
            "EA PWHE Summary";
          uses PWHE-EA-SUM;
        }
        leaf node-id {
          type xr:Node-id;
          description
            "Location";
        }
      }
    }
  }
}
