module Cisco-IOS-XR-emon-oper {
  namespace "http://cisco.com/ns/yang/Cisco-IOS-XR-emon-oper";
  prefix emon-oper;

  import Cisco-IOS-XR-types {
    prefix xr;
  }
  import cisco-semver {
    prefix semver;
  }
  include Cisco-IOS-XR-emon-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR emon package operational data.
     
     This module contains definitions
     for the following management objects:
       show-emon: EMON statistics
     
     Copyright (c) 2013-2019, 2022 by Cisco Systems, Inc.
     All rights reserved.";

  revision 2019-04-05 {
    description
      "Establish semantic version baseline.";
    semver:module-version "1.0.0";
  }
  revision 2019-03-08 {
    description
      "and entry for show controller switch bridge";
  }
  revision 2019-03-01 {
    description
      "Rename esdma-oper to switch-oper, esdma-emon-oper to emon-oper";
  }
  revision 2019-02-07 {
    description
      "Rework clear and set operations.";
  }
  revision 2015-11-09 {
    description
      "IOS XR 6.0 revision.";
  }

  container show-emon {
    config false;
    description
      "EMON statistics";
    container emon-statistics {
      description
        "EMON TX and RX statistics";
      container emon-statistics-instances {
        description
          "Table of EmonStatisticsLocation";
        list emon-statistics-instance {
          key "node-id";
          description
            "Location information for EMON statistics";
          leaf node-id {
            type xr:Node-id;
            description
              "NodeID of the Location";
          }
          uses ESDMA-SHOW-EMON-STATS-INFO;
        }
      }
    }
  }
}
