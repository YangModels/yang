submodule Cisco-IOS-XR-envmon-oper-sub1 {
  belongs-to Cisco-IOS-XR-envmon-oper {
    prefix Cisco-IOS-XR-envmon-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR envmon package operational data.
     
     Copyright (c) 2013-2023 by Cisco Systems, Inc.
     All rights reserved.";

  revision 2021-06-10 {
    description
      "IOS XR 7.5.1 revision. Decoupled chassis sensors from being reported as part of RP card";
    semver:module-version "1.2.0";
  }
  revision 2020-09-25 {
    description
      "IOS XR 7.3.1 revision. Added alarm port oper commands.";
    semver:module-version "1.1.0";
  }
  revision 2020-04-07 {
    description
      "IOS XR 7.2.1 revision. Added extra description to interpret Threshold Value -32768.";
    semver:module-version "1.1.0";
  }
  revision 2019-04-05 {
    description
      "Establish semantic version baseline.";
    semver:module-version "1.0.0";
  }
  revision 2015-11-09 {
    description
      "IOS XR 6.0 revision.";
  }

  grouping DPB-CLIENT-PORTS-DATA-B {
    description
      "DPB Client Ports Data";
    leaf port {
      type uint32;
      description
        "Port Number";
    }
    leaf power {
      type uint32;
      description
        "Power Alloc";
    }
    leaf location {
      type string;
      description
        "Port location";
    }
  }

  grouping DPB-CLIENTS-PWR-INFO-B {
    description
      "Consumer DPB Clients Power Info";
    leaf client-name {
      type string;
      description
        "Client Name";
    }
    leaf bulk-power {
      type uint32;
      description
        "Bulk Power";
    }
    leaf ports-allocated-power {
      type uint32;
      description
        "Ports Allocated Power";
    }
    leaf ports-data-count {
      type uint32;
      description
        "Ports Data Count";
    }
    list dpb-client-ports-data {
      description
        "DPB Client Ports Data Array";
      uses DPB-CLIENT-PORTS-DATA-B;
    }
  }

  grouping CONSUMER-PWR-INFO-B {
    description
      "Power Consumer Info";
    leaf node-name {
      type string;
      description
        "Name of the Node";
    }
    leaf node-type {
      type string;
      description
        "PID of the Entity";
    }
    leaf pwr-alctd {
      type uint32;
      description
        "Power Allocated";
    }
    leaf pwr-used {
      type uint32;
      description
        "Power Used";
    }
    leaf node-status {
      type string;
      description
        "Node Status";
    }
    leaf slot {
      type uint32;
      description
        "Slot number";
    }
    list dpb-clients-power-info-array {
      description
        "DPB Clients Power Info";
      uses DPB-CLIENTS-PWR-INFO-B;
    }
  }

  grouping CHASSIS-PWR-GRP-INFO-B {
    description
      "Group Level Power Info";
    leaf total-pwr-in {
      type uint64;
      description
        "Total Power Input in watts";
    }
    leaf total-pwr-out {
      type uint64;
      description
        "Total Power Output in watts";
    }
    leaf total-current-in-a {
      type string;
      description
        "Total Current Input A in amps";
    }
    leaf total-current-in-b {
      type string;
      description
        "Total Current Input B in amps";
    }
    leaf total-current-out {
      type string;
      description
        "Total Current Output in amps";
    }
    leaf total-output-capacity {
      type uint64;
      description
        "Total Output capacity in watts";
    }
  }

  grouping CHASSIS-PWR-INFO-B {
    description
      "Chassis Level Power Info";
    leaf total-pwr-required {
      type uint32;
      description
        "Total Power required";
    }
    leaf red-mode {
      type uint32;
      description
        "Redundancy Mode";
    }
    leaf total-pe-ms {
      type uint32;
      description
        "Total Number of PEMs";
    }
    leaf red-num-pe-ms {
      type uint32;
      description
        "Redundant Number of PEMs";
    }
    leaf psu-non-fruable {
      type uint8;
      description
        "PSU Fixed Hardware";
    }
    leaf total-out-capacity {
      type uint32;
      description
        "Total out capacity";
    }
    leaf total-pwr-output {
      type uint32;
      description
        "Total Power output";
    }
    leaf total-pwr-input {
      type uint32;
      description
        "Total Power input";
    }
    list grp-info {
      max-elements "3";
      description
        "Total Info Group wise";
      uses CHASSIS-PWR-GRP-INFO-B;
    }
  }

  grouping PRODUCER-PWR-PEM-INFO-B {
    description
      "Power Producer PEM Info";
    leaf node-name {
      type string;
      description
        "Name of the Node";
    }
    leaf node-type {
      type string;
      description
        "PID of the PEM";
    }
    leaf num-feed {
      type uint32;
      description
        "Number of Feeds";
    }
    leaf voltage-in-a {
      type uint32;
      description
        "Input Voltage A";
    }
    leaf voltage-in-b {
      type uint32;
      description
        "Input Voltage B";
    }
    leaf voltage-out {
      type uint32;
      description
        "Output Voltage";
    }
    leaf current-in-a {
      type uint32;
      description
        "Input Current A";
    }
    leaf current-in-b {
      type uint32;
      description
        "Input Current B";
    }
    leaf current-out {
      type uint32;
      description
        "Output Current";
    }
    leaf node-status {
      type string;
      description
        "Node Status";
    }
  }

  grouping PRODUCER-PWR-PT-INFO-B {
    description
      "Power Producer PT Info";
    list pem-info-array {
      description
        "PEM Info Array";
      uses PRODUCER-PWR-PEM-INFO-B;
    }
  }
}
