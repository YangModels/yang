module Cisco-IOS-XR-envmon-alt-cfg {
  namespace "http://cisco.com/ns/yang/Cisco-IOS-XR-envmon-alt-cfg";
  prefix envmon-alt-cfg;

  import cisco-semver {
    prefix semver;
  }
  import Cisco-IOS-XR-envmon-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR envmon-alt package configuration.
     
     This YANG module augments the
       Cisco-IOS-XR-envmon-cfg
     module with configuration data.
     
     Copyright (c) 2013-2019, 2022 by Cisco Systems, Inc.
     All rights reserved.";

  revision 2019-04-05 {
    description
      "Establish semantic version baseline.";
    semver:module-version "1.0.0";
  }
  revision 2015-11-09 {
    description
      "IOS XR 6.0 revision.";
  }

  augment "/a1:environmental-monitoring" {
    description
      "This augment extends the configuration data of
       'Cisco-IOS-XR-envmon-cfg'";
    leaf altitude {
      type uint32 {
        range "0..4000";
      }
      description
        "Altitude value in meters";
    }
  }
}
