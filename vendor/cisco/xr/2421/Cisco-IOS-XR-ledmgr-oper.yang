module Cisco-IOS-XR-ledmgr-oper {
  namespace "http://cisco.com/ns/yang/Cisco-IOS-XR-ledmgr-oper";
  prefix ledmgr-oper;

  import cisco-semver {
    prefix semver;
  }
  include Cisco-IOS-XR-ledmgr-oper-sub1 {
    revision-date 2019-10-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ledmgr package operational data.
     
     This module contains definitions
     for the following management objects:
       led-management: LED operational data
     
     Copyright (c) 2013-2019, 2022 by Cisco Systems, Inc.
     All rights reserved.";

  revision 2019-10-15 {
    description
      "IOS XR 7.0.12 revision.";
    semver:module-version "2.0.0";
  }
  revision 2019-04-05 {
    description
      "Establish semantic version baseline.";
    semver:module-version "1.0.0";
  }
  revision 2015-11-09 {
    description
      "IOS XR 6.0 revision.";
  }

  container led-management {
    config false;
    description
      "LED operational data";
    container locations {
      description
        "Table of LED Locations";
      list location {
        key "name";
        description
          "Location";
        container leds {
          description
            "LED operational data";
          list led {
            key "name";
            description
              "LED";
            leaf name {
              type string;
              description
                "LED Name";
            }
            uses LED-ATTRIBUTES;
          }
        }
        leaf name {
          type string;
          description
            "External node name (as seen in show platform)";
        }
      }
    }
  }
}
