submodule Cisco-IOS-XR-controller-fc-oper-sub1 {
  belongs-to Cisco-IOS-XR-controller-fc-oper {
    prefix Cisco-IOS-XR-controller-fc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-fc package operational data.
     
     Copyright (c) 2013-2022 by Cisco Systems, Inc.
     All rights reserved.";

  revision 2021-06-30 {
    description
      "sf-ber-threshold and sd-ber-threshold added in fc_ctrlr_port_info bag";
    semver:module-version "1.0.0";
  }
  revision 2021-04-20 {
    description
      "Fibre Channel controller oper model added";
  }
  revision 2019-04-05 {
    description
      "Establish semantic version baseline.";
  }
  revision 2015-11-09 {
    description
      "IOS XR 6.0 revision.";
  }

  typedef Fc-ctrlr-prbs-status {
    type enumeration {
      enum "locked" {
        value 0;
        description
          "Locked";
      }
      enum "unlocked" {
        value 1;
        description
          "Unlocked";
      }
      enum "not-applicable" {
        value 2;
        description
          "Not Applicable";
      }
    }
    description
      "Fc ctrlr prbs status";
  }

  typedef Fc-ctrlr-prbs-pattern {
    type enumeration {
      enum "pn-none" {
        value 0;
        description
          "PNNONE";
      }
      enum "pn31" {
        value 1;
        description
          "PN31";
      }
      enum "pn23" {
        value 2;
        description
          "PN23";
      }
      enum "pn15" {
        value 3;
        description
          "PN15";
      }
      enum "pn11" {
        value 4;
        description
          "PN11";
      }
      enum "pn9" {
        value 5;
        description
          "PN9";
      }
      enum "pn7" {
        value 6;
        description
          "PN7";
      }
    }
    description
      "Fc ctrlr prbs pattern";
  }

  typedef Fc-ctrlr-prbs-mode {
    type enumeration {
      enum "none" {
        value 0;
        description
          "None";
      }
      enum "source" {
        value 1;
        description
          "Source";
      }
      enum "sink" {
        value 2;
        description
          "Sink";
      }
      enum "source-sink" {
        value 3;
        description
          "Source Sink";
      }
    }
    description
      "Fc ctrlr prbs mode";
  }

  typedef Fc-ctrlr-prbs-test {
    type enumeration {
      enum "disable" {
        value 0;
        description
          "Disable";
      }
      enum "enable" {
        value 1;
        description
          "Enable";
      }
    }
    description
      "Fc ctrlr prbs test";
  }

  typedef Fc-fec {
    type enumeration {
      enum "none" {
        description
          "None";
      }
      enum "not-configured" {
        description
          "Not Configured";
      }
      enum "standard" {
        description
          "Standard";
      }
      enum "disabled" {
        description
          "Disabled";
      }
    }
    description
      "FEC Type";
  }

  typedef Fc-loopback-info {
    type enumeration {
      enum "none" {
        description
          "None";
      }
      enum "line" {
        description
          "LoopBack Line ";
      }
      enum "loop-back-internal" {
        description
          "LoopBack Internal";
      }
    }
    description
      "loopback info";
  }

  typedef Fc-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Fc state et";
  }

  typedef Fc-sa-state {
    type enumeration {
      enum "normal" {
        description
          "Normal";
      }
      enum "maintenance" {
        description
          "Maintenance";
      }
      enum "ains" {
        description
          "AINS";
      }
    }
    description
      "Secondary admin state";
  }

  grouping FC-CTRLR-PORT-STATS {
    description
      "FC port operational stats";
    leaf los {
      type uint64;
      description
        "Loss of signal";
    }
    leaf local-fault {
      type uint64;
      description
        "Local Fault";
    }
    leaf remote-fault {
      type uint64;
      description
        "Remote Fault";
    }
    leaf pcs-error {
      type uint64;
      description
        "PCS Error";
    }
    leaf high-ber {
      type uint64;
      description
        "High BER Error";
    }
    leaf syncloss {
      type uint64;
      description
        "Sync loss count";
    }
  }

  grouping FC-CTRLR-PRBS-INFO {
    description
      "PRBS";
    leaf test {
      type Fc-ctrlr-prbs-test;
      description
        "PRBS test";
    }
    leaf mode {
      type Fc-ctrlr-prbs-mode;
      description
        "PRBS mode";
    }
    leaf pattern {
      type Fc-ctrlr-prbs-pattern;
      description
        "PRBS pattern";
    }
    leaf status {
      type Fc-ctrlr-prbs-status;
      description
        "PRBS status";
    }
  }

  grouping FC-CTRLR-PORT-INFO {
    description
      "FC port operational info";
    leaf secondary-admin-state {
      type Fc-sa-state;
      description
        "Secondary Admin State";
    }
    leaf operational-state {
      type Fc-state-et;
      description
        "Port's IM state";
    }
    leaf loopback {
      type Fc-loopback-info;
      description
        "Loopback info";
    }
    leaf perf-mon-disabled {
      type boolean;
      description
        "Perf mon disabled";
    }
    leaf fec {
      type Fc-fec;
      description
        "FEC type";
    }
    leaf fec-method {
      type string {
        length "0..64";
      }
      description
        "FEC method";
    }
    leaf laser-squelch-enabled {
      type boolean;
      description
        "Laser squelch enabled";
    }
    leaf holdoff-time {
      type uint32;
      description
        "Hold off Time";
    }
    leaf signal-degrade-ber-threshold {
      type uint32;
      description
        "Signal Degrade BER Threshold";
    }
    leaf signal-failure-ber-threshold {
      type uint32;
      description
        "Signal Failure BER Threshold";
    }
  }
}
