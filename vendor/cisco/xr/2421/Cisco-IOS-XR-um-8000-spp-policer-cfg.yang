module Cisco-IOS-XR-um-8000-spp-policer-cfg {
  namespace "http://cisco.com/ns/yang/Cisco-IOS-XR-um-8000-spp-policer-cfg";
  prefix um-8000-spp-policer-cfg;

  import Cisco-IOS-XR-um-location-cfg {
    prefix location;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-spp-policer package configuration.
     
     This YANG module augments the
     modules with configuration data.
     
     Copyright (c) 2022 by Cisco Systems, Inc.
     All rights reserved.";

  revision 2022-12-02 {
    description
      "Initial release";
  }

  grouping LOCATION-BODY {
    description
      "";
    container lpts {
      description
        "lpts configuration commands";
      container punt {
        description
          "punt configuration commands";
        container police {
          description
            "ingress policers configuration command";
          container spp {
            description
              "SPP policers";
            container nd {
              description
                "ND policer";
              leaf rate {
                type uint32 {
                  range "1..200" {
                    description
                      "Packets Per Second";
                  }
                }
                description
                  "Rate in PPS";
              }
              container disable {
                presence "Indicates a disable node is configured.";
                description
                  "Disable ND policer";
              }
            }
          }
        }
      }
    }
  }

  augment "/location:locations/location:location" {
    description
      "";
    uses LOCATION-BODY;
  }
  augment "/location:locations/location:preconfigured-location" {
    description
      "";
    uses LOCATION-BODY;
  }
}
