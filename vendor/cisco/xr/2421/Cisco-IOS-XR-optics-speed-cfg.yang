module Cisco-IOS-XR-optics-speed-cfg {
  namespace "http://cisco.com/ns/yang/Cisco-IOS-XR-optics-speed-cfg";
  prefix optics-speed-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-speed package configuration.
     
     This YANG module augments the
       Cisco-IOS-XR-ifmgr-cfg
     module with configuration data.
     
     Copyright (c) 2013-2022 by Cisco Systems, Inc.
     All rights reserved.";

  revision 2021-06-16 {
    description
      "updated SpeedModeList with speed strings to make case insensitive";
    semver:module-version "1.0.0";
  }
  revision 2021-04-19 {
    description
      "Implement speed none CLI";
  }
  revision 2020-06-18 {
    description
      "Schema added.";
  }
  revision 2019-04-05 {
    description
      "Establish semantic version baseline.";
  }
  revision 2015-11-09 {
    description
      "IOS XR 6.0 revision.";
  }

  typedef Speed-mode-list {
    type string {
      pattern "(1g)|(1G)|(10g)|(10G)|(25g)|(25G)|(40g)|(40G)|(50g)|(50G)|(100g)|(100G)|(200g)|(200G)|(400g)|(400G)|(none)";
    }
    description
      "1g:set optics 1g speed config, 1G:set optics 1G
       speed config, 10g:set optics 10g speed config,
       10G:set optics 10G speed config, 25g:set optics
       25g speed config, 25G:set optics 25G speed config
       , 40g:set optics 40g speed config, 40G:set optics
       40G speed config, 50g:set optics 50g speed config
       , 50G:set optics 50G speed config, 100g:set
       optics 100g speed config, 100G:set optics 100G
       speed config, 200g:set optics 200g speed config,
       200G:set optics 200G speed config, 400g:set
       optics 400g speed config, 400G:set optics 400G
       speed config, none:delete the interface";
  }

  augment "/a1:interface-configurations/a1:interface-configuration" {
    description
      "This augment extends the configuration data of
       'Cisco-IOS-XR-ifmgr-cfg'";
    leaf speed {
      type Speed-mode-list;
      description
        "optics speed set configuration";
    }
  }
}
