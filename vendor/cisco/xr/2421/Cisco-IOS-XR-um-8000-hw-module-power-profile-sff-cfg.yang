module Cisco-IOS-XR-um-8000-hw-module-power-profile-sff-cfg {
  namespace "http://cisco.com/ns/yang/Cisco-IOS-XR-um-8000-hw-module-power-profile-sff-cfg";
  prefix um-8000-hw-module-power-profile-sff-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-hw-module-power-profile-sff package configuration.
     
     This YANG module augments the
     modules with configuration data.
     
     Copyright (c) 2022 by Cisco Systems, Inc.
     All rights reserved.";

  revision 2022-01-24 {
    description
      "Initial release";
  }

  container hw-module {
    description
      "Configure h/w module";
    leaf npu-power-profile {
      type enumeration {
        enum "low" {
          value 1;
          description
            "Use low performance/power";
        }
        enum "medium" {
          value 2;
          description
            "Use medium performance/power";
        }
        enum "high" {
          value 3;
          description
            "Use high performance/power";
        }
      }
      description
        "Asic power usage";
    }
  }
}
