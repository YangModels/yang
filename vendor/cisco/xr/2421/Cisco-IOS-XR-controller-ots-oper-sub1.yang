submodule Cisco-IOS-XR-controller-ots-oper-sub1 {
  belongs-to Cisco-IOS-XR-controller-ots-oper {
    prefix Cisco-IOS-XR-controller-ots-oper;
  }

  import Cisco-IOS-XR-types {
    prefix xr;
  }
  import cisco-semver {
    prefix semver;
  }
  import oc-xr-mapping {
    prefix emmi;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-ots package operational data.
     
     Copyright (c) 2013-2022 by Cisco Systems, Inc.
     All rights reserved.";

  revision 2021-06-14 {
    description
      "Added support for Channel Slice Attenuation Info and Spectrum Info";
    semver:module-version "1.0.0";
  }
  revision 2021-02-17 {
    description
      "Raman Safety Params added";
  }
  revision 2021-02-08 {
    description
      "Ingress/Egress Safety Params added";
  }
  revision 2020-11-10 {
    description
      "Photodiode State Params Added for Ots Controller";
  }
  revision 2020-09-02 {
    description
      "Raman Transmit Params Added for Ots Controller";
  }
  revision 2020-08-21 {
    description
      "New Oper Model Added for Ots Controller";
  }
  revision 2019-04-05 {
    description
      "Establish semantic version baseline.";
  }
  revision 2015-11-09 {
    description
      "IOS XR 6.0 revision.";
  }

  typedef Ots-amplifier-control-mode {
    type enumeration {
      enum "automatic" {
        value 1;
        description
          "Automatic";
      }
      enum "manual" {
        value 2;
        description
          "Manual";
      }
    }
    description
      "Ots amplifier control mode";
  }

  typedef Ots-amplifier-safety-control-mode {
    type enumeration {
      enum "ots-amplifier-safety-mode-invalid" {
        value 0;
        description
          "Invalid";
      }
      enum "ots-amplifier-safety-mode-auto" {
        value 1;
        description
          "auto";
      }
      enum "ots-amplifier-safety-mode-disabled" {
        value 2;
        description
          "disabled";
      }
    }
    description
      "Ots amplifier safety control mode";
  }

  typedef Ots-back-reflection-state-v1 {
    type enumeration {
      enum "disable" {
        value 0;
        description
          "Disable";
      }
      enum "enable" {
        value 1;
        description
          "Enable";
      }
    }
    description
      "Ots back reflection state v1";
  }

  typedef Ots-amplifier-gain-range {
    type enumeration {
      enum "ots-amplifier-gain-range-invalid" {
        value 0;
        description
          "Invalid";
      }
      enum "ots-amplifier-gain-range-normal" {
        value 1;
        description
          "Normal";
      }
      enum "ots-amplifier-gain-range-ext-end-ed" {
        value 2;
        description
          "Extended";
      }
    }
    description
      "Ots amplifier gain range";
  }

  typedef Ots-controller-state {
    type enumeration {
      enum "ots-state-up" {
        value 0;
        description
          "Up";
      }
      enum "ots-state-down" {
        value 1;
        description
          "Down";
      }
      enum "ots-state-admin-down" {
        value 2;
        description
          "Administratively Down";
      }
    }
    description
      "Ots controller state";
  }

  typedef Ots-tas {
    type enumeration {
      enum "ots-tas-ui-oos" {
        value 0;
        description
          "Out Of Service";
      }
      enum "ots-tas-ui-main" {
        value 1;
        description
          "Maintenance";
      }
      enum "ots-tas-ui-is" {
        value 2;
        description
          "In Service";
      }
      enum "ots-tas-ui-ains" {
        value 3;
        description
          "Automatic In Service";
      }
    }
    description
      "Ots tas";
  }

  grouping OTS-EDM-SPECTRUM-POWER-INFO-V1 {
    description
      "OTS EDM SPECTRUM POWER INFO V1";
    leaf slice-num {
      type uint32;
      description
        "spectrum slice number";
    }
    leaf lower-frequency {
      type uint64;
      description
        "Lower frequency of the specified PSD(in unit of
         100MHZ)";
    }
    leaf upper-frequency {
      type uint64;
      description
        "Upper frequency of the specified PSD(in unit of
         100MHz)";
    }
    leaf rx-power {
      type int32;
      description
        "Received Power in dBm multiplied by 100";
    }
    leaf tx-power {
      type int32;
      description
        "Transmit Power in dBm multiplied by 100";
    }
    leaf rx-psd {
      type int32;
      description
        "Received Power spectral density in microwatts
         per megahertz, uW/MHz";
    }
    leaf tx-psd {
      type int32;
      description
        "Transmit Power spectral density in microwatts
         per megahertz, uW/MHz";
    }
  }

  grouping OTS-EDM-SPECTRUM-INFO-V1 {
    description
      "power information of slices in optical spectrum";
    leaf total-spectrum-slice-count {
      type uint32;
      description
        "Total number of slices in Spectrum";
    }
    leaf spectrum-slice-spacing {
      type uint32;
      description
        "Spacing between spectrum slices (in unit of 0
         .01GHz)";
    }
    leaf first-slice-wavelength {
      type uint32;
      description
        "Wavelength of first slice (in unit of 0.01 nm)";
    }
    list spectrum-slice-power-info {
      description
        "Power information of spectrum slice info";
      uses OTS-EDM-SPECTRUM-POWER-INFO-V1;
    }
  }

  grouping OTS-EDM-SPECTRUM-BAG-INFO {
    description
      "ots spectrum information";
    container spectrum-info {
      description
        "OTS Spectrum information";
      uses OTS-EDM-SPECTRUM-INFO-V1;
    }
  }

  grouping OTS-EGRESS-CHANNEL-SLICE-V1 {
    description
      "OTS Egress Channel Slice Attenuation Information";
    leaf egress-channel-slice {
      type uint32;
      description
        "Egress Channel Slice";
    }
    leaf egress-channel-slice-attenuation {
      type int32;
      description
        "Egress Channel Slice Attenuation in units of 0.1
         dB";
    }
  }

  grouping OTS-EGRESS-CHANNEL-SLICE-PARAM-V1 {
    description
      "Egress Channel Slice Attenuation Params";
    list egress-channel-slice {
      description
        "Egress Channel Slice List";
      uses OTS-EGRESS-CHANNEL-SLICE-V1;
    }
  }

  grouping OTS-INGRESS-CHANNEL-SLICE-V1 {
    description
      "OTS Ingress Channel Slice Attenuation Information";
    leaf ingress-channel-slice {
      type uint32;
      description
        "Ingress Channel Slice";
    }
    leaf ingress-channel-slice-attenuation {
      type int32;
      description
        "Ingress Channel Slice Attenuation in units of 0
         .1 dB";
    }
  }

  grouping OTS-INGRESS-CHANNEL-SLICE-PARAM-V1 {
    description
      "Ingress Channel Slice Attenuation Parameters";
    list ingress-channel-slice {
      description
        "Ingress Channel Slice List";
      uses OTS-INGRESS-CHANNEL-SLICE-V1;
    }
  }

  grouping OTS-RECEIVE-POWER-V1 {
    description
      "Proprietary OTS Receive Power Parameters";
    list receive-power {
      description
        "Receive Power count";
      uses OTS-POWER-LIST-V1;
    }
  }

  grouping OTS-POWER-LIST-V1 {
    description
      "Proprietary OTS Transmit/Receive Power Parameters";
    leaf instance {
      type uint32;
      description
        "Transmit/Receive Power Parameter Type(in units
         of 0.01dBm)";
    }
    leaf value {
      type int32;
      description
        "Transmit/Receive Power Parameter Value(in unit
         of 0.01dBm)";
    }
  }

  grouping OTS-TRANSMIT-POWER-V1 {
    description
      "Proprietary OTS Transmit Power Parameters";
    list transmit-power {
      description
        "Transmit Power count";
      uses OTS-POWER-LIST-V1;
    }
  }

  grouping OTS-RAMAN-TX-POWER {
    description
      "OTS Raman Transmit Power information";
    leaf raman-tx-power-instance {
      type uint32;
      description
        "Raman Transmit Power Intance";
    }
    leaf raman-tx-power-value {
      type uint32;
      description
        "Raman Transmit Power Value in units of 0.01mW";
    }
    leaf raman-tx-wavelength {
      type uint32;
      description
        "Raman Transmit Wavelength in units of nm";
    }
  }

  grouping OTS-RAMAN-PARAM {
    description
      "Proprietary Raman transmit power Parameters";
    list raman-tx-power {
      description
        "raman transmit power count";
      uses OTS-RAMAN-TX-POWER;
    }
  }

  grouping OTS-EDM-INFO {
    description
      "ots transponder information";
    container raman-tx-power {
      description
        "Raman Tx Power";
      uses OTS-RAMAN-PARAM;
    }
    container transmit-n-power {
      description
        "Transmit N Power in the unit of 0.01dBm";
      uses OTS-TRANSMIT-POWER-V1;
    }
    container receive-n-power {
      description
        "Receive N Power in the unit of 0.01dBm";
      uses OTS-RECEIVE-POWER-V1;
    }
    container ingress-channel-slice-attenuation {
      description
        "Ingress Channel Slice Attenuation in units of 0
         .1 dB";
      uses OTS-INGRESS-CHANNEL-SLICE-PARAM-V1;
    }
    container egress-channel-slice-attenuation {
      description
        "Egress Channel Slice Attenuation in units of 0.1
         dB";
      uses OTS-EGRESS-CHANNEL-SLICE-PARAM-V1;
    }
    container raman-tx-power-config {
      description
        "Raman Tx Power";
      uses OTS-RAMAN-PARAM;
    }
    container ingress-channel-slice-attenuation-configured {
      description
        "Ingress Channel Slice Attenuation Configured in
         units of 0.1 dB";
      uses OTS-INGRESS-CHANNEL-SLICE-PARAM-V1;
    }
    container egress-channel-slice-attenuation-configured {
      description
        "Egress Channel Slice Attenuation Configured in
         units of 0.1 dB";
      uses OTS-EGRESS-CHANNEL-SLICE-PARAM-V1;
    }
    leaf transport-admin-state {
      type Ots-tas;
      description
        "Transport Admin State";
      xr:event-telemetry "Subscribe Telemetry Event";
    }
    leaf rx-pow-low-threshold {
      type int32;
      description
        "Rx Low threshold value in units of 0.1dBm";
    }
    leaf rx-pow-high-threshold {
      type int32;
      description
        "Rx High threshold value in units of 0.1dBm";
    }
    leaf tx-pow-low-threshold {
      type int32;
      description
        "Tx Low threshold value in units of 0.1dBm";
    }
    leaf tx-pow-high-threshold {
      type int32;
      description
        "Tx High threshold value in units of 0.1dBm";
    }
    leaf pm-enable {
      type uint32;
      description
        "PmEable or Disable";
    }
    leaf controller-state {
      type Ots-controller-state;
      description
        "Ots controller state: Up, Down or
         Administratively Down";
      xr:event-telemetry "Subscribe Telemetry Event";
    }
    leaf rx-voa-attenuation {
      type int32;
      description
        "Rx Voa Attenuation in the units of 0.1dB";
    }
    leaf tx-voa-attenuation {
      type int32;
      description
        "Tx Voa Attenuation in the units of 0.1dB";
      emmi:map-to {
        emmi:from {
          emmi:parent "/ots-oper/ots-ports/ots-port/ots-info";
          emmi:function "oc_opt_att_state_attenuation_to_high" {
            emmi:category "manual_function";
          }
          emmi:function "oc_opt_att_enabled_to_high" {
            emmi:category "manual_function";
          }
          emmi:function "oc_opt_att_state_actual_atten_instant_to_high" {
            emmi:category "manual_function";
          }
        }
      }
    }
    leaf channel-width {
      type uint32;
      description
        "Channel Width (in Unit of 0.1 GHz)";
    }
    leaf central-frequncy {
      type uint32;
      description
        "frequency read from hw in the units of 0.01 THz";
    }
    leaf add-drop-channel {
      type string;
      description
        "Add Drop Channel R/S/I/P/ch";
    }
    leaf line-channel {
      type string;
      description
        "Line Channel R/S/I/P/ch";
    }
    leaf ingress-ampli-gain {
      type uint32;
      description
        "Ingress Ampli Gain in the unit of 0.01dB";
    }
    leaf ingress-ampli-tilt {
      type int32;
      description
        "Ingress Ampli Tilt in the unit of 0.01dB";
    }
    leaf ingress-amp-gain-deg-thres-low {
      type uint32;
      description
        "IngressAmpli Gain Deg Low threshold in the unit
         of 0.01dB";
    }
    leaf ingress-amp-gain-deg-thres-high {
      type uint32;
      description
        "Ingress Ampli Gain Deg High threshold in the
         unit of 0.01dB";
    }
    leaf ingress-ampli-gain-range {
      type Ots-amplifier-gain-range;
      description
        "Ingress Ampli gain range";
    }
    leaf egress-ampli-gain {
      type uint32;
      description
        "Egress Ampli Gain in the unit of 0.01dB";
    }
    leaf egress-ampli-tilt {
      type int32;
      description
        "Egress Ampli Tilt in the unit of 0.01dB";
    }
    leaf egress-amp-gain-deg-thres-low {
      type uint32;
      description
        "EgressAmpli Gain Deg Low Threshold in the unit
         of 0.01dB";
    }
    leaf egress-amp-gain-deg-thres-high {
      type uint32;
      description
        "Egress Ampli Gain Deg High Threshold in the unit
         of 0.01dB";
    }
    leaf egress-ampli-gain-range {
      type Ots-amplifier-gain-range;
      description
        "Egress Ampli gain range";
    }
    leaf composite-raman-power {
      type uint32;
      description
        "Composite Raman Power in the unit of 0.01 mW";
    }
    leaf wavelength {
      type uint32;
      description
        "Wavelength in unit of 0.01 nm";
    }
    leaf transmit-power {
      type int32;
      description
        "Transmit power in the units of 0.01dBm";
    }
    leaf receive-power {
      type int32;
      description
        "Receive power in the units of 0.01dBm";
    }
    leaf total-cl-tx-power {
      type int32;
      description
        "Total (L+C)-transmit Power in the unit of 0
         .01dBm";
    }
    leaf total-cl-rx-power {
      type int32;
      description
        "Total (L+C)-receive Power in the unit of 0.01dBm";
    }
    leaf ingress-ampli-osri {
      type boolean;
      description
        "Ingress Ampli Osri";
    }
    leaf egress-ampli-osri {
      type boolean;
      description
        "Egress Ampli Osri";
    }
    leaf ingress-ampli-force-apr {
      type boolean;
      description
        "Ingress Ampli Force Apr";
    }
    leaf egress-ampli-force-apr {
      type boolean;
      description
        "Egress Ampli Force Apr";
    }
    leaf egress-ampli-br {
      type Ots-back-reflection-state-v1;
      description
        "Egress Ampli Br";
    }
    leaf ingress-ampli-safety-control-mode {
      type Ots-amplifier-safety-control-mode;
      description
        "Ingress Ampli Safety control mode";
    }
    leaf egress-ampli-safety-control-mode {
      type Ots-amplifier-safety-control-mode;
      description
        "Egress Ampli Safety control mode";
    }
    leaf ingress-ampli-safety-control-mode-configured {
      type Ots-amplifier-safety-control-mode;
      description
        "Ingress Ampli Safety Control Mode Configured";
    }
    leaf egress-ampli-safety-control-mode-configured {
      type Ots-amplifier-safety-control-mode;
      description
        "Egress Ampli Safety Control Mode Configured";
    }
    leaf egress-br-high-threshold {
      type int32;
      description
        "Egress Br High Threshold in units of 0.1 dBm";
    }
    leaf ingress-ampli-osri-configured {
      type boolean;
      description
        "Ingress Ampli Osri Configured";
    }
    leaf egress-ampli-osri-configured {
      type boolean;
      description
        "Egress Ampli Osri Configured";
    }
    leaf ingress-ampli-force-apr-configured {
      type boolean;
      description
        "Ingress Ampli Force Apr Configured";
    }
    leaf egress-ampli-force-apr-configured {
      type boolean;
      description
        "Egress Ampli Force Apr Configured";
    }
    leaf egress-ampli-br-configured {
      type Ots-back-reflection-state-v1;
      description
        "Egress Ampli Br Configured";
    }
    leaf raman-safety-control-mode {
      type Ots-amplifier-safety-control-mode;
      description
        "Raman Safety control mode";
    }
    leaf raman-safety-control-mode-configured {
      type Ots-amplifier-safety-control-mode;
      description
        "Raman Safety control mode Configured";
    }
    leaf raman-osri {
      type boolean;
      description
        "Raman Osri";
    }
    leaf raman-force-apr {
      type boolean;
      description
        "Raman Force Apr";
    }
    leaf raman-br {
      type Ots-back-reflection-state-v1;
      description
        "Raman Br";
    }
    leaf raman-br-high-threshold {
      type int32;
      description
        "Raman Br High Threshold in units of 0.1 dBm";
    }
    leaf raman-osri-configured {
      type boolean;
      description
        "Raman Osri Configured";
    }
    leaf raman-force-apr-configured {
      type boolean;
      description
        "Raman Force Apr Configured";
    }
    leaf raman-br-configured {
      type Ots-back-reflection-state-v1;
      description
        "Raman Br Configured";
    }
    leaf rx-pow-low-warning-threshold {
      type int32;
      description
        "Rx Low Warning threshold value in units of 0
         .1dBm";
    }
    leaf rx-pow-high-warning-threshold {
      type int32;
      description
        "Rx High Warning threshold value in units of 0
         .1dBm";
    }
    leaf tx-pow-low-warning-threshold {
      type int32;
      description
        "Tx Low Warning threshold value in units of 0
         .1dBm";
    }
    leaf tx-pow-high-warning-threshold {
      type int32;
      description
        "Tx High Warning threshold value in units of 0
         .1dBm";
    }
    leaf description {
      type string;
      description
        "Controller description string";
    }
    leaf channel-attenuation {
      type int32;
      description
        "Channel Attenuation in units of 0.1 dB";
    }
    leaf rx-voa-attenuation-config-val {
      type int32;
      description
        "RX VOA attenuation configured value in units of
         0.1dB";
    }
    leaf tx-voa-attenuation-config-val {
      type int32;
      description
        "TX VOA attenuation configured value in units of
         0.1dB";
    }
    leaf ampli-control-mode-config-val {
      type Ots-amplifier-control-mode;
      description
        "ampli control mode config val";
    }
    leaf rx-low-th-psd-config-val {
      type int32;
      description
        "Rx Low threshold psd value in units of 0.001
         nW/MHz";
    }
    leaf total-rx-power {
      type int32;
      description
        "Total Receive Power  -> C/L-band power + OSC
         power (in units of 0.01 dBm)";
    }
    leaf total-tx-power {
      type int32;
      description
        "Total Transmit Power -> C/L-band power + OSC
         power (in units of 0.01 dBm)";
    }
    leaf ingress-ampli-gain-range-config-val {
      type Ots-amplifier-gain-range;
      description
        "ingress ampli gain range config val";
    }
    leaf ingress-ampli-gain-config {
      type uint32;
      description
        "Ingress Ampli gain configured value in units of
         0.01dB";
    }
    leaf ingress-ampli-tilt-config {
      type int32;
      description
        "Ingress Ampli tilt configured value in units of
         0.01dB";
    }
    leaf ingress-ampli-thr-deg-low-config {
      type uint32;
      description
        "Ingress Ampli gain low degrade threshold
         configured value in units of 0.01dB";
    }
    leaf ingress-ampli-thr-deg-high-config {
      type uint32;
      description
        "Ingress Ampli gain high degrade threshold
         configured value in units of 0.01dB";
    }
    leaf egress-ampli-gain-range-config-val {
      type Ots-amplifier-gain-range;
      description
        "egress ampli gain range config val";
    }
    leaf egress-ampli-gain-config {
      type uint32;
      description
        "Egress Ampli gain configured value in units of 0
         .01dB";
    }
    leaf egress-ampli-tilt-config {
      type int32;
      description
        "Egress Ampli tilt configured value in units of 0
         .01dB";
    }
    leaf egress-ampli-gain-thr-deg-low-config {
      type uint32;
      description
        "Egress Ampli gain low degrade threshold
         configured value in units of 0.01dB";
    }
    leaf egress-ampli-gain-thr-deg-high-config {
      type uint32;
      description
        "Egress Ampli gain high degrade threshold
         configured value in units of 0.01dB";
    }
    leaf channel-attenuation-configured {
      type int32;
      description
        "Channel Attenuation Configured in units of 0.1
         dB";
    }
  }
  emmi:mapping {
    emmi:package-name "ocopticalattenuator";
    emmi:model-id "xr";
    emmi:module-id "cisco_ios_xr_controller_ots_oper_sub1";
    emmi:target {
      emmi:model-id "oc";
      emmi:module-id "openconfig_optical_attenuator";
      emmi:namespace "oc-types|http://openconfig.net/yang/openconfig-types";
      emmi:namespace "oc-opt-att|http://openconfig.net/yang/optical-attenuator";
      emmi:namespace "oc-platform|http://openconfig.net/yang/platform";
      emmi:namespace "oc-ext|http://openconfig.net/yang/openconfig-ext";
      emmi:namespace "oc-ext|http://openconfig.net/yang/openconfig-ext";
      emmi:namespace "oc-platform|http://openconfig.net/yang/platform";
      emmi:namespace "oc-yang|http://openconfig.net/yang/types/yang";
      emmi:namespace "oc-platform-types|http://openconfig.net/yang/platform-types";
      emmi:namespace "oc-alarm-types|http://openconfig.net/yang/alarms/types";
    }
  }
}
