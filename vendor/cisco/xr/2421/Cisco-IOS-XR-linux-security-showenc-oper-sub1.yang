submodule Cisco-IOS-XR-linux-security-showenc-oper-sub1 {
  belongs-to Cisco-IOS-XR-linux-security-showenc-oper {
    prefix Cisco-IOS-XR-linux-security-showenc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR linux-security-showenc package operational data.
     
     Copyright (c) 2013-2022 by Cisco Systems, Inc.
     All rights reserved.";

  revision 2021-07-01 {
    description
      "Adding show disk-encryption status yang model";
    semver:module-version "1.0.0";
  }
  revision 2019-04-05 {
    description
      "Establish semantic version baseline.";
  }
  revision 2015-11-09 {
    description
      "IOS XR 6.0 revision.";
  }

  grouping SHOW-DISK-ENC-STATUS-DATA {
    description
      "Show disk-encryption status output";
    leaf lv-mnt-pt {
      type string {
        length "0..256";
      }
      description
        "string lv_mntpt";
    }
    leaf enc-status {
      type string {
        length "0..32";
      }
      description
        "string enc_status";
    }
    leaf mnt-status {
      type string {
        length "0..32";
      }
      description
        "string mount_status";
    }
    leaf prep-status {
      type string {
        length "0..32";
      }
      description
        "string prep_status";
    }
  }
}
