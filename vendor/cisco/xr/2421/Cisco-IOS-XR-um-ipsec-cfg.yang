module Cisco-IOS-XR-um-ipsec-cfg {
  namespace "http://cisco.com/ns/yang/Cisco-IOS-XR-um-ipsec-cfg";
  prefix um-ipsec-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipsec package configuration.
     
     This YANG module augments the
     modules with configuration data.
     
     Copyright (c) 2022-2024 by Cisco Systems, Inc.
     All rights reserved.";

  revision 2024-01-31 {
    description
      "change in transform-set enum values";
  }
  revision 2023-06-09 {
    description
      "responder-only CLI added";
  }
  revision 2022-03-29 {
    description
      "Initial release";
  }

  container ipsec {
    description
      "Configure IPSEC policy";
    container transform-sets {
      description
        "Define transform and settings";
      list transform-set {
        key "transform-set-name";
        description
          "Define transform and settings";
        leaf transform-set-name {
          type xr:Cisco-ios-xr-string {
            length "1..32" {
              description
                "Transform set tag - maximum 32 characters";
            }
          }
          description
            "Define transform and settings";
        }
        container transform {
          must "esp-hmac-sha-256 or esp-hmac-sha-384 or esp-hmac-sha-512 or esp-hmac-sha1 or esp-aes or esp-192-aes or esp-256-aes";
          presence "Indicates a transform node is configured.";
          description
            "Define transforms (protocols) for the transform set";
          container esp-hmac-sha1 {
            must "not(../esp-hmac-sha-256 or ../esp-hmac-sha-384 or ../esp-hmac-sha-512)";
            presence "Indicates a esp-hmac-sha1 node is configured.";
            description
              "ESP transform using HMAC-SHA1 auth";
          }
          container esp-hmac-sha-256 {
            must "not(../esp-hmac-sha1 or ../esp-hmac-sha-384 or ../esp-hmac-sha-512)";
            presence "Indicates a esp-hmac-sha-256 node is configured.";
            description
              "ESP transform using HMAC-SHA-256 auth";
          }
          container esp-hmac-sha-384 {
            must "not(../esp-hmac-sha-256 or ../esp-hmac-sha1 or ../esp-hmac-sha-512)";
            presence "Indicates a esp-hmac-sha-384 node is configured.";
            description
              "ESP transform using HMAC-SHA-384 auth";
          }
          container esp-hmac-sha-512 {
            must "not(../esp-hmac-sha-256 or ../esp-hmac-sha-384 or ../esp-hmac-sha1)";
            presence "Indicates a esp-hmac-sha-512 node is configured.";
            description
              "ESP transform using HMAC-SHA-512 auth";
          }
          container esp-aes {
            must "not(../esp-192-aes or ../esp-256-aes)";
            presence "Indicates a esp-aes node is configured.";
            description
              "ESP transform using AES cipher (128 bits)";
          }
          container esp-192-aes {
            must "not(../esp-aes or ../esp-256-aes)";
            presence "Indicates a esp-192-aes node is configured.";
            description
              "ESP transform using AES cipher (192 bits)";
          }
          container esp-256-aes {
            must "not(../esp-192-aes or ../esp-aes)";
            presence "Indicates a esp-256-aes node is configured.";
            description
              "ESP transform using AES cipher (256 bits)";
          }
        }
        container mode {
          description
            "encapsulation mode (transport/tunnel)";
          container tunnel {
            presence "Indicates a tunnel node is configured.";
            description
              "tunnel encapsulation mode";
          }
        }
      }
    }
    container profiles {
      description
        "Configure IPSEC profile";
      list profile {
        key "profile-name";
        description
          "Configure IPSEC profile";
        leaf profile-name {
          type xr:Cisco-ios-xr-string {
            length "1..32" {
              description
                "IPSec profile name - maximum 32 characters";
            }
          }
          description
            "Configure IPSEC profile";
        }
        container set {
          description
            "Specify profile settings";
          container pfs {
            description
              "Specify PFS setting ";
            container group19 {
              must "not(../group20 or ../group21)";
              presence "Indicates a group19 node is configured.";
              description
                "D-H Group1 (768-bit modp)";
            }
            container group20 {
              must "not(../group19 or ../group21)";
              presence "Indicates a group20 node is configured.";
              description
                "D-H Group2 (1024-bit modp)";
            }
            container group21 {
              must "not(../group19 or ../group20)";
              presence "Indicates a group21 node is configured.";
              description
                "D-H Group5 (1536-bit modp)";
            }
          }
          container transform-set {
            description
              "Specify list of transform sets in priority order";
            leaf transform1 {
              type xr:Cisco-ios-xr-string {
                length "1..32" {
                  description
                    "Transform - maximum 32 characters";
                }
              }
              description
                "Transform - maximum 32 characters";
            }
            leaf transform2 {
              type xr:Cisco-ios-xr-string {
                length "1..32" {
                  description
                    "Transform - maximum 32 characters";
                }
              }
              must "../transform1";
              description
                "Transform - maximum 32 characters";
            }
            leaf transform3 {
              type xr:Cisco-ios-xr-string {
                length "1..32" {
                  description
                    "Transform - maximum 32 characters";
                }
              }
              must "../transform1 and ../transform2";
              description
                "Transform - maximum 32 characters";
            }
            leaf transform4 {
              type xr:Cisco-ios-xr-string {
                length "1..32" {
                  description
                    "Transform - maximum 32 characters";
                }
              }
              must "../transform1 and ../transform2 and ../transform3";
              description
                "Transform - maximum 32 characters";
            }
            leaf transform5 {
              type xr:Cisco-ios-xr-string {
                length "1..32" {
                  description
                    "Transform - maximum 32 characters";
                }
              }
              must "../transform1 and ../transform2 and ../transform3 and ../transform4";
              description
                "Transform - maximum 32 characters";
            }
          }
          leaf ikev2-profile {
            type xr:Cisco-ios-xr-string {
              length "1..32" {
                description
                  "Enter name of IKEV2 profile of max length 32";
              }
            }
            description
              "Specify the ikev2 profile";
          }
          container security-association {
            description
              "Security association parameters";
            container lifetime {
              description
                "Security association lifetime";
              leaf seconds {
                type uint32 {
                  range "120..2592000" {
                    description
                      "Security-association duration in seconds";
                  }
                }
                description
                  "Time-based key duration in seconds";
              }
            }
          }
          container responder-only {
            presence "Indicates a responder-only node is configured.";
            description
              "Waits for connection request from peer";
          }
        }
      }
    }
  }
}
