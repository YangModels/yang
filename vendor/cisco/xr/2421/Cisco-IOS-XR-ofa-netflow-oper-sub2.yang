submodule Cisco-IOS-XR-ofa-netflow-oper-sub2 {
  belongs-to Cisco-IOS-XR-ofa-netflow-oper {
    prefix Cisco-IOS-XR-ofa-netflow-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-netflow package operational data.
     
     Copyright (c) 2013-2019, 2022 by Cisco Systems, Inc.
     All rights reserved.";

  revision 2019-08-26 {
    description
      "Update leaf fields";
    semver:module-version "1.0.0";
  }
  revision 2019-04-05 {
    description
      "Establish semantic version baseline.";
  }
  revision 2015-11-09 {
    description
      "IOS XR 6.0 revision.";
  }

  grouping NF-PRODUCER-STATS {
    description
      "Netflow Platform Producer Process statistics";
    leaf ipv4-ingress-flows {
      type uint64;
      description
        "IPv4 ingress flows";
    }
    leaf ipv4-egress-flows {
      type uint64;
      description
        "IPv4 egress flows";
    }
    leaf ipv6-ingress-flows {
      type uint64;
      description
        "IPv6 ingress flows";
    }
    leaf ipv6-egress-flows {
      type uint64;
      description
        "IPv6 egress flows";
    }
    leaf mpls-ingress-flows {
      type uint64;
      description
        "MPLS ingress flows";
    }
    leaf mpls-egress-flows {
      type uint64;
      description
        "MPLS egress flows";
    }
    leaf ipfix315-ingress-flows {
      type uint64;
      description
        "IPFIX315 ingress flows";
    }
    leaf ipfix315-egress-flows {
      type uint64;
      description
        "IPFIX315 egress flows";
    }
    leaf sflow-ingress-flows {
      type uint64;
      description
        "sFlow ingress flows";
    }
    leaf sflow-egress-flows {
      type uint64;
      description
        "sFlow egress flows";
    }
    leaf drops-no-space {
      type uint64;
      description
        "Drops (no space)";
    }
    leaf drops-others {
      type uint64;
      description
        "Drops (others)";
    }
    leaf unknown-ingress-flows {
      type uint64;
      description
        "Unknown ingress flows";
    }
    leaf unknown-egress-flows {
      type uint64;
      description
        "Unknown egress flows";
    }
    leaf last-cleared {
      type string;
      description
        "Last time Statistics cleared in 'Mon Jan 1 12:00
         :00 2xxx' format";
    }
  }
}
