module Cisco-IOS-XR-acl-hw-oper {
  namespace "http://cisco.com/ns/yang/Cisco-IOS-XR-acl-hw-oper";
  prefix acl-hw-oper;

  import Cisco-IOS-XR-types {
    prefix xr;
  }
  import cisco-semver {
    prefix semver;
  }
  include Cisco-IOS-XR-acl-hw-oper-sub1 {
    revision-date 2023-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR acl-hw package operational data.
     
     This module contains definitions
     for the following management objects:
       access-list-hardware: Root class of accesslist hardware
     
     Copyright (c) 2013-2023 by Cisco Systems, Inc.
     All rights reserved.";

  revision 2023-11-09 {
    description
      "Removal of enum qos-ea in schema, CSCwh91588";
    semver:module-version "1.0.0";
  }
  revision 2023-02-21 {
    description
      "Fixed the Traceback error CSCwe41742";
  }
  revision 2023-02-03 {
    description
      "Adding support for ACL HW schema";
  }
  revision 2019-04-05 {
    description
      "Establish semantic version baseline.";
  }
  revision 2015-11-09 {
    description
      "IOS XR 6.0 revision.";
  }

  typedef Client-id {
    type enumeration {
      enum "pfilter-ea" {
        value 0;
        description
          "pfilter client id";
      }
    }
    description
      "Client id";
  }

  typedef Acl-hw-sequence-number-range {
    type uint32 {
      range "0..2147483646";
    }
    description
      "Acl hw sequence number range";
  }

  grouping IPV4-VERIFY {
    description
      "Common node of egress-verify, ingress-verify";
    container ipv4-verify {
      description
        "Verify Accesslist version IPv4";
      uses ACCESS-LIST-TABLE-VERIFY;
    }
  }

  grouping ACCESS-LIST-TABLE {
    description
      "Common node of ipv4, ipv6, common-acl-ipv4,
       common-acl-ipv6";
    container accesses {
      description
        "Table for access lists";
      list access {
        key "access-list-name";
        description
          "List of ACLs";
        container implicit {
          description
            "Implicit ACL information";
          uses DPA-FM-CLIENT-SH-ENTRY-IMPLICIT-DETAIL-ARRAY;
        }
        container sequence-details {
          description
            "Table of all sequence numbers per ACL";
          list sequence-detail {
            key "sequence-number";
            description
              "Detail ACL information";
            leaf sequence-number {
              type Acl-hw-sequence-number-range;
              description
                "Detail ACL information for a particular
                 sequence";
            }
            uses DPA-FM-CLIENT-SH-ENTRY-DETAIL-ARRAY;
          }
        }
        leaf access-list-name {
          type string;
          description
            "Name of the access list";
        }
      }
    }
  }

  grouping COMMON-ACL-IPV4 {
    description
      "Common node of egress, ingress";
    container common-acl-ipv4 {
      description
        "Common Accesslist list";
      uses ACCESS-LIST-TABLE;
    }
  }

  grouping COMMON-ACL-IPV6 {
    description
      "Common node of egress, ingress";
    container common-acl-ipv6 {
      description
        "Common Accesslist list";
      uses ACCESS-LIST-TABLE;
    }
  }

  grouping IPV6-VERIFY {
    description
      "Common node of egress-verify, ingress-verify";
    container ipv6-verify {
      description
        "Verify accesslist version IPv6";
      uses ACCESS-LIST-TABLE-VERIFY;
    }
  }

  grouping ACCESS-LIST-TABLE-VERIFY {
    description
      "Common node of ipv4-verify, ipv6-verify,
       common-acl-ipv4-verify, common-acl-ipv6-verify";
    container access-list-verifies {
      description
        "Table for verifying access lists";
      list access-list-verify {
        key "access-list-name";
        description
          "List of ACLs";
        container tcam-verify {
          description
            "Verify ACL TCAM on all NPUs";
          uses DPA-FM-CLIENT-VERIFY-NPU-ARRAY;
        }
        leaf access-list-name {
          type string;
          description
            "Name of the access list";
        }
      }
    }
  }

  grouping IPV4 {
    description
      "Common node of egress, ingress";
    container ipv4 {
      description
        "Accesslist version IPv4";
      uses ACCESS-LIST-TABLE;
    }
  }

  grouping IPV6 {
    description
      "Common node of egress, ingress";
    container ipv6 {
      description
        "Accesslist version IPv6";
      uses ACCESS-LIST-TABLE;
    }
  }

  grouping COMMON-ACL-IPV4-VERIFY {
    description
      "Common node of egress-verify, ingress-verify";
    container common-acl-ipv4-verify {
      description
        "Verify Common accesslist version IPv4";
      uses ACCESS-LIST-TABLE-VERIFY;
    }
  }

  grouping COMMON-ACL-IPV6-VERIFY {
    description
      "Common node of egress-verify, ingress-verify";
    container common-acl-ipv6-verify {
      description
        "Verify Common accesslist version IPv6";
      uses ACCESS-LIST-TABLE-VERIFY;
    }
  }

  container access-list-hardware {
    config false;
    description
      "Root class of accesslist hardware";
    container nodes {
      description
        "Accesslist nodes";
      list node {
        key "node-name";
        description
          "Accesslist node";
        leaf node-name {
          type xr:Node-id;
          description
            "Node name";
        }
        list acl-client-id {
          key "client";
          description
            "Client ID of ACL";
          container verify-hw {
            description
              "Accesslist list hardware";
            container ingress-verify {
              description
                "Verify accesslist on direction ingress";
              uses COMMON-ACL-IPV4-VERIFY;
              uses IPV4-VERIFY;
              uses COMMON-ACL-IPV6-VERIFY;
              uses IPV6-VERIFY;
            }
            container egress-verify {
              description
                "Verify Accesslist on direction egress";
              uses COMMON-ACL-IPV4-VERIFY;
              uses IPV4-VERIFY;
              uses COMMON-ACL-IPV6-VERIFY;
              uses IPV6-VERIFY;
            }
          }
          container acl-list-lookup-types {
            description
              "List the ACE entries of the ACL";
            list acl-list-lookup-type {
              key "acl-lookup-type";
              description
                "Lookup type of the ACL";
              leaf acl-lookup-type {
                type uint32;
                description
                  "ACL Lookup Type";
              }
              list acl-list-direction {
                key "direction";
                description
                  "Direction of the ACL";
                leaf direction {
                  type uint32;
                  description
                    "ACL Direction";
                }
                list acl-list-name {
                  key "access-list-name";
                  description
                    "Name of the ACL";
                  leaf access-list-name {
                    type xr:Cisco-ios-xr-string {
                      length "1..65";
                    }
                    description
                      "Name of the access list";
                  }
                  list ace-list-sequence {
                    key "sequence-number";
                    description
                      "ACE sequence number";
                    leaf sequence-number {
                      type Acl-hw-sequence-number-range;
                      description
                        "Detail ACL information for a particular
                         sequence";
                    }
                    list acl-list-interface {
                      key "name";
                      description
                        "Interface to which the ACL is attached";
                      leaf name {
                        type xr:Interface-name;
                        description
                          "ACL Interface";
                      }
                      list acl-list-implicit {
                        key "acl-implicit";
                        description
                          "Implicit ACL information";
                        leaf acl-implicit {
                          type uint32;
                          description
                            "Get the details of Implicit ACL";
                        }
                        uses DPA-FM-CLIENT-SH-ENTRY-ARRAY;
                      }
                    }
                  }
                }
              }
            }
          }
          container check-lookup-types {
            description
              "Check to verify if ACL exists";
            list check-lookup-type {
              key "check-acl-lookup-type";
              description
                "Lookup type of the ACL";
              leaf check-acl-lookup-type {
                type uint32;
                description
                  "ACL Lookup Type";
              }
              list check-acl-direction {
                key "check-direction";
                description
                  "Direction of the ACL";
                leaf check-direction {
                  type uint32;
                  description
                    "ACL Direction";
                }
                list check-acl-name {
                  key "access-list-name";
                  description
                    "Name of the ACL";
                  leaf access-list-name {
                    type xr:Cisco-ios-xr-string {
                      length "1..65";
                    }
                    description
                      "Name of the access list";
                  }
                  list check-acl-interface {
                    key "name";
                    description
                      "Interface to which the ACL is attached";
                    leaf name {
                      type xr:Interface-name;
                      description
                        "ACL Interface";
                    }
                    leaf is-attach {
                      type uint32;
                      mandatory true;
                      description
                        "Usage Statistics Details";
                    }
                  }
                }
              }
            }
          }
          container verify-lookup-types {
            description
              "Verify ACL configuration";
            list verify-lookup-type {
              key "acl-lookup-type";
              description
                "Lookup type of the ACL";
              leaf acl-lookup-type {
                type uint32;
                description
                  "ACL Lookup Type";
              }
              list verify-acl-direction {
                key "direction";
                description
                  "Direction of the ACL";
                leaf direction {
                  type uint32;
                  description
                    "ACL Direction";
                }
                list verify-acl-name {
                  key "access-list-name";
                  description
                    "Name of the ACL";
                  leaf access-list-name {
                    type xr:Cisco-ios-xr-string {
                      length "1..65";
                    }
                    description
                      "Name of the access list";
                  }
                  list verify-acl-interface {
                    key "name";
                    description
                      "Interface to which the ACL is attached";
                    leaf name {
                      type xr:Interface-name;
                      description
                        "ACL Interface";
                    }
                    uses DPA-FM-CLIENT-VERIFY-REGION-ARRAY;
                  }
                }
              }
            }
          }
          container list-hw {
            description
              "Accesslist list hardware";
            container ingress {
              description
                "Accesslist list direction ingress";
              uses IPV4;
              uses COMMON-ACL-IPV6;
              uses COMMON-ACL-IPV4;
              uses IPV6;
            }
            container egress {
              description
                "Accesslist list direction egress";
              uses IPV4;
              uses COMMON-ACL-IPV6;
              uses COMMON-ACL-IPV4;
              uses IPV6;
            }
          }
          container acl-stats-lookup-types {
            description
              "ACE entries statistics";
            list acl-stats-lookup-type {
              key "acl-lookup-type";
              description
                "Lookup type of the ACL";
              leaf acl-lookup-type {
                type uint32;
                description
                  "ACL Lookup Type";
              }
              list acl-stats-direction {
                key "direction";
                description
                  "Direction of the ACL";
                leaf direction {
                  type uint32;
                  description
                    "ACL Direction";
                }
                list acl-stats-name {
                  key "access-list-name";
                  description
                    "Name of the ACL";
                  leaf access-list-name {
                    type xr:Cisco-ios-xr-string {
                      length "1..65";
                    }
                    description
                      "Name of the access list";
                  }
                  list ace-stats-sequence {
                    key "sequence-number";
                    description
                      "ACE sequence number";
                    leaf sequence-number {
                      type Acl-hw-sequence-number-range;
                      description
                        "Detail ACL information for a particular
                         sequence";
                    }
                    list acl-stats-interface {
                      key "name";
                      description
                        "Interface to which the ACL is attached";
                      leaf name {
                        type xr:Interface-name;
                        description
                          "ACL Interface";
                      }
                      uses DPA-FM-CLIENT-SH-ENTRY-INFO;
                    }
                  }
                }
              }
            }
          }
          leaf client {
            type Client-id;
            description
              "Client ID";
          }
        }
      }
    }
  }
}
