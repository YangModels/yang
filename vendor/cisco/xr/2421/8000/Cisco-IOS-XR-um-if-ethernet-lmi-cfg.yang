module Cisco-IOS-XR-um-if-ethernet-lmi-cfg {
  namespace "http://cisco.com/ns/yang/Cisco-IOS-XR-um-if-ethernet-lmi-cfg";
  prefix um-if-ethernet-lmi-cfg;

  import Cisco-IOS-XR-um-interface-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-ethernet-lmi package configuration.
     
     This YANG module augments the
     modules with configuration data.
     
     Copyright (c) 2020-2022 by Cisco Systems, Inc.
     All rights reserved.";

  revision 2022-07-11 {
    description
      "Added missing description statement to nodes";
  }
  revision 2021-06-02 {
    description
      "Initial release";
  }

  grouping IF-ETHER-BODY {
    description
      "Grouping for if-ether";
    container ethernet {
      description
        "Ethernet per-interface configuration commands";
      container lmi {
        presence "Indicates a lmi node is configured.";
        description
          "Enable the Local Management Interface protocol";
        leaf status-counter {
          type uint32 {
            range "2..10" {
              description
                "Status counter threshold value";
            }
          }
          description
            "Status counter threshold (N393 in MEF 16)";
        }
        container polling-verification-timer {
          description
            "polling-verification-timer configuration";
          leaf timer-interval {
            type uint32 {
              range "5..30" {
                description
                  "Timer interval in seconds";
              }
            }
            must "not(../disable)";
            description
              "Polling verification timer interval (T392 in MEF 16)";
          }
          container disable {
            must "not(../timer-interval)";
            presence "Indicates a disable node is configured.";
            description
              "Disable the polling verification timer";
          }
        }
        container extension {
          description
            "Configure Cisco proprietary extensions";
          container remote-uni {
            description
              "Configure the Remote UNI Details extension";
            container disable {
              presence "Indicates a disable node is configured.";
              description
                "Disable the Remote UNI Details extension";
            }
          }
        }
        container log {
          description
            "Configure logging for particular types of event";
          container errors {
            description
              "Configure logging of protocol and reliability errors";
            container disable {
              presence "Indicates a disable node is configured.";
              description
                "Disable logging of protocol and reliability errors";
            }
          }
          container events {
            description
              "Configure logging of significant protocol events";
            container disable {
              presence "Indicates a disable node is configured.";
              description
                "Disable logging of significant protocol events";
            }
          }
        }
      }
    }
  }

  augment "/a1:interfaces/a1:interface" {
    description
      "This augment extends active nodes configuration";
    uses IF-ETHER-BODY;
  }
  augment "/a1:interfaces/a1:interface-preconfigure" {
    description
      "This augment extends preconfigured nodes
       configuration";
    uses IF-ETHER-BODY;
  }
}
