module Cisco-IOS-XR-aaa-lib-cfg {
  namespace "http://cisco.com/ns/yang/Cisco-IOS-XR-aaa-lib-cfg";
  prefix aaa-lib-cfg;

  import Cisco-IOS-XR-types {
    prefix xr;
  }
  import cisco-semver {
    prefix semver;
  }
  import Cisco-IOS-XR-aaa-lib-datatypes {
    prefix dt1;
  }
  import oc-xr-mapping {
    prefix emmi;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-lib package configuration.
     
     This module contains definitions
     for the following management objects:
       aaa: Authentication, Authorization and Accounting
     
     Copyright (c) 2013-2020 by Cisco Systems, Inc.
     All rights reserved.";

  revision 2019-04-05 {
    description
      "Establish semantic version baseline.";
    semver:module-version "1.0.1";
  }
  revision 2017-11-14 {
    description
      "Modified Accounting method to support local accounting as syslog";
  }
  revision 2017-05-01 {
    description
      "Fixing backward compatibility error in module.";
  }
  revision 2015-11-09 {
    description
      "IOS XR 6.0 revision.";
  }

  container aaa {
    description
      "Authentication, Authorization and Accounting";
    container accountings {
      description
        "AAA accounting";
      list accounting {
        key "type listname";
        description
          "Configurations related to accounting";
        leaf type {
          type xr:Cisco-ios-xr-string;
          description
            "exec:Account exec sessions, commands: Account
             CLI commands";
          emmi:map-to {
            emmi:function "xr_accountings_accounting" {
              emmi:category "manual_function";
            }
            emmi:path "/oc-sys:system/oc-sys:aaa/oc-sys:accounting/oc-sys:events/oc-sys:event/oc-sys:event-type" {
              emmi:path-attributes {
                emmi:node-key "true";
              }
            }
          }
        }
        leaf listname {
          type xr:Cisco-ios-xr-string;
          description
            "Named accounting list";
        }
        leaf rp-failover {
          type dt1:Aaa-accounting-rp-failover;
          description
            "rpfailover";
        }
        leaf broadcast {
          type dt1:Aaa-accounting-broadcast;
          description
            "Broadcast";
        }
        leaf type-xr {
          type dt1:Aaa-accounting;
          description
            "Stop only/Start Stop";
          emmi:map-to {
            emmi:function "xr_type_xr" {
              emmi:category "manual_function";
            }
          }
        }
        leaf method1 {
          type dt1:Aaa-method-accounting;
          description
            "Method Type";
          emmi:map-to {
            emmi:function "xr_acctMethod" {
              emmi:category "manual_function";
            }
          }
        }
        leaf method2 {
          type dt1:Aaa-method-accounting;
          description
            "Method Type";
          emmi:map-to {
            emmi:function "xr_acctMethod" {
              emmi:category "manual_function";
            }
          }
        }
        leaf method3 {
          type dt1:Aaa-method-accounting;
          description
            "Method Type";
          emmi:map-to {
            emmi:function "xr_acctMethod" {
              emmi:category "manual_function";
            }
          }
        }
        leaf method4 {
          type dt1:Aaa-method-accounting;
          description
            "Method Type";
          emmi:map-to {
            emmi:function "xr_acctMethod" {
              emmi:category "manual_function";
            }
          }
        }
        leaf server-group-name1 {
          type string;
          description
            "Server group name";
          emmi:map-to {
            emmi:function "xr_acctMethod" {
              emmi:category "manual_function";
            }
          }
        }
        leaf server-group-name2 {
          type string;
          description
            "Server group name";
          emmi:map-to {
            emmi:function "xr_acctMethod" {
              emmi:category "manual_function";
            }
          }
        }
        leaf server-group-name3 {
          type string;
          description
            "Server group name";
          emmi:map-to {
            emmi:function "xr_acctMethod" {
              emmi:category "manual_function";
            }
          }
        }
        leaf server-group-name4 {
          type string;
          description
            "Server group name";
          emmi:map-to {
            emmi:function "xr_acctMethod" {
              emmi:category "manual_function";
            }
          }
        }
        emmi:map-to {
          emmi:function "xr_accountings_accounting" {
            emmi:category "manual_function";
          }
        }
      }
      emmi:map-to {
        emmi:path "/oc-sys:system/oc-sys:aaa/oc-sys:accounting";
      }
    }
    container authorizations {
      description
        "AAA authorization";
      list authorization {
        key "type listname";
        description
          "Configurations related to authorization";
        leaf type {
          type xr:Cisco-ios-xr-string;
          description
            "network: Authorize IKE requests, commands:
             Authorize CLI commands";
          emmi:map-to {
            emmi:function "xr_authorizations_auth" {
              emmi:category "manual_function";
            }
            emmi:path "/oc-sys:system/oc-sys:aaa/oc-sys:authorization/oc-sys:events/oc-sys:event/oc-sys:event-type" {
              emmi:path-attributes {
                emmi:node-key "true";
              }
            }
          }
        }
        leaf listname {
          type xr:Cisco-ios-xr-string;
          description
            "List name for AAA authorization";
        }
        leaf method1 {
          type dt1:Aaa-method;
          description
            "Method Type";
          emmi:map-to {
            emmi:function "xr_authMethod" {
              emmi:category "manual_function";
            }
          }
        }
        leaf method2 {
          type dt1:Aaa-method;
          description
            "Method Type";
          emmi:map-to {
            emmi:function "xr_authMethod" {
              emmi:category "manual_function";
            }
          }
        }
        leaf method3 {
          type dt1:Aaa-method;
          description
            "Method Type";
          emmi:map-to {
            emmi:function "xr_authMethod" {
              emmi:category "manual_function";
            }
          }
        }
        leaf method4 {
          type dt1:Aaa-method;
          description
            "Method Type";
          emmi:map-to {
            emmi:function "xr_authMethod" {
              emmi:category "manual_function";
            }
          }
        }
        leaf server-group-name1 {
          type string;
          description
            "Server group name";
          emmi:map-to {
            emmi:function "xr_authMethod" {
              emmi:category "manual_function";
            }
          }
        }
        leaf server-group-name2 {
          type string;
          description
            "Server group name";
          emmi:map-to {
            emmi:function "xr_authMethod" {
              emmi:category "manual_function";
            }
          }
        }
        leaf server-group-name3 {
          type string;
          description
            "Server group name";
          emmi:map-to {
            emmi:function "xr_authMethod" {
              emmi:category "manual_function";
            }
          }
        }
        leaf server-group-name4 {
          type string;
          description
            "Server group name";
          emmi:map-to {
            emmi:function "xr_authMethod" {
              emmi:category "manual_function";
            }
          }
        }
        emmi:map-to {
          emmi:function "xr_authorizations_auth" {
            emmi:category "manual_function";
          }
        }
      }
      emmi:map-to {
        emmi:path "/oc-sys:system/oc-sys:aaa/oc-sys:authorization";
      }
    }
    container accounting-update {
      presence "Indicates a accounting-update node is configured.";
      description
        "Configuration related to 'update' accounting";
      leaf type {
        type dt1:Aaa-accounting-update;
        mandatory true;
        description
          "newinfo/periodic";
      }
      leaf periodic-interval {
        type uint32 {
          range "0..35791394";
        }
        units "minute";
        description
          "Periodic update interval in minutes";
      }
    }
    container banner {
      description
        "AAA banner";
      leaf login {
        type string;
        description
          "AAA login banner";
      }
    }
    container authentications {
      description
        "AAA authentication";
      list authentication {
        key "type listname";
        description
          "Configurations related to authentication";
        leaf type {
          type xr:Cisco-ios-xr-string;
          description
            "login: Authenticate login sessions, ppp:
             Authenticate ppp sessions";
        }
        leaf listname {
          type xr:Cisco-ios-xr-string;
          description
            "List name for AAA authentication";
        }
        leaf method1 {
          type dt1:Aaa-method;
          description
            "Method Type";
          emmi:map-to {
            emmi:function "xr_authenticationMethod" {
              emmi:category "manual_function";
            }
          }
        }
        leaf method2 {
          type dt1:Aaa-method;
          description
            "Method Type";
          emmi:map-to {
            emmi:function "xr_authenticationMethod" {
              emmi:category "manual_function";
            }
          }
        }
        leaf method3 {
          type dt1:Aaa-method;
          description
            "Method Type";
          emmi:map-to {
            emmi:function "xr_authenticationMethod" {
              emmi:category "manual_function";
            }
          }
        }
        leaf method4 {
          type dt1:Aaa-method;
          description
            "Method Type";
          emmi:map-to {
            emmi:function "xr_authenticationMethod" {
              emmi:category "manual_function";
            }
          }
        }
        leaf server-group-name1 {
          type string;
          description
            "Server group name";
          emmi:map-to {
            emmi:function "xr_authenticationMethod" {
              emmi:category "manual_function";
            }
          }
        }
        leaf server-group-name2 {
          type string;
          description
            "Server group name";
          emmi:map-to {
            emmi:function "xr_authenticationMethod" {
              emmi:category "manual_function";
            }
          }
        }
        leaf server-group-name3 {
          type string;
          description
            "Server group name";
          emmi:map-to {
            emmi:function "xr_authenticationMethod" {
              emmi:category "manual_function";
            }
          }
        }
        leaf server-group-name4 {
          type string;
          description
            "Server group name";
          emmi:map-to {
            emmi:function "xr_authenticationMethod" {
              emmi:category "manual_function";
            }
          }
        }
        emmi:map-to;
      }
      emmi:map-to {
        emmi:path "/oc-sys:system/oc-sys:aaa/oc-sys:authentication";
      }
    }
    emmi:map-to {
      emmi:function "xr_aaa" {
        emmi:category "manual_function";
      }
    }
  }
  emmi:mapping {
    emmi:package-name "ocsystem";
    emmi:model-id "xr";
    emmi:module-id "cisco_ios_xr_aaa_lib_cfg";
    emmi:target {
      emmi:model-id "oc";
      emmi:module-id "openconfig_system";
      emmi:namespace "oc-log|http://openconfig.net/yang/system/logging";
      emmi:namespace "oc-platform-types|http://openconfig.net/yang/platform-types";
      emmi:namespace "oc-alarm-types|http://openconfig.net/yang/alarms/types";
      emmi:namespace "oc-yang|http://openconfig.net/yang/types/yang";
      emmi:namespace "oc-sys-mgmt|http://openconfig.net/yang/system/management";
      emmi:namespace "oc-aaa|http://openconfig.net/yang/aaa";
      emmi:namespace "oc-types|http://openconfig.net/yang/openconfig-types";
      emmi:namespace "oc-alarms|http://openconfig.net/yang/alarms";
      emmi:namespace "oc-inet|http://openconfig.net/yang/types/inet";
      emmi:namespace "oc-platform|http://openconfig.net/yang/platform";
      emmi:namespace "oc-sys-term|http://openconfig.net/yang/system/terminal";
      emmi:namespace "oc-aaa-types|http://openconfig.net/yang/aaa/types";
      emmi:namespace "oc-sys|http://openconfig.net/yang/system";
      emmi:namespace "oc-proc|http://openconfig.net/yang/system/procmon";
      emmi:namespace "oc-ext|http://openconfig.net/yang/openconfig-ext";
    }
  }
}
