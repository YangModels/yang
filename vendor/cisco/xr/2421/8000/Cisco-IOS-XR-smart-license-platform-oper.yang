module Cisco-IOS-XR-smart-license-platform-oper {
  namespace "http://cisco.com/ns/yang/Cisco-IOS-XR-smart-license-platform-oper";
  prefix smart-license-platform-oper;

  import cisco-semver {
    prefix semver;
  }
  include Cisco-IOS-XR-smart-license-platform-oper-sub1 {
    revision-date 2021-06-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR smart-license-platform package operational data.
     
     This module contains definitions
     for the following management objects:
       plat-smart-license: Smart License info
     
     Copyright (c) 2013-2022 by Cisco Systems, Inc.
     All rights reserved.";

  revision 2021-06-03 {
    description
      "Added support for enum node-deactivated.";
    semver:module-version "1.1.0";
  }
  revision 2020-09-15 {
    description
      "Structured the yang response for show CLIs.";
    semver:module-version "1.0.0";
  }
  revision 2019-04-05 {
    description
      "Establish semantic version baseline.";
  }
  revision 2015-11-09 {
    description
      "IOS XR 6.0 revision.";
  }

  container plat-smart-license {
    config false;
    description
      "Smart License info";
    container detail {
      description
        "Node Detail";
      uses PLAT-SL-DETAIL;
    }
    container summary {
      description
        "Node Summary";
      uses PLAT-SL-SUMMARY;
    }
  }
}
