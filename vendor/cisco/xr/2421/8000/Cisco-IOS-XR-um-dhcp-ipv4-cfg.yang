module Cisco-IOS-XR-um-dhcp-ipv4-cfg {
  namespace "http://cisco.com/ns/yang/Cisco-IOS-XR-um-dhcp-ipv4-cfg";
  prefix um-dhcp-ipv4-cfg;

  import Cisco-IOS-XR-types {
    prefix xr;
  }
  import ietf-inet-types {
    prefix inet;
  }
  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dhcp-ipv4 package configuration.
     
     This YANG module augments the
     modules with configuration data.
     
     Copyright (c) 2021-2022 by Cisco Systems, Inc.
     All rights reserved.";

  revision 2021-01-08 {
    description
      "Initial release";
  }

  container dhcp {
    description
      "Dynamic Host Configuration Protocol";
    container ipv4 {
      presence "Indicates a ipv4 node is configured.";
      description
        "Configure IPv4 DHCP";
      container vrfs {
        description
          "Assign a profile to VRF";
        list vrf {
          must "proxy or relay";
          key "vrf-name";
          description
            "VRF name";
          leaf vrf-name {
            type union {
              type string {
                pattern "(default|all)" {
                  description
                    "Assign a profile to default VRF or all VRFs";
                }
              }
              type xr:Cisco-ios-xr-string {
                length "1..32" {
                  description
                    "VRF name";
                }
              }
            }
            description
              "VRF name";
          }
          container proxy {
            must "not(../relay)";
            presence "Indicates a proxy node is configured.";
            description
              "Assign a proxy profile to VRF";
            leaf profile {
              type xr:Cisco-ios-xr-string {
                length "1..64" {
                  description
                    "Profile name";
                }
              }
              description
                "Enter profile name";
            }
          }
          container relay {
            must "not(../proxy)";
            presence "Indicates a relay node is configured.";
            description
              "Assign a relay profile to VRF";
            leaf profile {
              type xr:Cisco-ios-xr-string {
                length "1..64" {
                  description
                    "Profile name";
                }
              }
              description
                "Enter profile name";
            }
          }
        }
      }
      container profiles {
        description
          "Create or enter a profile";
        list profile {
          key "profile-name";
          description
            "Profile name";
          leaf profile-name {
            type xr:Cisco-ios-xr-string {
              length "1..64" {
                description
                  "Profile name";
              }
            }
            description
              "Profile name";
          }
          container base {
            presence "Indicates a base node is configured.";
            description
              "Create or enter base profile";
            container default {
              must "profile/profile-name and (profile/proxy or profile/server)";
              description
                "Create or enter default profile";
              container profile {
                description
                  "Enter a profile";
                leaf profile-name {
                  type xr:Cisco-ios-xr-string {
                    length "1..64" {
                      description
                        "Profile name";
                    }
                  }
                  description
                    "Profile name";
                }
                container proxy {
                  must "not(../server)";
                  presence "Indicates a proxy node is configured.";
                  description
                    "Proxy profile";
                }
                container server {
                  must "not(../proxy)";
                  presence "Indicates a server node is configured.";
                  description
                    "Server profile";
                }
              }
            }
            container match {
              description
                "Insert match keyword";
              container option {
                description
                  "Specify match option";
                container option-60-vendor-class-id {
                  description
                    "Insert option 60 vendor class id";
                  container default {
                    description
                      "Create or enter default action";
                    leaf action {
                      type enumeration {
                        enum "allow" {
                          value 0;
                          description
                            "Allow vendor-id specific Discover packet";
                        }
                        enum "drop" {
                          value 1;
                          description
                            "Drop vendor-id specific Discover packet";
                        }
                      }
                      description
                        "Enter action";
                    }
                  }
                  container hex-actions {
                    description
                      "Insert hex pattern";
                    list hex-action {
                      must "action";
                      key "pattern";
                      description
                        "Insert hex pattern";
                      leaf pattern {
                        type xr:Cisco-ios-xr-string {
                          length "1..64" {
                            description
                              "Enter hex pattern string";
                          }
                        }
                        description
                          "Insert hex pattern";
                      }
                      leaf action {
                        type enumeration {
                          enum "allow" {
                            value 0;
                            description
                              "Allow vendor specific DISCOVER";
                          }
                          enum "drop" {
                            value 1;
                            description
                              "Drop vendor specific DISCOVER";
                          }
                        }
                        description
                          "Enter action";
                      }
                    }
                  }
                  container hex-profiles {
                    description
                      "Insert hex pattern";
                    list hex-profile {
                      must "profile/profile-name and (profile/proxy or profile/server)";
                      key "pattern";
                      description
                        "Insert hex pattern";
                      leaf pattern {
                        type xr:Cisco-ios-xr-string {
                          length "1..64" {
                            description
                              "Enter hex pattern string";
                          }
                        }
                        description
                          "Insert hex pattern";
                      }
                      container profile {
                        description
                          "Enter a profile";
                        leaf profile-name {
                          type xr:Cisco-ios-xr-string {
                            length "1..64" {
                              description
                                "Profile name";
                            }
                          }
                          description
                            "Profile name";
                        }
                        container proxy {
                          must "not(../server)";
                          presence "Indicates a proxy node is configured.";
                          description
                            "Proxy profile";
                        }
                        container server {
                          must "not(../proxy)";
                          presence "Indicates a server node is configured.";
                          description
                            "Server profile";
                        }
                      }
                    }
                  }
                  container string-actions {
                    description
                      "Insert string pattern";
                    list string-action {
                      must "action";
                      key "pattern";
                      description
                        "Insert string pattern";
                      leaf pattern {
                        type string {
                          length "1..64" {
                            description
                              "Enter ascii double quoted string pattern";
                          }
                          pattern "[\"].*.[\"]";
                        }
                        description
                          "Insert string pattern";
                      }
                      leaf action {
                        type enumeration {
                          enum "allow" {
                            value 0;
                            description
                              "Allow vendor specific DISCOVER";
                          }
                          enum "drop" {
                            value 1;
                            description
                              "Drop vendor specific DISCOVER";
                          }
                        }
                        description
                          "Enter action";
                      }
                    }
                  }
                  container string-profiles {
                    description
                      "Insert string pattern";
                    list string-profile {
                      must "profile/profile-name and (profile/proxy or profile/server)";
                      key "pattern";
                      description
                        "Insert string pattern";
                      leaf pattern {
                        type string {
                          length "1..64" {
                            description
                              "Enter ascii double quoted string pattern";
                          }
                          pattern "[\"].*.[\"]";
                        }
                        description
                          "Insert string pattern";
                      }
                      container profile {
                        description
                          "Enter a profile";
                        leaf profile-name {
                          type xr:Cisco-ios-xr-string {
                            length "1..64" {
                              description
                                "Profile name";
                            }
                          }
                          description
                            "Profile name";
                        }
                        container proxy {
                          must "not(../server)";
                          presence "Indicates a proxy node is configured.";
                          description
                            "Proxy profile";
                        }
                        container server {
                          must "not(../proxy)";
                          presence "Indicates a server node is configured.";
                          description
                            "Server profile";
                        }
                      }
                    }
                  }
                }
              }
              container mode-classes {
                description
                  "Specify PPP/IPoE class option";
                list mode-class {
                  key "mode-class-name";
                  description
                    "Specify PPP/IPoE class option";
                  leaf mode-class-name {
                    type xr:Cisco-ios-xr-string {
                      length "1..64" {
                        description
                          "Class name";
                      }
                    }
                    description
                      "Specify PPP/IPoE class option";
                  }
                  leaf profile {
                    type xr:Cisco-ios-xr-string {
                      length "1..64" {
                        description
                          "Profile name";
                      }
                    }
                    description
                      "Enter proxy or server profile";
                  }
                  container proxy {
                    must "not(../server)";
                    presence "Indicates a proxy node is configured.";
                    description
                      "Proxy profile";
                  }
                  container server {
                    must "not(../proxy)";
                    presence "Indicates a server node is configured.";
                    description
                      "Server profile";
                  }
                }
              }
            }
            container match-default {
              description
                "Default match option";
              leaf profile {
                type xr:Cisco-ios-xr-string {
                  length "1..64" {
                    description
                      "Profile name";
                  }
                }
                must "../server";
                description
                  "Enter server profile";
              }
              container server {
                must "../profile";
                presence "Indicates a server node is configured.";
                description
                  "Specify mode-class based Server option";
              }
            }
            container dhcp-to-aaa {
              description
                "Enable to provide the list of options need to send to aaa";
              container option {
                description
                  "option type";
                container list {
                  description
                    "List of options";
                  container all {
                    presence "Indicates a all node is configured.";
                    description
                      "Allow all DHCP option to AAA";
                    leaf option-number {
                      type uint32 {
                        range "1..255" {
                          description
                            "Option number";
                        }
                      }
                      description
                        "Option number";
                    }
                  }
                }
              }
            }
            container relay {
              description
                "Specify Relay Agent Information Option configuration";
              container information {
                description
                  "Specify Relay Agent Information Option configuration";
                container authenticate {
                  description
                    "Specify Relay Agent Information Option authenticate";
                  container received {
                    must "not(../inserted)";
                    presence "Indicates a received node is configured.";
                    description
                      "Authenticate using received Relay Agent Information Option";
                  }
                  container inserted {
                    must "not(../received)";
                    presence "Indicates a inserted node is configured.";
                    description
                      "Authenticate using inserted Relay Agent Information Option";
                  }
                }
                container option {
                  description
                    "Insert Relay Agent Information circuit ID and remote ID suboptions in client request";
                  leaf remote-id {
                    type xr:Cisco-ios-xr-string {
                      length "1..512" {
                        description
                          "Remote id value";
                      }
                    }
                    description
                      "Enter remote-id value";
                  }
                }
              }
            }
          }
          container cnbng {
            presence "Indicates a cnbng node is configured.";
            description
              "Create or enter cnbng profile";
          }
          container proxy {
            presence "Indicates a proxy node is configured.";
            description
              "Create or enter proxy profile";
            container helper-address {
              description
                "Specify the server address to relay packets";
              container vrfs {
                description
                  "Specify server VRF";
                list vrf {
                  key "vrf-name";
                  description
                    "VRF name";
                  leaf vrf-name {
                    type union {
                      type string {
                        pattern "default" {
                          description
                            "Default VRF";
                        }
                      }
                      type xr:Cisco-ios-xr-string {
                        length "1..32" {
                          description
                            "VRF name";
                        }
                      }
                    }
                    description
                      "VRF name";
                  }
                  container ip-addresses {
                    description
                      "configure this node";
                    list ip-address {
                      key "address";
                      description
                        "configure this node";
                      leaf address {
                        type inet:ipv4-address-no-zone;
                        description
                          "configure this node";
                      }
                      leaf giaddr {
                        type inet:ipv4-address-no-zone;
                        mandatory true;
                        description
                          "Specify gateway address to use in packets relayed to server";
                      }
                    }
                  }
                }
              }
            }
            container match {
              description
                "Insert match keyword";
              container option {
                description
                  "Specify match option";
                container option-60-vendor-class-id {
                  description
                    "Insert option 60 vendor class id";
                  container hexes {
                    description
                      "Insert hex pattern";
                    list hex {
                      must "action";
                      key "pattern";
                      description
                        "Insert hex pattern";
                      leaf pattern {
                        type xr:Cisco-ios-xr-string {
                          length "1..64" {
                            description
                              "Enter hex pattern string";
                          }
                        }
                        description
                          "Insert hex pattern";
                      }
                      leaf action {
                        type enumeration {
                          enum "allow" {
                            value 0;
                            description
                              "Allow vendor-id specific Discover packet";
                          }
                          enum "drop" {
                            value 1;
                            description
                              "Drop vendor-id specific Discover packet";
                          }
                          enum "relay" {
                            value 2;
                            description
                              "Relay vendor-id specific DHCP packets unaltered";
                          }
                        }
                        description
                          "Enter action";
                      }
                    }
                  }
                  container strings {
                    description
                      "Insert string pattern";
                    list string {
                      key "pattern";
                      description
                        "Insert string pattern";
                      leaf pattern {
                        type string {
                          length "1..64" {
                            description
                              "Enter ascii double quoted string pattern to match";
                          }
                          pattern "[\"].*.[\"]";
                        }
                        description
                          "Insert string pattern";
                      }
                      leaf action {
                        type enumeration {
                          enum "allow" {
                            value 0;
                            description
                              "Allow vendor-id specific Discover packet";
                          }
                          enum "drop" {
                            value 1;
                            description
                              "Drop vendor-id specific Discover packet";
                          }
                          enum "relay" {
                            value 2;
                            description
                              "Relay vendor-id specific DHCP packets unaltered";
                          }
                        }
                        description
                          "Enter action";
                      }
                    }
                  }
                  container default {
                    description
                      "Default action";
                    leaf action {
                      type enumeration {
                        enum "allow" {
                          value 0;
                          description
                            "Allow vendor-id specific Discover packet";
                        }
                        enum "drop" {
                          value 1;
                          description
                            "Drop vendor-id specific Discover packet";
                        }
                        enum "relay" {
                          value 2;
                          description
                            "Relay vendor-id specific DHCP packets unaltered";
                        }
                      }
                      description
                        "Enter action";
                    }
                  }
                }
              }
            }
            container relay {
              description
                "Specify Relay Agent Information Option configuration";
              container information {
                description
                  "Specify Relay Agent Information Option configuration";
                container check {
                  presence "Indicates a check node is configured.";
                  description
                    "Check Relay Agent Information Option in server reply";
                }
                container option {
                  presence "Indicates a option node is configured.";
                  description
                    "Insert Relay Agent Information circuit ID and remote ID suboptions in client request";
                  container vpn {
                    presence "Indicates a vpn node is configured.";
                    description
                      "Insert Relay Agent Information VPN suboptions in client request";
                  }
                  container vpn-mode {
                    description
                      "Relay Agent Information VPN suboptions mode";
                    container rfc {
                      must "not(../cisco)";
                      presence "Indicates a rfc node is configured.";
                      description
                        "Relay Agent Information VPN suboptions in RFC compliance";
                    }
                    container cisco {
                      must "not(../rfc)";
                      presence "Indicates a cisco node is configured.";
                      description
                        "Relay Agent Information VPN suboptions in CISCO proprietary";
                    }
                  }
                  container allow-untrusted {
                    presence "Indicates a allow-untrusted node is configured.";
                    description
                      "Forward untrusted packets";
                  }
                  leaf remote-id {
                    type xr:Cisco-ios-xr-string {
                      length "1..512" {
                        description
                          "Remote id value";
                      }
                    }
                    description
                      "Enter remote-id value";
                  }
                  container suppress {
                    presence "Indicates a suppress node is configured.";
                    description
                      "Suppress remote id";
                  }
                  container enable {
                    presence "Indicates a enable node is configured.";
                    description
                      "Enable";
                  }
                  container circuit-id {
                    description
                      "Insert Relay Agent Information circuit ID suboption in client request";
                    container enable {
                      presence "Indicates a enable node is configured.";
                      description
                        "Enable";
                    }
                  }
                  container allow-in-release-msg {
                    presence "Indicates a allow-in-release-msg node is configured.";
                    description
                      "allow to insert option82 in release message";
                  }
                }
                container policy {
                  description
                    "Specify Relay Agent Information Option policy";
                  container drop {
                    presence "Indicates a drop node is configured.";
                    description
                      "Drop client request packets with Relay Agent Information Option";
                  }
                }
                container keep {
                  presence "Indicates a keep node is configured.";
                  description
                    "Keep existing Relay Agent Information Option in client request";
                }
                container replace {
                  presence "Indicates a replace node is configured.";
                  description
                    "Replace existing Relay Agent Information Option in client request";
                }
                container encapsulate {
                  presence "Indicates a encapsulate node is configured.";
                  description
                    "Encapsulate existing Relay Agent Information Option in client request";
                }
                container authenticate {
                  description
                    "Specify Relay Agent Information Option authenticate";
                  container received {
                    must "not(../inserted)";
                    presence "Indicates a received node is configured.";
                    description
                      "Authenticate using received Relay Agent Information Option";
                  }
                  container inserted {
                    must "not(../received)";
                    presence "Indicates a inserted node is configured.";
                    description
                      "Authenticate using inserted Relay Agent Information Option";
                  }
                }
              }
            }
            container giaddr {
              description
                "Specify gateway address policy";
              container policy {
                description
                  "Specify gateway address policy";
                container keep {
                  presence "Indicates a keep node is configured.";
                  description
                    "Retain gateway address in client Request";
                }
              }
            }
            container broadcast-flag {
              description
                "Specify broadcast flag";
              container policy {
                description
                  "Specify broadcast flag policy";
                container check {
                  must "not(../unicast-always)";
                  presence "Indicates a check node is configured.";
                  description
                    "Check the broadcast flag in packets";
                }
                container unicast-always {
                  must "not(../check)";
                  presence "Indicates a unicast-always node is configured.";
                  description
                    "Set the broadcast-flag policy to unicast-always";
                }
              }
            }
            container allow-move {
              presence "Indicates a allow-move node is configured.";
              description
                "Allow dhcp subscriber move";
            }
            container handle-discover-in-bound {
              presence "Indicates a handle-discover-in-bound node is configured.";
              description
                "handle-discover-in-bound <proxy mode only>";
            }
            container limit {
              description
                "Specify limit";
              container lease {
                description
                  "Specify limit lease";
                leaf per-circuit-id {
                  type uint32 {
                    range "1..240000" {
                      description
                        "Value of limit lease count";
                    }
                  }
                  must "not(../per-remote-id or ../per-circuit-id-remote-id or ../per-interface)";
                  description
                    "Insert the limit lease type circuit-id";
                }
                leaf per-remote-id {
                  type uint32 {
                    range "1..240000" {
                      description
                        "Value of limit lease count";
                    }
                  }
                  must "not(../per-circuit-id or ../per-circuit-id-remote-id or ../per-interface)";
                  description
                    "Insert the limit lease type remote-id";
                }
                leaf per-circuit-id-remote-id {
                  type uint32 {
                    range "1..240000" {
                      description
                        "Value of limit lease count";
                    }
                  }
                  must "not(../per-remote-id or ../per-circuit-id or ../per-interface)";
                  description
                    "Insert the limit lease type circuit-id+remote-id";
                }
                leaf per-interface {
                  type uint32 {
                    range "1..240000" {
                      description
                        "Value of limit lease count";
                    }
                  }
                  must "not(../per-remote-id or ../per-circuit-id-remote-id or ../per-circuit-id)";
                  description
                    "Insert the limit lease type interface";
                }
              }
            }
            container lease {
              description
                "Specify lease";
              container proxy {
                description
                  "Specify lease proxy";
                leaf client-lease-time {
                  type uint32 {
                    range "300..4294967295" {
                      description
                        "Value of lease proxy client-time in seconds";
                    }
                  }
                  description
                    "Specify the lease proxy client lease time";
                }
                container set-server-options {
                  presence "Indicates a set-server-options node is configured.";
                  description
                    "Set DHCP server sent options in lease proxy generating ACK";
                }
              }
            }
            container secure-arp {
              presence "Indicates a secure-arp node is configured.";
              description
                "Enable Secure Arp";
            }
            container sessions {
              description
                "Change sessions configuration";
              container mac {
                presence "Indicates a mac node is configured.";
                description
                  "Throttle DHCP sessions based on MAC address";
                leaf throttle {
                  type uint32 {
                    range "1..65535" {
                      description
                        "Number of discovers at which to throttle";
                    }
                  }
                  must "../throttle-request-period";
                  mandatory true;
                  description
                    "Throttle DHCP sessions from any one MAC address";
                }
                leaf throttle-request-period {
                  type uint32 {
                    range "1..100" {
                      description
                        "Throttle request period (in secs)";
                    }
                  }
                  must "../throttle";
                  mandatory true;
                  description
                    "Throttle request period (in secs)";
                }
                leaf throttle-blocking-period {
                  type uint32 {
                    range "1..100" {
                      description
                        "Throttle blocking period (in secs)";
                    }
                  }
                  mandatory true;
                  description
                    "Throttle blocking period (in secs)";
                }
              }
            }
            container delayed {
              description
                "For BNG session, delay the authentication";
              container authentication {
                presence "Indicates a authentication node is configured.";
                description
                  "authentiaction";
              }
            }
            container authentication {
              description
                " Authentication username foramt";
              container username {
                description
                  "Set username";
                container mac {
                  must "not(../giaddr)";
                  presence "Indicates a mac node is configured.";
                  description
                    "Set mac in username";
                }
                container giaddr {
                  must "not(../mac)";
                  presence "Indicates a giaddr node is configured.";
                  description
                    "Set giaddr in username";
                }
              }
            }
            container dhcp-to-aaa {
              description
                "Enable to provide the list of options need to send to aaa";
              container option {
                description
                  "option type";
                container list {
                  description
                    "List of options";
                  container all {
                    presence "Indicates a all node is configured.";
                    description
                      "Allow all DHCP option to AAA";
                    leaf option-number {
                      type uint32 {
                        range "1..255" {
                          description
                            "Option number";
                        }
                      }
                      description
                        "Option number";
                    }
                  }
                }
              }
            }
            container classes {
              description
                "Create or enter proxy profile class";
              list class {
                key "class-name";
                description
                  "Create or enter proxy profile class";
                leaf class-name {
                  type xr:Cisco-ios-xr-string {
                    length "1..128" {
                      description
                        "class name";
                    }
                  }
                  description
                    "Create or enter proxy profile class";
                }
                container match {
                  presence "Indicates a match node is configured.";
                  description
                    "Insert match keyword";
                  container option {
                    description
                      "Specify match option";
                    container option-60-vendor-class-id {
                      presence "Indicates a option-60-vendor-class-id node is configured.";
                      description
                        "Insert option 60 vendor class id";
                      leaf hex {
                        type xr:Cisco-ios-xr-string {
                          length "1..64" {
                            description
                              "Enter hex pattern string";
                          }
                        }
                        description
                          "Insert hex pattern";
                      }
                      leaf mask {
                        type xr:Cisco-ios-xr-string {
                          length "1..64" {
                            description
                              "Enter bit mask pattern string";
                          }
                        }
                        must "../hex";
                        description
                          "Insert bit mask pattern";
                      }
                    }
                    container option-77-user-class {
                      presence "Indicates a option-77-user-class node is configured.";
                      description
                        "Insert option 77 user class";
                      leaf hex {
                        type xr:Cisco-ios-xr-string {
                          length "1..64" {
                            description
                              "Enter hex pattern string";
                          }
                        }
                        description
                          "Insert hex pattern";
                      }
                      leaf mask {
                        type xr:Cisco-ios-xr-string {
                          length "1..64" {
                            description
                              "Enter bit mask pattern string";
                          }
                        }
                        must "../hex";
                        description
                          "Insert bit mask pattern";
                      }
                    }
                    container option-124-vendor-identifying-vendor-class {
                      presence "Indicates a option-124-vendor-identifying-vendor-class node is configured.";
                      description
                        "Insert option 124 vendor-identifying vendor class";
                      leaf hex {
                        type xr:Cisco-ios-xr-string {
                          length "1..64" {
                            description
                              "Enter hex pattern string";
                          }
                        }
                        description
                          "Insert hex pattern";
                      }
                      leaf mask {
                        type xr:Cisco-ios-xr-string {
                          length "1..64" {
                            description
                              "Enter bit mask pattern string";
                          }
                        }
                        must "../hex";
                        description
                          "Insert bit mask pattern";
                      }
                    }
                    container option-125-vendor-identifying-vendor-specific-info {
                      presence "Indicates a option-125-vendor-identifying-vendor-specific-info node is configured.";
                      description
                        "Insert option 125 vendor-identifying vendor-specific info";
                      leaf hex {
                        type xr:Cisco-ios-xr-string {
                          length "1..64" {
                            description
                              "Enter hex pattern string";
                          }
                        }
                        description
                          "Insert hex pattern";
                      }
                      leaf mask {
                        type xr:Cisco-ios-xr-string {
                          length "1..64" {
                            description
                              "Enter bit mask pattern string";
                          }
                        }
                        must "../hex";
                        description
                          "Insert bit mask pattern";
                      }
                    }
                  }
                  leaf vrf {
                    type xr:Cisco-ios-xr-string {
                      length "1..32" {
                        description
                          "VRF name";
                      }
                    }
                    description
                      "Specify match VRF";
                  }
                }
                container helper-address {
                  description
                    "Specify the server address to relay packets";
                  container vrfs {
                    description
                      "Specify server VRF";
                    list vrf {
                      key "vrf-name";
                      description
                        "VRF name";
                      leaf vrf-name {
                        type union {
                          type string {
                            pattern "default" {
                              description
                                "Default VRF";
                            }
                          }
                          type xr:Cisco-ios-xr-string {
                            length "1..32" {
                              description
                                "VRF name";
                            }
                          }
                        }
                        description
                          "VRF name";
                      }
                      container ip-addresses {
                        description
                          "configure this node";
                        list ip-address {
                          key "address";
                          description
                            "configure this node";
                          leaf address {
                            type inet:ipv4-address-no-zone;
                            description
                              "configure this node";
                          }
                          leaf giaddr {
                            type inet:ipv4-address-no-zone;
                            mandatory true;
                            description
                              "Specify gateway address to use in packets relayed to server";
                          }
                        }
                      }
                    }
                  }
                }
              }
            }
          }
          container relay {
            presence "Indicates a relay node is configured.";
            description
              "Create or enter relay profile";
            container broadcast-flag {
              description
                "Specify broadcast flag policy";
              container policy {
                description
                  "Specify broadcast flag policy";
                container check {
                  must "not(../unicast-always)";
                  presence "Indicates a check node is configured.";
                  description
                    "Check the broadcast flag in packets";
                }
                container unicast-always {
                  must "not(../check)";
                  presence "Indicates a unicast-always node is configured.";
                  description
                    "Set the broadcast-flag policy to unicast-always";
                }
              }
            }
            container helper-address {
              description
                "Specify the server address to relay packets";
              container vrfs {
                description
                  "Specify server VRF";
                list vrf {
                  key "vrf-name";
                  description
                    "VRF name";
                  leaf vrf-name {
                    type union {
                      type string {
                        pattern "default" {
                          description
                            "Default VRF";
                        }
                      }
                      type xr:Cisco-ios-xr-string {
                        length "1..32" {
                          description
                            "VRF name";
                        }
                      }
                    }
                    description
                      "VRF name";
                  }
                  container ip-addresses {
                    description
                      "configure this node";
                    list ip-address {
                      key "address";
                      description
                        "configure this node";
                      leaf address {
                        type inet:ipv4-address-no-zone;
                        description
                          "configure this node";
                      }
                      leaf giaddr {
                        type inet:ipv4-address-no-zone;
                        description
                          "Specify gateway address to use in packets relayed to server";
                      }
                    }
                  }
                }
              }
            }
            container relay {
              description
                "Specify Relay Agent Information Option configuration";
              container information {
                description
                  "Specify Relay Agent Information Option configuration";
                container check {
                  presence "Indicates a check node is configured.";
                  description
                    "Check Relay Agent Information Option in server reply";
                }
                container option {
                  presence "Indicates a option node is configured.";
                  description
                    "Insert Relay Agent Information circuit ID and remote ID suboptions in client request";
                  container vpn {
                    presence "Indicates a vpn node is configured.";
                    description
                      "Insert Relay Agent Information VPN suboptions in client request";
                  }
                  container vpn-mode {
                    description
                      "Relay Agent Information VPN suboptions mode";
                    container rfc {
                      must "not(../cisco)";
                      presence "Indicates a rfc node is configured.";
                      description
                        "Relay Agent Information VPN suboptions in RFC compliance";
                    }
                    container cisco {
                      must "not(../rfc)";
                      presence "Indicates a cisco node is configured.";
                      description
                        "Relay Agent Information VPN suboptions in CISCO proprietary";
                    }
                  }
                  container allow-untrusted {
                    presence "Indicates a allow-untrusted node is configured.";
                    description
                      "Forward untrusted packets";
                  }
                  container remote-id {
                    description
                      "Enter remote-id value";
                    container format-type {
                      description
                        "Enter the format-type of remote-id";
                      leaf hex {
                        type xr:Cisco-ios-xr-string {
                          length "1..512" {
                            description
                              "remote-id value";
                          }
                        }
                        must "not(../ascii)";
                        description
                          "Choose the hex string format";
                      }
                      leaf ascii {
                        type xr:Cisco-ios-xr-string {
                          length "1..512" {
                            description
                              "remote-id value";
                          }
                        }
                        must "not(../hex)";
                        description
                          "Choose the ascii string format";
                      }
                    }
                  }
                  leaf subscriber-id {
                    type xr:Cisco-ios-xr-string {
                      length "1..512" {
                        description
                          "Subscriber id value";
                      }
                    }
                    description
                      "Enter subscriber-id value";
                  }
                }
                container policy {
                  description
                    "Specify Relay Agent Information Option policy";
                  container drop {
                    presence "Indicates a drop node is configured.";
                    description
                      "Drop client request packets with Relay Agent Information Option";
                  }
                }
                container keep {
                  presence "Indicates a keep node is configured.";
                  description
                    "Keep existing Relay Agent Information Option in client request";
                }
                container encapsulate {
                  presence "Indicates a encapsulate node is configured.";
                  description
                    "Encapsulate existing Relay Agent Information Option in client request";
                }
              }
            }
            container giaddr {
              description
                "Specify gateway address policy";
              container policy {
                description
                  "Specify gateway address policy";
                container drop {
                  must "not(../replace)";
                  presence "Indicates a drop node is configured.";
                  description
                    "Drop client requests with non-zero gateway address";
                }
                container replace {
                  must "not(../drop)";
                  presence "Indicates a replace node is configured.";
                  description
                    "Replace existing gateway address in client request";
                }
              }
            }
            container client-mac-mismatch {
              description
                "Configure action to take on source mac mismatch";
              container action {
                description
                  "Action to take on mismatch";
                container drop {
                  presence "Indicates a drop node is configured.";
                  description
                    "Drop it";
                }
              }
            }
          }
          container server {
            presence "Indicates a server node is configured.";
            description
              "Create or enter server profile";
            container dns-server {
              description
                "DNS servers";
              leaf-list ip-address {
                type inet:ipv4-address-no-zone;
                max-elements "8";
                description
                  "configure this node";
              }
            }
            leaf domain-name {
              type xr:Cisco-ios-xr-string {
                length "1..256" {
                  description
                    "Domain name";
                }
              }
              description
                "Domain name";
            }
            container delete-binding-on-discover {
              description
                "Delete binding on receiving discover";
              container disable {
                presence "Indicates a disable node is configured.";
                description
                  "Disable delete binding on discover";
              }
            }
            container default-router {
              description
                "default routers";
              leaf-list ip-address {
                type inet:ipv4-address-no-zone;
                max-elements "8";
                description
                  "configure this node";
              }
            }
            leaf subnet-mask {
              type inet:ipv4-address-no-zone;
              description
                "Configure Subnet Mask";
            }
            leaf bootfile {
              type xr:Cisco-ios-xr-string {
                length "1..128" {
                  description
                    "Boot Filename";
                }
              }
              description
                "Boot Filename";
            }
            container netbios-name-server {
              description
                "NetBIOS name servers";
              leaf-list ip-address {
                type inet:ipv4-address-no-zone;
                max-elements "8";
                description
                  "configure this node";
              }
            }
            container lease {
              description
                "lease";
              container infinite {
                must "not(../days)";
                presence "Indicates a infinite node is configured.";
                description
                  "Infinite lease";
              }
              leaf days {
                type uint32 {
                  range "0..365" {
                    description
                      "Days";
                  }
                }
                must "not(../infinite)";
                description
                  "Days";
              }
              leaf hours {
                type uint32 {
                  range "0..23" {
                    description
                      "Hours";
                  }
                }
                must "../days";
                must "../days";
                description
                  "Hours";
              }
              leaf minutes {
                type uint32 {
                  range "0..59" {
                    description
                      "Minutes";
                  }
                }
                must "../hours";
                must "../hours";
                description
                  "Minutes";
              }
            }
            container allow-move {
              presence "Indicates a allow-move node is configured.";
              description
                "Allow dhcp subscriber move";
            }
            container requested-ip-address-check {
              description
                "Validate Requested IP Address";
              container disable {
                presence "Indicates a disable node is configured.";
                description
                  "specify requested-ip-address-check disable";
              }
            }
            container server-id-check {
              description
                "Validate server ID check";
              container disable {
                presence "Indicates a disable node is configured.";
                description
                  "specify server-id-check disable";
              }
            }
            container netbios-node-type {
              description
                "NetBIOS node type";
              leaf hexadecimal-number {
                type uint32 {
                  range "0..255" {
                    description
                      "Hexadecimal number";
                  }
                }
                description
                  "Hexadecimal number";
              }
              container b-node {
                presence "Indicates a b-node node is configured.";
                description
                  "Broadcast node";
              }
              container h-node {
                presence "Indicates a h-node node is configured.";
                description
                  "Hybrid node";
              }
              container m-node {
                presence "Indicates a m-node node is configured.";
                description
                  "Mixed node";
              }
              container p-node {
                presence "Indicates a p-node node is configured.";
                description
                  "Peer-to-peer node";
              }
            }
            leaf pool {
              type xr:Cisco-ios-xr-string {
                length "1..64" {
                  description
                    "Dap's pool name";
                }
              }
              description
                "Specify the Pool name";
            }
            leaf next-server {
              type inet:ipv4-address-no-zone;
              description
                "Configure the tftp-server IP to be used by the client";
            }
            container secure-arp {
              presence "Indicates a secure-arp node is configured.";
              description
                "Enable Secure Arp";
            }
            container arp-install-skip-stdalone {
              presence "Indicates a arp-install-skip-stdalone node is configured.";
              description
                "Skip ARP installation for standalone sessions";
            }
            container broadcast-flag {
              description
                "Specify broadcast flag";
              leaf policy {
                type enumeration {
                  enum "Ignore" {
                    value 0;
                    description
                      "Ignore the broadcast policy";
                  }
                  enum "Check" {
                    value 1;
                    description
                      "Check for broadcast flag";
                  }
                  enum "UnicastAlways" {
                    value 2;
                    description
                      "Always Unicast the reply";
                  }
                }
                description
                  "Specify broadcast flag policy";
              }
            }
            container limit {
              description
                "Specify limit";
              container lease {
                presence "Indicates a lease node is configured.";
                description
                  "Specify limit lease";
                leaf type {
                  type enumeration {
                    enum "per-interface" {
                      value 1;
                      description
                        "Insert the limit lease type interface";
                    }
                    enum "per-circuit-id" {
                      value 2;
                      description
                        "Insert the limit lease type circuit-id";
                    }
                    enum "per-remote-id" {
                      value 3;
                      description
                        "Insert the limit lease type remote-id";
                    }
                  }
                  mandatory true;
                  description
                    "Specify limit lease";
                }
                leaf count {
                  type uint32 {
                    range "1..240000" {
                      description
                        "Value of limit lease count in Decimal";
                    }
                  }
                  mandatory true;
                  description
                    "Value of limit lease count in Decimal";
                }
              }
            }
            container relay {
              description
                "Specify Relay Agent Information Option configuration";
              container information {
                description
                  "Specify Relay Agent Information Option configuration";
                container authenticate {
                  description
                    "Specify Relay Agent Information Option authenticate";
                  container received {
                    must "not(../inserted)";
                    presence "Indicates a received node is configured.";
                    description
                      "Authenticate using received Relay Agent Information Option";
                  }
                  container inserted {
                    must "not(../received)";
                    presence "Indicates a inserted node is configured.";
                    description
                      "Authenticate using inserted Relay Agent Information Option";
                  }
                }
              }
            }
            container match {
              description
                "Insert match keyword";
              container option {
                description
                  "Specify match option";
                container option-60-vendor-class-id {
                  description
                    "Match option 60 vendor class id";
                  container hexes {
                    description
                      "Insert hex pattern string";
                    list hex {
                      must "action";
                      key "pattern";
                      description
                        "Insert hex pattern string";
                      leaf pattern {
                        type xr:Cisco-ios-xr-string {
                          length "1..64" {
                            description
                              "Enter hex pattern string";
                          }
                        }
                        description
                          "Insert hex pattern string";
                      }
                      leaf action {
                        type enumeration {
                          enum "allow" {
                            value 0;
                            description
                              "Allow vendor specific DHCP Discover";
                          }
                          enum "drop" {
                            value 1;
                            description
                              "Drop vendor specific DHCP Discover";
                          }
                        }
                        description
                          "Enter action to be performed";
                      }
                    }
                  }
                  container strings {
                    description
                      "Insert string pattern";
                    list string {
                      must "action";
                      key "pattern";
                      description
                        "Insert string pattern";
                      leaf pattern {
                        type string {
                          length "1..64" {
                            description
                              "Enter ascii double quoted string pattern to match";
                          }
                          pattern "[\"].*.[\"]";
                        }
                        description
                          "Insert string pattern";
                      }
                      leaf action {
                        type enumeration {
                          enum "allow" {
                            value 0;
                            description
                              "Allow vendor specific DHCP Discover";
                          }
                          enum "drop" {
                            value 1;
                            description
                              "Drop vendor specific DHCP Discover";
                          }
                        }
                        description
                          "Enter action to be performed";
                      }
                    }
                  }
                  container default {
                    description
                      "Default action";
                    leaf action {
                      type enumeration {
                        enum "allow" {
                          value 0;
                          description
                            "Allow DHCP Discover";
                        }
                        enum "drop" {
                          value 1;
                          description
                            "Drop DHCP Discover";
                        }
                      }
                      description
                        "Enter action to be performed";
                    }
                  }
                }
              }
            }
            container options {
              description
                "DHCP option code";
              list option {
                key "option-code";
                description
                  "DHCP option code";
                leaf option-code {
                  type uint32 {
                    range "0..255" {
                      description
                        "DHCP option code";
                    }
                  }
                  description
                    "DHCP option code";
                }
                leaf ascii {
                  type xr:Cisco-ios-xr-string {
                    length "1..800" {
                      description
                        "ASCII string";
                    }
                  }
                  description
                    "Data is an NVT ASCII string";
                }
                leaf hex {
                  type xr:Cisco-ios-xr-string {
                    length "1..800" {
                      description
                        "Hexadecimal string";
                    }
                  }
                  description
                    "Hex string";
                }
                container force-insert {
                  presence "Indicates a force-insert node is configured.";
                  description
                    "Force insert raw option";
                }
                container ip {
                  description
                    "Server's IP address";
                  leaf-list ip-address {
                    type inet:ipv4-address-no-zone;
                    max-elements "8";
                    description
                      "configure this node";
                  }
                }
              }
            }
            container sessions {
              description
                "Change sessions configuration";
              container mac {
                presence "Indicates a mac node is configured.";
                description
                  "Throttle DHCP sessions based on MAC address";
                leaf throttle {
                  type uint32 {
                    range "1..65535" {
                      description
                        "Number of discovers at which to throttle";
                    }
                  }
                  must "../throttle-request-period";
                  mandatory true;
                  description
                    "Throttle DHCP sessions from any one MAC address";
                }
                leaf throttle-request-period {
                  type uint32 {
                    range "1..100" {
                      description
                        "Throttle request period (in secs)";
                    }
                  }
                  must "../throttle";
                  mandatory true;
                  description
                    "Throttle request period (in secs)";
                }
                leaf throttle-blocking-period {
                  type uint32 {
                    range "1..100" {
                      description
                        "Throttle blocking period (in secs)";
                    }
                  }
                  mandatory true;
                  description
                    "Throttle blocking period (in secs)";
                }
              }
            }
            container aaa {
              description
                "Enable aaa dhcp option force-insert";
              container dhcp-option {
                description
                  "Enable aaa dhcp option force-insert";
                container force-insert {
                  presence "Indicates a force-insert node is configured.";
                  description
                    "Enable aaa dhcp option force-insert";
                }
              }
            }
            container dhcp-to-aaa {
              description
                "Enable to provide the list of options need to send to aaa";
              container option {
                description
                  "option type";
                container list {
                  description
                    "List of options";
                  container all {
                    must "not(../option-number)";
                    presence "Indicates a all node is configured.";
                    description
                      "Allow all DHCP option to AAA";
                  }
                  leaf-list option-number {
                    type uint32 {
                      range "1..255" {
                        description
                          "Option number";
                      }
                    }
                    must "not(../all)";
                    max-elements "12";
                    description
                      "Option number";
                  }
                }
              }
            }
            container enable-vlan-intf-session-limit {
              presence "Indicates a enable-vlan-intf-session-limit node is configured.";
              description
                "Enable vlan or interface session limit";
            }
            container insert-bootfile {
              presence "Indicates a insert-bootfile node is configured.";
              description
                "Force insert bootfile name";
            }
            container classes {
              description
                "Create or enter server profile class";
              list class {
                key "class-name";
                description
                  "Create or enter server profile class";
                leaf class-name {
                  type xr:Cisco-ios-xr-string {
                    length "1..128" {
                      description
                        "class-name";
                    }
                  }
                  description
                    "Create or enter server profile class";
                }
                container match {
                  description
                    "Insert match keyword";
                  container options {
                    description
                      "Specify match option";
                    list option {
                      key "option-code";
                      description
                        "Specify match option";
                      leaf option-code {
                        type enumeration {
                          enum "circuitid" {
                            value 1;
                            description
                              "Match circuit id of option 82 Relay-agent specific class";
                          }
                          enum "remoteid" {
                            value 2;
                            description
                              "Match remote id of option 82 Relay-agent specific class";
                          }
                          enum "60" {
                            value 60;
                            description
                              "Match option 60 vendor class id";
                          }
                          enum "77" {
                            value 77;
                            description
                              "Match option 77 user class";
                          }
                          enum "124" {
                            value 124;
                            description
                              "Match option 124 vendor-identifying vendor class";
                          }
                          enum "125" {
                            value 125;
                            description
                              "Match option 125 vendor-indentifying vendor-specific info";
                          }
                        }
                        description
                          "Specify match option";
                      }
                      leaf hex {
                        type xr:Cisco-ios-xr-string {
                          length "1..64" {
                            description
                              "Enter hex pattern string";
                          }
                        }
                        description
                          "Insert hex pattern string";
                      }
                      leaf mask {
                        type xr:Cisco-ios-xr-string {
                          length "1..64" {
                            description
                              "Enter bit mask pattern string";
                          }
                        }
                        must "../hex";
                        description
                          "Insert bit mask pattern";
                      }
                    }
                  }
                  leaf vrf {
                    type xr:Cisco-ios-xr-string {
                      length "1..32" {
                        description
                          "VRF name";
                      }
                    }
                    description
                      "Specify match VRF";
                  }
                  leaf l2-interface {
                    type xr:Interface-name;
                    description
                      "Specify match l2-interface";
                  }
                }
                leaf pool {
                  type xr:Cisco-ios-xr-string {
                    length "1..800" {
                      description
                        "Pool name";
                    }
                  }
                  description
                    "Specify the pool";
                }
                leaf next-server {
                  type inet:ipv4-address-no-zone;
                  description
                    "Configure the tftp-server IP to be used by the client";
                }
                container dns-server {
                  description
                    "DNS servers";
                  leaf-list ip-address {
                    type inet:ipv4-address-no-zone;
                    max-elements "8";
                    description
                      "configure this node";
                  }
                }
                leaf domain-name {
                  type xr:Cisco-ios-xr-string {
                    length "1..256" {
                      description
                        "Domain name";
                    }
                  }
                  description
                    "Domain name";
                }
                container default-router {
                  description
                    "default routers";
                  leaf-list ip-address {
                    type inet:ipv4-address-no-zone;
                    max-elements "8";
                    description
                      "configure this node";
                  }
                }
                container lease {
                  description
                    "lease";
                  container infinite {
                    must "not(../days)";
                    presence "Indicates a infinite node is configured.";
                    description
                      "Infinite lease";
                  }
                  leaf days {
                    type uint32 {
                      range "0..365" {
                        description
                          "Days";
                      }
                    }
                    must "not(../infinite)";
                    description
                      "Days";
                  }
                  leaf hours {
                    type uint32 {
                      range "0..23" {
                        description
                          "Hours";
                      }
                    }
                    must "../days";
                    must "../days";
                    description
                      "Hours";
                  }
                  leaf minutes {
                    type uint32 {
                      range "0..59" {
                        description
                          "Minutes";
                      }
                    }
                    must "../hours";
                    must "../hours";
                    description
                      "Minutes";
                  }
                }
                leaf subnet-mask {
                  type inet:ipv4-address-no-zone;
                  description
                    "Configure Subnet Mask";
                }
                leaf bootfile {
                  type xr:Cisco-ios-xr-string {
                    length "1..128" {
                      description
                        "Boot Filename";
                    }
                  }
                  description
                    "Boot Filename";
                }
                container netbios-name-server {
                  description
                    "NetBIOS name servers";
                  leaf-list ip-address {
                    type inet:ipv4-address-no-zone;
                    max-elements "8";
                    description
                      "configure this node";
                  }
                }
                container netbios-node-type {
                  description
                    "NetBIOS node type";
                  leaf hexadecimal-number {
                    type uint32 {
                      range "0..255" {
                        description
                          "Hexadecimal number";
                      }
                    }
                    description
                      "Hexadecimal number";
                  }
                  container b-node {
                    presence "Indicates a b-node node is configured.";
                    description
                      "Broadcast node";
                  }
                  container h-node {
                    presence "Indicates a h-node node is configured.";
                    description
                      "Hybrid node";
                  }
                  container m-node {
                    presence "Indicates a m-node node is configured.";
                    description
                      "Mixed node";
                  }
                  container p-node {
                    presence "Indicates a p-node node is configured.";
                    description
                      "Peer-to-peer node";
                  }
                }
                container options {
                  description
                    "DHCP option code";
                  list option {
                    key "option-code";
                    description
                      "DHCP option code";
                    leaf option-code {
                      type uint32 {
                        range "0..255" {
                          description
                            "DHCP option code";
                        }
                      }
                      description
                        "DHCP option code";
                    }
                    leaf ascii {
                      type xr:Cisco-ios-xr-string {
                        length "1..800" {
                          description
                            "ASCII string";
                        }
                      }
                      description
                        "Data is an NVT ASCII string";
                    }
                    leaf hex {
                      type xr:Cisco-ios-xr-string {
                        length "1..800" {
                          description
                            "Hexadecimal string";
                        }
                      }
                      description
                        "Hex string";
                    }
                    container force-insert {
                      presence "Indicates a force-insert node is configured.";
                      description
                        "Force insert raw option";
                    }
                    container ip {
                      description
                        "Server's IP address";
                      leaf-list ip-address {
                        type inet:ipv4-address-no-zone;
                        max-elements "8";
                        description
                          "configure this node";
                      }
                    }
                  }
                }
              }
            }
          }
          container snoop {
            presence "Indicates a snoop node is configured.";
            description
              "Create or enter snoop profile";
            container trusted {
              presence "Indicates a trusted node is configured.";
              description
                "Trusted sources";
            }
            container relay {
              description
                "Relay Agent Information Option configuration";
              container information {
                description
                  "Relay Agent Information Option configuration";
                container option {
                  presence "Indicates a option node is configured.";
                  description
                    "Insert Relay Agent Information circuit ID and remote ID suboptions in client request";
                  container allow-untrusted {
                    presence "Indicates a allow-untrusted node is configured.";
                    description
                      "Forward untrusted packets";
                  }
                  container remote-id {
                    description
                      "Enter remote-id value";
                    container format-type {
                      description
                        "Enter the format-type of remote-id";
                      leaf hex {
                        type xr:Cisco-ios-xr-string {
                          length "1..512" {
                            description
                              "Remote id value";
                          }
                        }
                        must "not(../ascii)";
                        description
                          "Choose the hex string format";
                      }
                      leaf ascii {
                        type xr:Cisco-ios-xr-string {
                          length "1..512" {
                            description
                              "Remote id value";
                          }
                        }
                        must "not(../hex)";
                        description
                          "Choose the ascii string format";
                      }
                    }
                  }
                }
                container policy {
                  description
                    "Specify Relay Agent Information Option policy";
                  container drop {
                    must "not(../keep or ../replace or ../encapsulate)";
                    presence "Indicates a drop node is configured.";
                    description
                      "Drop client request packets with Relay Agent Information Option";
                  }
                  container keep {
                    must "not(../drop or ../replace or ../encapsulate)";
                    presence "Indicates a keep node is configured.";
                    description
                      "Keep existing Relay Agent Information Option in client request";
                  }
                  container replace {
                    must "not(../drop or ../keep or ../encapsulate)";
                    presence "Indicates a replace node is configured.";
                    description
                      "Replace existing Relay Agent Information Option in client request";
                  }
                  container encapsulate {
                    must "not(../drop or ../replace or ../keep)";
                    presence "Indicates a encapsulate node is configured.";
                    description
                      "Encapsulate existing Relay Agent Information Option in client request";
                  }
                }
              }
            }
          }
        }
      }
      container interfaces {
        description
          "Assign a profile to interface";
        list interface {
          key "interface-name";
          description
            "Assign a profile to interface";
          leaf interface-name {
            type xr:Interface-name;
            description
              "Assign a profile to interface";
          }
          container base {
            presence "Indicates a base node is configured.";
            description
              "Assign base profile/Option 82 to interface";
            leaf profile {
              type xr:Cisco-ios-xr-string {
                length "1..64" {
                  description
                    "Profile name";
                }
              }
              description
                "Enter profile name";
            }
            container information {
              description
                "Information";
              container option {
                description
                  "Insert option 82 for this interface";
                container format-type {
                  description
                    "Format type";
                  container circuit-id {
                    description
                      "Enter circuit-id value";
                    leaf format-string {
                      type string {
                        length "1..512" {
                          description
                            "format string (conversion specifier) enclosed in double quotes";
                        }
                        pattern "[\"].*.[\"]";
                      }
                      must "not(../circuit-id-value) and ../format-argument1";
                      description
                        "Extended format";
                    }
                    leaf format-argument1 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-string";
                      description
                        "Format argument 1";
                    }
                    leaf format-argument2 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument1";
                      description
                        "Format argument 1";
                    }
                    leaf format-argument3 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument2";
                      description
                        "Format argument 1";
                    }
                    leaf format-argument4 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument3";
                      description
                        "Format argument 1";
                    }
                    leaf format-argument5 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument4";
                      description
                        "Format argument 1";
                    }
                    leaf format-argument6 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument5";
                      description
                        "Format argument 1";
                    }
                    leaf format-argument7 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument6";
                      description
                        "Format argument 1";
                    }
                    leaf format-argument8 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument7";
                      description
                        "Format argument 1";
                    }
                    leaf format-argument9 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument8";
                      description
                        "Format argument 1";
                    }
                    leaf format-argument10 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument9";
                      description
                        "Format argument 1";
                    }
                    leaf format-argument11 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument10";
                      description
                        "Format argument 1";
                    }
                    leaf format-argument12 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument11";
                      description
                        "Format argument 1";
                    }
                    leaf format-argument13 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument12";
                      description
                        "Format argument 1";
                    }
                    leaf format-argument14 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument13";
                      description
                        "Format argument 1";
                    }
                    leaf format-argument15 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument14";
                      description
                        "Format argument 1";
                    }
                    leaf format-argument16 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument15";
                      description
                        "Format argument 1";
                    }
                    leaf circuit-id-value {
                      type xr:Cisco-ios-xr-string {
                        length "1..512" {
                          description
                            "circuit id value";
                        }
                      }
                      must "not(../format-string)";
                      description
                        "circuit id value";
                    }
                  }
                }
              }
            }
          }
          container cnbng {
            description
              "Assign cnbng profile to interface";
            leaf profile {
              type xr:Cisco-ios-xr-string {
                length "1..64" {
                  description
                    "Profile name";
                }
              }
              description
                "Enter profile name";
            }
          }
          container proxy {
            description
              "Assign proxy profile/Option 82 to interface";
            leaf profile {
              type xr:Cisco-ios-xr-string {
                length "1..64" {
                  description
                    "Profile name";
                }
              }
              description
                "Enter profile name";
            }
            container information {
              description
                "Information";
              container option {
                description
                  "Insert option 82 for this interface";
                container format-type {
                  description
                    "Format type";
                  container circuit-id {
                    description
                      "Enter circuit-id value";
                    leaf format-string {
                      type string {
                        length "1..512" {
                          description
                            "format string (conversion specifier) enclosed in double quotes";
                        }
                        pattern "[\"].*.[\"]";
                      }
                      must "not(../circuit-id-value) and ../format-argument1";
                      description
                        "Extended format";
                    }
                    leaf format-argument1 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-string";
                      description
                        "Format argument 1";
                    }
                    leaf format-argument2 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument1";
                      description
                        "Format argument 1";
                    }
                    leaf format-argument3 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument2";
                      description
                        "Format argument 1";
                    }
                    leaf format-argument4 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument3";
                      description
                        "Format argument 1";
                    }
                    leaf format-argument5 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument4";
                      description
                        "Format argument 1";
                    }
                    leaf format-argument6 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument5";
                      description
                        "Format argument 1";
                    }
                    leaf format-argument7 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument6";
                      description
                        "Format argument 1";
                    }
                    leaf format-argument8 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument7";
                      description
                        "Format argument 1";
                    }
                    leaf format-argument9 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument8";
                      description
                        "Format argument 1";
                    }
                    leaf format-argument10 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument9";
                      description
                        "Format argument 1";
                    }
                    leaf format-argument11 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument10";
                      description
                        "Format argument 1";
                    }
                    leaf format-argument12 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument11";
                      description
                        "Format argument 1";
                    }
                    leaf format-argument13 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument12";
                      description
                        "Format argument 1";
                    }
                    leaf format-argument14 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument13";
                      description
                        "Format argument 1";
                    }
                    leaf format-argument15 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument14";
                      description
                        "Format argument 1";
                    }
                    leaf format-argument16 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument15";
                      description
                        "Format argument 1";
                    }
                    leaf circuit-id-value {
                      type xr:Cisco-ios-xr-string {
                        length "1..512" {
                          description
                            "circuit id value";
                        }
                      }
                      must "not(../format-string)";
                      description
                        "circuit id value";
                    }
                  }
                }
                container remote-id {
                  description
                    "Insert remote ID sub-option";
                  container mac-address {
                    presence "Indicates a mac-address node is configured.";
                    description
                      "Insert client MAC address";
                  }
                }
              }
            }
          }
          container relay {
            description
              "Assign relay profile/Option 82 to interface";
            leaf profile {
              type xr:Cisco-ios-xr-string {
                length "1..64" {
                  description
                    "Profile name";
                }
              }
              description
                "Enter profile Name";
            }
            container information {
              description
                "Information";
              container option {
                description
                  "Insert option 82 for this interface";
                container circuit-id {
                  description
                    "Enter circuit-id value";
                  container format-type {
                    description
                      "Format type";
                    leaf ascii {
                      type xr:Cisco-ios-xr-string {
                        length "1..512" {
                          description
                            "circuit id value";
                        }
                      }
                      must "not(../hex)";
                      description
                        "Choose the ascii string format";
                    }
                    leaf hex {
                      type xr:Cisco-ios-xr-string {
                        length "1..512" {
                          description
                            "circuit id value";
                        }
                      }
                      must "not(../ascii)";
                      description
                        "Choose the hex string format";
                    }
                  }
                }
                container format-type {
                  description
                    "Format type";
                  container circuit-id {
                    presence "Indicates a circuit-id node is configured.";
                    description
                      "Enter circuit-id value";
                    leaf format-string {
                      type string {
                        length "1..512" {
                          description
                            "format string (conversion specifier) enclosed in double quotes";
                        }
                        pattern "[\"].*.[\"]";
                      }
                      mandatory true;
                      description
                        "Extended format";
                    }
                    leaf format-argument1 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      mandatory true;
                      description
                        "Format argument";
                    }
                    leaf format-argument2 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument1";
                      description
                        "Format argument";
                    }
                    leaf format-argument3 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument2";
                      description
                        "Format argument";
                    }
                    leaf format-argument4 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument3";
                      description
                        "Format argument";
                    }
                    leaf format-argument5 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument4";
                      description
                        "Format argument";
                    }
                    leaf format-argument6 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument5";
                      description
                        "Format argument";
                    }
                    leaf format-argument7 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument6";
                      description
                        "Format argument";
                    }
                    leaf format-argument8 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument7";
                      description
                        "Format argument";
                    }
                    leaf format-argument9 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument8";
                      description
                        "Format argument";
                    }
                    leaf format-argument10 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument9";
                      description
                        "Format argument";
                    }
                    leaf format-argument11 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument10";
                      description
                        "Format argument";
                    }
                    leaf format-argument12 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument11";
                      description
                        "Format argument";
                    }
                    leaf format-argument13 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument12";
                      description
                        "Format argument";
                    }
                    leaf format-argument14 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument13";
                      description
                        "Format argument";
                    }
                    leaf format-argument15 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument14";
                      description
                        "Format argument";
                    }
                    leaf format-argument16 {
                      type enumeration {
                        enum "l2-interface" {
                          value 8;
                          description
                            "Ingress L2 Interface";
                        }
                        enum "l3-interface" {
                          value 9;
                          description
                            "Ingress L3 Interface";
                        }
                        enum "hostname" {
                          value 10;
                          description
                            "host name";
                        }
                      }
                      must "../format-argument15";
                      description
                        "Format argument";
                    }
                  }
                }
                container remote-id {
                  description
                    "Insert remote ID sub-option";
                  container mac-address {
                    must "not(../format-type/ascii or ../format-type/hex)";
                    presence "Indicates a mac-address node is configured.";
                    description
                      "Insert client MAC address";
                  }
                  container format-type {
                    description
                      "Format type";
                    leaf ascii {
                      type xr:Cisco-ios-xr-string {
                        length "1..512" {
                          description
                            "circuit id value";
                        }
                      }
                      must "not(../hex or ../../mac-address)";
                      description
                        "Choose the ascii string format";
                    }
                    leaf hex {
                      type xr:Cisco-ios-xr-string {
                        length "1..512" {
                          description
                            "circuit id value";
                        }
                      }
                      must "not(../ascii or ../../mac-address)";
                      description
                        "Choose the hex string format";
                    }
                  }
                }
              }
            }
          }
          container server {
            presence "Indicates a server node is configured.";
            description
              "Assign server profile/Option 82 to interface";
            leaf profile {
              type xr:Cisco-ios-xr-string {
                length "1..64" {
                  description
                    "Profile name";
                }
              }
              description
                "Enter profile name";
            }
            container information {
              description
                "Information";
              container option {
                description
                  "Insert option 82 for this interface";
                container format-type {
                  description
                    "Format type";
                  container circuit-id {
                    description
                      "Enter circuit-id value";
                    leaf format-string {
                      type string {
                        length "1..512" {
                          description
                            "format string (conversion specifier) enclosed in double quotes";
                        }
                        pattern "[\"].*.[\"]";
                      }
                      must "not(../circuit-id-value) and ../format-argument1";
                      description
                        "Extended format";
                    }
                    leaf format-argument1 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-string";
                      description
                        "Format argument 1";
                    }
                    leaf format-argument2 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument1";
                      description
                        "Format argument 1";
                    }
                    leaf format-argument3 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument2";
                      description
                        "Format argument 1";
                    }
                    leaf format-argument4 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument3";
                      description
                        "Format argument 1";
                    }
                    leaf format-argument5 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument4";
                      description
                        "Format argument 1";
                    }
                    leaf format-argument6 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument5";
                      description
                        "Format argument 1";
                    }
                    leaf format-argument7 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument6";
                      description
                        "Format argument 1";
                    }
                    leaf format-argument8 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument7";
                      description
                        "Format argument 1";
                    }
                    leaf format-argument9 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument8";
                      description
                        "Format argument 1";
                    }
                    leaf format-argument10 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument9";
                      description
                        "Format argument 1";
                    }
                    leaf format-argument11 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument10";
                      description
                        "Format argument 1";
                    }
                    leaf format-argument12 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument11";
                      description
                        "Format argument 1";
                    }
                    leaf format-argument13 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument12";
                      description
                        "Format argument 1";
                    }
                    leaf format-argument14 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument13";
                      description
                        "Format argument 1";
                    }
                    leaf format-argument15 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument14";
                      description
                        "Format argument 1";
                    }
                    leaf format-argument16 {
                      type enumeration {
                        enum "physical-chassis" {
                          value 1;
                          description
                            "Rack";
                        }
                        enum "physical-slot" {
                          value 2;
                          description
                            "Slot";
                        }
                        enum "physical-subslot" {
                          value 3;
                          description
                            "Subslot";
                        }
                        enum "physical-port" {
                          value 4;
                          description
                            "Port";
                        }
                        enum "physical-subport" {
                          value 5;
                          description
                            "Subport";
                        }
                        enum "inner-vlan-id" {
                          value 6;
                          description
                            "Inner vlan id tag";
                        }
                        enum "outer-vlan-id" {
                          value 7;
                          description
                            "Outer vlan id tag";
                        }
                      }
                      must "../format-argument15";
                      description
                        "Format argument 1";
                    }
                    leaf circuit-id-value {
                      type xr:Cisco-ios-xr-string {
                        length "1..512" {
                          description
                            "circuit id value";
                        }
                      }
                      must "not(../format-string)";
                      description
                        "circuit id value";
                    }
                  }
                }
              }
            }
          }
          container snoop {
            description
              "Assign snoop static entry/Option 82 to interface";
            container snoops {
              description
                "Assign snoop static entry/Option 82 to interface";
              list snoop {
                key "mac-address";
                description
                  "Assign snoop static entry/Option 82 to interface";
                leaf mac-address {
                  type yang:mac-address;
                  description
                    "Assign snoop static entry/Option 82 to interface";
                }
                leaf ip-address {
                  type inet:ipv4-address-no-zone;
                  mandatory true;
                  description
                    "IP address";
                }
              }
            }
            container snoop-client-ids {
              description
                "Assign snoop static entry/Option 82 to interface";
              list snoop-client-id {
                key "mac-address client-id";
                description
                  "Assign snoop static entry/Option 82 to interface";
                leaf mac-address {
                  type yang:mac-address;
                  description
                    "Assign snoop static entry/Option 82 to interface";
                }
                leaf client-id {
                  type uint32 {
                    range "1..4294967295" {
                      description
                        "Enter hex number";
                    }
                  }
                  description
                    "Client Identifier";
                }
                leaf ip-address {
                  type inet:ipv4-address-no-zone;
                  mandatory true;
                  description
                    "IP address";
                }
              }
            }
            container information {
              description
                "Information";
              container option {
                description
                  "Insert option 82 for this interface";
                container circuit-id {
                  description
                    "Enter circuit-id value";
                  container format-type {
                    description
                      "Format type";
                    leaf hex {
                      type xr:Cisco-ios-xr-string {
                        length "1..512" {
                          description
                            "circuit id value";
                        }
                      }
                      must "not(../ascii)";
                      description
                        "Choose the hex string format";
                    }
                    leaf ascii {
                      type xr:Cisco-ios-xr-string {
                        length "1..512" {
                          description
                            "circuit id value";
                        }
                      }
                      must "not(../hex)";
                      description
                        "Choose the ascii string format";
                    }
                  }
                }
              }
            }
          }
        }
      }
      container database {
        presence "Indicates a database node is configured.";
        description
          "Enable DHCP binding database storage to file system";
        container proxy {
          presence "Indicates a proxy node is configured.";
          description
            "Enable DHCP proxy binding database storage to file system";
        }
        container server {
          presence "Indicates a server node is configured.";
          description
            "Enable DHCP server binding database storage to file system";
        }
        container snoop {
          presence "Indicates a snoop node is configured.";
          description
            "Enable DHCP snoop binding database storage to file system";
        }
        leaf full-write-interval {
          type uint32 {
            range "1..1440" {
              description
                "Enter full file write interval (minutes)";
            }
          }
          description
            "Full file write interval (default 10 minutes)";
        }
        leaf incremental-write-interval {
          type uint32 {
            range "1..1440" {
              description
                "Enter incremental file write interval (minutes)";
            }
          }
          description
            "Incremental file write interval (default 1 minute)";
        }
      }
      container duplicate-mac-allowed {
        presence "Indicates a duplicate-mac-allowed node is configured.";
        description
          "Clients with duplicate  mac allowed";
        container exclude-vlan {
          presence "Indicates a exclude-vlan node is configured.";
          description
            "Exclude-vlan";
        }
        container include-giaddr {
          presence "Indicates a include-giaddr node is configured.";
          description
            "Include giaddr as client key";
        }
      }
      container allow-client-id-change {
        presence "Indicates a allow-client-id-change node is configured.";
        description
          "For BNG session, allow client id change for a client MAC";
      }
      container disable-shadow-binding {
        presence "Indicates a disable-shadow-binding node is configured.";
        description
          "Option to disable shadow binding";
      }
      leaf inner-cos {
        type uint32 {
          range "0..7" {
            description
              "inner cos value";
          }
        }
        description
          "Configure inner cos values for dhcp packets";
      }
      leaf outer-cos {
        type uint32 {
          range "0..7" {
            description
              "Outer cos value";
          }
        }
        description
          "Configure outer cos values for dhcp packets";
      }
      container rate-limit {
        description
          "Rate limit ingress packets";
        leaf period {
          type uint32 {
            range "1..1000" {
              description
                "Period in msec (Default: 200 msec)";
            }
          }
          must "../discover";
          description
            "Rate limiter period in msec";
        }
        leaf discover {
          type uint32 {
            range "0..1000" {
              description
                "Number of Discover packets (Default: 100, 0: No limit)";
            }
          }
          must "../period";
          description
            "Rate limit DISCOVER packets";
        }
      }
      leaf inflight-limit {
        type uint32 {
          range "50..400" {
            description
              "BNG session maximum inflight";
          }
        }
        description
          "For BNG session, Maximum inflight ";
      }
      container ipoe-dhcp-client-reboot {
        description
          "For BNG, timed wait for term a session";
        leaf period {
          type uint32 {
            range "10..30" {
              description
                "time wait in seconds";
            }
          }
          must "../max-period";
          description
            "ipoe dhcp time wait";
        }
        leaf max-period {
          type uint32 {
            range "10..300" {
              description
                "max time to wait in seconds ";
            }
          }
          must "../period";
          description
            "ipoe dhcp max time wait";
        }
      }
    }
  }
}
