module Cisco-IOS-XR-um-traps-otn-cfg {
  namespace "http://cisco.com/ns/yang/Cisco-IOS-XR-um-traps-otn-cfg";
  prefix um-traps-otn-cfg;

  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps-otn package configuration.
     
     This YANG module augments the
     modules with configuration data.
     
     Copyright (c) 2020, 2022 by Cisco Systems, Inc.
     All rights reserved.";

  revision 2020-03-23 {
    description
      "Initial release";
    semver:module-version "1.0.0";
  }

  augment "/a1:snmp-server/a1:traps" {
    container otn {
      presence "Indicates a otn node is configured.";
      description
        "Enable SNMP Cisco otn traps";
    }
  }
}
