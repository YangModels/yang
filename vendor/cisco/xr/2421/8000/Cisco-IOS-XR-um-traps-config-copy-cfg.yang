module Cisco-IOS-XR-um-traps-config-copy-cfg {
  namespace "http://cisco.com/ns/yang/Cisco-IOS-XR-um-traps-config-copy-cfg";
  prefix um-traps-config-copy-cfg;

  import Cisco-IOS-XR-um-snmp-server-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps-config-copy package configuration.
     
     This YANG module augments the
     modules with configuration data.
     
     Copyright (c) 2020-2022 by Cisco Systems, Inc.
     All rights reserved.";

  revision 2022-07-11 {
    description
      "Added missing description statement to nodes";
  }
  revision 2020-04-24 {
    description
      "Initial release";
  }

  augment "/a1:snmp-server/a1:traps" {
    description
      "This augment extends snmp-server traps nodes
       configuration";
    container copy-complete {
      presence "Indicates a copy-complete node is configured.";
      description
        "Enable CISCO-CONFIG-COPY-MIB ccCopyCompletion traps";
    }
  }
}
