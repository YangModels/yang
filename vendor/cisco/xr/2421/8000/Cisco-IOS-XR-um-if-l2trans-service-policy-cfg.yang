module Cisco-IOS-XR-um-if-l2trans-service-policy-cfg {
  namespace "http://cisco.com/ns/yang/Cisco-IOS-XR-um-if-l2trans-service-policy-cfg";
  prefix um-if-l2trans-service-policy-cfg;

  import Cisco-IOS-XR-um-interface-cfg {
    prefix a1;
  }
  import Cisco-IOS-XR-um-if-l2transport-cfg {
    prefix a2;
  }
  import tailf-common {
    prefix tailf;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-l2trans-service-policy package configuration.
     
     This YANG module augments the
     modules with configuration data.
     
     Copyright (c) 2021-2022, 2024 by Cisco Systems, Inc.
     All rights reserved.";

  revision 2024-04-12 {
    description
      "Removed presence statements from two account nodes";
  }
  revision 2022-07-11 {
    description
      "Added missing description statement to nodes";
  }
  revision 2021-10-08 {
    description
      "Initial release";
  }

  feature qos_ui_supp_qfab_cfg {
    description
      "qos ui supp qfab cfg";
  }

  feature qos_ui_supp_gre_qos {
    description
      "qos ui supp gre qos";
  }

  feature qos_ui_supp_l2_acct {
    description
      "qos ui supp l2 acct";
  }

  feature qos_ui_supp_spi {
    description
      "qos ui supp spi";
  }

  feature qos_ui_supp_subscriber_parent_policy {
    description
      "qos ui supp subscriber parent policy";
  }

  feature qos_ui_supp_subscriber_group {
    description
      "qos ui supp subscriber group";
  }

  feature qos_ui_supp_sfrag_parent_policy {
    description
      "qos ui supp sfrag parent policy";
  }

  feature qos_ui_supp_ipsec_policy {
    description
      "qos ui supp ipsec policy";
  }

  feature qos_ui_supp_l2transport_cac_acct {
    description
      "qos ui supp l2transport cac acct";
  }

  feature qos_ui_supp_l2transport_acct {
    description
      "qos ui supp l2transport acct";
  }

  grouping L2TRANS-BODY {
    description
      "Grouping for l2transport";
    container service-policy {
      description
        "Configure QoS Service policy";
      container outputs {
        when "../../../a1:interface-name[not(contains(text(),'.'))]" {
          tailf:dependency "../../../a1:interface-name";
        }
        description
          "direction of service policy application";
        list output {
          key "service-policy-name";
          description
            "direction of service policy application";
          leaf service-policy-name {
            type string {
              length "1..800" {
                description
                  "Name of the service policy";
              }
              pattern "[a-zA-Z0-9][a-zA-Z0-9._@$%+#:=<>-]{0,62}";
            }
            description
              "direction of service policy application";
          }
          container account {
            if-feature "qos_ui_supp_l2transport_acct";
            description
              "Turn off layer specific accounting";
            container layer2 {
              must "not(../nolayer2 or ../user-defined)";
              presence "Indicates a layer2 node is configured.";
              description
                "Turn on l2 accounting";
            }
            container nolayer2 {
              must "not(../layer2 or ../user-defined)";
              presence "Indicates a nolayer2 node is configured.";
              description
                "Turn off l2 accounting";
            }
            leaf user-defined {
              type int32 {
                range "-63..63" {
                  description
                    "Overhead accounting value";
                }
              }
              must "not(../layer2 or ../nolayer2)";
              description
                "User defined accounting";
            }
          }
        }
      }
      container inputs {
        when "../../../a1:interface-name[not(contains(text(),'.'))]" {
          tailf:dependency "../../../a1:interface-name";
        }
        description
          "configure a policy in the input direction";
        list input {
          key "service-policy-name";
          description
            "configure a policy in the input direction";
          leaf service-policy-name {
            type string {
              length "1..800" {
                description
                  "Name of the service policy";
              }
              pattern "[a-zA-Z0-9][a-zA-Z0-9._@$%+#:=<>-]{0,62}";
            }
            description
              "configure a policy in the input direction";
          }
          container account {
            if-feature "qos_ui_supp_l2transport_acct";
            description
              "Turn off layer specific accounting";
            container layer2 {
              must "not(../nolayer2 or ../user-defined)";
              presence "Indicates a layer2 node is configured.";
              description
                "Turn on l2 accounting";
            }
            container nolayer2 {
              must "not(../layer2 or ../user-defined)";
              presence "Indicates a nolayer2 node is configured.";
              description
                "Turn off l2 accounting";
            }
            leaf user-defined {
              type int32 {
                range "-63..63" {
                  description
                    "Overhead accounting value";
                }
              }
              must "not(../layer2 or ../nolayer2)";
              description
                "User defined accounting";
            }
          }
        }
      }
    }
  }

  grouping L2TRANS-BODY-SUBINTF {
    description
      "Grouping for l2transport-body-subinterface";
    container l2transport-service-policy {
      description
        "Configure QoS Service policy";
      container inputs-subintf {
        when "../../a1:interface-name[(contains(text(),'.'))] and ../../a1:sub-interface-type/a1:l2transport" {
          tailf:dependency "../../a1:interface-name";
        }
        description
          "configure a policy in the input direction";
        list input {
          key "service-policy-name";
          description
            "configure a policy in the input direction";
          leaf service-policy-name {
            type string {
              length "1..800" {
                description
                  "Name of the service policy";
              }
              pattern "[a-zA-Z0-9][a-zA-Z0-9._@$%+#:=<>-]{0,62}";
            }
            description
              "configure a policy in the input direction";
          }
          leaf shared-policy-instance {
            if-feature "qos_ui_supp_spi";
            type xr:Cisco-ios-xr-string {
              length "1..31" {
                description
                  "Name of the shared-policy-instance(Max 31 chars)";
              }
            }
            description
              "Configure a shared-policy-instance";
          }
          container account {
            if-feature "qos_ui_supp_l2transport_cac_acct";
            description
              "Turn off layer specific accounting";
            container layer2 {
              must "not(../nolayer2 or ../user-defined)";
              presence "Indicates a layer2 node is configured.";
              description
                "Turn on l2 accounting";
            }
            container nolayer2 {
              must "not(../layer2 or ../user-defined)";
              presence "Indicates a nolayer2 node is configured.";
              description
                "Turn off l2 accounting";
            }
            leaf user-defined {
              type int32 {
                range "-63..63" {
                  description
                    "Overhead accounting value";
                }
              }
              must "not(../layer2 or ../nolayer2)";
              description
                "User defined accounting";
            }
          }
        }
      }
      container outputs-subintf {
        when "../../a1:interface-name[(contains(text(),'.'))] and ../../a1:sub-interface-type/a1:l2transport" {
          tailf:dependency "../../a1:interface-name";
        }
        description
          "configure a policy in the output direction";
        list output {
          key "service-policy-name";
          description
            "configure a policy in the output direction";
          leaf service-policy-name {
            type string {
              length "1..800" {
                description
                  "Name of the service policy";
              }
              pattern "[a-zA-Z0-9][a-zA-Z0-9._@$%+#:=<>-]{0,62}";
            }
            description
              "configure a policy in the output direction";
          }
          leaf shared-policy-instance {
            if-feature "qos_ui_supp_spi";
            type xr:Cisco-ios-xr-string {
              length "1..31" {
                description
                  "Name of the shared-policy-instance(Max 31 chars)";
              }
            }
            description
              "Configure a shared-policy-instance";
          }
          container account {
            if-feature "qos_ui_supp_l2transport_cac_acct";
            description
              "Turn off layer specific accounting";
            container layer2 {
              must "not(../nolayer2 or ../user-defined)";
              presence "Indicates a layer2 node is configured.";
              description
                "Turn on l2 accounting";
            }
            container nolayer2 {
              must "not(../layer2 or ../user-defined)";
              presence "Indicates a nolayer2 node is configured.";
              description
                "Turn off l2 accounting";
            }
            leaf user-defined {
              type int32 {
                range "-63..63" {
                  description
                    "Overhead accounting value";
                }
              }
              must "not(../layer2 or ../nolayer2)";
              description
                "User defined accounting";
            }
          }
        }
      }
    }
  }

  augment "/a1:interfaces/a1:interface/a2:l2transport" {
    description
      "This augment extends active nodes configuration";
    uses L2TRANS-BODY;
  }
  augment "/a1:interfaces/a1:interface-preconfigure/a2:l2transport" {
    description
      "This augment extends preconfigured nodes
       configuration";
    uses L2TRANS-BODY;
  }
  augment "/a1:interfaces/a1:interface" {
    description
      "This augment extends active nodes configuration";
    uses L2TRANS-BODY-SUBINTF;
  }
  augment "/a1:interfaces/a1:interface-preconfigure" {
    description
      "This augment extends preconfigured nodes
       configuration";
    uses L2TRANS-BODY-SUBINTF;
  }
}
