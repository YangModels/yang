module Cisco-IOS-XR-um-line-cfg {
  namespace "http://cisco.com/ns/yang/Cisco-IOS-XR-um-line-cfg";
  prefix um-line-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR line package configuration.
     
     This YANG module augments the
     modules with configuration data.
     
     Copyright (c) 2021-2022 by Cisco Systems, Inc.
     All rights reserved.";

  revision 2021-05-10 {
    description
      "Initial release";
  }

  container line {
    description
      "Line subcommands";
    container console {
      description
        "console template";
      container access-class {
        description
          "Filter connections based on an IP access list";
        leaf ingress {
          type xr:Cisco-ios-xr-string {
            length "1..800" {
              description
                "IP access list name";
            }
          }
          description
            "Filter incoming connections";
        }
        leaf egress {
          type xr:Cisco-ios-xr-string {
            length "1..800" {
              description
                "IP access list name";
            }
          }
          description
            "Filter outgoing connections";
        }
      }
      leaf disconnect-character {
        type xr:Char-num;
        description
          "Define the disconnect character";
      }
      leaf escape-character {
        type xr:Tty-escape-char-num;
        default "30";
        description
          "Change the current line template's escape character";
      }
      container session-timeout {
        presence "Indicates a session-timeout node is configured.";
        description
          "Set interval for closing connection when there is no input traffic";
        leaf timeout-interval {
          type uint32 {
            range "0..35791" {
              description
                "Session timeout interval in minutes";
            }
          }
          mandatory true;
          description
            "Set interval for closing connection when there is no input traffic";
        }
        container output {
          presence "Indicates a output node is configured.";
          description
            "Include output traffic as well as input traffic";
        }
      }
      container transport {
        description
          "Define transport protocols for line";
        container input {
          description
            "Define which protocols to use when connecting to the terminal server";
          container none {
            must "not(../ssh) and not(../telnet) and not(../all)";
            presence "Indicates a none node is configured.";
            description
              "No protocols";
          }
          container ssh {
            must "not(../none) and not(../telnet) and not(../all)";
            presence "Indicates a ssh node is configured.";
            description
              "Unix ssh protocol";
            container telnet {
              presence "Indicates a telnet node is configured.";
              description
                "TCP/IP Telnet protocol";
            }
          }
          container telnet {
            must "not(../none) and not(../ssh) and not(../all)";
            presence "Indicates a telnet node is configured.";
            description
              "TCP/IP Telnet protocol";
            container ssh {
              presence "Indicates a ssh node is configured.";
              description
                "Unix ssh protocol";
            }
          }
          container all {
            must "not(../ssh) and not(../telnet) and not(../none)";
            presence "Indicates a all node is configured.";
            description
              "All protocols";
          }
        }
        container output {
          description
            "Define which protocols to use for outgoing connections";
          container all {
            must "not(../ssh) and not(../telnet) and not(../none)";
            presence "Indicates a all node is configured.";
            description
              "All protocols";
          }
          container none {
            must "not(../ssh) and not(../telnet) and not(../all)";
            presence "Indicates a none node is configured.";
            description
              "No protocols";
          }
          container ssh {
            must "not(../none) and not(../telnet) and not(../all)";
            presence "Indicates a ssh node is configured.";
            description
              "Unix ssh protocol";
            container telnet {
              presence "Indicates a telnet node is configured.";
              description
                "TCP/IP Telnet protocol";
            }
          }
          container telnet {
            must "not(../none) and not(../ssh) and not(../all)";
            presence "Indicates a telnet node is configured.";
            description
              "TCP/IP Telnet protocol";
            container ssh {
              presence "Indicates a ssh node is configured.";
              description
                "Unix ssh protocol";
            }
          }
        }
        container preferred {
          description
            "Specify the preferred protocol to use";
          container none {
            must "not(../ssh) and not(../telnet)";
            presence "Indicates a none node is configured.";
            description
              "No protocols";
          }
          container telnet {
            must "not(../ssh) and not(../none)";
            presence "Indicates a telnet node is configured.";
            description
              "TCP/IP Telnet protocol";
          }
          container ssh {
            must "not(../telnet) and not(../none)";
            presence "Indicates a ssh node is configured.";
            description
              "Unix ssh protocol";
          }
        }
      }
      leaf session-limit {
        type uint32 {
          range "0..20" {
            description
              "Number of outgoing connections";
          }
        }
        description
          "Set the number of outgoing connections";
      }
      container cli {
        description
          "Set the behaviour of cli.";
        container whitespace {
          description
            "Whitespace behaviour";
          container completion {
            presence "Indicates a completion node is configured.";
            description
              "Command completion on whitespace";
          }
        }
      }
      container interactive {
        description
          "Interactive behaviour";
        container syntax {
          description
            "Syntax of user input";
          container check {
            presence "Indicates a check node is configured.";
            description
              "Enable the check";
          }
        }
      }
    }
    container default {
      description
        "default template";
      container access-class {
        description
          "Filter connections based on an IP access list";
        leaf ingress {
          type xr:Cisco-ios-xr-string {
            length "1..800" {
              description
                "IP access list name";
            }
          }
          description
            "Filter incoming connections";
        }
        leaf egress {
          type xr:Cisco-ios-xr-string {
            length "1..800" {
              description
                "IP access list name";
            }
          }
          description
            "Filter outgoing connections";
        }
      }
      leaf disconnect-character {
        type xr:Char-num;
        description
          "Define the disconnect character";
      }
      leaf escape-character {
        type xr:Tty-escape-char-num;
        default "30";
        description
          "Change the current line template's escape character";
      }
      container session-timeout {
        presence "Indicates a session-timeout node is configured.";
        description
          "Set interval for closing connection when there is no input traffic";
        leaf timeout-interval {
          type uint32 {
            range "0..35791" {
              description
                "Session timeout interval in minutes";
            }
          }
          mandatory true;
          description
            "Set interval for closing connection when there is no input traffic";
        }
        container output {
          presence "Indicates a output node is configured.";
          description
            "Include output traffic as well as input traffic";
        }
      }
      container transport {
        description
          "Define transport protocols for line";
        container input {
          description
            "Define which protocols to use when connecting to the terminal server";
          container none {
            must "not(../ssh) and not(../telnet) and not(../all)";
            presence "Indicates a none node is configured.";
            description
              "No protocols";
          }
          container ssh {
            must "not(../none) and not(../telnet) and not(../all)";
            presence "Indicates a ssh node is configured.";
            description
              "Unix ssh protocol";
            container telnet {
              presence "Indicates a telnet node is configured.";
              description
                "TCP/IP Telnet protocol";
            }
          }
          container telnet {
            must "not(../none) and not(../ssh) and not(../all)";
            presence "Indicates a telnet node is configured.";
            description
              "TCP/IP Telnet protocol";
            container ssh {
              presence "Indicates a ssh node is configured.";
              description
                "Unix ssh protocol";
            }
          }
          container all {
            must "not(../ssh) and not(../telnet) and not(../none)";
            presence "Indicates a all node is configured.";
            description
              "All protocols";
          }
        }
        container output {
          description
            "Define which protocols to use for outgoing connections";
          container all {
            must "not(../ssh) and not(../telnet) and not(../none)";
            presence "Indicates a all node is configured.";
            description
              "All protocols";
          }
          container none {
            must "not(../ssh) and not(../telnet) and not(../all)";
            presence "Indicates a none node is configured.";
            description
              "No protocols";
          }
          container ssh {
            must "not(../none) and not(../telnet) and not(../all)";
            presence "Indicates a ssh node is configured.";
            description
              "Unix ssh protocol";
            container telnet {
              presence "Indicates a telnet node is configured.";
              description
                "TCP/IP Telnet protocol";
            }
          }
          container telnet {
            must "not(../none) and not(../ssh) and not(../all)";
            presence "Indicates a telnet node is configured.";
            description
              "TCP/IP Telnet protocol";
            container ssh {
              presence "Indicates a ssh node is configured.";
              description
                "Unix ssh protocol";
            }
          }
        }
        container preferred {
          description
            "Specify the preferred protocol to use";
          container none {
            must "not(../ssh) and not(../telnet)";
            presence "Indicates a none node is configured.";
            description
              "No protocols";
          }
          container telnet {
            must "not(../ssh) and not(../none)";
            presence "Indicates a telnet node is configured.";
            description
              "TCP/IP Telnet protocol";
          }
          container ssh {
            must "not(../telnet) and not(../none)";
            presence "Indicates a ssh node is configured.";
            description
              "Unix ssh protocol";
          }
        }
      }
      leaf session-limit {
        type uint32 {
          range "0..20" {
            description
              "Number of outgoing connections";
          }
        }
        description
          "Set the number of outgoing connections";
      }
      container cli {
        description
          "Set the behaviour of cli.";
        container whitespace {
          description
            "Whitespace behaviour";
          container completion {
            presence "Indicates a completion node is configured.";
            description
              "Command completion on whitespace";
          }
        }
      }
      container interactive {
        description
          "Interactive behaviour";
        container syntax {
          description
            "Syntax of user input";
          container check {
            presence "Indicates a check node is configured.";
            description
              "Enable the check";
          }
        }
      }
      leaf autocommand {
        type string {
          length "1..800" {
            description
              "Appropriate EXEC command";
          }
        }
        description
          "Automatically execute an EXEC command";
      }
    }
    container templates {
      description
        "user defined template";
      list template {
        key "template-name";
        description
          "user defined template";
        leaf template-name {
          type xr:Cisco-ios-xr-string {
            length "1..800" {
              description
                "Name of template to configure";
            }
          }
          description
            "user defined template";
        }
        container access-class {
          description
            "Filter connections based on an IP access list";
          leaf ingress {
            type xr:Cisco-ios-xr-string {
              length "1..800" {
                description
                  "IP access list name";
              }
            }
            description
              "Filter incoming connections";
          }
          leaf egress {
            type xr:Cisco-ios-xr-string {
              length "1..800" {
                description
                  "IP access list name";
              }
            }
            description
              "Filter outgoing connections";
          }
        }
        leaf disconnect-character {
          type xr:Char-num;
          description
            "Define the disconnect character";
        }
        leaf escape-character {
          type xr:Tty-escape-char-num;
          default "30";
          description
            "Change the current line template's escape character";
        }
        container session-timeout {
          presence "Indicates a session-timeout node is configured.";
          description
            "Set interval for closing connection when there is no input traffic";
          leaf timeout-interval {
            type uint32 {
              range "0..35791" {
                description
                  "Session timeout interval in minutes";
              }
            }
            mandatory true;
            description
              "Set interval for closing connection when there is no input traffic";
          }
          container output {
            presence "Indicates a output node is configured.";
            description
              "Include output traffic as well as input traffic";
          }
        }
        container transport {
          description
            "Define transport protocols for line";
          container input {
            description
              "Define which protocols to use when connecting to the terminal server";
            container none {
              must "not(../ssh) and not(../telnet) and not(../all)";
              presence "Indicates a none node is configured.";
              description
                "No protocols";
            }
            container ssh {
              must "not(../none) and not(../telnet) and not(../all)";
              presence "Indicates a ssh node is configured.";
              description
                "Unix ssh protocol";
              container telnet {
                presence "Indicates a telnet node is configured.";
                description
                  "TCP/IP Telnet protocol";
              }
            }
            container telnet {
              must "not(../none) and not(../ssh) and not(../all)";
              presence "Indicates a telnet node is configured.";
              description
                "TCP/IP Telnet protocol";
              container ssh {
                presence "Indicates a ssh node is configured.";
                description
                  "Unix ssh protocol";
              }
            }
            container all {
              must "not(../ssh) and not(../telnet) and not(../none)";
              presence "Indicates a all node is configured.";
              description
                "All protocols";
            }
          }
          container output {
            description
              "Define which protocols to use for outgoing connections";
            container all {
              must "not(../ssh) and not(../telnet) and not(../none)";
              presence "Indicates a all node is configured.";
              description
                "All protocols";
            }
            container none {
              must "not(../ssh) and not(../telnet) and not(../all)";
              presence "Indicates a none node is configured.";
              description
                "No protocols";
            }
            container ssh {
              must "not(../none) and not(../telnet) and not(../all)";
              presence "Indicates a ssh node is configured.";
              description
                "Unix ssh protocol";
              container telnet {
                presence "Indicates a telnet node is configured.";
                description
                  "TCP/IP Telnet protocol";
              }
            }
            container telnet {
              must "not(../none) and not(../ssh) and not(../all)";
              presence "Indicates a telnet node is configured.";
              description
                "TCP/IP Telnet protocol";
              container ssh {
                presence "Indicates a ssh node is configured.";
                description
                  "Unix ssh protocol";
              }
            }
          }
          container preferred {
            description
              "Specify the preferred protocol to use";
            container none {
              must "not(../ssh) and not(../telnet)";
              presence "Indicates a none node is configured.";
              description
                "No protocols";
            }
            container telnet {
              must "not(../ssh) and not(../none)";
              presence "Indicates a telnet node is configured.";
              description
                "TCP/IP Telnet protocol";
            }
            container ssh {
              must "not(../telnet) and not(../none)";
              presence "Indicates a ssh node is configured.";
              description
                "Unix ssh protocol";
            }
          }
        }
        leaf session-limit {
          type uint32 {
            range "0..20" {
              description
                "Number of outgoing connections";
            }
          }
          description
            "Set the number of outgoing connections";
        }
        container cli {
          description
            "Set the behaviour of cli.";
          container whitespace {
            description
              "Whitespace behaviour";
            container completion {
              presence "Indicates a completion node is configured.";
              description
                "Command completion on whitespace";
            }
          }
        }
        container interactive {
          description
            "Interactive behaviour";
          container syntax {
            description
              "Syntax of user input";
            container check {
              presence "Indicates a check node is configured.";
              description
                "Enable the check";
            }
          }
        }
        leaf autocommand {
          type string {
            length "1..800" {
              description
                "Appropriate EXEC command";
            }
          }
          description
            "Automatically execute an EXEC command";
        }
      }
    }
  }
}
