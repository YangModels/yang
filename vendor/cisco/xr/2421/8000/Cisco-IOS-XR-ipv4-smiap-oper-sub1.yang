submodule Cisco-IOS-XR-ipv4-smiap-oper-sub1 {
  belongs-to Cisco-IOS-XR-ipv4-smiap-oper {
    prefix Cisco-IOS-XR-ipv4-smiap-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-smiap package operational data.
     
     Copyright (c) 2013-2019, 2022 by Cisco Systems, Inc.
     All rights reserved.";

  revision 2019-04-05 {
    description
      "Establish semantic version baseline.";
    semver:module-version "1.0.0";
  }
  revision 2015-11-09 {
    description
      "IOS XR 6.0 revision.";
  }

  typedef Smiap-address-family {
    type enumeration {
      enum "ipv4" {
        value 2;
        description
          "IPv4 Address family";
      }
      enum "ipv6" {
        value 10;
        description
          "IPv6 Address family";
      }
    }
    description
      "SMIAP Address family";
  }

  grouping SMIAP-ACT-INTERFACE {
    description
      "Active interface information";
    leaf interface-name {
      type string;
      description
        "Active Interface name";
    }
    leaf mac-address {
      type yang:mac-address;
      description
        "MAC address pf the active interface";
    }
  }

  grouping SMIAP-IPV6-ADDR {
    description
      "SMIAP IPv6 Address";
    leaf address {
      type inet:ipv6-address;
      description
        "IPv6 Address";
    }
    leaf prefix-length {
      type uint32;
      description
        "IPv6 Prefix Lenghth";
    }
  }

  grouping SMIAP-IPV4-ADDR {
    description
      "SMIAP IPv4 Address";
    leaf address {
      type inet:ipv4-address;
      description
        "IPv4 Address";
    }
    leaf prefix-length {
      type uint32;
      description
        "IPv4 Prefix Length";
    }
  }

  grouping SMIAP-VIRTUAL-IP-UNION {
    description
      "Union of IPV4 and IPV6 address types";
    container ipv4-address {
      when "../address-family = 'ipv4'" {
        description
          "../AddressFamily = 'IPV4'";
      }
      description
        "IPv4 Address";
      uses SMIAP-IPV4-ADDR;
    }
    container ipv6-address {
      when "../address-family = 'ipv6'" {
        description
          "../AddressFamily = 'IPV6'";
      }
      description
        "IPv6 Address";
      uses SMIAP-IPV6-ADDR;
    }
    leaf address-family {
      type Smiap-address-family;
      description
        "AddressFamily";
    }
  }

  grouping SMIAP-VRF-ENTRY {
    description
      "SMIAP VRF Database entry";
    container virtual-ip {
      description
        "Virtual IP";
      uses SMIAP-VIRTUAL-IP-UNION;
    }
    container active-interface {
      description
        "Active Interface";
      uses SMIAP-ACT-INTERFACE;
    }
    leaf vrf-name-xr {
      type string;
      description
        "VRF Name";
    }
  }
}
