module Cisco-IOS-XR-ztp-act {
  namespace "http://cisco.com/ns/yang/Cisco-IOS-XR-ztp-act";
  prefix ztp-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2022 by Cisco Systems, Inc.
     All rights reserved.";

  revision 2022-08-10 {
    description
      "Initial revision";
  }

  grouping ztp-initiate-options {
    description
      "ZTP Initiate options";
    leaf mode {
      type enumeration {
        enum "dataport" {
          description
            "Run on dataport interfaces only";
        }
        enum "management" {
          description
            "Run on management interfaces only";
        }
        enum "interface" {
          description
            "Run on a specific interface only";
        }
        enum "usb" {
          description
            "Run on a USB source only";
        }
      }
      must "../mode = 'usb' and not(../interface-name or ../dhcp-version or ../override or ../client-id)" {
        error-message "Given options are incompatible with USB mode";
      }
      description
        "Initiate ZTP in dataport/management/interface/usb mode";
    }
    leaf interface-name {
      type string;
      must "(../mode = 'interface')";
      description
        "Interface name";
    }
    leaf dhcp-version {
      type enumeration {
        enum "dhcp4" {
          description
            "Send only DHCP IPv4 requests";
        }
        enum "dhcp6" {
          description
            "Send only DHCP IPv6 requests";
        }
      }
      description
        "Initiate ZTP sending only DHCPv4/DHCPv6 requests";
    }
    leaf override {
      type enumeration {
        enum "dhcp4-client-id" {
          description
            "Override DHCPv4 client ID";
        }
        enum "dhcp6-client-id" {
          description
            "Override DHCPv6 client ID";
        }
      }
      must "(../client-id)";
      description
        "Override DHCPv4/DHCPv6 client ID";
    }
    leaf client-id {
      type string;
      must "(../override)";
      description
        "Client ID";
    }
  }

  rpc ztp-initiate {
    description
      "Start ZTP with specific parameters";
    input {
      uses ztp-initiate-options;
    }
  }
  rpc ztp-initiate-change-hostname {
    description
      "Start ZTP with specific parameters and change hostname";
    input {
      uses ztp-initiate-options;
      leaf hostname {
        type string {
          length "1..255";
          pattern "[a-zA-Z0-9_.{}+-:]+";
        }
        mandatory true;
        description
          "Specify the hostname to be applied";
      }
    }
  }
  rpc ztp-initiate-apply-configuration {
    description
      "Start ZTP with specific parameters with a prerequisite configuration";
    input {
      uses ztp-initiate-options;
      leaf configuration {
        type string {
          length "1..65535";
        }
        mandatory true;
        description
          "Specify XR configuration commands to apply, \\; separated";
      }
    }
  }
  rpc ztp-enable {
    description
      "Enables ZTP";
  }
  rpc ztp-disable {
    description
      "Disables ZTP";
  }
  rpc ztp-clean {
    description
      "Remove all ZTP logs and temporary files.";
  }
  rpc ztp-secure-mode-enable {
    description
      "Enable Secure ZTP";
  }
  rpc ztp-terminate {
    description
      "Terminate all existing ZTP processes";
  }
}
