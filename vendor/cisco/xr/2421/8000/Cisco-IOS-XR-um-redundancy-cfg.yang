module Cisco-IOS-XR-um-redundancy-cfg {
  namespace "http://cisco.com/ns/yang/Cisco-IOS-XR-um-redundancy-cfg";
  prefix um-redundancy-cfg;

  import Cisco-IOS-XR-types {
    prefix xr;
  }
  import ietf-inet-types {
    prefix inet;
  }
  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR redundancy package configuration.
     
     This YANG module augments the
     modules with configuration data.
     
     Copyright (c) 2021-2022 by Cisco Systems, Inc.
     All rights reserved.";

  revision 2021-06-29 {
    description
      "Initial release";
  }

  container redundancy {
    presence "Indicates a redundancy node is configured.";
    description
      "Interchassis redundancy configuration";
    container iccp {
      description
        "configure iccp parameter";
      container groups {
        description
          "group configuration";
        list group {
          key "group-number";
          description
            "group configuration";
          leaf group-number {
            type uint32 {
              range "1..4294967295" {
                description
                  "Enter group number";
              }
            }
            description
              "group configuration";
          }
          container mlacp {
            description
              "Multi-chassis Link Aggregation Control Protocol commands";
            leaf node {
              type uint32 {
                range "0..7" {
                  description
                    "Unique node ID in the ICCP Group for this system.";
                }
              }
              description
                "Set mLACP node ID to use in this ICCP Group";
            }
            container system {
              description
                "Set the default system parameters for LACP bundles";
              leaf priority {
                type uint32 {
                  range "1..65535" {
                    description
                      "Priority for this system. Lower value is higher priority.";
                  }
                }
                description
                  "Set the LACP system priority to be used in this ICCP Group.";
              }
              leaf mac {
                type yang:mac-address;
                description
                  "The LACP System ID to be used in this ICCP Group.";
              }
            }
            container connect {
              description
                "Specify configuration options for connecting to mLACP peers.";
              leaf timeout {
                type uint32 {
                  range "0..65534" {
                    description
                      "Number of seconds to wait before assuming mLACP peer is down.";
                  }
                }
                description
                  "Specify time to wait before assuming mLACP peer is down.";
              }
            }
          }
          container member {
            description
              "configure ICCP members";
            container neighbors {
              description
                "configure interchassis group ICCP members";
              list neighbor {
                key "address";
                description
                  "configure interchassis group ICCP members";
                leaf address {
                  type inet:ipv4-address-no-zone;
                  description
                    "configure interchassis group ICCP members";
                }
              }
            }
          }
          container backbone {
            description
              "configure ICCP backbone interfaces";
            container interfaces {
              description
                "configure interchasis group ICCP backbone interface";
              list interface {
                key "interface-name";
                description
                  "configure interchasis group ICCP backbone interface";
                leaf interface-name {
                  type xr:Interface-name;
                  description
                    "configure interchasis group ICCP backbone interface";
                }
              }
            }
          }
          container isolation {
            description
              "Set the isolation parameters";
            leaf recovery-delay {
              type uint32 {
                range "30..600" {
                  description
                    "Recovery delay in seconds.";
                }
              }
              description
                "Specify delay before clearing isolation condition after recovery from failure";
            }
          }
          container mode {
            description
              "Set the group mode";
            container singleton {
              presence "Indicates a singleton node is configured.";
              description
                "Run the group in singleton mode";
            }
          }
        }
      }
    }
    container multi-router {
      description
        "multi-router redundancy configuration";
      container aps {
        description
          "multi-route aps redundancy configuration";
        container groups {
          description
            "group configuration";
          list group {
            key "group-number";
            description
              "group configuration";
            leaf group-number {
              type uint32 {
                range "1..32" {
                  description
                    "Enter group number";
                }
              }
              description
                "group configuration";
            }
            container controllers {
              description
                "Sonet controller backup configuration";
              list controller {
                key "controller-name";
                description
                  "Sonet controller backup configuration";
                leaf controller-name {
                  type xr:Interface-name {
                    pattern "SONET.*";
                  }
                  description
                    "Sonet controller name";
                }
                container member {
                  description
                    "Interchassis redundancy group member";
                  leaf ipv4 {
                    type inet:ipv4-address-no-zone;
                    mandatory true;
                    description
                      "Group member next hop IPv4 address";
                  }
                  leaf backup-interface {
                    type xr:Interface-name {
                      pattern "(Bundle-Ether.*|GigabitEther.*|TenGigE.*)";
                    }
                    mandatory true;
                    description
                      "Group member backup interface";
                  }
                }
              }
            }
          }
        }
        container default-group {
          description
            "default configuration";
          container member {
            description
              "default aps group member";
            leaf ipv4 {
              type inet:ipv4-address-no-zone;
              must "../backup-interface";
              description
                "Group member next hop IPv4 address";
            }
            leaf backup-interface {
              type xr:Interface-name;
              must "../ipv4";
              description
                "Group member backup interface";
            }
          }
        }
      }
    }
  }
}
