module Cisco-IOS-XR-um-config-hostname-cfg {
  namespace "http://cisco.com/ns/yang/Cisco-IOS-XR-um-config-hostname-cfg";
  prefix um-config-hostname-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-hostname package configuration.
     
     This YANG module augments the
     modules with configuration data.
     
     Copyright (c) 2020, 2022 by Cisco Systems, Inc.
     All rights reserved.";

  revision 2020-12-14 {
    description
      "Initial release";
  }

  container config-hostname {
    description
      "Set system's test network name";
    leaf system-network-name {
      type xr:Cisco-ios-xr-string {
        length "1..800" {
          description
            "This system's network name";
        }
        pattern "[a-zA-Z0-9_.{}+-]+";
      }
      description
        "Set system's test network name";
    }
  }
  container config-sleep {
    description
      "Block config commit for n seconds";
    leaf sleep-time {
      type uint32 {
        range "10..299" {
          description
            "time in seconds";
        }
      }
      description
        "Block config commit for n seconds";
    }
  }
}
