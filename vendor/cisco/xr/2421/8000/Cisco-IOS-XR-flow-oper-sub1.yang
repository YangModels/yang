submodule Cisco-IOS-XR-flow-oper-sub1 {
  belongs-to Cisco-IOS-XR-flow-oper {
    prefix Cisco-IOS-XR-flow-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR flow package operational data.
     
     Copyright (c) 2013-2022 by Cisco Systems, Inc.
     All rights reserved.";

  revision 2021-06-16 {
    description
      "Added tunnel egress related options for sflow
       2021-04-23
         Added new node for data-template info";
    semver:module-version "1.1.0";
  }
  revision 2019-04-05 {
    description
      "Establish semantic version baseline.";
    semver:module-version "1.0.0";
  }
  revision 2015-11-09 {
    description
      "IOS XR 6.0 revision.";
  }

  grouping NFSVR-TEMPLATE-IE-ITEM-ST {
    description
      "NFSVR TEMPLATE IE ITEM ST";
    leaf ie-name {
      type string;
      description
        "Name of the Information Element";
    }
    leaf ie-id {
      type uint16;
      description
        "Integer identifier of the Information Element";
    }
    leaf ie-length {
      type uint16;
      units "byte";
      description
        "Length of the Information Element item in bytes";
    }
  }

  grouping NFSVR-SHOW-FLOW-DATA-TEMPLATE {
    description
      "Data Template Info";
    leaf fm-name {
      type string;
      description
        "Name of the flow monitor";
    }
    leaf frec-name {
      type string;
      description
        "Name of flow record";
    }
    leaf template-description {
      type string;
      description
        "Name of template description";
    }
    list v9-ie-array {
      description
        "Array of template items for v9 export protocol";
      uses NFSVR-TEMPLATE-IE-ITEM-ST;
    }
    list ipfix-ie-array {
      description
        "Array of template items for ipfix export
         protocol";
      uses NFSVR-TEMPLATE-IE-ITEM-ST;
    }
  }

  grouping NFSVR-HASH-BUCKET-STATS-RESP {
    description
      "Bucket stats";
    leaf depth-min {
      type uint16;
      description
        "Minimum depth";
    }
    leaf depth-max {
      type uint16;
      description
        "Maximum depth";
    }
    leaf curr-depth {
      type uint32;
      description
        "Buckets with current depth in range";
    }
    leaf max-depth {
      type uint32;
      description
        "Buckets with maximum depth in range";
    }
  }

  grouping NFSVR-SHOW-FLOW-CACHE-RESP-INTERNAL {
    description
      "Flow cache internal details";
    leaf cache-hits {
      type uint64;
      description
        "Hits";
    }
    leaf cache-misses {
      type uint64;
      description
        "Misses";
    }
    leaf cache-overflows {
      type uint64;
      description
        "Overflows";
    }
    leaf cache-above-hi-water {
      type uint64;
      description
        "Exceed Hi water mark";
    }
    leaf flows-dropped-by-ager {
      type uint64;
      description
        "flows dropped by ager";
    }
    leaf flows-not-exported-by-clear-cache {
      type uint64;
      description
        "flows not exported by clear cache";
    }
    leaf flows-not-aged-export-ring-full {
      type uint64;
      description
        "flows not exported due to exporter ring full";
    }
    leaf flows-periodic-export-failure {
      type uint64;
      description
        "flows not exported by updated timeout";
    }
    leaf cache-state {
      type uint32;
      description
        "Cache state";
    }
    leaf total-memory {
      type uint32;
      description
        "Total memory usage by this monitor";
    }
    leaf num-hash-buckets {
      type uint64;
      description
        "Total number of hash buckets";
    }
    leaf max-hash-depth {
      type uint64;
      description
        "Summary data";
    }
    list bucket-stat {
      description
        "Hash bucket Statistics";
      uses NFSVR-HASH-BUCKET-STATS-RESP;
    }
  }

  grouping NFSVR-SHOW-FLOW-CACHE-RESP-SUMMARY {
    description
      "Flow cache summary";
    leaf cache-name {
      type string;
      description
        "Cache name";
    }
    leaf frec-name {
      type string;
      description
        "Typename of flow record";
    }
    leaf cache-size {
      type uint32;
      description
        "Cache size";
    }
    leaf current-entries {
      type uint32;
      description
        "Current number of entries";
    }
    leaf match-entries {
      type uint32;
      description
        "Entries that match this search criteria";
    }
    leaf display-entries {
      type uint32;
      description
        "Number of cache entries returned";
    }
    leaf high-watermark {
      type uint32;
      description
        "Cache high watermark";
    }
    leaf fl-added {
      type uint64;
      description
        "Number of flows added";
    }
    leaf fl-dropped {
      type uint64;
      description
        "Number of flows dropped because of cache full";
    }
    leaf ager-polls {
      type uint64;
      description
        "Total number of ager polls";
    }
    leaf fl-age-active-tout {
      type uint64;
      description
        "Flows aged on active timeout";
    }
    leaf fl-age-inactive-tout {
      type uint64;
      description
        "Flows aged on  inactive timeout";
    }
    leaf fl-age-immediate {
      type uint64;
      description
        "Flows aged immediately";
    }
    leaf fl-age-watermark {
      type uint64;
      description
        "Flows aged due to exceeding high water mark";
    }
    leaf fl-age-ememrgency {
      type uint64;
      description
        "Flows aged due to emergency aging";
    }
    leaf fl-age-tcp-fin {
      type uint64;
      description
        "Flows aged due to TCP FIN";
    }
    leaf fl-age-counter-wrap {
      type uint64;
      description
        "Flows aged due to counter wrap";
    }
    leaf fl-tcp-fin {
      type uint64;
      description
        "Flows exported with TCP FIN";
    }
    leaf fl-counter-wrap {
      type uint64;
      description
        "Flows exported with counter wrap";
    }
    leaf fl-exported {
      type uint64;
      description
        "Total flows given to the exporter";
    }
    leaf sflow-flow-samples {
      type uint64;
      description
        "sFlow flow samples which came in";
    }
    leaf sflow-counter-samples {
      type uint64;
      description
        "sFlow counter samples which came in";
    }
  }

  grouping NFSVR-SHOW-FLOW-CACHE-RESP-SINGLE-MONITOR-MAP {
    description
      "Response to a show cache internal cmd for a
       single monitor";
    container summary {
      description
        "Summary of the flow cache";
      uses NFSVR-SHOW-FLOW-CACHE-RESP-SUMMARY;
    }
    container internal {
      description
        "Internal info of the flow cache";
      uses NFSVR-SHOW-FLOW-CACHE-RESP-INTERNAL;
    }
  }

  grouping NFSVR-TRING-BAG {
    description
      "NFSVR TRING BAG";
    leaf exist-flag {
      type uint8;
      description
        "Flag where name exists or not";
    }
    leaf name {
      type string;
      description
        "Name of flow exporter";
    }
  }

  grouping NFSVR-SHOW-FLOW-MONITOR-BASIC {
    description
      "Basic flow monitor information";
    leaf fm-name {
      type string;
      description
        "Name of the flow monitor";
    }
    leaf frec-name {
      type string;
      description
        "Name of flow record";
    }
    leaf num-labels {
      type uint32;
      description
        "Number of labels";
    }
    leaf aging-mode {
      type uint32;
      description
        "Type of cache";
    }
    leaf num-entries {
      type uint32;
      description
        "Total number of cache entries";
    }
    leaf inactive-timeout {
      type uint32;
      description
        "Cache inactive timeout";
    }
    leaf active-timeout {
      type uint32;
      description
        "Cache active timeout";
    }
    leaf update-timeout {
      type uint32;
      description
        "Cache update timeout";
    }
    leaf rate-limit {
      type uint32;
      description
        "Cache timeout rate-limit";
    }
    leaf options {
      type uint32;
      description
        "flow monitor options";
    }
    leaf sflow-ext-router {
      type uint8;
      description
        "sFlow extended router enabled";
    }
    leaf sflow-ext-gateway {
      type uint8;
      description
        "sFlow extended gateway enabled";
    }
    leaf sflow-input-ifindex-physical {
      type uint8;
      description
        "sFlow Using input physical interface ifindex";
    }
    leaf sflow-output-ifindex-physical {
      type uint8;
      description
        "sFlow Using output physical interface ifindex";
    }
    leaf sflow-sample-header-max {
      type uint32;
      description
        "sFlow Maximum size of packet header to be
         exported";
    }
    leaf sflow-if-stats-interval {
      type uint32;
      description
        "sFlow if_stats counter sampling interval";
    }
    leaf sflow-ext-ipv4-tun-egress {
      type uint8;
      description
        "sFlow extended ipv4 tunnel egress enabled";
    }
    leaf sflow-ext-ipv6-tun-egress {
      type uint8;
      description
        "sFlow extended ipv6 tunnel egress enabled";
    }
    list fe-name {
      max-elements "8";
      description
        "Name of flow exporter";
      uses NFSVR-TRING-BAG;
    }
  }
}
