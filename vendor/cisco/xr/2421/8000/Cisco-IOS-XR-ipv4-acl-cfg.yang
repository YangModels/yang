module Cisco-IOS-XR-ipv4-acl-cfg {
  namespace "http://cisco.com/ns/yang/Cisco-IOS-XR-ipv4-acl-cfg";
  prefix ipv4-acl-cfg;

  import ietf-inet-types {
    prefix inet;
  }
  import Cisco-IOS-XR-types {
    prefix xr;
  }
  import Cisco-IOS-XR-ipv4-acl-datatypes {
    prefix dt1;
  }
  import oc-xr-mapping {
    prefix emmi;
  }
  include Cisco-IOS-XR-ipv4-ace-cfg {
    revision-date 2021-09-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-acl package configuration.
     
     This module contains definitions
     for the following management objects:
       ipv4-acl-and-prefix-list: IPv4 ACL configuration data
     
     Copyright (c) 2013-2018, 2023 by Cisco Systems, Inc.
     All rights reserved.";

  revision 2021-09-20 {
    description
      "7.6.1 revision. Adding icmp-on for ace in the schema
       2021-07-28
         7.5.1 revision. Adding additional units for policer
       2021-06-20
         7.5.1 revision. Adding icmp-off in the schema
       2021-03-17
         7.3.15 revision. Adding vrrp and rsvp keywords for protocol under access-list config CLI.";
    semver:module-version "2.1.0";
  }
  revision 2020-12-04 {
    description
      "7.4.1 revision. Fixing Remark Length
       2020-11-23
          7.3.2 revision. Changing the bag version";
    semver:module-version "2.0.0";
  }
  revision 2019-10-22 {
    description
      "7.0.1 revision. Fixing ICMP TYPE CODE datatype from Enum to RangeEnum";
    semver:module-version "1.1.1";
  }
  revision 2019-04-05 {
    description
      "Establish semantic version baseline.";
    semver:module-version "1.0.0";
  }
  revision 2018-05-08 {
    description
      "6.5.1 revision. Remove the when statement for fragments.";
  }
  revision 2018-04-03 {
    description
      "6.5.1 revision. Correct enum value for Next-hop-type.";
  }
  revision 2018-03-23 {
    description
      "6.5.1 revision. Removing none-next-type.";
  }
  revision 2018-02-01 {
    description
      "Using YANG bit types for tcp flags.";
  }
  revision 2018-01-03 {
    description
      "6.4.1 revision. Fixed a few typos in the description.";
  }
  revision 2017-10-15 {
    description
      "Removed presence statement generated from internal CLI data.";
  }
  revision 2017-06-08 {
    description
      "6.3.1 fragment-type revision.";
  }
  revision 2016-11-07 {
    description
      "6.2.1 revision.";
  }
  revision 2015-11-09 {
    description
      "IOS XR 6.0 revision.";
  }

  container ipv4-acl-and-prefix-list {
    description
      "IPv4 ACL configuration data";
    container accesses {
      description
        "Table of access lists.  Entries in this table
         and the AccessListExistenceTable table must be
         kept consistent";
      list access {
        key "access-list-name";
        description
          "An ACL";
        container access-list-entries {
          description
            "ACL entry table; contains list of ACEs";
          list access-list-entry {
            key "sequence-number";
            description
              "An ACL entry; either a description (remark)
               or an ACE to match against";
            leaf sequence-number {
              type dt1:Ipv4-acl-sequence-number-range;
              description
                "Sequence number for this entry";
              emmi:map-to {
                emmi:path "/oc-acl:acl/oc-acl:acl-sets/oc-acl:acl-set/oc-acl:acl-entries/oc-acl:acl-entry/oc-acl:sequence-id" {
                  emmi:path-attributes {
                    emmi:node-key "true";
                  }
                }
                emmi:path "/oc-acl:acl/oc-acl:acl-sets/oc-acl:acl-set/oc-acl:acl-entries/oc-acl:acl-entry/oc-acl:config/oc-acl:sequence-id";
              }
            }
            uses IPV4-ACE;
            emmi:map-to {
              emmi:path "/oc-acl:acl/oc-acl:acl-sets/oc-acl:acl-set/oc-acl:acl-entries/oc-acl:acl-entry";
              emmi:function "xr_to_oc_access_list_entry_cb" {
                emmi:category "manual_function";
              }
            }
          }
          emmi:map-to;
        }
        leaf access-list-name {
          type string;
          description
            "Access list name - 64 characters max";
          emmi:map-to {
            emmi:path "/oc-acl:acl/oc-acl:acl-sets/oc-acl:acl-set/oc-acl:name" {
              emmi:path-attributes {
                emmi:node-key "true";
              }
            }
            emmi:function "xr_to_oc_acl_ipv4_type" {
              emmi:category "manual_function";
            }
            emmi:path "/oc-acl:acl/oc-acl:acl-sets/oc-acl:acl-set/oc-acl:config/oc-acl:name";
            emmi:function "xr_to_oc_acl_ipv4_type" {
              emmi:category "manual_function";
            }
          }
        }
        emmi:map-to {
          emmi:path "/oc-acl:acl/oc-acl:acl-sets/oc-acl:acl-set";
          emmi:function "xr_to_oc_access_cb" {
            emmi:category "manual_function";
          }
        }
      }
      emmi:map-to;
    }
    container prefixes {
      description
        "Table of ACL prefix lists.  Entries in this
         table and the PrefixListExistenceTable table
         must be kept consistent";
      list prefix {
        key "prefix-list-name";
        description
          "Name of a prefix list";
        container prefix-list-entries {
          presence "Indicates a prefix-list-entries node is configured.";
          description
            "Sequence of entries forming a prefix list";
          list prefix-list-entry {
            key "sequence-number";
            description
              "A prefix list entry; either a description
               (remark) or a prefix to match against";
            leaf sequence-number {
              type dt1:Ipv4-acl-sequence-number-range;
              description
                "Sequence number of prefix list";
            }
            leaf grant {
              type dt1:Ipv4-acl-grant-enum;
              description
                "Whether to forward or drop packets matching
                 the prefix list";
            }
            leaf prefix {
              type inet:ipv4-address-no-zone;
              description
                "IPv4 address prefix to match";
            }
            leaf netmask {
              type inet:ipv4-address-no-zone;
              description
                "Mask of IPv4 address prefix";
            }
            leaf match-exact-length {
              type empty;
              description
                "Set to perform an exact prefix length match.
                 Item is mutually exclusive with minimum and
                 maximum length match items";
            }
            leaf exact-prefix-length {
              type dt1:Ipv4-acl-prefix-length-range;
              description
                "If exact prefix length matching specified,
                 set the length of prefix to be matched";
            }
            leaf match-max-length {
              type empty;
              description
                "Set to perform a maximum length prefix match
                 .  Item is mutually exclusive with exact
                 length match item";
            }
            leaf max-prefix-length {
              type dt1:Ipv4-acl-prefix-length-range;
              description
                "If maximum length prefix matching specified,
                 set the maximum length of prefix to be
                 matched";
            }
            leaf match-min-length {
              type empty;
              description
                "Set to perform a minimum length prefix match
                 .  Item is mutually exclusive with exact
                 length match item";
            }
            leaf min-prefix-length {
              type dt1:Ipv4-acl-prefix-length-range;
              description
                "If minimum length prefix matching specified,
                 set the minimum length of prefix to be
                 matched";
            }
            leaf remark {
              type string;
              description
                "Comments or a description for the prefix
                 list.  Item is mutually exclusive with all
                 others in the object";
            }
          }
        }
        leaf prefix-list-name {
          type string;
          description
            "Prefix list name - max 32 characters";
        }
      }
    }
    container log-update {
      description
        "Control access lists log updates";
      leaf threshold {
        type dt1:Ipv4-acl-log-threshold-range;
        description
          "Log update threshold (number of hits)";
      }
      leaf rate {
        type dt1:Ipv4-acl-log-rate-range;
        description
          "Log update rate (log msgs per second)";
      }
    }
    leaf icmp-off {
      type empty;
      description
        "This is set to disable the icmpoff messages";
    }
    emmi:map-to;
  }
  emmi:mapping {
    emmi:package-name "ocacl";
    emmi:model-id "xr";
    emmi:module-id "cisco_ios_xr_ipv4_acl_cfg";
    emmi:target {
      emmi:model-id "oc";
      emmi:module-id "openconfig_acl";
      emmi:namespace "oc-pkt-match-types|http://openconfig.net/yang/packet-match-types";
      emmi:namespace "if|urn:ietf:params:xml:ns:yang:ietf-interfaces";
      emmi:namespace "oc-if|http://openconfig.net/yang/interfaces";
      emmi:namespace "oc-acl|http://openconfig.net/yang/acl";
      emmi:namespace "oc-inet|http://openconfig.net/yang/types/inet";
      emmi:namespace "oc-yang|http://openconfig.net/yang/types/yang";
      emmi:namespace "oc-ext|http://openconfig.net/yang/openconfig-ext";
      emmi:namespace "yang|urn:ietf:params:xml:ns:yang:ietf-yang-types";
      emmi:namespace "oc-match|http://openconfig.net/yang/header-fields";
    }
  }
}
