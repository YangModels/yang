module Cisco-IOS-XR-um-mibs-cbqosmib-cfg {
  namespace "http://cisco.com/ns/yang/Cisco-IOS-XR-um-mibs-cbqosmib-cfg";
  prefix um-mibs-cbqosmib-cfg;

  import Cisco-IOS-XR-um-snmp-server-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mibs-cbqosmib package configuration.
     
     This YANG module augments the
     modules with configuration data.
     
     Copyright (c) 2020-2023 by Cisco Systems, Inc.
     All rights reserved.";

  revision 2023-09-21 {
    description
      "Removed the test-collisions";
  }
  revision 2022-07-11 {
    description
      "Added missing description statement to nodes";
  }
  revision 2020-12-08 {
    description
      "Initial release";
  }

  augment "/a1:snmp-server-mibs" {
    description
      "This augment extends snmp-server-mibs nodes
       configuration";
    container cbqosmib {
      description
        "Configure CBQoSMIB parameters";
      container cache {
        presence "Indicates a cache node is configured.";
        description
          "Enable CBQoSMIB stats data caching";
        container refresh {
          description
            "Cache refresh interval";
          leaf time {
            type uint32 {
              range "5..60" {
                description
                  "Refresh time in secs";
              }
            }
            description
              "Cache refresh time in seconds ";
          }
        }
        container service-policy {
          description
            "Maximum number of service policies to cache the statistics for";
          leaf count {
            type uint32 {
              range "1..5000" {
                description
                  "Number of service-policys";
              }
            }
            description
              "Number of service-policy stats";
          }
        }
      }
      container persist {
        presence "Indicates a persist node is configured.";
        description
          "Persist CBQoSMIB config, service-policy and object indices";
      }
      container member-stats {
        presence "Indicates a member-stats node is configured.";
        description
          "Enable bundle member interface statistics retrieval";
      }
    }
  }
}
