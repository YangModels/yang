submodule Cisco-IOS-XR-pfi-im-cmd-oper-sub2 {
  belongs-to Cisco-IOS-XR-pfi-im-cmd-oper {
    prefix Cisco-IOS-XR-pfi-im-cmd-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pfi-im-cmd package operational data.
     
     Copyright (c) 2013-2022 by Cisco Systems, Inc.
     All rights reserved.";

  revision 2021-08-27 {
    description
      "added new mediatype for 25GBASE_ER.";
    semver:module-version "5.0.0";
  }
  revision 2021-05-23 {
    description
      "Removed container for non-dynamic interfaces.
       2020-12-02
          added new mediatype for 25GBASE_LR.
       2020-10-08
          Unit of last-data-time in milliseconds reverted to seconds for generic stats
       2020-10-01
          64-bit Bandwidth support
       2020-09-03
          Removed event-telemetry annotation from leaf interface-name of grouping BM-MEMBER-DATA
       2020-04-14
          Unit of last-data-time changed from seconds to milliseconds for generic stats
       2020-04-14
          Support added for non-dynamic interfaces.
       2020-04-14
          Data type of last-data-time changed from uint32 to uint64 for generic and proto stats";
    semver:module-version "4.0.0";
  }
  revision 2019-12-03 {
    description
      "Updated description.";
    semver:module-version "3.0.0";
  }
  revision 2019-08-14 {
    description
      "Added last state transition time.
       2019-07-23
        Changes in IosApi version.
       2019-05-30
       64 bit bandwidth changes.";
    semver:module-version "2.0.0";
  }
  revision 2019-04-05 {
    description
      "Establish semantic version baseline.";
    semver:module-version "1.0.0";
  }
  revision 2017-06-26 {
    description
      "Change identifiers to be more readable.";
  }
  revision 2017-05-01 {
    description
      "Fixing backward compatibility error in module.";
  }
  revision 2016-12-18 {
    description
      "Description updated.";
  }
  revision 2015-11-09 {
    description
      "IOS XR 6.0 revision.";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  grouping IMDS-IFATTR-BASE-INFO {
    description
      "Basic interface information";
    leaf interface {
      type xr:Interface-name;
      description
        "Interface";
    }
    leaf parent-interface {
      type xr:Interface-name;
      description
        "Parent Interface";
    }
    leaf type {
      type string;
      description
        "Interface type";
    }
    leaf state {
      type Im-state-enum;
      description
        "Operational state";
    }
    leaf actual-state {
      type Im-state-enum;
      description
        "Operational state with no translation of error
         disable or shutdown";
    }
    leaf line-state {
      type Im-state-enum;
      description
        "Line protocol state";
    }
    leaf actual-line-state {
      type Im-state-enum;
      description
        "Line protocol state with no translation of error
         disable or shutdown";
    }
    leaf encapsulation {
      type string;
      description
        "Interface encapsulation";
    }
    leaf encapsulation-type-string {
      type string {
        length "0..32";
      }
      description
        "Interface encapsulation description string";
    }
    leaf mtu {
      type uint32;
      units "byte";
      description
        "MTU in bytes";
    }
    leaf sub-interface-mtu-overhead {
      type uint32;
      description
        "Subif MTU overhead";
    }
    leaf l2-transport {
      type boolean;
      description
        "L2 transport";
    }
    leaf bandwidth {
      type uint32;
      description
        "Interface bandwidth (Kb/s)";
    }
    leaf bandwidth64-bit {
      type uint64;
      description
        "Interface bandwidth 64-bit (Kb/s)";
    }
  }

  grouping IM-IF-GROUP-COUNTS {
    description
      "Interface counts";
    leaf interface-count {
      type uint32;
      description
        "Number of interfaces";
    }
    leaf up-interface-count {
      type uint32;
      description
        "Number of interfaces in UP state";
    }
    leaf down-interface-count {
      type uint32;
      description
        "Number of interfaces in DOWN state";
    }
    leaf admin-down-interface-count {
      type uint32;
      description
        "Number of interfaces in an ADMINDOWN state";
    }
  }

  grouping IM-IF-TYPE-SUMMARY {
    description
      "Interface type summary information";
    container interface-counts {
      description
        "Counts for interfaces of this type";
      uses IM-IF-GROUP-COUNTS;
    }
    leaf interface-type-name {
      type string;
      description
        "Name of the interface type";
    }
    leaf interface-type-description {
      type string;
      description
        "Description of the interface type";
    }
  }

  grouping IM-IF-SUMMARY-INFO {
    description
      "Interface summary bag";
    container interface-counts {
      description
        "Counts for all interfaces";
      uses IM-IF-GROUP-COUNTS;
    }
    list interface-type {
      description
        "List of per interface type summary information";
      uses IM-IF-TYPE-SUMMARY;
    }
  }
}
