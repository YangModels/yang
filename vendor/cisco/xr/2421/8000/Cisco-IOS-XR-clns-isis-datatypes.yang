module Cisco-IOS-XR-clns-isis-datatypes {
  namespace "http://cisco.com/ns/yang/Cisco-IOS-XR-clns-isis-datatypes";
  prefix clns-isis-datatypes;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2019, 2022 by Cisco Systems, Inc.
     All rights reserved.";

  revision 2019-04-05 {
    description
      "Establish semantic version baseline.";
    semver:module-version "1.0.0";
  }
  revision 2017-05-01 {
    description
      "Fixing backward compatibility error in module.";
  }
  revision 2015-11-09 {
    description
      "IOS XR 6.0 revision.";
  }

  typedef Isis-address-family {
    type enumeration {
      enum "ipv4" {
        value 0;
        description
          "IPv4";
      }
      enum "ipv6" {
        value 1;
        description
          "IPv6";
      }
    }
    description
      "Isis address family";
  }

  typedef Isis-ipv6-prefix-length {
    type uint32 {
      range "0..128";
    }
    description
      "Isis ipv6 prefix length";
  }

  typedef Isis-packet-count-direction {
    type enumeration {
      enum "sending" {
        value 1;
        description
          "Packets sent";
      }
      enum "receiving" {
        value 2;
        description
          "Packets received";
      }
    }
    description
      "Isis packet count direction";
  }

  typedef Isis-ipv4-prefix-length {
    type uint32 {
      range "0..32";
    }
    description
      "Isis ipv4 prefix length";
  }

  typedef Isis-locator-name {
    type xr:Cisco-ios-xr-string {
      length "1..60";
    }
    description
      "Isis locator name";
  }

  typedef Isis-instance-name {
    type xr:Cisco-ios-xr-string {
      length "1..36";
    }
    description
      "Isis instance name";
  }

  typedef Isis-circuit {
    type enumeration {
      enum "lanlevel1" {
        value 1;
        description
          "Lan level 1";
      }
      enum "lanlevel2" {
        value 2;
        description
          "Lan level 2";
      }
      enum "p2pcircuit" {
        value 3;
        description
          "point to point";
      }
    }
    description
      "Isis circuit";
  }

  typedef Isis-internal-level {
    type enumeration {
      enum "not-set" {
        value 0;
        description
          "Level not set";
      }
      enum "level1" {
        value 1;
        description
          "Level1";
      }
      enum "level2" {
        value 2;
        description
          "Level2";
      }
    }
    description
      "Isis internal level";
  }

  typedef Isis-link-group-name {
    type xr:Cisco-ios-xr-string {
      length "1..40";
    }
    description
      "Isis link group name";
  }

  typedef Isis-sub-address-family {
    type enumeration {
      enum "unicast" {
        value 0;
        description
          "Unicast";
      }
      enum "multicast" {
        value 1;
        description
          "Multicast";
      }
    }
    description
      "Isis sub address family";
  }

  typedef Isis-topology-name {
    type xr:Cisco-ios-xr-string {
      length "1..32";
    }
    description
      "Isis topology name";
  }
}
