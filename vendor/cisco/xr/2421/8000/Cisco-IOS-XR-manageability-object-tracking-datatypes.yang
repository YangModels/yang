module Cisco-IOS-XR-manageability-object-tracking-datatypes {
  namespace "http://cisco.com/ns/yang/Cisco-IOS-XR-manageability-object-tracking-datatypes";
  prefix manageability-object-tracking-datatypes;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2017 by Cisco Systems, Inc.
     All rights reserved.";

  revision 2017-05-01 {
    description
      "Fixing backward compatibility error in module.";
  }
  revision 2015-11-09 {
    description
      "IOS XR 6.0 revision.";
  }

  typedef Object-tracking-boolean-sign {
    type enumeration {
      enum "without-not" {
        value 0;
        description
          "Object without not";
      }
      enum "with-not" {
        value 1;
        description
          "Object with not";
      }
    }
    description
      "Object tracking boolean sign";
  }

  typedef Object-tracking-name-string {
    type xr:Cisco-ios-xr-string {
      length "1..32";
    }
    description
      "Object tracking name string";
  }

  typedef Object-tracking-delay {
    type uint32 {
      range "1..10";
    }
    description
      "Object tracking delay";
  }
}
