submodule Cisco-IOS-XR-segment-routing-ms-oper-sub2 {
  belongs-to Cisco-IOS-XR-segment-routing-ms-oper {
    prefix Cisco-IOS-XR-segment-routing-ms-oper;
  }

  import ietf-inet-types {
    prefix inet;
  }
  import cisco-semver {
    prefix semver;
  }
  include Cisco-IOS-XR-segment-routing-ms-oper-sub3 {
    revision-date 2019-07-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR segment-routing-ms package operational data.
     
     Copyright (c) 2013-2019, 2022 by Cisco Systems, Inc.
     All rights reserved.";

  revision 2019-07-19 {
    description
      "Additional items added to operational model.";
    semver:module-version "2.0.0";
  }
  revision 2019-04-05 {
    description
      "Establish semantic version baseline.";
    semver:module-version "1.0.0";
  }
  revision 2017-09-07 {
    description
      "Fixed type translation error.";
  }
  revision 2015-11-09 {
    description
      "IOS XR 6.0 revision.";
  }

  typedef Srms-af {
    type enumeration {
      enum "none" {
        value 0;
        description
          "None";
      }
      enum "ipv4" {
        value 1;
        description
          "IPv4";
      }
      enum "ipv6" {
        value 2;
        description
          "IPv6";
      }
    }
    description
      "Srms af";
  }

  grouping ADDR1 {
    description
      "ADDR1";
    leaf af {
      type Srms-af;
      description
        "AF";
    }
    leaf ipv4 {
      when "../af = 'ipv4'" {
        description
          "../AF = 'IPv4'";
      }
      type inet:ipv4-address;
      description
        "IPv4";
    }
    leaf ipv6 {
      when "../af = 'ipv6'" {
        description
          "../AF = 'IPv6'";
      }
      type In6-addr-t-b;
      description
        "IPv6";
    }
  }

  grouping SRMS-L2-ADJ-T-B {
    description
      "SRMA show bag";
    container nexthop-address {
      description
        "Nexthop address";
      uses ADDR1;
    }
    leaf interface-name {
      type string {
        length "0..64";
      }
      description
        "Interface name";
    }
    leaf sid-value-xr {
      type uint32;
      description
        "SID Value";
    }
    leaf sid-type-xr {
      type uint32;
      description
        "SID type";
    }
    leaf address-family {
      type uint32;
      description
        "Interface address family";
    }
    leaf has-nexthop {
      type boolean;
      description
        "Has nexthop";
    }
    leaf interface-count {
      type int32;
      description
        "Interface count";
    }
    leaf interface-delete-count {
      type int32;
      description
        "Interface delete count";
    }
  }
}
