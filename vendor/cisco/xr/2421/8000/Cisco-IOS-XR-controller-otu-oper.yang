module Cisco-IOS-XR-controller-otu-oper {
  namespace "http://cisco.com/ns/yang/Cisco-IOS-XR-controller-otu-oper";
  prefix controller-otu-oper;

  import Cisco-IOS-XR-types {
    prefix xr;
  }
  import cisco-semver {
    prefix semver;
  }
  import oc-xr-mapping {
    prefix emmi;
  }
  include Cisco-IOS-XR-controller-otu-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-otu package operational data.
     
     This module contains definitions
     for the following management objects:
       otu: OTU operational data
     
     Copyright (c) 2013-2019 by Cisco Systems, Inc.
     All rights reserved.";

  revision 2019-04-05 {
    description
      "Establish semantic version baseline.";
    semver:module-version "1.0.0";
  }
  revision 2017-05-01 {
    description
      "Fixing backward compatibility error in module.";
  }
  revision 2017-03-13 {
    description
      "PRBS Info added";
  }
  revision 2015-11-09 {
    description
      "IOS XR 6.0 revision.";
  }

  container otu {
    config false;
    description
      "OTU operational data";
    container controllers {
      description
        "All OTU Port operational data";
      list controller {
        key "controller-name";
        description
          "OTU Port operational data";
        container prbs {
          description
            "OTU port PRBS operational data";
          uses OTU-PRBS-INFO;
        }
        container info {
          description
            "OTU port operational data";
          uses OTU-PER-PORT-INFO;
          emmi:map-to;
        }
        leaf controller-name {
          type xr:Interface-name;
          description
            "Port name";
        }
        emmi:map-to;
      }
      emmi:map-to;
    }
    emmi:map-to;
  }
  emmi:mapping {
    emmi:package-name "oc_optical";
    emmi:model-id "xr";
    emmi:module-id "cisco_ios_xr_controller_otu_oper";
    emmi:target {
      emmi:model-id "oc";
      emmi:module-id "openconfig_platform";
      emmi:namespace "oc-opt-types|http://openconfig.net/yang/transport-types";
      emmi:namespace "oc-platform-psu|http://openconfig.net/yang/platform/psu";
      emmi:namespace "oc-platform-types|http://openconfig.net/yang/platform-types";
      emmi:namespace "oc-transceiver|http://openconfig.net/yang/platform/transceiver";
      emmi:namespace "if|urn:ietf:params:xml:ns:yang:ietf-interfaces";
      emmi:namespace "oc-platform|http://openconfig.net/yang/platform";
      emmi:namespace "oc-opt-term|http://openconfig.net/yang/terminal-device";
      emmi:namespace "oc-types|http://openconfig.net/yang/openconfig-types";
      emmi:namespace "oc-lldp|http://openconfig.net/yang/lldp";
      emmi:namespace "oc-yang|http://openconfig.net/yang/types/yang";
      emmi:namespace "oc-linecard|http://openconfig.net/yang/platform/linecard";
      emmi:namespace "ianaift|urn:ietf:params:xml:ns:yang:iana-if-type";
      emmi:namespace "oc-lldp-types|http://openconfig.net/yang/lldp/types";
      emmi:namespace "oc-ext|http://openconfig.net/yang/openconfig-ext";
      emmi:namespace "yang|urn:ietf:params:xml:ns:yang:ietf-yang-types";
      emmi:namespace "oc-alarm-types|http://openconfig.net/yang/alarms/types";
      emmi:namespace "oc-eth|http://openconfig.net/yang/interfaces/ethernet";
      emmi:namespace "oc-if|http://openconfig.net/yang/interfaces";
      emmi:namespace "oc-port|http://openconfig.net/yang/platform/port";
      emmi:namespace "oc-opt-types|http://openconfig.net/yang/transport-types";
      emmi:namespace "oc-platform-types|http://openconfig.net/yang/platform-types";
      emmi:namespace "oc-transceiver|http://openconfig.net/yang/platform/transceiver";
      emmi:namespace "if|urn:ietf:params:xml:ns:yang:ietf-interfaces";
      emmi:namespace "oc-platform|http://openconfig.net/yang/platform";
      emmi:namespace "oc-opt-term|http://openconfig.net/yang/terminal-device";
      emmi:namespace "oc-types|http://openconfig.net/yang/openconfig-types";
      emmi:namespace "oc-lldp|http://openconfig.net/yang/lldp";
      emmi:namespace "oc-yang|http://openconfig.net/yang/types/yang";
      emmi:namespace "ianaift|urn:ietf:params:xml:ns:yang:iana-if-type";
      emmi:namespace "oc-lldp-types|http://openconfig.net/yang/lldp/types";
      emmi:namespace "oc-ext|http://openconfig.net/yang/openconfig-ext";
      emmi:namespace "yang|urn:ietf:params:xml:ns:yang:ietf-yang-types";
      emmi:namespace "oc-alarm-types|http://openconfig.net/yang/alarms/types";
      emmi:namespace "oc-eth|http://openconfig.net/yang/interfaces/ethernet";
      emmi:namespace "oc-if|http://openconfig.net/yang/interfaces";
      emmi:namespace "oc-port|http://openconfig.net/yang/platform/port";
    }
  }
}
