submodule Cisco-IOS-XR-infra-xtc-oper-sub1 {
  belongs-to Cisco-IOS-XR-infra-xtc-oper {
    prefix Cisco-IOS-XR-infra-xtc-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-xtc package operational data.
     
     Copyright (c) 2013-2022 by Cisco Systems, Inc.
     All rights reserved.";

  revision 2022-01-06 {
    description
      "Added SID algorithm constraint for LSP.";
  }
  revision 2021-05-26 {
    description
      "Added per prefix SID IGP information and fixed
       issues found by YANG validation.";
  }
  revision 2021-05-04 {
    description
      "Added FlexAlgo ASLA TE metric for v4 and v6 links.";
  }
  revision 2021-03-15 {
    description
      "Added Treesid related fields.";
  }
  revision 2021-03-04 {
    description
      "Added MSD list per topology link. Added SRLB list per topology node.
       2020-09-16
         Adding operational nodes for new features path invalidation drop protected and unprotected path Operational nodes for PCE segment-routing traffic-eng policy
       2020-09-01
         Added uB6SID field in the LSP object
       2020-08-18
         Added SRv6 LSP details fields in the LSP object
       2020-07-13
         Added NodeID fields in the uN SID object in the IPv6 topology.
       2020-04-20
         Added fields in the PCE IPv6 link object.";
  }
  revision 2021-03-01 {
    description
      "Added Flex Algo Prefix SID in SID enum.
       Removed Adj SID from SID enum - Not used & also makes
       value for Flex Algo Prefix SID consistent across yang
       files
       Added enum Cmn-metric-type & metric-type leaf.
       Added PCE-FA-DEFINTION group
       Added PCE-SR-FLEX-ALGO-BAG group
       Added SR Flex Algo list under NODE PID bag";
  }
  revision 2021-01-24 {
    description
      "Added ASLA admin group field in IPv4 & IPv6 links,
       modified SRv6 Endpoint function to Enum AND
       added performance-metrics field under IPv6 link.";
  }
  revision 2021-01-22 {
    description
      "Added an enum in PCE SR SID for IPv6 Link Local adjacency.
       Added local & remote interface index in PCE Hop type";
  }
  revision 2021-01-20 {
    description
      "Added X flag to Prefix SID";
  }
  revision 2021-01-15 {
    description
      "Fixed broken syntax and missing revision information";
  }
  revision 2020-07-13 {
    description
      "Added SRv6 Topology Information";
  }
  revision 2020-05-08 {
    description
      "Added Extended tunnel ID container and loose leaf";
  }
  revision 2019-04-17 {
    description
      "Added preference and interface-name";
  }
  revision 2017-09-07 {
    description
      "Fixed type translation error.";
  }
  revision 2017-08-24 {
    description
      "Added C flag to pcep flags.";
  }
  revision 2017-06-26 {
    description
      "Change identifiers to be more readable.";
  }
  revision 2017-05-01 {
    description
      "Fixing backward compatibility error in module.";
  }
  revision 2016-05-31 {
    description
      "Revision description string.";
  }
  revision 2015-11-09 {
    description
      "IOS XR 6.0 revision.";
  }

  typedef Pce-headend-swap {
    type enumeration {
      enum "pcehs-none" {
        description
          "Headends not swapped";
      }
      enum "pcehs-plain" {
        description
          "Headends swapped";
      }
      enum "pcehs-rwi" {
        description
          "Headends swapped with increment";
      }
    }
    description
      "PCE Headends Swap Code";
  }

  typedef Pce-treesid-initiate-type {
    type enumeration {
      enum "pcc-initiated" {
        description
          "Initiated by PCC";
      }
      enum "pce-initiated-cfg" {
        description
          "Initiated by PCE CFG ";
      }
      enum "pce-initiated-nba" {
        description
          "Initiated via NB API";
      }
    }
    description
      "Pce treesid initiator";
  }

  typedef Pce-treesid-state {
    type enumeration {
      enum "none" {
        description
          "No state";
      }
      enum "programming" {
        description
          "Programming non-root nodes";
      }
      enum "programming-root" {
        description
          "Programming the root node";
      }
      enum "pruning" {
        description
          "Pruning stale legs on non-root nodes";
      }
      enum "pruning-root" {
        description
          "Pruning stale legs on root node";
      }
      enum "deleting" {
        description
          "TreeSID is being deleted";
      }
    }
    description
      "Pce treesid state";
  }

  typedef Pce-treesid-role {
    type enumeration {
      enum "none" {
        description
          "No role";
      }
      enum "ingress" {
        description
          "Ingress";
      }
      enum "transit" {
        description
          "Transit";
      }
      enum "egress" {
        description
          "Egress";
      }
      enum "bud-node" {
        description
          "Bud Node";
      }
    }
    description
      "Pce treesid role";
  }

  typedef Pce-cspf-rc {
    type enumeration {
      enum "pce-cspf-not-set" {
        description
          "Not set";
      }
      enum "pce-cspf-src-not-found" {
        description
          "Source not found";
      }
      enum "pce-cspf-dst-not-found" {
        description
          "Destination not found";
      }
      enum "pce-cspf-second-src-not-found" {
        description
          "Second source not found";
      }
      enum "pce-cspf-second-dst-not-found" {
        description
          "Second destination not found";
      }
      enum "pce-cspf-no-mem" {
        description
          "No memory";
      }
      enum "pce-cspf-ex-path-not-resolved" {
        description
          "Second path not resolved";
      }
      enum "pce-cspf-no-path" {
        description
          "No path";
      }
      enum "pce-cspf-sp-success" {
        description
          "Shortest path success";
      }
      enum "pce-cspf-error" {
        description
          "Error";
      }
      enum "pce-cspf-fallback-srlg-node-node" {
        description
          "Fallback from SRLG-NODE to NODE";
      }
      enum "pce-cspf-fallback-srlg-node-link" {
        description
          "Fallback from SRLG-NODE to LINK";
      }
      enum "pce-cspf-fallback-srlg-node-sp" {
        description
          "Fallback from SRLG-NODE to SP";
      }
      enum "pce-cspf-fallback-node-link" {
        description
          "Fallback from NODE to LINK";
      }
      enum "pce-cspf-fallback-link-sp" {
        description
          "Fallback from LINK to SP";
      }
      enum "pce-cspf-fallback-node-sp" {
        description
          "Fallback from NODE to SP";
      }
      enum "pce-cspf-fallback-srlg-link" {
        description
          "Fallback from SRLG to LINK";
      }
      enum "pce-cspf-fallback-srlg-sp" {
        description
          "Fallback from SRLG to SP";
      }
      enum "pce-cspf-dp-success" {
        description
          "Disjoint path success";
      }
    }
    description
      "PCE CSPF Result Code";
  }

  typedef Topo-msd-subtype {
    type enumeration {
      enum "msd-type-mpls" {
        value 1;
        description
          "Base MPLS Imposition MSD";
      }
      enum "msd-type-erld" {
        value 2;
        description
          "ERLD MSD";
      }
      enum "msd-type-srh-max-sl" {
        value 41;
        description
          "SRH Max SL";
      }
      enum "msd-type-srh-max-end-pop" {
        value 42;
        description
          "SRH Max End Pop";
      }
      enum "msd-type-srh-max-h-encaps" {
        value 44;
        description
          "SRH Max H.encaps";
      }
      enum "msd-type-srh-max-end-d" {
        value 45;
        description
          "SRH Max End D";
      }
      enum "msd-type-unknown" {
        value 255;
        description
          "Unknown";
      }
    }
    description
      "Topo msd subtype";
  }

  typedef Sid {
    type enumeration {
      enum "sr-protected-adj-sid" {
        value 1;
        description
          "Protected Adjacency SID";
      }
      enum "sr-unprotected-adj-sid" {
        value 2;
        description
          "Unprotected Adjacency SID";
      }
      enum "srbgp-egress-peer-engineering-sid" {
        value 3;
        description
          "BGP egress peer engineering SID";
      }
      enum "sr-reqular-prefix-sid" {
        value 4;
        description
          "Regular prefix SID";
      }
      enum "sr-strict-prefix-sid" {
        value 5;
        description
          "Strict prefix SID";
      }
      enum "sr-flex-algo-prefix-sid" {
        value 6;
        description
          "Flex-algo prefix SID";
      }
    }
    description
      "SID Types";
  }

  typedef Cmn-metric-type {
    type enumeration {
      enum "metric-type-none" {
        value 0;
        description
          "Metric Type None";
      }
      enum "metric-type-igp" {
        value 1;
        description
          "Metric Type IGP";
      }
      enum "metric-type-te" {
        value 2;
        description
          "Metric Type TE";
      }
      enum "metric-type-hop-count" {
        value 3;
        description
          "Metric Type hop count";
      }
      enum "metric-type-msd" {
        value 11;
        description
          "Metric Type MSD";
      }
      enum "metric-type-latency" {
        value 12;
        description
          "Metric Type latency";
      }
    }
    description
      "PCE Metric Type";
  }

  typedef Pce-igp-info-id {
    type enumeration {
      enum "isis" {
        value 1;
        description
          "ISIS";
      }
      enum "ospf" {
        value 2;
        description
          "OSPF";
      }
      enum "bgp" {
        value 3;
        description
          "BGP";
      }
    }
    description
      "IGP IDs";
  }

  typedef Pcep-state {
    type enumeration {
      enum "tcp-close" {
        description
          "TCP close";
      }
      enum "tcp-listen" {
        description
          "TCP listen";
      }
      enum "tcp-connect" {
        description
          "TCP connect";
      }
      enum "pcep-closed" {
        description
          "PCEP closed";
      }
      enum "pcep-opening" {
        description
          "PCEP opening";
      }
      enum "pcep-open" {
        description
          "PCEP open";
      }
    }
    description
      "PCEP State";
  }

  typedef Pce-proto {
    type enumeration {
      enum "pcep" {
        description
          "PCE protocol";
      }
      enum "netconf" {
        description
          "Netconf protocol";
      }
    }
    description
      "PCE peer protocol";
  }

  typedef Pce-rro {
    type enumeration {
      enum "rro-type-ipv4-address" {
        description
          "IPv4 Address";
      }
      enum "rro-type-mpls-label" {
        description
          "MPLS Label";
      }
      enum "rro-type-sripv4-node-sid" {
        description
          "Segment Routing IPv4 Node SID";
      }
      enum "rro-type-sripv4-adjacency-sid" {
        description
          "Segment Routing IPv4 Adjacency SID";
      }
      enum "rro-type-sr-nai-null" {
        description
          "Segment Routing with NAI null";
      }
    }
    description
      "PCE RRO type";
  }

  typedef Pce-sr-sid {
    type enumeration {
      enum "ipv4-node-sid" {
        description
          "IPv4 Node SID";
      }
      enum "ipv4-adjacency-sid" {
        description
          "IPv4 Adjacency SID";
      }
      enum "ipv6-node-sid" {
        description
          "IPv6 Node SID";
      }
      enum "ipv6-adjacency-sid" {
        description
          "IPv6 Adjacency SID";
      }
      enum "ipv6-link-local-adjacency-sid" {
        description
          "IPv6 Link Local Adjacency SID";
      }
      enum "unknown-sid" {
        description
          "Unknown SID";
      }
    }
    description
      "PCE SR SID type";
  }

  typedef Lsp-state {
    type enumeration {
      enum "lsp-down" {
        description
          "LSP is down";
      }
      enum "lsp-up" {
        description
          "LSP is up";
      }
    }
    description
      "LSP setup type";
  }

  typedef Pcep-lsp-state {
    type enumeration {
      enum "lsp-down" {
        description
          "LSP is down";
      }
      enum "lsp-up" {
        description
          "LSP is up";
      }
      enum "lsp-active" {
        description
          "LSP is active (carrying traffic)";
      }
      enum "lsp-going-down" {
        description
          "LSP is going down";
      }
      enum "lsp-being-signaled" {
        description
          "LSP is being signaled";
      }
    }
    description
      "PCEP operation protocol";
  }

  typedef Lsp-setup {
    type enumeration {
      enum "setup-rsvp" {
        description
          "LSP is established using RSVP-TE";
      }
      enum "setup-sr" {
        description
          "LSP is established using SR-TE";
      }
      enum "setup-unknown" {
        description
          "Unknown LSP establishment method";
      }
    }
    description
      "LSP setup type";
  }

  typedef Pce-ipv6-address {
    type inet:ipv6-address;
    description
      "Pce ipv6 address";
  }

  typedef Pce-ipv4-address {
    type inet:ipv4-address;
    description
      "Pce ipv4 address";
  }

  typedef Pce-af-id {
    type enumeration {
      enum "none" {
        value 0;
        description
          "None";
      }
      enum "ipv4" {
        value 1;
        description
          "IPv4";
      }
      enum "ipv6" {
        value 2;
        description
          "IPv6";
      }
    }
    description
      "Pce af id";
  }

  typedef Mgmt-srv6-endpoint {
    type enumeration {
      enum "unknown" {
        description
          "Unknown Endpoint type";
      }
      enum "end" {
        description
          "End (no PSP/USP)";
      }
      enum "end-with-psp" {
        description
          "End with PSP";
      }
      enum "end-with-usp" {
        description
          "End with USP";
      }
      enum "end-with-psp-usp" {
        description
          "End with PSP/USP";
      }
      enum "end-x" {
        description
          "End.X (no PSP/USP)";
      }
      enum "end-x-with-psp" {
        description
          "End.X with PSP";
      }
      enum "end-x-with-usp" {
        description
          "End.X with USP";
      }
      enum "end-x-with-psp-usp" {
        description
          "End.X with PSP/USP";
      }
      enum "end-tbl" {
        description
          "End.T (no PSP/USP)";
      }
      enum "end-tbl-with-psp" {
        description
          "End.T with PSP";
      }
      enum "end-tbl-with-usp" {
        description
          "End.T with USP";
      }
      enum "end-tbl-with-psp-usp" {
        description
          "End.T with PSP/USP";
      }
      enum "end-b6-insert" {
        description
          "End.B6.Insert";
      }
      enum "end-b6-encaps" {
        description
          "End.B6.Encaps";
      }
      enum "end-bm" {
        description
          "End.BM";
      }
      enum "end-dx6" {
        description
          "End.DX6";
      }
      enum "end-dx4" {
        description
          "End.DX4";
      }
      enum "end-dt6" {
        description
          "End.DT6";
      }
      enum "end-dt4" {
        description
          "End.DT4";
      }
      enum "end-dt46" {
        description
          "End.DT46";
      }
      enum "end-dx2" {
        description
          "End.DX2";
      }
      enum "end-dx2v" {
        description
          "End.DX2V";
      }
      enum "end-dt2u" {
        description
          "End.DT2U";
      }
      enum "end-dt2m" {
        description
          "End.DT2M";
      }
      enum "end-s" {
        description
          "End.S";
      }
      enum "end-b6-insert-red" {
        description
          "End.B6.Insert.Reduced";
      }
      enum "end-b6-encaps-red" {
        description
          "End.B6.Encaps.Reduced";
      }
      enum "end-with-usd" {
        description
          "End with USD";
      }
      enum "end-with-psp-usd" {
        description
          "End with PSP/USD";
      }
      enum "end-with-usp-usd" {
        description
          "End with USP/USD";
      }
      enum "end-with-psp-usp-usd" {
        description
          "End with PSP/USP/USD";
      }
      enum "end-x-with-usd" {
        description
          "End.X with USD";
      }
      enum "end-x-with-psp-usd" {
        description
          "End.X with PSP/USD";
      }
      enum "end-x-with-usp-usd" {
        description
          "End.X with USP/USD";
      }
      enum "end-x-with-psp-usp-usd" {
        description
          "End.X with PSP/USP/USD";
      }
      enum "end-tbl-with-usd" {
        description
          "End.T with USD";
      }
      enum "end-tbl-with-psp-usd" {
        description
          "End.T with PSP/USD";
      }
      enum "end-tbl-with-usp-usd" {
        description
          "End.T with USP/USD";
      }
      enum "end-tbl-with-psp-usp-usd" {
        description
          "End.T with PSP/USP/USD";
      }
      enum "end-op" {
        description
          "End.OP";
      }
      enum "end-otp" {
        description
          "End.OTP";
      }
      enum "un-shift-only" {
        description
          "uN Shift-only";
      }
      enum "un" {
        description
          "uN";
      }
      enum "un-psp" {
        description
          "uN with PSP";
      }
      enum "un-usp" {
        description
          "uN with USP";
      }
      enum "un-psp-usp" {
        description
          "uN with PSP-USP";
      }
      enum "un-usd" {
        description
          "uN with USD";
      }
      enum "un-psp-usd" {
        description
          "uN with PSP-USD";
      }
      enum "un-usp-usd" {
        description
          "uN with USP-USD";
      }
      enum "un-psp-usp-usd" {
        description
          "uN with PSP_USP-USD";
      }
      enum "ua-shift-only" {
        description
          "uA Shift-only";
      }
      enum "ua" {
        description
          "uA";
      }
      enum "ua-psp" {
        description
          "uA with PSP";
      }
      enum "ua-usp" {
        description
          "uA with USP";
      }
      enum "ua-psp-usp" {
        description
          "uA with PSP-USP";
      }
      enum "ua-usd" {
        description
          "uA with USD";
      }
      enum "ua-psp-usd" {
        description
          "uA with PSP-USD";
      }
      enum "ua-usp-usd" {
        description
          "uA with USP-USD";
      }
      enum "ua-psp-usp-usd" {
        description
          "uA with PSP_USP-USD";
      }
      enum "udx6" {
        description
          "uDX6";
      }
      enum "udx4" {
        description
          "uDX4";
      }
      enum "udt6" {
        description
          "uDT6";
      }
      enum "udt4" {
        description
          "uDT4";
      }
      enum "udt46" {
        description
          "uDT46";
      }
      enum "udx2" {
        description
          "uDX2";
      }
      enum "udx2v" {
        description
          "uDX2V";
      }
      enum "udt2u" {
        description
          "uDT2U";
      }
      enum "udt2m" {
        description
          "uDT2M";
      }
      enum "ub6-insert" {
        description
          "uB6 Insert";
      }
      enum "ub6-encaps" {
        description
          "uB6 Encaps";
      }
      enum "ub6-insert-red" {
        description
          "uB6 Insert.Red";
      }
      enum "ub6-encaps-red" {
        description
          "uB6 Encaps.Red";
      }
      enum "ubm" {
        description
          "uBM";
      }
    }
    description
      "SRv6 Endpoint Behavior Type";
  }

  typedef Pce-resource-value-type {
    type enumeration {
      enum "resource-value-type-ipv4-address" {
        description
          "Resource identified by an IPv4 address";
      }
      enum "resource-value-type-ipv6-address" {
        description
          "Resource identified by an IPv6 address";
      }
      enum "resource-value-type-srlg" {
        description
          "Resource identified by SRLG";
      }
    }
    description
      "PCE resource value type";
  }

  typedef Pce-resource-type {
    type enumeration {
      enum "resource-type-interface" {
        description
          "Resource is an interface";
      }
      enum "resource-type-interface" {
        description
          "Resource is a node";
      }
      enum "resource-type-srlg" {
        description
          "Resource is an SRLG";
      }
    }
    description
      "PCE resource type";
  }

  grouping PCE-PATH-LIST-BAG {
    description
      "PCE path list";
    leaf headends-swapped {
      type Pce-headend-swap;
      description
        "Headends swapped";
    }
    leaf cspf-result {
      type Pce-cspf-rc;
      description
        "CSPF Result";
    }
    leaf iterations-done {
      type uint32;
      description
        "Iterations of the Suurballe-Tarjan algorithm";
    }
    list output-path {
      description
        "Output PCE paths";
      uses PCE-PATH-BAG;
    }
  }

  grouping PCE-ADDR-BAG {
    description
      "PCE Address Information";
    leaf address-family {
      type uint8;
      description
        "Address Family";
    }
    leaf ipv4-prefix {
      type inet:ipv4-address;
      description
        "IPv4 prefix";
    }
    leaf ipv6-prefix {
      type inet:ipv6-address;
      description
        "IPv6 prefix";
    }
  }

  grouping PCE-PATH-BAG {
    description
      "PCE path information";
    container source-xr {
      description
        "Source of path";
      uses PCE-IP-ADDR-TYPE;
    }
    container destination-xr {
      description
        "Destination of path";
      uses PCE-IP-ADDR-TYPE;
    }
    leaf cost {
      type uint64;
      description
        "Cost";
    }
    list hops {
      description
        "Hop addresses";
      uses PCE-ADDR-BAG;
    }
  }

  grouping PCE-ASSO-LSP-INFO {
    description
      "Association LSP common information";
    container pcc-address {
      description
        "PCC address";
      uses PCE-IP-ADDR-TYPE;
    }
    leaf tunnel-id {
      type uint32;
      description
        "Tunnel ID";
    }
    leaf lspid {
      type uint32;
      description
        "LSP ID";
    }
    leaf tunnel-name {
      type string;
      description
        "Tunnel Name";
    }
    leaf pce-based {
      type boolean;
      description
        "PCE Based";
    }
    leaf plsp-id {
      type uint32;
      description
        "PLSP ID";
    }
  }

  grouping PCE-ASSO-BAG {
    description
      "PCE Association information";
    container association-source {
      description
        "Association Source";
      uses PCE-IP-ADDR-TYPE;
    }
    leaf association-type {
      type uint32;
      description
        "Association Type";
    }
    leaf association-id {
      type uint32;
      description
        "Association ID";
    }
    leaf strict {
      type boolean;
      description
        "Association Strict Mode";
    }
    leaf status {
      type uint32;
      description
        "Association Status";
    }
    leaf headends-swapped {
      type uint32;
      description
        "Headends Swapped";
    }
    list association-lsp {
      description
        "Association LSP Info";
      uses PCE-ASSO-LSP-INFO;
    }
  }

  grouping PCE-PEER-PROTO-SUMMARY-BAG {
    description
      "Peer summary for specified protocol";
    leaf peer-count-up {
      type uint32;
      description
        "Number of peers in up state";
    }
    leaf peer-count-down {
      type uint32;
      description
        "Number of peers in down state";
    }
    leaf peer-count-all {
      type uint32;
      description
        "Number of all peers";
    }
  }

  grouping PCE-PEER-SUMMARY-BAG {
    description
      "Peer summary information";
    container pcep-peers {
      description
        "PCEP peers summary information";
      uses PCE-PEER-PROTO-SUMMARY-BAG;
    }
  }

  grouping PCE-SR-MPLS-PATH-BAG {
    description
      "PCE SR path information";
    container source {
      description
        "Source of path";
      uses PCE-IP-ADDR-TYPE;
    }
    container destination {
      description
        "Destination of path";
      uses PCE-IP-ADDR-TYPE;
    }
    leaf cost {
      type uint64;
      description
        "Cost";
    }
    list hops {
      description
        "SR hops";
      uses PCE-SR-HOP-TYPE;
    }
  }

  grouping PCE-TREESID-HOP-BAG {
    description
      "TreeSID hop information";
    leaf local-hop-address {
      type inet:ipv4-address;
      description
        "Next hop local address";
    }
    leaf next-hop-address {
      type inet:ipv4-address;
      description
        "Next hop remote address";
    }
    leaf next-hop-label {
      type uint32;
      description
        "Next hop outgoing label";
    }
    leaf next-hop-node-address {
      type inet:ipv4-address;
      description
        "Next hop node address";
    }
    leaf stale {
      type boolean;
      description
        "Stale hop; will be removed in next update";
    }
    leaf fast-reroute {
      type boolean;
      description
        "Fast Re-route to hop remote node";
    }
  }

  grouping PCE-TREESID-NODE-BAG {
    description
      "TreeSID node information";
    leaf prefix-address {
      type inet:ipv4-address;
      description
        "Node prefix address";
    }
    leaf role {
      type Pce-treesid-role;
      description
        "Node role";
    }
    leaf awaiting-report {
      type boolean;
      description
        "Awaiting report";
    }
    leaf stale {
      type boolean;
      description
        "Stale node";
    }
    leaf delegated-by-pcc {
      type boolean;
      description
        "Delegation by PCC";
    }
    leaf delegated-by-pce {
      type boolean;
      description
        "Delegation by PCE";
    }
    leaf delegated-pce-address {
      type inet:ipv4-address;
      description
        "Delegated PCE address";
    }
    list next-hop {
      description
        "Next hops";
      uses PCE-TREESID-HOP-BAG;
    }
  }

  grouping PCE-TREESID-BAG {
    description
      "TreeSID information";
    container attribute-info {
      description
        "TreeSID attributes";
      uses PCE-LSPA-INFO;
    }
    leaf metric-type {
      type Cmn-metric-type;
      description
        "Metric type of the TreeSID";
    }
    leaf error {
      type string;
      description
        "Last path computation error";
    }
    leaf label {
      type uint32;
      description
        "SID of the TreeSID";
    }
    leaf source-address {
      type inet:ipv4-address;
      description
        "Address of the source node";
    }
    leaf pcc-address {
      type inet:ipv4-address;
      description
        "PCC Address of the source node";
    }
    leaf operational-state {
      type boolean;
      description
        "Operational state: It is True when Tree is operationally UP
         and False if it is DOWN";
    }
    leaf administrative-state {
      type boolean;
      description
        "Administrative state: It is True when Tree is
         administratively UP and False if it is DOWN";
    }
    leaf teardown-state {
      type boolean;
      description
        "Tear Down state: True if report is sent after teardown
         due to the tree stuck in an intermediate state for too long;
         False otherwise";
    }
    leaf state_held {
      type boolean;
      description
        "Stuck in programming states: True if a Tree does not complete
         programming and stuck in intermediate state for a specific
         amount of time; False otherwise";
    }
    leaf frr-protected {
      type boolean;
      description
        "FRR Protection enabled?";
    }
    leaf initiator-entity {
      type Pce-treesid-initiate-type;
      description
        "Who Initiated the TreeSID Policy";
    }
    leaf state {
      type Pce-treesid-state;
      description
        "State of the TreeSID (ie, pending operation)";
    }
    leaf transition-count {
      type uint32;
      description
        "Number of transitions between operational
         up/down";
    }
    leaf tree-id-xr {
      type uint32;
      description
        "TreeSID Tree-ID";
    }
    leaf compute-role {
      type boolean;
      description
        "Compute PCE role";
    }
    leaf-list destination-address {
      type inet:ipv4-address;
      description
        "List of destination addresses";
    }
    list nodes {
      description
        "List of nodes associated with this TreeSID";
      uses PCE-TREESID-NODE-BAG;
    }
  }

  grouping PCE-SR-MPLS-PATH-LIST-BAG {
    description
      "PCE SR MPLS path list";
    leaf cspf-result {
      type Pce-cspf-rc;
      description
        "Result of the computation";
    }
    leaf iterations-done {
      type uint32;
      description
        "Iterations performed of the Suurballe-Tarjan
         algorithm";
    }
    list output-path {
      description
        "Output SR MPLS paths";
      uses PCE-SR-MPLS-PATH-BAG;
    }
  }

  grouping PCE-PFX-ENTRY {
    description
      "PCE prefix etnry";
    container ip {
      description
        "Prefix IP address";
      uses PCE-IP-ADDR-TYPE;
    }
  }

  grouping PCE-PFX-BAG {
    description
      "PCE Prefix Information";
    container node-protocol-identifier {
      description
        "Node protocol identifier";
      uses PCE-NODE-PID-BAG;
    }
    leaf node-identifier-xr {
      type uint32;
      description
        "Node identifier";
    }
    list address {
      description
        "Prefix address";
      uses PCE-PFX-ENTRY;
    }
  }

  grouping PCE-TOPO-STATS-BAG {
    description
      "Statistics on topology update";
    leaf num-nodes-added {
      type uint32;
      description
        "Number of nodes added";
    }
    leaf num-nodes-deleted {
      type uint32;
      description
        "Number of nodes deleted";
    }
    leaf num-links-added {
      type uint32;
      description
        "Number of links added";
    }
    leaf num-links-deleted {
      type uint32;
      description
        "Number of links deleted";
    }
    leaf num-prefixes-added {
      type uint32;
      description
        "Number of prefixes added";
    }
    leaf num-prefixes-deleted {
      type uint32;
      description
        "Number of prefixes deleted";
    }
  }

  grouping PCE-NODE-SUMMARY-BAG {
    description
      "PCE Node Summary Information";
    container stats-topology-update {
      description
        "Statistics on topology update";
      uses PCE-TOPO-STATS-BAG;
    }
    leaf nodes {
      type uint32;
      description
        "Number of PCE nodes";
    }
    leaf lookup-nodes {
      type uint32;
      description
        "Number of lookup nodes";
    }
    leaf prefixes {
      type uint32;
      description
        "Number of prefixes";
    }
    leaf prefix-sids {
      type uint32;
      description
        "Number of total prefix SIDs";
    }
    leaf regular-prefix-sids {
      type uint32;
      description
        "Number of reguar prefix SIDs";
    }
    leaf strict-prefix-sids {
      type uint32;
      description
        "Number of strict prefix SIDs";
    }
    leaf links {
      type uint32;
      description
        "Number of links";
    }
    leaf epe-links {
      type uint32;
      description
        "Number of EPE links";
    }
    leaf adjacency-sids {
      type uint32;
      description
        "Number of total adjacency SIDs";
    }
    leaf epesids {
      type uint32;
      description
        "Number of total EPE SIDs";
    }
    leaf protected-adjacency-sids {
      type uint32;
      description
        "Number of protected adjacency SIDs";
    }
    leaf un-protected-adjacency-sids {
      type uint32;
      description
        "Number of unprotected adjacency SIDs";
    }
    leaf topology-consistent {
      type boolean;
      description
        "True if topology is consistent";
    }
  }

  grouping SRV6-NODE-SID-BAG {
    description
      "SRv6 Node SID bag";
    container srv6sid {
      description
        "SRv6 node SID";
      uses SRV6-SID-BAG;
    }
    container node-id {
      description
        "Link-state node identifier";
      uses PCE-NODE-ID-BAG;
    }
    leaf domain-identifier {
      type uint64;
      description
        "Domain identifier";
    }
  }

  grouping PCE-IPV6-LINK-BAG {
    description
      "PCE IPv6 Link Information";
    container local-igp-information {
      description
        "Local node IGP information";
      uses PCE-IGP-INFO-BAG;
    }
    container remote-node-protocol-identifier {
      description
        "Remote node protocol identifier";
      uses PCE-NODE-PID-BAG;
    }
    container performance-metrics {
      description
        "Performance metrics";
      uses PCE-LINK-PM-METRICS;
    }
    leaf local-ipv6-address {
      type inet:ipv6-address;
      description
        "Local IPv6 address";
    }
    leaf remote-ipv6-address {
      type inet:ipv6-address;
      description
        "Remote IPv6 address";
    }
    leaf igp-metric {
      type uint32;
      description
        "IGP Metric";
    }
    leaf te-metric {
      type uint32;
      description
        "TE Metric";
    }
    leaf administrative-groups {
      type uint32;
      description
        "Administrative Groups";
    }
    leaf-list flex-algo-asla-administrative-group {
      type uint32;
      description
        "Flex-algo specific Link Extended admin-groups";
    }
    leaf flex-algo-asla-te-metric {
      type uint32;
      description
        "Flex-algo specific Link TE metric";
    }
    leaf maximum-link-bandwidth {
      type uint64;
      description
        "Max link bandwidth";
    }
    leaf max-reservable-bandwidth {
      type uint64;
      description
        "Max Reservable bandwidth";
    }
    list adjacency-sid {
      description
        "Adjacency SIDs";
      uses PCE-SID-BAG;
    }
    list srv6-adjacency-sid {
      description
        "SRv6 Adjacecny micro-SIDs";
      uses SRV6-SID-BAG;
    }
    list msd {
      description
        "Advertised MSDs";
      uses TOPO-MSD-BAG;
    }
  }

  grouping TOPO-MSD-BAG {
    description
      "Topology MSD";
    leaf subtype {
      type Topo-msd-subtype;
      description
        "Subtype of the MSD as defined by IANA";
    }
    leaf value {
      type uint8;
      description
        "MSD value";
    }
  }

  grouping PCE-LINK-PM-METRICS {
    description
      "PCE link performance metric information";
    leaf unidirectional-min-delay {
      type uint32;
      units "microsecond";
      description
        "Min delay in microseconds";
    }
  }

  grouping PCE-IPV4-LINK-BAG {
    description
      "PCE IPv4 Link Information";
    container local-igp-information {
      description
        "Local node IGP information";
      uses PCE-IGP-INFO-BAG;
    }
    container remote-node-protocol-identifier {
      description
        "Remote node protocol identifier";
      uses PCE-NODE-PID-BAG;
    }
    container performance-metrics {
      description
        "Performance metrics";
      uses PCE-LINK-PM-METRICS;
    }
    leaf local-ipv4-address {
      type inet:ipv4-address;
      description
        "Local IPv4 address";
    }
    leaf remote-ipv4-address {
      type inet:ipv4-address;
      description
        "Remote IPv4 address";
    }
    leaf igp-metric {
      type uint32;
      description
        "IGP Metric";
    }
    leaf te-metric {
      type uint32;
      description
        "TE Metric";
    }
    leaf maximum-link-bandwidth {
      type uint64;
      description
        "Max link bandwidth";
    }
    leaf max-reservable-bandwidth {
      type uint64;
      description
        "Max Reservable bandwidth";
    }
    leaf administrative-groups {
      type uint32;
      description
        "Link admin-groups";
    }
    leaf-list flex-algo-asla-administrative-group {
      type uint32;
      description
        "Flex-algo specific Link Extended admin-groups";
    }
    leaf flex-algo-asla-te-metric {
      type uint32;
      description
        "Flex-algo specific Link TE metric";
    }
    leaf-list srlgs {
      type uint32;
      description
        "SRLG Values";
    }
    list adjacency-sid {
      description
        "Adjacency SIDs";
      uses PCE-SID-BAG;
    }
    list msd {
      description
        "Advertised MSDs";
      uses TOPO-MSD-BAG;
    }
  }

  grouping PCE-SID-BAG {
    description
      "PCE SID bags";
    container sid-prefix {
      description
        "Prefix";
      uses PCE-IP-ADDR-TYPE;
    }
    container igp {
      description
        "IGP information";
      uses PCE-IGP-INFO-TYPE;
    }
    leaf sid-type {
      type Sid;
      description
        "SID Type";
    }
    leaf mpls-label {
      type uint32;
      description
        "MPLS Label - absolute value";
    }
    leaf domain-identifier {
      type uint64;
      description
        "Domain identifier";
    }
    leaf algorithm {
      type uint32;
      description
        "SID algorithm number";
    }
    leaf rflag {
      type boolean;
      description
        "R Flag";
    }
    leaf nflag {
      type boolean;
      description
        "N Flag";
    }
    leaf pflag {
      type boolean;
      description
        "P Flag";
    }
    leaf eflag {
      type boolean;
      description
        "E Flag";
    }
    leaf vflag {
      type boolean;
      description
        "V Flag";
    }
    leaf lflag {
      type boolean;
      description
        "L Flag";
    }
    leaf xflag {
      type boolean;
      description
        "X Flag. Set if the prefix has been
         redistributed from another protocol.";
    }
    leaf label-index {
      type uint32;
      description
        "MPLS Label index - relative value in SRGB";
    }
  }

  grouping PCE-PREFIX-BAG {
    description
      "PCE Prefix bag";
    container pfx-sid {
      description
        "Prefix SID";
      uses PCE-SID-BAG;
    }
    container node-id {
      description
        "Link-state node identifier";
      uses PCE-NODE-ID-BAG;
    }
    leaf domain-identifier {
      type uint64;
      description
        "Domain identifier";
    }
  }

  grouping PCE-FA-DEFINITION {
    description
      "Flex-algo definition";
    leaf number {
      type uint8;
      description
        "Flex-Algo Number";
    }
    leaf local-priority {
      type uint8;
      description
        "Local Priority";
    }
    leaf metric-type {
      type Cmn-metric-type;
      description
        "Metric Type";
    }
    leaf-list affinity-exclude-any {
      type uint32;
      description
        "Affinity exclude any";
    }
    leaf-list affinity-include-any {
      type uint32;
      description
        "Affinity include any";
    }
    leaf-list affinity-include-all {
      type uint32;
      description
        "Affinity include all";
    }
  }

  grouping PCE-SR-FLEX-ALGO-BAG {
    description
      "PCE SR Algo Information";
    container node-id {
      description
        "Link-state node identifier";
      uses PCE-NODE-ID-BAG;
    }
    leaf domain-identifier {
      type uint64;
      description
        "Domain identifier";
    }
    leaf-list algo-participation {
      type uint8;
      description
        "Algos participated by this node";
    }
    list flex-algo-advertised-definition {
      description
        "Flex-algo definition advertised";
      uses PCE-FA-DEFINITION;
    }
  }

  grouping PCE-SRLB-INFO-BAG {
    description
      "PCE SRLB information bag";
    container node-id {
      description
        "Link-state node identifier";
      uses PCE-NODE-ID-BAG;
    }
    leaf start {
      type uint32;
      description
        "SRLB start";
    }
    leaf size {
      type uint32;
      description
        "SRLB size";
    }
    leaf domain-identifier {
      type uint64;
      description
        "Domain identifier";
    }
  }

  grouping PCE-SRGB-INFO-BAG {
    description
      "PCE SRGB information bag";
    container node-id {
      description
        "Link-state node identifier";
      uses PCE-NODE-ID-BAG;
    }
    container igp-srgb {
      description
        "IGP-specific information";
      uses PCE-IGP-INFO-TYPE;
    }
    leaf start {
      type uint32;
      description
        "SRGB start";
    }
    leaf size {
      type uint32;
      description
        "SRGB size";
    }
    leaf domain-identifier {
      type uint64;
      description
        "Domain identifier";
    }
  }

  grouping PCE-IGP-INFO-BGP {
    description
      "PCE BGP Information";
    leaf router-id {
      type Pce-ipv4-address;
      description
        "BGP router ID";
    }
    leaf confed-asn {
      type uint32;
      description
        "Confederation ASN";
    }
  }

  grouping PCE-IGP-INFO-OSPF {
    description
      "PCE OSPF Information";
    leaf router-id {
      type Pce-ipv4-address;
      description
        "OSPF router ID";
    }
    leaf area {
      type uint32;
      description
        "OSPF area";
    }
  }

  grouping PCE-IGP-INFO-ISIS {
    description
      "PCE ISIS Information";
    leaf system-id {
      type string;
      description
        "ISIS system ID";
    }
    leaf level {
      type uint32;
      description
        "ISIS level";
    }
    leaf area-id {
      type string;
      description
        "ISIS area ID";
    }
  }

  grouping PCE-IGP-INFO-TYPE {
    description
      "PCE IGP INFO TYPE";
    container isis {
      when "../igp-id = 'isis'" {
        description
          "../IGP_ID = 'ISIS'";
      }
      description
        "ISIS information";
      uses PCE-IGP-INFO-ISIS;
    }
    container ospf {
      when "../igp-id = 'ospf'" {
        description
          "../IGP_ID = 'OSPF'";
      }
      description
        "OSPF information";
      uses PCE-IGP-INFO-OSPF;
    }
    container bgp {
      when "../igp-id = 'bgp'" {
        description
          "../IGP_ID = 'BGP'";
      }
      description
        "BGP information";
      uses PCE-IGP-INFO-BGP;
    }
    leaf igp-id {
      type Pce-igp-info-id;
      description
        "IGP ID";
    }
  }

  grouping PCE-NODE-ID-BAG {
    description
      "PCE Node ID information";
    container igp {
      description
        "IGP-specific information";
      uses PCE-IGP-INFO-TYPE;
    }
    leaf autonomous-system-number {
      type uint32;
      description
        "Autonomous System Number";
    }
    leaf ls-identifier {
      type uint32;
      description
        "Link-State identifier";
    }
  }

  grouping PCE-IGP-INFO-BAG {
    description
      "PCE IGP information bag";
    container igp {
      description
        "IGP-specific information";
      uses PCE-IGP-INFO-TYPE;
    }
    container node-id {
      description
        "Link-state node identifier";
      uses PCE-NODE-ID-BAG;
    }
    leaf domain-identifier {
      type uint64;
      description
        "Domain identifier";
    }
    leaf autonomous-system-number {
      type uint32;
      description
        "Autonomous System Number";
    }
    leaf msd-mpls {
      type uint8;
      description
        "Base MPLS Imposition MSD";
    }
    leaf is-virtual-domain {
      type boolean;
      description
        "Whether the node is in virtual domain";
    }
  }

  grouping PCE-NODE-PID-BAG {
    description
      "PCE Node Protocol Identifier Information";
    leaf node-name {
      type string;
      description
        "Node Name";
    }
    leaf ipv4bgp-router-id-set {
      type boolean;
      description
        "True if IPv4 BGP router ID is set";
    }
    leaf ipv4bgp-router-id {
      type inet:ipv4-address;
      description
        "IPv4 TE router ID";
    }
    leaf ipv4te-router-id-set {
      type boolean;
      description
        "True if IPv4 TE router ID is set";
    }
    leaf ipv4te-router-id {
      type inet:ipv4-address;
      description
        "IPv4 BGP router ID";
    }
    list igp-information {
      description
        "IGP information";
      uses PCE-IGP-INFO-BAG;
    }
    list srgb-information {
      description
        "SRGB information";
      uses PCE-SRGB-INFO-BAG;
    }
    list sr-flex-algo {
      description
        "SR Flex-algo information";
      uses PCE-SR-FLEX-ALGO-BAG;
    }
    list srlb-information {
      description
        "SRLB information";
      uses PCE-SRLB-INFO-BAG;
    }
  }

  grouping PCE-XTC-NODE-SECONDARY-IDS {
    description
      "PCE XTC Node Secondary identifiers";
    leaf common-ipv4-router-id {
      type inet:ipv4-address;
      description
        "TE or BGP or OSPF router ID";
    }
    leaf system-id {
      type string;
      description
        "ISIS system ID";
    }
  }

  grouping PCE-XTC-NODE-BAG {
    description
      "PCE XTC Node Information";
    container node-protocol-identifier {
      description
        "Node protocol identifier";
      uses PCE-NODE-PID-BAG;
    }
    container secondary-identifiers {
      description
        "Supplementary identifiers to node-id";
      uses PCE-XTC-NODE-SECONDARY-IDS;
    }
    leaf node-identifier-xr {
      type uint32;
      description
        "Node identifier";
    }
    leaf overload {
      type boolean;
      description
        "Node Overload Bit";
    }
    list prefixe {
      description
        "Prefixes";
      uses PCE-PREFIX-BAG;
    }
    list prefix-sid {
      description
        "Prefix SIDs";
      uses PCE-SID-BAG;
    }
    list ipv4-link {
      description
        "IPv4 Link information";
      uses PCE-IPV4-LINK-BAG;
    }
    list ipv6-link {
      description
        "IPv6 Link information";
      uses PCE-IPV6-LINK-BAG;
    }
    list srv6-node-sid {
      description
        "SRv6 Node micro-SIDs";
      uses SRV6-NODE-SID-BAG;
    }
  }

  grouping PCE-PEER-BAG {
    description
      "Peer information";
    container peer-address-xr {
      description
        "Peer address";
      uses PCE-IP-ADDR-TYPE;
    }
    container brief-pcep-information {
      description
        "PCE protocol information";
      uses PCE-PCEP-BAG;
    }
    leaf peer-protocol {
      type Pce-proto;
      description
        "Protocol between PCE and peer";
    }
  }

  grouping PCE-PCEP-ERROR-BAG {
    description
      "PCEP Error information";
    leaf pc-error-type {
      type uint8;
      description
        "PCEP Error type";
    }
    leaf pc-error-value {
      type uint8;
      description
        "PCEP Error Value";
    }
  }

  grouping PCE-PCEP-BAG {
    description
      "PCEP information";
    leaf pcep-state {
      type Pcep-state;
      description
        "PCEP State";
    }
    leaf stateful {
      type boolean;
      description
        "Stateful";
    }
    leaf capability-update {
      type boolean;
      description
        "Update capability";
    }
    leaf capability-instantiate {
      type boolean;
      description
        "Instantiation capability";
    }
    leaf capability-segment-routing {
      type boolean;
      description
        "Segment Routing capability";
    }
    leaf capability-triggered-sync {
      type boolean;
      description
        "Triggered Synchronization capability";
    }
    leaf capability-db-version {
      type boolean;
      description
        "DB version capability";
    }
    leaf capability-delta-sync {
      type boolean;
      description
        "Delta Synchronization capability";
    }
  }

  grouping PCE-PCEP-DETAIL-BAG {
    description
      "Detailed PCE protocol information";
    container brief-pcep-information {
      description
        "Brief PCE protocol information";
      uses PCE-PCEP-BAG;
    }
    container last-error-rx {
      description
        "Last PCError received";
      uses PCE-PCEP-ERROR-BAG;
    }
    container last-error-tx {
      description
        "Last PCError sent";
      uses PCE-PCEP-ERROR-BAG;
    }
    leaf error {
      type string;
      description
        "Error (for display only)";
    }
    leaf speaker-id {
      type string;
      description
        "Speaker Entity ID";
    }
    leaf pcep-up-time {
      type uint32;
      description
        "PCEP Up Time";
    }
    leaf keepalives {
      type uint32;
      description
        "Keepalive count";
    }
    leaf md5-enabled {
      type boolean;
      description
        "MD5 Authentication Enabled";
    }
    leaf keychain-enabled {
      type boolean;
      description
        "Keychain based Authentication Enabled";
    }
    leaf negotiated-local-keepalive {
      type uint32;
      description
        "Negotiated KA";
    }
    leaf negotiated-remote-keepalive {
      type uint32;
      description
        "Negotiated KA";
    }
    leaf negotiated-dead-time {
      type uint32;
      description
        "Negotiated DT";
    }
    leaf pce-request-rx {
      type uint32;
      description
        "PCEReq Rx";
    }
    leaf pce-request-tx {
      type uint32;
      description
        "PCEReq Tx";
    }
    leaf pce-reply-rx {
      type uint32;
      description
        "PCERep Rx";
    }
    leaf pce-reply-tx {
      type uint32;
      description
        "PCERep Tx";
    }
    leaf pce-error-rx {
      type uint32;
      description
        "PCEErr Rx";
    }
    leaf pce-error-tx {
      type uint32;
      description
        "PCEErr Tx";
    }
    leaf pce-open-tx {
      type uint32;
      description
        "PCEOpen Tx";
    }
    leaf pce-open-rx {
      type uint32;
      description
        "PCEOpen Rx";
    }
    leaf pce-report-rx {
      type uint32;
      description
        "PCERpt Rx";
    }
    leaf pce-report-tx {
      type uint32;
      description
        "PCERpt Tx";
    }
    leaf pce-update-rx {
      type uint32;
      description
        "PCEUpd Rx";
    }
    leaf pce-update-tx {
      type uint32;
      description
        "PCEUpd Tx";
    }
    leaf pce-initiate-rx {
      type uint32;
      description
        "PCEInit Rx";
    }
    leaf pce-initiate-tx {
      type uint32;
      description
        "PCEInit Tx";
    }
    leaf pce-keepalive-tx {
      type uint64;
      description
        "PCE Keepalive Tx";
    }
    leaf pce-keepalive-rx {
      type uint64;
      description
        "PCE Keepalive Rx";
    }
    leaf local-session-id {
      type uint8;
      description
        "Local PCEP session ID";
    }
    leaf remote-session-id {
      type uint8;
      description
        "Remote PCEP session ID";
    }
    leaf minimum-keepalive-interval {
      type uint8;
      description
        "Minimum keepalive interval for the peer";
    }
    leaf maximum-dead-interval {
      type uint8;
      description
        "Maximum dead interval for the peer";
    }
    leaf max-sid-depth {
      type uint8;
      description
        "Maximum number of labels the peer can impose";
    }
  }

  grouping PCE-PEER-DETAIL-BAG {
    description
      "Detailed PCEP peer information";
    container peer-address-xr {
      description
        "Peer address";
      uses PCE-IP-ADDR-TYPE;
    }
    container detail-pcep-information {
      description
        "Detailed PCE protocol information";
      uses PCE-PCEP-DETAIL-BAG;
    }
    leaf peer-protocol {
      type Pce-proto;
      description
        "Protocol between PCE and peer";
    }
    leaf max-sid-depth {
      type uint32;
      description
        "Maximum SID Depth";
    }
  }

  grouping PCE-EVENT-INFO {
    description
      "PCE Event information";
    leaf event-id {
      type uint32;
      description
        "Event ID in range 1 - 0xFFFFFFFF. 0 is invalid.";
    }
    leaf event-message {
      type string;
      description
        "Event message";
    }
    leaf time-stamp {
      type uint32;
      description
        "Event time, relative to Jan 1, 1970";
    }
  }

  grouping PCE-EVENT-BAG {
    description
      "Private LSP information";
    list event-buffer {
      description
        "LSP Event buffer";
      uses PCE-EVENT-INFO;
    }
  }

  grouping PCE-API-LOCAL-BAG {
    description
      "LSP API local parameters";
    leaf allow-xtc-reoptimization {
      type boolean;
      description
        "True if local reoptimization is permitted";
    }
    leaf protection {
      type boolean;
      description
        "True if protection requested by API";
    }
  }

  grouping PCE-LSPA-INFO {
    description
      "PCE LSP attribute information";
    leaf affinity-exclude-any {
      type uint32;
      description
        "Affinity exclude any";
    }
    leaf affinity-include-any {
      type uint32;
      description
        "Affinity include any";
    }
    leaf affinity-include-all {
      type uint32;
      description
        "Affinity include all";
    }
    leaf setup-priority {
      type uint8;
      description
        "Setup Priority";
    }
    leaf hold-priority {
      type uint8;
      description
        "Hold Priority";
    }
    leaf local-protection {
      type boolean;
      description
        "True, if local protection is desired";
    }
    leaf adjacency-sid-only {
      type boolean;
      description
        "True, if Adjacency SIDs only can be used";
    }
    leaf blocked-reoptimization {
      type boolean;
      description
        "True, if path should not be re-computated based on topology
         change, periodic trigger, but it can be changed
         after explicit request from operator.";
    }
  }

  grouping MGMT-SRV6-ENDPOINT-BEHAVIOR {
    description
      "SRv6 Endpoint Behavior Info";
    leaf type {
      type Mgmt-srv6-endpoint;
      description
        "Behavior type";
    }
    leaf description {
      type string;
      description
        "Behavior description";
    }
  }

  grouping PCE-ASSO-INFO {
    description
      "PCE LSP association information";
    leaf association-type {
      type uint32;
      description
        "Association Type";
    }
    leaf association-id {
      type uint32;
      description
        "Association ID";
    }
    leaf association-source {
      type inet:ipv4-address;
      description
        "Association Source";
    }
  }

  grouping PCE-LSP-RSVP-ERROR-BAG {
    description
      "RSVP error information";
    leaf node-address {
      type inet:ipv4-address;
      description
        "RSVP error node address";
    }
    leaf error-flags {
      type uint8;
      description
        "RSVP error flags";
    }
    leaf error-code {
      type uint8;
      description
        "RSVP error code";
    }
    leaf error-value {
      type uint16;
      description
        "RSVP error value";
    }
  }

  grouping PCE-PCEP-INFO {
    description
      "PCEP LSP information";
    container rsvp-error {
      description
        "RSVP error info";
      uses PCE-LSP-RSVP-ERROR-BAG;
    }
    leaf pcepid {
      type uint32;
      description
        "PCE protocol identifier";
    }
    leaf pcep-flag-d {
      type boolean;
      description
        "PCEP LSP delegation flag";
    }
    leaf pcep-flag-s {
      type boolean;
      description
        "PCEP LSP state-sync flag";
    }
    leaf pcep-flag-r {
      type boolean;
      description
        "PCEP LSP remove flag";
    }
    leaf pcep-flag-a {
      type boolean;
      description
        "PCEP LSP admin flag";
    }
    leaf pcep-flag-o {
      type uint8;
      description
        "PCEP LSP operation flag";
    }
    leaf pcep-flag-c {
      type uint8;
      description
        "PCEP LSP initiated flag";
    }
  }

  grouping PCE-RRO-INFO {
    description
      "RRO information";
    container sr-rro {
      description
        "Segment Routing RRO info";
      uses PCE-SR-HOP-TYPE;
    }
    leaf rro-type {
      type Pce-rro;
      description
        "RRO Type";
    }
    leaf ipv4-address {
      type inet:ipv4-address;
      description
        "IPv4 address of RRO";
    }
    leaf mpls-label {
      type uint32;
      description
        "MPLS label of RRO";
    }
    leaf flags {
      type uint8;
      description
        "RRO Flags";
    }
  }

  grouping SRV6-SID-STRUCTURE-BAG {
    description
      "SRv6 MicroSID Structure";
    leaf locator-block-length {
      type uint8;
      description
        "Block Length";
    }
    leaf locator-node-length {
      type uint8;
      description
        "Node Length";
    }
    leaf function-length {
      type uint8;
      description
        "Function Length";
    }
    leaf argument-length {
      type uint8;
      description
        "Argument Length";
    }
  }

  grouping SRV6-SID-BAG {
    description
      "PCE SRv6 SID bag";
    container structure {
      description
        "The SRv6 strucutre of the SID";
      uses SRV6-SID-STRUCTURE-BAG;
    }
    container endpoint-function {
      description
        "Endpoint Function or behavior of the SRv6SID";
      uses MGMT-SRV6-ENDPOINT-BEHAVIOR;
    }
    leaf srv6sid {
      type inet:ipv6-address;
      description
        "Full SRv6 SID";
    }
    leaf type {
      type uint8;
      description
        "SRv6 SID Type";
    }
    leaf flags {
      type uint8;
      description
        "SRv6 SID flags";
    }
    leaf algorithm {
      type uint8;
      description
        "Flex-Algo value used for this SRv6SID";
    }
    leaf weight {
      type uint8;
      description
        "Weight";
    }
  }

  grouping PCE-SR-HOP-TYPE {
    description
      "SR hop type";
    container srv6sid {
      description
        "SRv6 SID";
      uses SRV6-SID-BAG;
    }
    leaf sid-type {
      type Pce-sr-sid;
      description
        "SID type";
    }
    leaf mpls-label {
      type uint32;
      description
        "Label";
    }
    leaf local-addr {
      type inet:ipv4-address;
      description
        "Local Address";
    }
    leaf local-addr-v6 {
      type inet:ipv6-address;
      description
        "IPv6 Local Address";
    }
    leaf remote-addr {
      type inet:ipv4-address;
      description
        "Remote Address";
    }
    leaf remote-addr-v6 {
      type inet:ipv6-address;
      description
        "IPv6 Remote Address";
    }
    leaf hop-type {
      type Sid;
      description
        "Hop Type";
    }
    leaf local-interface-index {
      type uint32;
      description
        "SNMP index of the upstream interface of this hop";
    }
    leaf remote-interface-index {
      type uint32;
      description
        "SNMP index of the downstream interface of this hop";
    }
  }

  grouping PCE-RSVP-HOP-TYPE {
    description
      "RSVP hop type";
    leaf hop-address {
      type inet:ipv4-address;
      description
        "RSVP hop address";
    }
    leaf loose {
      type boolean;
      description
        "True if loose hop";
    }
  }

  grouping PCE-ERO-INFO {
    description
      "ERO information";
    leaf reported-metric-type {
      type uint32;
      description
        "Reported Metric Type";
    }
    leaf reported-metric-value {
      type uint32;
      description
        "Reported Metric Value";
    }
    leaf computed-metric-type {
      type uint32;
      description
        "Computed Metric Type";
    }
    leaf computed-metric-value {
      type uint32;
      description
        "Computed Metric Value";
    }
    leaf computed-hop-list-time {
      type uint32;
      description
        "Computed Hop List Time";
    }
    list reported-rsvp-path {
      description
        "Reported RSVP path";
      uses PCE-RSVP-HOP-TYPE;
    }
    list reported-sr-path {
      description
        "Reported SR path";
      uses PCE-SR-HOP-TYPE;
    }
    list computed-rsvp-path {
      description
        "Computed RSVP path";
      uses PCE-RSVP-HOP-TYPE;
    }
    list computed-sr-path {
      description
        "Computed SR path";
      uses PCE-SR-HOP-TYPE;
    }
  }

  grouping PCE-LSP-DETAIL-INFO {
    description
      "Detailed LSP information";
    container brief-lsp-information {
      description
        "Brief LSP information";
      uses PCE-LSP-INFO;
    }
    container eros {
      description
        "Paths";
      uses PCE-ERO-INFO;
    }
    container lsppcep-information {
      description
        "PCEP related LSP information";
      uses PCE-PCEP-INFO;
    }
    container lsp-association-info {
      description
        "LSP association information";
      uses PCE-ASSO-INFO;
    }
    container lsp-attributes {
      description
        "LSP attributes";
      uses PCE-LSPA-INFO;
    }
    leaf signaled-bandwidth-specified {
      type boolean;
      description
        "True if router notifies signal bandwidth";
    }
    leaf signaled-bandwidth {
      type uint64;
      description
        "Signaled Bandwidth";
    }
    leaf actual-bandwidth-specified {
      type boolean;
      description
        "True if router notifies actual bandwidth";
    }
    leaf actual-bandwidth {
      type uint64;
      description
        "Actual bandwidth utilized in the data-plane";
    }
    leaf preference {
      type uint32;
      description
        "LSP Preference";
    }
    leaf lsp-role {
      type uint32;
      description
        "LSP Role";
    }
    leaf computing-pce {
      type uint32;
      description
        "Computing PCE";
    }
    leaf sub-delegated-pce {
      type inet:ipv4-address;
      description
        "Sub delegated PCE";
    }
    leaf state-sync-pce {
      type inet:ipv4-address;
      description
        "State-sync PCE";
    }
    leaf reporting-pcc-address {
      type inet:ipv4-address;
      description
        "Reporting PCC address";
    }
    leaf-list srlg-info {
      type uint32;
      description
        "List of SLRGs used by LSP";
    }
    list rro {
      description
        "RRO";
      uses PCE-RRO-INFO;
    }
    leaf sid-algo {
      type uint8;
      description
        "SID algorithm constraint
         0 - SPF
         1 - Strict SPF
         ...
         128-255 - Flex-algo";
    }
    leaf max-delay {
      type uint32;
      description
        "Maximum delay constraint applicable for latency
         metric-type";
    }
    container bidirectional {
      description
        "LSP bidirectional related information";
      leaf association-id {
        type uint16;
        description
          "Assocation group ID";
      }
      container source {
        description
          "Bidirectional association source address";
        uses PCE-IP-ADDR-TYPE;
      }
      leaf corouted-lsp {
        type boolean;
        description
          "Bidirectional co-routed LSP";
      }
      leaf reverse-lsp {
        type boolean;
        description
          "Bidirectional reverse LSP";
      }
    }
    list exclude-resources {
      description
        "LSP exclude resources constraint";
      leaf resource-value-type {
        type Pce-resource-value-type;
        description
          "Type of the resource value";
      }
      leaf resource-type {
        type Pce-resource-type;
        description
          "Type of the resource being excluded";
      }
      leaf ipv4-address {
        type inet:ipv4-address;
        description
          "IPv4 address of the resource";
      }
      leaf ipv6-address {
        type inet:ipv6-address;
        description
          "IPv6 address of the resource";
      }
      leaf srlg-value {
        type uint32;
        description
          "SRLG value of the resource";
      }
      leaf x-flag {
        type boolean;
        description
          "Whether the X flag is specified";
      }
    }
  }

  grouping PCE-TUN-DETAIL-BAG {
    description
      "Tunnel detail information";
    leaf pcc-address {
      type inet:ipv4-address;
      description
        "PCC address";
    }
    leaf tunnel-name-xr {
      type string;
      description
        "Tunnel Name";
    }
    leaf xtc-controlled {
      type boolean;
      description
        "Allow XTC reoptimizations";
    }
    leaf color {
      type uint32;
      description
        "Color";
    }
    leaf interface-name {
      type string;
      description
        "Interface name";
    }
    leaf profile-id {
      type uint16;
      description
        "Profile ID";
    }
    leaf is-zombie {
      type boolean;
      description
        "tunnel exists after PCC disconnect";
    }
    list detail-lsp-information {
      description
        "Detail LSP information";
      uses PCE-LSP-DETAIL-INFO;
    }
    container local-parameters {
      description
        "Local LSP parameters";
      uses PCE-API-LOCAL-BAG;
    }
  }

  grouping PCE-LSP-COUNTS-BAG {
    description
      "Number of LSPs";
    leaf all-ls-ps {
      type uint32;
      description
        "Number of all LSPs";
    }
    leaf up-ls-ps {
      type uint32;
      description
        "Number of operational LSPs";
    }
    leaf admin-up-ls-ps {
      type uint32;
      description
        "Number of administratively up LSPs";
    }
    leaf sr-ls-ps {
      type uint32;
      description
        "Number of LSPs with Segment routing setup type";
    }
    leaf rsvp-ls-ps {
      type uint32;
      description
        "Number of LSPs with RSVP setup type";
    }
  }

  grouping PCE-LSP-PER-PEER-SUMMARY-BAG {
    description
      "Number of LSPs for specific peer";
    container lsp-summary {
      description
        "Number of LSPs for specific peer";
      uses PCE-LSP-COUNTS-BAG;
    }
    container peer-address {
      description
        "Peer address";
      uses PCE-IP-ADDR-TYPE;
    }
  }

  grouping PCE-LSP-SUMMARY-BAG {
    description
      "PCE LSP summary information";
    container all-ls-ps {
      description
        "Summary for all peers";
      uses PCE-LSP-COUNTS-BAG;
    }
    list peer-ls-ps-info {
      description
        "Number of LSPs for specific peer";
      uses PCE-LSP-PER-PEER-SUMMARY-BAG;
    }
  }

  grouping PCE-SRV6-BSID-INFO {
    description
      "SRv6 Binding SID Info";
    container srv6-bsid {
      description
        "srv6 bsid";
      uses PCE-IP-ADDR-TYPE;
    }
    leaf bsid-behavior {
      type uint16;
      description
        "bsid behavior";
    }
    leaf block-len {
      type uint8;
      description
        "block len";
    }
    leaf nodeid-len {
      type uint8;
      description
        "nodeid len";
    }
    leaf func-len {
      type uint8;
      description
        "func len";
    }
    leaf args-len {
      type uint8;
      description
        "args len";
    }
  }

  grouping PCE-LSP-INFO {
    description
      "LSP common information";
    container extended-tunnel-id {
      description
        "Extended tunnel ID";
      uses PCE-EXTENDED-TUN-ID-TYPE;
    }
    leaf source-address {
      type inet:ipv4-address;
      description
        "Source address";
    }
    leaf destination-address {
      type inet:ipv4-address;
      description
        "Destination address";
    }
    container srv6-binding-sid {
      description
        "SRv6 Binding SID";
      uses PCE-SRV6-BSID-INFO;
    }
    leaf tunnel-id {
      type uint32;
      description
        "Tunnel ID";
    }
    leaf lspid {
      type uint32;
      description
        "LSP ID";
    }
    leaf binding-sid {
      type uint32;
      description
        "Binding SID";
    }
    leaf lsp-setup-type {
      type Lsp-setup;
      description
        "LSP Setup Type";
    }
    leaf operational-state {
      type Pcep-lsp-state;
      description
        "Operational state";
    }
    leaf administrative-state {
      type Lsp-state;
      description
        "Admin state";
    }
    leaf msd {
      type uint32;
      description
        "Maximum SID Depth";
    }
    leaf absolute-margin {
      type uint32;
      description
        "Absolute Margin";
    }
    leaf relative-margin {
      type uint32;
      description
        "Relative Margin";
    }
  }

  grouping PCE-IP-ADDR-TYPE {
    description
      "PCE IP ADDR TYPE";
    leaf af-name {
      type Pce-af-id;
      description
        "AFName";
    }
    leaf ipv4 {
      when "../af-name = 'ipv4'" {
        description
          "../AFName = 'IPv4'";
      }
      type Pce-ipv4-address;
      description
        "IPv4 address type";
    }
    leaf ipv6 {
      when "../af-name = 'ipv6'" {
        description
          "../AFName = 'IPv6'";
      }
      type Pce-ipv6-address;
      description
        "IPv6 address type";
    }
  }

  grouping PCE-EXTENDED-TUN-ID-TYPE {
    description
      "PCE Extended tunnel ID type";
    leaf af-name {
      type Pce-af-id;
      description
        "AFName";
    }
    leaf ipv4 {
      when "../af-name = 'ipv4'" {
        description
          "../AFName = 'IPv4'";
      }
      type uint32;
      description
        "IPv4 extended tunnel ID type";
    }
    leaf ipv6 {
      when "../af-name = 'ipv6'" {
        description
          "../AFName = 'IPv6'";
      }
      type Pce-ipv6-address;
      description
        "IPv6 address type";
    }
  }

  grouping PCE-TUN-BAG {
    description
      "Tunnel information";
    container pcc-address {
      description
        "PCC address";
      uses PCE-IP-ADDR-TYPE;
    }
    leaf tunnel-name-xr {
      type string;
      description
        "Tunnel Name";
    }
    list brief-lsp-information {
      description
        "Brief LSP information";
      uses PCE-LSP-INFO;
    }
  }
}
