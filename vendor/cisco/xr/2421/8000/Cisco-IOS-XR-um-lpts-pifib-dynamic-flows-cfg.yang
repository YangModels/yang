module Cisco-IOS-XR-um-lpts-pifib-dynamic-flows-cfg {
  namespace "http://cisco.com/ns/yang/Cisco-IOS-XR-um-lpts-pifib-dynamic-flows-cfg";
  prefix um-lpts-pifib-dynamic-flows-cfg;

  import Cisco-IOS-XR-um-location-cfg {
    prefix location;
  }
  import Cisco-IOS-XR-um-lpts-pifib-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-pifib-dynamic-flows package configuration.
     
     This YANG module augments the
     modules with configuration data.
     
     Copyright (c) 2020-2022 by Cisco Systems, Inc.
     All rights reserved.";

  revision 2022-07-11 {
    description
      "Added missing description statement to nodes";
  }
  revision 2020-09-17 {
    description
      "Initial release";
  }

  feature pifib_dynamic_flows_gl_config_check {
    description
      "pifib dynamic flows gl config check";
  }

  feature pifib_dynamic_flows_lo_config_check {
    description
      "pifib dynamic flows lo config check";
  }

  feature pifib_xipc_throt_policer_config_check {
    description
      "pifib xipc throt policer config check";
  }

  feature pifib_dynamic_flows_node_check {
    description
      "pifib dynamic flows node check";
  }

  grouping LOCATION-BODY {
    description
      "Grouping for location";
    container dynamic-flows {
      presence "Indicates a dynamic-flows node is configured.";
      description
        "ingress flows configuration command";
      container flow {
        description
          "lpts flow type";
        container fragment {
          description
            "Fragmented IP packets";
          leaf max {
            type uint32 {
              range "0..4294967295" {
                description
                  "TCAM Entries NUM";
              }
            }
            description
              "Max number of TCAM entries";
          }
        }
        container ospf {
          description
            "OSPF ";
          container unicast {
            description
              "Unicast ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container multicast {
            description
              "Multicast";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
        }
        container isis {
          description
            "ISIS ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container bfd {
          description
            "BFD ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
          container multipath {
            description
              "Multipath ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container blb {
            description
              "BLB ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container singlepath {
            description
              "Singlepath ";
            leaf max {
              type uint32 {
                range "0..4294967295" {
                  description
                    "TCAM Entries NUM";
                }
              }
              description
                "Max number of TCAM entries";
            }
          }
        }
        container bgp {
          description
            "BGP ";
          container known {
            description
              "Known ";
            leaf max {
              type uint32 {
                range "0..4294967295" {
                  description
                    "TCAM Entries NUM";
                }
              }
              description
                "Max number of TCAM entries";
            }
          }
          container configured {
            description
              "Configured";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container pim {
          description
            "PIM ";
          container unicast {
            description
              "Unicast ";
            leaf max {
              type uint32 {
                range "0..4294967295" {
                  description
                    "TCAM Entries NUM";
                }
              }
              description
                "Max number of TCAM entries";
            }
          }
          container multicast {
            description
              "Multicast ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
        }
        container igmp {
          description
            "IGMP ";
          leaf max {
            type uint32 {
              range "0..4294967295" {
                description
                  "TCAM Entries NUM";
              }
            }
            description
              "Max number of TCAM entries";
          }
        }
        container icmp {
          description
            "ICMP ";
          container local {
            description
              "Local interest packets ";
            leaf max {
              type uint32 {
                range "0..4294967295" {
                  description
                    "TCAM Entries NUM";
                }
              }
              description
                "Max number of TCAM entries";
            }
          }
          container application {
            description
              "Specific application packets ";
            leaf max {
              type uint32 {
                range "0..4294967295" {
                  description
                    "TCAM Entries NUM";
                }
              }
              description
                "Max number of TCAM entries";
            }
          }
          container control {
            description
              "Control packets ";
            leaf max {
              type uint32 {
                range "0..4294967295" {
                  description
                    "TCAM Entries NUM";
                }
              }
              description
                "Max number of TCAM entries";
            }
          }
          container default {
            description
              "Default packets ";
            leaf max {
              type uint32 {
                range "0..4294967295" {
                  description
                    "TCAM Entries NUM";
                }
              }
              description
                "Max number of TCAM entries";
            }
          }
          container generic {
            description
              "Generic application packets ";
            container echo-reply {
              description
                "Echo-reply packets ";
              leaf max {
                type uint32 {
                  range "0..4294967295" {
                    description
                      "TCAM Entries NUM";
                  }
                }
                description
                  "Max number of TCAM entries";
              }
            }
          }
        }
        container ldp {
          description
            "LDP ";
          container tcp {
            description
              "TCP ";
            container known {
              description
                "Known ";
              leaf max {
                type uint32 {
                  range "0..4294967295" {
                    description
                      "TCAM Entries NUM";
                  }
                }
                description
                  "Max number of TCAM entries";
              }
            }
            container configured {
              description
                "Configured";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container udp {
            description
              "UDP ";
            leaf max {
              type uint32 {
                range "0..4294967295" {
                  description
                    "TCAM Entries NUM";
                }
              }
              description
                "Max number of TCAM entries";
            }
          }
        }
        container all-routers {
          description
            "All Routers";
          leaf max {
            type uint32 {
              range "0..4294967295" {
                description
                  "TCAM Entries NUM";
              }
            }
            description
              "Max number of TCAM entries";
          }
        }
        container lmp {
          description
            "LMP ";
          container tcp {
            description
              "TCP ";
            container known {
              description
                "Known ";
              leaf max {
                type uint32 {
                  range "0..4294967295" {
                    description
                      "TCAM Entries NUM";
                  }
                }
                description
                  "Max number of TCAM entries";
              }
            }
            container configured {
              description
                "Configured";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container udp {
            description
              "UDP ";
            leaf max {
              type uint32 {
                range "0..4294967295" {
                  description
                    "TCAM Entries NUM";
                }
              }
              description
                "Max number of TCAM entries";
            }
          }
        }
        container rsvp {
          description
            "RSVP ";
          container default {
            description
              "RSVP Default ";
            leaf max {
              type uint32 {
                range "0..4294967295" {
                  description
                    "TCAM Entries NUM";
                }
              }
              description
                "Max number of TCAM entries";
            }
          }
          container known {
            description
              "RSVP Known ";
            leaf max {
              type uint32 {
                range "0..4294967295" {
                  description
                    "TCAM Entries NUM";
                }
              }
              description
                "Max number of TCAM entries";
            }
          }
          container udp {
            description
              "UDP";
            leaf max {
              type uint32 {
                range "0..4294967295" {
                  description
                    "TCAM Entries NUM";
                }
              }
              description
                "Max number of TCAM entries";
            }
          }
        }
        container ike {
          description
            "IKE ";
          leaf max {
            type uint32 {
              range "0..4294967295" {
                description
                  "TCAM Entries NUM";
              }
            }
            description
              "Max number of TCAM entries";
          }
        }
        container ipsec {
          description
            "IPSEC ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container msdp {
          description
            "MSDP ";
          container known {
            description
              "Known ";
            leaf max {
              type uint32 {
                range "0..4294967295" {
                  description
                    "TCAM Entries NUM";
                }
              }
              description
                "Max number of TCAM entries";
            }
          }
          container configured {
            description
              "Configured";
            leaf max {
              type uint32 {
                range "0..4294967295" {
                  description
                    "TCAM Entries NUM";
                }
              }
              description
                "Max number of TCAM entries";
            }
          }
          container default {
            description
              "Default";
            leaf max {
              type uint32 {
                range "0..4294967295" {
                  description
                    "TCAM Entries NUM";
                }
              }
              description
                "Max number of TCAM entries";
            }
          }
        }
        container snmp {
          description
            "SNMP ";
          leaf max {
            type uint32 {
              range "0..4294967295" {
                description
                  "TCAM Entries NUM";
              }
            }
            description
              "Max number of TCAM entries";
          }
        }
        container ssh {
          description
            "SSH ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container http {
          description
            "HTTP ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container shttp {
          description
            "SHTTP ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container telnet {
          description
            "TELNET ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container css {
          description
            "CSS ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container rsh {
          description
            "RSH ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container udp {
          description
            "UDP ";
          container known {
            description
              "Known ";
            leaf max {
              type uint32 {
                range "0..4294967295" {
                  description
                    "TCAM Entries NUM";
                }
              }
              description
                "Max number of TCAM entries";
            }
          }
          container listen {
            description
              "Listen ";
            leaf max {
              type uint32 {
                range "0..4294967295" {
                  description
                    "TCAM Entries NUM";
                }
              }
              description
                "Max number of TCAM entries";
            }
          }
          container configured {
            description
              "Config peer ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container tcp {
          description
            "TCP ";
          container known {
            description
              "Known ";
            leaf max {
              type uint32 {
                range "0..4294967295" {
                  description
                    "TCAM Entries NUM";
                }
              }
              description
                "Max number of TCAM entries";
            }
          }
          container listen {
            description
              "Listen ";
            leaf max {
              type uint32 {
                range "0..4294967295" {
                  description
                    "TCAM Entries NUM";
                }
              }
              description
                "Max number of TCAM entries";
            }
          }
          container configured {
            description
              "Configured ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container multicast {
          description
            "Multicast ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container raw {
          description
            "Raw ";
          container listen {
            description
              "Listen ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container ip-sla {
          description
            "IP-SLA ";
          leaf max {
            type uint32 {
              range "0..4294967295" {
                description
                  "TCAM Entries NUM";
              }
            }
            description
              "Max number of TCAM entries";
          }
        }
        container eigrp {
          description
            "EIGRP ";
          leaf max {
            type uint32 {
              range "0..4294967295" {
                description
                  "TCAM Entries NUM";
              }
            }
            description
              "Max number of TCAM entries";
          }
        }
        container rip {
          description
            "RIP ";
          leaf max {
            type uint32 {
              range "0..4294967295" {
                description
                  "TCAM Entries NUM";
              }
            }
            description
              "Max number of TCAM entries";
          }
        }
        container l2tpv3 {
          description
            "L2TPv3 ";
          leaf max {
            type uint32 {
              range "0..4294967295" {
                description
                  "TCAM Entries NUM";
              }
            }
            description
              "Max number of TCAM entries";
          }
        }
        container pcep {
          description
            "PCEP ";
          leaf max {
            type uint32 {
              range "0..4294967295" {
                description
                  "TCAM Entries NUM";
              }
            }
            description
              "Max number of TCAM entries";
          }
        }
        container gre {
          description
            "GRE ";
          leaf max {
            type uint32 {
              range "0..4294967295" {
                description
                  "TCAM Entries NUM";
              }
            }
            description
              "Max number of TCAM entries";
          }
        }
        container vrrp {
          description
            "VRRP ";
          leaf max {
            type uint32 {
              range "0..4294967295" {
                description
                  "TCAM Entries NUM";
              }
            }
            description
              "Max number of TCAM entries";
          }
        }
        container hsrp {
          description
            "HSRP ";
          leaf max {
            type uint32 {
              range "0..4294967295" {
                description
                  "TCAM Entries NUM";
              }
            }
            description
              "Max number of TCAM entries";
          }
        }
        container mpls {
          description
            "MPLS ";
          container oam {
            description
              "Oam ";
            leaf max {
              type uint32 {
                range "0..4294967295" {
                  description
                    "TCAM Entries NUM";
                }
              }
              description
                "Max number of TCAM entries";
            }
          }
        }
        container l2tpv2 {
          description
            "L2TPv2 ";
          container default {
            description
              "Default ";
            leaf max {
              type uint32 {
                range "0..4294967295" {
                  description
                    "TCAM Entries NUM";
                }
              }
              description
                "Max number of TCAM entries";
            }
          }
          container known {
            description
              "Known ";
            leaf max {
              type uint32 {
                range "0..4294967295" {
                  description
                    "TCAM Entries NUM";
                }
              }
              description
                "Max number of TCAM entries";
            }
          }
        }
        container dns {
          description
            "DNS ";
          leaf max {
            type uint32 {
              range "0..4294967295" {
                description
                  "TCAM Entries NUM";
              }
            }
            description
              "Max number of TCAM entries";
          }
        }
        container radius {
          description
            "RADIUS ";
          leaf max {
            type uint32 {
              range "0..4294967295" {
                description
                  "TCAM Entries NUM";
              }
            }
            description
              "Max number of TCAM entries";
          }
        }
        container tacacs {
          description
            "TACACS ";
          leaf max {
            type uint32 {
              range "0..4294967295" {
                description
                  "TCAM Entries NUM";
              }
            }
            description
              "Max number of TCAM entries";
          }
        }
        container ntp {
          description
            "NTP ";
          container default {
            description
              "Default ";
            leaf max {
              type uint32 {
                range "0..4294967295" {
                  description
                    "TCAM Entries NUM";
                }
              }
              description
                "Max number of TCAM entries";
            }
          }
          container known {
            description
              "Known ";
            leaf max {
              type uint32 {
                range "0..4294967295" {
                  description
                    "TCAM Entries NUM";
                }
              }
              description
                "Max number of TCAM entries";
            }
          }
        }
        container mipv6 {
          description
            "MIPv6 ";
          leaf max {
            type uint32 {
              range "0..4294967295" {
                description
                  "TCAM Entries NUM";
              }
            }
            description
              "Max number of TCAM entries";
          }
        }
        container amt {
          description
            "AMT ";
          leaf max {
            type uint32 {
              range "0..4294967295" {
                description
                  "TCAM Entries NUM";
              }
            }
            description
              "Max number of TCAM entries";
          }
        }
        container sdac {
          description
            "SDAC-TCP ";
          leaf max {
            type uint32 {
              range "0..4294967295" {
                description
                  "TCAM Entries NUM";
              }
            }
            description
              "Max number of TCAM entries";
          }
        }
        container radius-coa {
          description
            "RADIUS COA ";
          leaf max {
            type uint32 {
              range "0..4294967295" {
                description
                  "TCAM Entries NUM";
              }
            }
            description
              "Max number of TCAM entries";
          }
        }
        container rel-udp {
          description
            "Syslog/netflow packets";
          leaf max {
            type uint32 {
              range "0..4294967295" {
                description
                  "TCAM Entries NUM";
              }
            }
            description
              "Max number of TCAM entries";
          }
        }
        container dhcpv4 {
          description
            "DHCPv4 ";
          leaf max {
            type uint32 {
              range "0..4294967295" {
                description
                  "TCAM Entries NUM";
              }
            }
            description
              "Max number of TCAM entries";
          }
        }
        container dhcpv6 {
          description
            "DHCPv6 ";
          leaf max {
            type uint32 {
              range "0..4294967295" {
                description
                  "TCAM Entries NUM";
              }
            }
            description
              "Max number of TCAM entries";
          }
        }
        container onepk {
          description
            "ONEPK ";
          leaf max {
            type uint32 {
              range "0..4294967295" {
                description
                  "TCAM Entries NUM";
              }
            }
            description
              "Max number of TCAM entries";
          }
        }
        container tpa {
          description
            "Third Party Applications";
          leaf max {
            type uint32 {
              range "0..4294967295" {
                description
                  "TCAM Entries NUM";
              }
            }
            description
              "Max number of TCAM entries";
          }
        }
        container ietf-bob {
          description
            "IETF BOB Packets";
          leaf max {
            type uint32 {
              range "0..4294967295" {
                description
                  "TCAM Entries NUM";
              }
            }
            description
              "Max number of TCAM entries";
          }
        }
        container xipc {
          if-feature "pifib_xipc_throt_policer_config_check";
          description
            "XIPC rate limit";
          leaf max {
            type uint32 {
              range "0..4294967295" {
                description
                  "TCAM Entries NUM";
              }
            }
            description
              "Max number of TCAM entries";
          }
        }
        container pm-twamp {
          description
            "PM TWAMP Packets";
          leaf max {
            type uint32 {
              range "0..4294967295" {
                description
                  "TCAM Entries NUM";
              }
            }
            description
              "Max number of TCAM entries";
          }
        }
      }
      container platform {
        description
          "lpts max entries for platform";
        leaf max {
          type uint32 {
            range "0..4294967295" {
              description
                "TCAM Entries NUM";
            }
          }
          description
            "Max number of TCAM entries";
        }
      }
    }
  }

  augment "/a1:lpts/a1:pifib/a1:hardware" {
    description
      "This augment extends lpts pifib hardware nodes
       configuration";
    container dynamic-flows {
      presence "Indicates a dynamic-flows node is configured.";
      description
        "ingress flows configuration command";
      container flow {
        description
          "lpts flow type";
        container fragment {
          description
            "Fragmented IP packets";
          leaf max {
            type uint32 {
              range "0..4294967295" {
                description
                  "TCAM Entries NUM";
              }
            }
            description
              "Max number of TCAM entries";
          }
        }
        container ospf {
          description
            "OSPF ";
          container unicast {
            description
              "Unicast ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container multicast {
            description
              "Multicast";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
        }
        container isis {
          description
            "ISIS ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container bfd {
          description
            "BFD ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
          container multipath {
            description
              "Multipath ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container blb {
            description
              "BLB ";
            container known {
              description
                "Known ";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container singlepath {
            description
              "Singlepath ";
            leaf max {
              type uint32 {
                range "0..4294967295" {
                  description
                    "TCAM Entries NUM";
                }
              }
              description
                "Max number of TCAM entries";
            }
          }
        }
        container bgp {
          description
            "BGP ";
          container known {
            description
              "Known ";
            leaf max {
              type uint32 {
                range "0..4294967295" {
                  description
                    "TCAM Entries NUM";
                }
              }
              description
                "Max number of TCAM entries";
            }
          }
          container configured {
            description
              "Configured";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container pim {
          description
            "PIM ";
          container unicast {
            description
              "Unicast ";
            leaf max {
              type uint32 {
                range "0..4294967295" {
                  description
                    "TCAM Entries NUM";
                }
              }
              description
                "Max number of TCAM entries";
            }
          }
        }
        container igmp {
          description
            "IGMP ";
          leaf max {
            type uint32 {
              range "0..4294967295" {
                description
                  "TCAM Entries NUM";
              }
            }
            description
              "Max number of TCAM entries";
          }
        }
        container icmp {
          description
            "ICMP ";
          container local {
            description
              "Local interest packets ";
            leaf max {
              type uint32 {
                range "0..4294967295" {
                  description
                    "TCAM Entries NUM";
                }
              }
              description
                "Max number of TCAM entries";
            }
          }
          container application {
            description
              "Specific application packets ";
            leaf max {
              type uint32 {
                range "0..4294967295" {
                  description
                    "TCAM Entries NUM";
                }
              }
              description
                "Max number of TCAM entries";
            }
          }
          container control {
            description
              "Control packets ";
            leaf max {
              type uint32 {
                range "0..4294967295" {
                  description
                    "TCAM Entries NUM";
                }
              }
              description
                "Max number of TCAM entries";
            }
          }
          container default {
            description
              "Default packets ";
            leaf max {
              type uint32 {
                range "0..4294967295" {
                  description
                    "TCAM Entries NUM";
                }
              }
              description
                "Max number of TCAM entries";
            }
          }
          container generic {
            description
              "Generic application packets ";
            container echo-reply {
              description
                "Echo-reply packets ";
              leaf max {
                type uint32 {
                  range "0..4294967295" {
                    description
                      "TCAM Entries NUM";
                  }
                }
                description
                  "Max number of TCAM entries";
              }
            }
          }
        }
        container ldp {
          description
            "LDP ";
          container tcp {
            description
              "TCP ";
            container known {
              description
                "Known ";
              leaf max {
                type uint32 {
                  range "0..4294967295" {
                    description
                      "TCAM Entries NUM";
                  }
                }
                description
                  "Max number of TCAM entries";
              }
            }
            container configured {
              description
                "Configured";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container udp {
            description
              "UDP ";
            leaf max {
              type uint32 {
                range "0..4294967295" {
                  description
                    "TCAM Entries NUM";
                }
              }
              description
                "Max number of TCAM entries";
            }
          }
        }
        container all-routers {
          description
            "All Routers";
          leaf max {
            type uint32 {
              range "0..4294967295" {
                description
                  "TCAM Entries NUM";
              }
            }
            description
              "Max number of TCAM entries";
          }
        }
        container lmp {
          description
            "LMP ";
          container tcp {
            description
              "TCP ";
            container known {
              description
                "Known ";
              leaf max {
                type uint32 {
                  range "0..4294967295" {
                    description
                      "TCAM Entries NUM";
                  }
                }
                description
                  "Max number of TCAM entries";
              }
            }
            container configured {
              description
                "Configured";
              leaf max {
                type uint32 {
                  range "0..4294967295" {
                    description
                      "TCAM Entries NUM";
                  }
                }
                description
                  "Max number of TCAM entries";
              }
            }
            container default {
              description
                "Default ";
              leaf max {
                type uint32 {
                  range "0..4294967295" {
                    description
                      "TCAM Entries NUM";
                  }
                }
                description
                  "Max number of TCAM entries";
              }
            }
          }
          container udp {
            description
              "UDP ";
            leaf max {
              type uint32 {
                range "0..4294967295" {
                  description
                    "TCAM Entries NUM";
                }
              }
              description
                "Max number of TCAM entries";
            }
          }
        }
        container rsvp {
          description
            "RSVP ";
          container default {
            description
              "RSVP Default ";
            leaf max {
              type uint32 {
                range "0..4294967295" {
                  description
                    "TCAM Entries NUM";
                }
              }
              description
                "Max number of TCAM entries";
            }
          }
          container known {
            description
              "RSVP Known ";
            leaf max {
              type uint32 {
                range "0..4294967295" {
                  description
                    "TCAM Entries NUM";
                }
              }
              description
                "Max number of TCAM entries";
            }
          }
          container udp {
            description
              "UDP";
            leaf max {
              type uint32 {
                range "0..4294967295" {
                  description
                    "TCAM Entries NUM";
                }
              }
              description
                "Max number of TCAM entries";
            }
          }
        }
        container ike {
          description
            "IKE ";
          leaf max {
            type uint32 {
              range "0..4294967295" {
                description
                  "TCAM Entries NUM";
              }
            }
            description
              "Max number of TCAM entries";
          }
        }
        container ipsec {
          description
            "IPSEC ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container msdp {
          description
            "MSDP ";
          container known {
            description
              "Known ";
            leaf max {
              type uint32 {
                range "0..4294967295" {
                  description
                    "TCAM Entries NUM";
                }
              }
              description
                "Max number of TCAM entries";
            }
          }
          container configured {
            description
              "Configured";
            leaf max {
              type uint32 {
                range "0..4294967295" {
                  description
                    "TCAM Entries NUM";
                }
              }
              description
                "Max number of TCAM entries";
            }
          }
          container default {
            description
              "Default";
            leaf max {
              type uint32 {
                range "0..4294967295" {
                  description
                    "TCAM Entries NUM";
                }
              }
              description
                "Max number of TCAM entries";
            }
          }
        }
        container snmp {
          description
            "SNMP ";
          leaf max {
            type uint32 {
              range "0..4294967295" {
                description
                  "TCAM Entries NUM";
              }
            }
            description
              "Max number of TCAM entries";
          }
        }
        container ssh {
          description
            "SSH ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container http {
          description
            "HTTP ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container shttp {
          description
            "SHTTP ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container telnet {
          description
            "TELNET ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container css {
          description
            "CSS ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container rsh {
          description
            "RSH ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container udp {
          description
            "UDP ";
          container known {
            description
              "Known ";
            leaf max {
              type uint32 {
                range "0..4294967295" {
                  description
                    "TCAM Entries NUM";
                }
              }
              description
                "Max number of TCAM entries";
            }
          }
          container listen {
            description
              "Listen ";
            leaf max {
              type uint32 {
                range "0..4294967295" {
                  description
                    "TCAM Entries NUM";
                }
              }
              description
                "Max number of TCAM entries";
            }
          }
          container configured {
            description
              "Config peer ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container tcp {
          description
            "TCP ";
          container known {
            description
              "Known ";
            leaf max {
              type uint32 {
                range "0..4294967295" {
                  description
                    "TCAM Entries NUM";
                }
              }
              description
                "Max number of TCAM entries";
            }
          }
          container listen {
            description
              "Listen ";
            leaf max {
              type uint32 {
                range "0..4294967295" {
                  description
                    "TCAM Entries NUM";
                }
              }
              description
                "Max number of TCAM entries";
            }
          }
          container configured {
            description
              "Configured ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container multicast {
          description
            "Multicast ";
          container known {
            description
              "Known ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container raw {
          description
            "Raw ";
          container listen {
            description
              "Listen ";
            leaf max {
              type uint32 {
                range "0..4294967295" {
                  description
                    "TCAM Entries NUM";
                }
              }
              description
                "Max number of TCAM entries";
            }
          }
          container default {
            description
              "Default ";
            leaf max {
              type uint32 {
                range "0..4294967295" {
                  description
                    "TCAM Entries NUM";
                }
              }
              description
                "Max number of TCAM entries";
            }
          }
        }
        container ip-sla {
          description
            "IP-SLA ";
          leaf max {
            type uint32 {
              range "0..4294967295" {
                description
                  "TCAM Entries NUM";
              }
            }
            description
              "Max number of TCAM entries";
          }
        }
        container eigrp {
          description
            "EIGRP ";
          leaf max {
            type uint32 {
              range "0..4294967295" {
                description
                  "TCAM Entries NUM";
              }
            }
            description
              "Max number of TCAM entries";
          }
        }
        container rip {
          description
            "RIP ";
          leaf max {
            type uint32 {
              range "0..4294967295" {
                description
                  "TCAM Entries NUM";
              }
            }
            description
              "Max number of TCAM entries";
          }
        }
        container l2tpv3 {
          description
            "L2TPv3 ";
          leaf max {
            type uint32 {
              range "0..4294967295" {
                description
                  "TCAM Entries NUM";
              }
            }
            description
              "Max number of TCAM entries";
          }
        }
        container pcep {
          description
            "PCEP ";
          leaf max {
            type uint32 {
              range "0..4294967295" {
                description
                  "TCAM Entries NUM";
              }
            }
            description
              "Max number of TCAM entries";
          }
        }
        container gre {
          description
            "GRE ";
          leaf max {
            type uint32 {
              range "0..4294967295" {
                description
                  "TCAM Entries NUM";
              }
            }
            description
              "Max number of TCAM entries";
          }
        }
        container vrrp {
          description
            "VRRP ";
          leaf max {
            type uint32 {
              range "0..4294967295" {
                description
                  "TCAM Entries NUM";
              }
            }
            description
              "Max number of TCAM entries";
          }
        }
        container hsrp {
          description
            "HSRP ";
          leaf max {
            type uint32 {
              range "0..4294967295" {
                description
                  "TCAM Entries NUM";
              }
            }
            description
              "Max number of TCAM entries";
          }
        }
        container mpls {
          description
            "MPLS ";
          container oam {
            description
              "Oam ";
            leaf max {
              type uint32 {
                range "0..4294967295" {
                  description
                    "TCAM Entries NUM";
                }
              }
              description
                "Max number of TCAM entries";
            }
          }
        }
        container l2tpv2 {
          description
            "L2TPv2 ";
          container default {
            description
              "Default ";
            leaf max {
              type uint32 {
                range "0..4294967295" {
                  description
                    "TCAM Entries NUM";
                }
              }
              description
                "Max number of TCAM entries";
            }
          }
          container known {
            description
              "Known ";
            leaf max {
              type uint32 {
                range "0..4294967295" {
                  description
                    "TCAM Entries NUM";
                }
              }
              description
                "Max number of TCAM entries";
            }
          }
        }
        container dns {
          description
            "DNS ";
          leaf max {
            type uint32 {
              range "0..4294967295" {
                description
                  "TCAM Entries NUM";
              }
            }
            description
              "Max number of TCAM entries";
          }
        }
        container radius {
          description
            "RADIUS ";
          leaf max {
            type uint32 {
              range "0..4294967295" {
                description
                  "TCAM Entries NUM";
              }
            }
            description
              "Max number of TCAM entries";
          }
        }
        container tacacs {
          description
            "TACACS ";
          leaf max {
            type uint32 {
              range "0..4294967295" {
                description
                  "TCAM Entries NUM";
              }
            }
            description
              "Max number of TCAM entries";
          }
        }
        container ntp {
          description
            "NTP ";
          container default {
            description
              "Default ";
            leaf max {
              type uint32 {
                range "0..4294967295" {
                  description
                    "TCAM Entries NUM";
                }
              }
              description
                "Max number of TCAM entries";
            }
          }
          container known {
            description
              "Known ";
            leaf max {
              type uint32 {
                range "0..4294967295" {
                  description
                    "TCAM Entries NUM";
                }
              }
              description
                "Max number of TCAM entries";
            }
          }
        }
        container mipv6 {
          description
            "MIPv6 ";
          leaf max {
            type uint32 {
              range "0..4294967295" {
                description
                  "TCAM Entries NUM";
              }
            }
            description
              "Max number of TCAM entries";
          }
        }
        container amt {
          description
            "AMT ";
          leaf max {
            type uint32 {
              range "0..4294967295" {
                description
                  "TCAM Entries NUM";
              }
            }
            description
              "Max number of TCAM entries";
          }
        }
        container sdac {
          description
            "SDAC-TCP ";
          leaf max {
            type uint32 {
              range "0..4294967295" {
                description
                  "TCAM Entries NUM";
              }
            }
            description
              "Max number of TCAM entries";
          }
        }
        container radius-coa {
          description
            "RADIUS COA ";
          leaf max {
            type uint32 {
              range "0..4294967295" {
                description
                  "TCAM Entries NUM";
              }
            }
            description
              "Max number of TCAM entries";
          }
        }
        container rel-udp {
          description
            "Syslog/netflow packets";
          leaf max {
            type uint32 {
              range "0..4294967295" {
                description
                  "TCAM Entries NUM";
              }
            }
            description
              "Max number of TCAM entries";
          }
        }
        container dhcpv4 {
          description
            "DHCPv4 ";
          leaf max {
            type uint32 {
              range "0..4294967295" {
                description
                  "TCAM Entries NUM";
              }
            }
            description
              "Max number of TCAM entries";
          }
        }
        container dhcpv6 {
          description
            "DHCPv6 ";
          leaf max {
            type uint32 {
              range "0..4294967295" {
                description
                  "TCAM Entries NUM";
              }
            }
            description
              "Max number of TCAM entries";
          }
        }
        container onepk {
          description
            "ONEPK ";
          leaf max {
            type uint32 {
              range "0..4294967295" {
                description
                  "TCAM Entries NUM";
              }
            }
            description
              "Max number of TCAM entries";
          }
        }
        container tpa {
          description
            "Third Party Applications";
          leaf max {
            type uint32 {
              range "0..4294967295" {
                description
                  "TCAM Entries NUM";
              }
            }
            description
              "Max number of TCAM entries";
          }
        }
        container ietf-bob {
          description
            "IETF BOB Packets";
          leaf max {
            type uint32 {
              range "0..4294967295" {
                description
                  "TCAM Entries NUM";
              }
            }
            description
              "Max number of TCAM entries";
          }
        }
        container xipc {
          if-feature "pifib_xipc_throt_policer_config_check";
          description
            "XIPC rate limit";
          leaf max {
            type uint32 {
              range "0..4294967295" {
                description
                  "TCAM Entries NUM";
              }
            }
            description
              "Max number of TCAM entries";
          }
        }
        container pm-twamp {
          description
            "PM TWAMP Packets";
          leaf max {
            type uint32 {
              range "0..4294967295" {
                description
                  "TCAM Entries NUM";
              }
            }
            description
              "Max number of TCAM entries";
          }
        }
      }
      container platform {
        description
          "lpts max entries for platform";
        leaf max {
          type uint32 {
            range "0..4294967295" {
              description
                "TCAM Entries NUM";
            }
          }
          description
            "Max number of TCAM entries";
        }
      }
    }
  }
  augment "/location:locations/location:location/a1:lpts/a1:pifib/a1:hardware" {
    description
      "This augment extends lpts pifib hardware police active nodes
       configuration";
    uses LOCATION-BODY;
  }
  augment "/location:locations/location:preconfigured-location/a1:lpts/a1:pifib/a1:hardware" {
    description
      "This augment extends lpts pifib hardware police preconfigured nodes
       configuration";
    uses LOCATION-BODY;
  }
}
