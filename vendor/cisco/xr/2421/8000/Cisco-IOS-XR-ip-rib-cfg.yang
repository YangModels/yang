module Cisco-IOS-XR-ip-rib-cfg {
  namespace "http://cisco.com/ns/yang/Cisco-IOS-XR-ip-rib-cfg";
  prefix ip-rib-cfg;

  import cisco-semver {
    prefix semver;
  }
  import Cisco-IOS-XR-infra-rsi-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-rib package configuration.
     
     This model is deprecated and is replaced by
     Cisco-IOS-XR-um-router-rib-cfg.yang which will provide the
     compatible functionalities.
     
     This module contains definitions
     for the following management objects:
       rib: RIB configuration.
     
     This YANG module augments the
       Cisco-IOS-XR-infra-rsi-cfg
     module with configuration data.
     
     Copyright (c) 2013-2019, 2022 by Cisco Systems, Inc.
     All rights reserved.";

  revision 2019-05-12 {
    description
      "Deprecated the native model, replaced by UM model.";
    semver:module-version "1.0.1";
  }
  revision 2019-04-05 {
    description
      "Establish semantic version baseline.";
  }
  revision 2017-07-31 {
    description
      "Fixed missing augmentation from multiple MDA parent.";
  }
  revision 2015-11-09 {
    description
      "IOS XR 6.0 revision.";
  }

  grouping NEXT-HOP-DAMPENING-DISABLE {
    description
      "Common node of ipv4, ipv6";
    leaf next-hop-dampening-disable {
      type empty;
      description
        "Disable next-hop dampening";
    }
  }

  grouping REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type uint32 {
          range "10..2000000";
        }
        description
          "Maximum BCDL redistribution history size.";
      }
      leaf protocol-client {
        type uint32 {
          range "10..250000";
        }
        description
          "Maximum protocol redistribution history size.";
      }
    }
  }

  augment "/a1:vrfs/a1:vrf/a1:afs/a1:af" {
    description
      "This augment extends the configuration data of
       'Cisco-IOS-XR-infra-rsi-cfg'";
    container maximum-prefix {
      presence "Indicates a maximum-prefix node is configured.";
      status deprecated;
      description
        "This model is deprecated and is replaced by
         Cisco-IOS-XR-um-router-rib-cfg.yang which will
         provide the compatible functionalities.  Set
         maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
  }
  augment "/a1:global-af/a1:afs/a1:af" {
    description
      "This augment extends the configuration data of
       'Cisco-IOS-XR-infra-rsi-cfg'";
    container maximum-prefix {
      presence "Indicates a maximum-prefix node is configured.";
      status deprecated;
      description
        "This model is deprecated and is replaced by
         Cisco-IOS-XR-um-router-rib-cfg.yang which will
         provide the compatible functionalities.  Set
         maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
  }
  container rib {
    status deprecated;
    description
      "This model is deprecated and is replaced by
       Cisco-IOS-XR-um-router-rib-cfg.yang which will
       provide the compatible functionalities.  RIB
       configuration.";
    container af {
      description
        "RIB address family configuration";
      container ipv4 {
        description
          "IPv4 configuration";
        uses NEXT-HOP-DAMPENING-DISABLE;
        uses REDISTRIBUTION-HISTORY;
      }
      container ipv6 {
        description
          "IPv6 configuration";
        uses NEXT-HOP-DAMPENING-DISABLE;
        uses REDISTRIBUTION-HISTORY;
      }
    }
    leaf max-recursion-depth {
      type uint32 {
        range "5..16";
      }
      description
        "Set maximum depth for route recursion check";
    }
  }
}
