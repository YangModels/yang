submodule Cisco-IOS-XR-alarmgr-server-oper-sub1 {
  belongs-to Cisco-IOS-XR-alarmgr-server-oper {
    prefix Cisco-IOS-XR-alarmgr-server-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR alarmgr-server package operational data.
     
     Copyright (c) 2013-2022 by Cisco Systems, Inc.
     All rights reserved.";

  revision 2021-09-15 {
    description
      "Removed enum last in Alarm-groups.
       2021-05-17
         Alarm support for CEM interface. Added enum cem to Alarm-groups.
       2021-05-11
         PTAH support for E1 controller.";
    semver:module-version "4.0.0";
  }
  revision 2021-05-06 {
    description
      "Adding new alarm groups to alarm_mgr_edm_spi.bag
       2020-12-02
          PTAH support for Fibre Channel controller.
       2020-09-02
          SNMP Trap support added for Alarm mib";
    semver:module-version "3.0.0";
  }
  revision 2020-05-29 {
    description
      "Addressing Yang inconsistency across platforms
       2019-06-28
        PTAH support for CPRI controller in Felidae 5G platform.";
    semver:module-version "2.1.0";
  }
  revision 2019-04-05 {
    description
      "Establish semantic version baseline.";
    semver:module-version "2.0.0";
  }
  revision 2015-11-09 {
    description
      "IOS XR 6.0 revision.";
  }

  typedef Alarm-client {
    type enumeration {
      enum "unknown" {
        value 1;
        description
          "Client type unknown";
      }
      enum "producer" {
        value 2;
        description
          "Client type producer";
      }
      enum "consumer" {
        value 4;
        description
          "Client type consumer";
      }
      enum "subscriber" {
        value 8;
        description
          "Client type subscriber";
      }
      enum "client-last" {
        value 16;
        description
          "Client type last";
      }
    }
    description
      "Alarm client";
  }

  typedef Alarm-client-state {
    type enumeration {
      enum "start" {
        value 0;
        description
          "Starting state. Should be 0";
      }
      enum "init" {
        value 1;
        description
          "Client initalized";
      }
      enum "connecting" {
        value 2;
        description
          "Sent connect request";
      }
      enum "connected" {
        value 3;
        description
          "Initial connected";
      }
      enum "registered" {
        value 4;
        description
          "Has sent registration message";
      }
      enum "disconnected" {
        value 5;
        description
          "Has been disconnected due to request of error";
      }
      enum "ready" {
        value 6;
        description
          "The client is ready";
      }
    }
    description
      "Alarm client state";
  }

  typedef Alarm-object-mib-index {
    type enumeration {
      enum "hwentity" {
        value 0;
        description
          "Object MIB index type Hardware Entity";
      }
      enum "interface-entity" {
        value 1;
        description
          "Object MIB index type Interface Entity";
      }
      enum "sw-entity" {
        value 2;
        description
          "Object MIB index type Software Entity";
      }
    }
    description
      "Alarm object mib index";
  }

  typedef Alarm-event {
    type enumeration {
      enum "default" {
        value 0;
        description
          "Default Alarm Event Type";
      }
      enum "notification" {
        value 1;
        description
          "Alarm Notifcation Event Type";
      }
      enum "condition" {
        value 2;
        description
          "Alarm Type Condition";
      }
      enum "last" {
        value 3;
        description
          "Last Event Type";
      }
    }
    description
      "Alarm event";
  }

  typedef Timing-bucket {
    type enumeration {
      enum "not-specified" {
        value 0;
        description
          "Bucket Type not applicable";
      }
      enum "fifteen-min" {
        value 1;
        description
          "Fifteen minute time bucket";
      }
      enum "one-day" {
        value 2;
        description
          "One day time bucket";
      }
      enum "thirty-sec" {
        value 3;
        description
          "Thirty second time bucket";
      }
    }
    description
      "Timing bucket";
  }

  typedef Alarm-notification-src {
    type enumeration {
      enum "not-specified" {
        value 0;
        description
          "Notification src not specified";
      }
      enum "near-end" {
        value 1;
        description
          "Notification src near end";
      }
      enum "far-end" {
        value 2;
        description
          "Notification src far end";
      }
    }
    description
      "Alarm notification src";
  }

  typedef Alarm-direction {
    type enumeration {
      enum "not-specified" {
        value 0;
        description
          "Direction Not Specified";
      }
      enum "send" {
        value 1;
        description
          "Direction Send";
      }
      enum "receive" {
        value 2;
        description
          "Direction Receive";
      }
      enum "send-receive" {
        value 3;
        description
          "Direction Send and Receive";
      }
    }
    description
      "Alarm direction";
  }

  typedef Alarm-service-affecting {
    type enumeration {
      enum "unknown" {
        value 0;
        description
          "Unknown whether alarm severity is service
           affecting";
      }
      enum "not-service-affecting" {
        value 1;
        description
          "Alarm severity is not service affecting";
      }
      enum "service-affecting" {
        value 2;
        description
          "Alarm severity is service affecting";
      }
    }
    description
      "Alarm service affecting";
  }

  typedef Alarm-groups {
    type enumeration {
      enum "unknown" {
        value 0;
        description
          "An unknown alarm group";
      }
      enum "environ" {
        value 1;
        description
          "Environomental alarm group";
      }
      enum "ethernet" {
        value 2;
        description
          "Ethernet alarm group";
      }
      enum "fabric" {
        value 3;
        description
          "Fabric related alarm group";
      }
      enum "power" {
        value 4;
        description
          "Power and PEM group of alarms";
      }
      enum "software" {
        value 5;
        description
          "Software group of alarms";
      }
      enum "slice" {
        value 6;
        description
          "Slice group of alarms";
      }
      enum "cpu" {
        value 7;
        description
          "CPU group of alarms";
      }
      enum "controller" {
        value 8;
        description
          "Controller group of alarms";
      }
      enum "sonet" {
        value 9;
        description
          "Sonet group of alarms";
      }
      enum "otn" {
        value 10;
        description
          "OTN group of alarms";
      }
      enum "sdh-controller" {
        value 11;
        description
          "SDH group of alarms";
      }
      enum "asic" {
        value 12;
        description
          "ASIC group of alarms";
      }
      enum "fpd-infra" {
        value 13;
        description
          "FPD group of alarms";
      }
      enum "shelf" {
        value 14;
        description
          "Shelf group of alarms";
      }
      enum "mpa" {
        value 15;
        description
          "MPA group of alarms";
      }
      enum "ots" {
        value 16;
        description
          "OTS group of alarms";
      }
      enum "timing" {
        value 17;
        description
          "Timing group of alarms";
      }
      enum "cpri" {
        value 18;
        description
          "CPRI group of alarms";
      }
      enum "fibre-channel" {
        value 19;
        description
          "Fibre channel group of alarms";
      }
      enum "e1" {
        value 20;
        description
          "E1 group of alarms";
      }
      enum "cem" {
        value 21;
        description
          "CEM group of alarms";
      }
    }
    description
      "Alarm groups";
  }

  typedef Alarm-status {
    type enumeration {
      enum "unknown" {
        value 0;
        description
          "Unknown alarm status level";
      }
      enum "set" {
        value 1;
        description
          "Status of active alarm that is SET by the
           controller";
      }
      enum "clear" {
        value 2;
        description
          "Status of cleared alarm that is done by the
           controller";
      }
      enum "suppress" {
        value 3;
        description
          "Status of suppressed alarm that is done by the
           controller";
      }
      enum "last" {
        value 4;
        description
          "Last status level";
      }
    }
    description
      "Alarm status";
  }

  typedef Alarm-severity {
    type enumeration {
      enum "unknown" {
        value 0;
        description
          "Unknown severity level";
      }
      enum "not-reported" {
        value 1;
        description
          "Severity level not reported will not raise an
           alarm";
      }
      enum "not-alarmed" {
        value 2;
        description
          "Severity level of info to cater to events such
           as Performance TCAS";
      }
      enum "minor" {
        value 3;
        description
          "Severity level of minor fault not traffic
           affecting";
      }
      enum "major" {
        value 4;
        description
          "Severity level of major fault leading to
           service disruption";
      }
      enum "critical" {
        value 5;
        description
          "Severity level of critical leading to drops
           ,route loss, loss of service etc.";
      }
      enum "severity-last" {
        value 6;
        description
          "Last severity level";
      }
    }
    description
      "Alarm severity";
  }

  grouping ALARM-MGR-SHOW-ALARM-BRIEF-SUPPR-DATA {
    description
      "Alarm mgr show alarm brief suppressed data";
    leaf location {
      type string {
        length "0..128";
      }
      description
        "Alarm location";
    }
    leaf severity {
      type Alarm-severity;
      description
        "Alarm severity";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf suppressed-time {
      type string {
        length "0..64";
      }
      description
        "Alarm suppressed time";
    }
    leaf suppressed-timestamp {
      type uint64;
      description
        "Alarm suppressed time(timestamp format)";
    }
    leaf description {
      type string {
        length "0..256";
      }
      description
        "Alarm description";
    }
  }

  grouping ALARM-MGR-SHOW-ALARM-BRIEF-SUPPR-INFO {
    description
      "Alarm mgr show alarm brief suppressed info";
    list suppressed-info {
      description
        "Suppressed Alarm List";
      uses ALARM-MGR-SHOW-ALARM-BRIEF-SUPPR-DATA;
    }
  }

  grouping ALARM-MGR-SHOW-ALARM-BRIEF-DATA {
    description
      "Alarm mgr show alarm brief data";
    leaf location {
      type string {
        length "0..128";
      }
      description
        "Alarm location";
    }
    leaf severity {
      type Alarm-severity;
      description
        "Alarm severity";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf clear-time {
      type string {
        length "0..64";
      }
      description
        "Alarm clear time";
    }
    leaf clear-timestamp {
      type uint64;
      description
        "Alarm clear time(timestamp format)";
    }
    leaf description {
      type string {
        length "0..256";
      }
      description
        "Alarm description";
    }
  }

  grouping ALARM-MGR-SHOW-ALARM-BRIEF-INFO {
    description
      "Alarm mgr show alarm brief info";
    list alarm-info {
      description
        "Alarm List";
      uses ALARM-MGR-SHOW-ALARM-BRIEF-DATA;
    }
  }

  grouping SYSTEM-ALARM {
    description
      "Alarm mgr show alarm brief data";
    leaf location {
      type string {
        length "0..128";
      }
      description
        "Alarm location";
    }
    leaf severity {
      type Alarm-severity;
      description
        "Alarm severity";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf clear-time {
      type string {
        length "0..64";
      }
      description
        "Alarm clear time";
    }
    leaf clear-timestamp {
      type uint64;
      description
        "Alarm clear time(timestamp format)";
    }
    leaf description {
      type string {
        length "0..256";
      }
      description
        "Alarm description";
    }
  }

  grouping ALARM-MGR-SHOW-ALARM-AID-BRIEF-INFO {
    description
      "Alarm mgr show alarm brief info";
    container alarm {
      description
        "Alarm Brief";
      uses SYSTEM-ALARM;
    }
  }

  grouping ALARM-DETAIL-TCA {
    description
      "Alarm Detail TCA Attributes";
    container tca-value {
      description
        "TCA Attributes";
      uses ALARM-TCA;
    }
    leaf tca-data {
      type string {
        length "0..5";
      }
      description
        "TCA Data";
    }
  }

  grouping SYSTEM-ALARM-DETAIL {
    description
      "Alarm mgr show alarm detail info";
    container otn {
      description
        "OTN feature specific alarm attributes";
      uses ALARM-OTN;
    }
    container tca {
      description
        "TCA feature specific alarm attributes";
      uses ALARM-DETAIL-TCA;
    }
    leaf alarm-id {
      type string {
        length "0..256";
      }
      description
        "Alarm ID";
    }
    leaf description {
      type string {
        length "0..256";
      }
      description
        "Alarm description";
    }
    leaf location {
      type string {
        length "0..128";
      }
      description
        "Alarm location";
    }
    leaf aid {
      type string {
        length "0..128";
      }
      description
        "Alarm aid";
    }
    leaf tag {
      type string {
        length "0..128";
      }
      description
        "Alarm tag description";
    }
    leaf module {
      type string {
        length "0..128";
      }
      description
        "Alarm module description";
    }
    leaf eid {
      type string {
        length "0..128";
      }
      description
        "Alarm eid";
    }
    leaf pending-sync {
      type boolean;
      description
        "Pending async flag";
    }
    leaf severity {
      type Alarm-severity;
      description
        "Alarm severity";
    }
    leaf status {
      type Alarm-status;
      description
        "Alarm status";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf clear-time {
      type string {
        length "0..64";
      }
      description
        "Alarm clear time";
    }
    leaf clear-timestamp {
      type uint64;
      description
        "Alarm clear time(timestamp format)";
    }
    leaf service-affecting {
      type Alarm-service-affecting;
      description
        "Alarm service affecting";
    }
    leaf interface {
      type string {
        length "0..128";
      }
      description
        "Alarm interface name";
    }
    leaf alarm-name {
      type string {
        length "0..128";
      }
      description
        "Alarm name";
    }
    leaf event-type {
      type string {
        length "0..128";
      }
      description
        "Alarm Type";
    }
  }

  grouping ALARM-MGR-SHOW-ALARM-AID-DETAIL-INFO {
    description
      "Alarm mgr show alarm Detail info";
    container alarm {
      description
        "Alarm Detail";
      uses SYSTEM-ALARM-DETAIL;
    }
  }

  grouping ALARM-MGR-SHOW-ALARM-SUPPR-DATA {
    description
      "Alarm mgr show alarm suppressed data";
    container otn {
      description
        "OTN feature specific alarm attributes";
      uses ALARM-OTN;
    }
    leaf description {
      type string {
        length "0..256";
      }
      description
        "Alarm description";
    }
    leaf location {
      type string {
        length "0..128";
      }
      description
        "Alarm location";
    }
    leaf aid {
      type string {
        length "0..128";
      }
      description
        "Alarm aid";
    }
    leaf tag {
      type string {
        length "0..128";
      }
      description
        "Alarm tag description";
    }
    leaf module {
      type string {
        length "0..128";
      }
      description
        "Alarm module description";
    }
    leaf eid {
      type string {
        length "0..128";
      }
      description
        "Alarm eid";
    }
    leaf reporting-agent-id {
      type uint32;
      description
        "Reporting agent id";
    }
    leaf pending-sync {
      type boolean;
      description
        "Pending async flag";
    }
    leaf severity {
      type Alarm-severity;
      description
        "Alarm severity";
    }
    leaf status {
      type Alarm-status;
      description
        "Alarm status";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf suppressed-time {
      type string {
        length "0..64";
      }
      description
        "Alarm suppressed time";
    }
    leaf suppressed-timestamp {
      type uint64;
      description
        "Alarm suppressed time(timestamp format)";
    }
    leaf service-affecting {
      type Alarm-service-affecting;
      description
        "Alarm service affecting ";
    }
    leaf interface {
      type string {
        length "0..128";
      }
      description
        "Alarm interface name";
    }
    leaf alarm-name {
      type string {
        length "0..128";
      }
      description
        "Alarm name";
    }
    leaf object-mib-index-type {
      type Alarm-object-mib-index;
      description
        "Alarm Object MIB Index Type";
    }
    leaf alarm-type {
      type uint32;
      description
        "Alarm Type";
    }
    leaf object-mib-index {
      type uint32;
      description
        "Alarm Object MIB Index Type";
    }
    leaf trap-flag {
      type uint32;
      description
        "Trap Flag";
    }
  }

  grouping ALARM-MGR-SHOW-ALARM-INFO-SUPPR-CLI {
    description
      "alarm mgr show alarm suppressed info for CLI";
    list suppressed-info {
      description
        "Suppressed Alarm List";
      uses ALARM-MGR-SHOW-ALARM-SUPPR-DATA;
    }
  }

  grouping ALARM-MGR-SHOW-CLIENT-DATA {
    description
      "Alarm mgr show client data";
    leaf name {
      type string {
        length "0..128";
      }
      description
        "Alarm client";
    }
    leaf id {
      type uint32;
      description
        "Alarms agent id of the client";
    }
    leaf location {
      type string {
        length "0..128";
      }
      description
        "The location of this client";
    }
    leaf handle {
      type string {
        length "0..128";
      }
      description
        "The client handle through which interface";
    }
    leaf state {
      type Alarm-client-state;
      description
        "The current state of the client";
    }
    leaf type {
      type Alarm-client;
      description
        "The type of the client";
    }
    leaf filter-disp {
      type boolean;
      description
        "The current subscription status of the client";
    }
    leaf subscriber-id {
      type uint32;
      description
        "Alarms agent subscriber id of the client";
    }
    leaf filter-severity {
      type Alarm-severity;
      description
        "The filter used for alarm severity";
    }
    leaf filter-state {
      type Alarm-status;
      description
        "The filter used for alarm bi-state state+";
    }
    leaf filter-group {
      type Alarm-groups;
      description
        "The filter used for alarm group";
    }
    leaf connect-count {
      type uint32;
      description
        "Number of times the agent connected to the alarm
         mgr";
    }
    leaf connect-timestamp {
      type string {
        length "0..64";
      }
      description
        "Agent connect timestamp";
    }
    leaf get-count {
      type uint32;
      description
        "Number of times the agent queried for alarms";
    }
    leaf subscribe-count {
      type uint32;
      description
        "Number of times the agent subscribed for alarms";
    }
    leaf report-count {
      type uint32;
      description
        "Number of times the agent reported alarms";
    }
  }

  grouping ALARM-MGR-SHOW-CLIENT-INFO {
    description
      "Alarm mgr show alarm info";
    list client-info {
      description
        "Client List";
      uses ALARM-MGR-SHOW-CLIENT-DATA;
    }
  }

  grouping ALARM-MGR-SHOW-ALARM-STATS {
    description
      "alarm mgr show alarm stats";
    leaf reported {
      type uint64;
      description
        "Alarms that were in all reported to this Alarm
         Mgr";
    }
    leaf dropped {
      type uint64;
      description
        "Alarms that we couldn't keep track due to some
         error or other";
    }
    leaf active {
      type uint64;
      description
        "Alarms that are currently in the active state";
    }
    leaf history {
      type uint64;
      description
        "Alarms that are cleared. This one is counted
         over a long period of time";
    }
    leaf suppressed {
      type uint64;
      description
        "Alarms that are in suppressed state";
    }
    leaf sysadmin-active {
      type uint64;
      description
        "Alarms that are currently in the active
         state(sysadmin plane)";
    }
    leaf sysadmin-history {
      type uint64;
      description
        "Alarms that are cleared in sysadmin plane. This
         one is counted over a long period of time";
    }
    leaf sysadmin-suppressed {
      type uint64;
      description
        "Alarms that are suppressed in sysadmin plane.";
    }
    leaf dropped-invalid-aid {
      type uint32;
      description
        "Alarms dropped due to invalid aid";
    }
    leaf dropped-insuff-mem {
      type uint32;
      description
        "Alarms dropped due to insufficient memory";
    }
    leaf dropped-db-error {
      type uint32;
      description
        "Alarms dropped due to db error";
    }
    leaf dropped-clear-without-set {
      type uint32;
      description
        "Alarms dropped clear without set";
    }
    leaf dropped-duplicate {
      type uint32;
      description
        "Alarms dropped which were duplicate";
    }
    leaf cache-hit {
      type uint32;
      description
        "Total alarms which had the cache hit";
    }
    leaf cache-miss {
      type uint32;
      description
        "Total alarms which had the cache miss";
    }
  }

  grouping ALARM-TCA {
    description
      "Alarm TCA Attributes";
    leaf threshold-value {
      type string {
        length "0..20";
      }
      description
        "Alarm Threshold ";
    }
    leaf current-value {
      type string {
        length "0..20";
      }
      description
        "Alarm Threshold";
    }
    leaf bucket-type {
      type Timing-bucket;
      description
        "Timing Bucket";
    }
  }

  grouping ALARM-OTN {
    description
      "Alarm transport attributes";
    leaf direction {
      type Alarm-direction;
      description
        "Alarm direction ";
    }
    leaf notification-source {
      type Alarm-notification-src;
      description
        "Source of Alarm";
    }
  }

  grouping ALARM-MGR-SHOW-ALARM-DATA {
    description
      "Alarm mgr show alarm data";
    container otn {
      description
        "OTN feature specific alarm attributes";
      uses ALARM-OTN;
    }
    container tca {
      description
        "TCA feature specific alarm attributes";
      uses ALARM-TCA;
    }
    leaf description {
      type string {
        length "0..256";
      }
      description
        "Alarm description";
    }
    leaf location {
      type string {
        length "0..128";
      }
      description
        "Alarm location";
    }
    leaf aid {
      type string {
        length "0..128";
      }
      description
        "Alarm aid";
    }
    leaf tag {
      type string {
        length "0..128";
      }
      description
        "Alarm tag description";
    }
    leaf module {
      type string {
        length "0..128";
      }
      description
        "Alarm module description";
    }
    leaf eid {
      type string {
        length "0..128";
      }
      description
        "Alarm eid";
    }
    leaf reporting-agent-id {
      type uint32;
      description
        "Reporting agent id";
    }
    leaf pending-sync {
      type boolean;
      description
        "Pending async flag";
    }
    leaf severity {
      type Alarm-severity;
      description
        "Alarm severity";
    }
    leaf status {
      type Alarm-status;
      description
        "Alarm status";
    }
    leaf group {
      type Alarm-groups;
      description
        "Alarm group";
    }
    leaf set-time {
      type string {
        length "0..64";
      }
      description
        "Alarm set time";
    }
    leaf set-timestamp {
      type uint64;
      description
        "Alarm set time(timestamp format)";
    }
    leaf clear-time {
      type string {
        length "0..64";
      }
      description
        "Alarm clear time";
    }
    leaf clear-timestamp {
      type uint64;
      description
        "Alarm clear time(timestamp format)";
    }
    leaf service-affecting {
      type Alarm-service-affecting;
      description
        "Alarm service affecting";
    }
    leaf type {
      type Alarm-event;
      description
        "alarm event type";
    }
    leaf interface {
      type string {
        length "0..128";
      }
      description
        "Alarm interface name";
    }
    leaf alarm-name {
      type string {
        length "0..128";
      }
      description
        "Alarm name";
    }
    leaf object-mib-index-type {
      type Alarm-object-mib-index;
      description
        "Alarm Object MIB Index Type";
    }
    leaf alarm-type {
      type uint32;
      description
        "Alarm Type";
    }
    leaf object-mib-index {
      type uint32;
      description
        "Alarm Object MIB Index Type";
    }
    leaf trap-flag {
      type uint32;
      description
        "Trap Flag";
    }
  }

  grouping ALARM-MGR-SHOW-ALARM-INFO-CLI {
    description
      "alarm mgr show alarm info for CLI";
    list alarm-info {
      description
        "Alarm List";
      uses ALARM-MGR-SHOW-ALARM-DATA;
    }
  }
}
