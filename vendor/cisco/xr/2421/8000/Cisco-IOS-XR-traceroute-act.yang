module Cisco-IOS-XR-traceroute-act {
  namespace "http://cisco.com/ns/yang/Cisco-IOS-XR-traceroute-act";
  prefix traceroute-act;

  import cisco-semver {
    prefix semver;
  }
  include Cisco-IOS-XR-ipv4-traceroute-act;
  include Cisco-IOS-XR-ipv6-traceroute-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ping action package configuration.
     
     Copyright (c) 2016-2019, 2021-2023 by Cisco Systems, Inc.
     All rights reserved.";

  revision 2023-10-31 {
    description
      "Addition of dscp leaf";
  }
  revision 2022-12-06 {
    description
      "Additional leaves for google_b4_traceroute";
  }
  revision 2021-03-05 {
    description
      "Removed support for use-srv6-op-sid";
  }
  revision 2019-10-01 {
    description
      "Made changes to be RFC6087 compliant";
    semver:module-version "1.0.1";
  }
  revision 2019-04-05 {
    description
      "Establish semantic version baseline.";
  }
  revision 2018-10-01 {
    description
      "IOS XR 6.2.1 revision.";
  }

  rpc traceroute {
    description
      "Trace route to destination";
    input {
      container destination {
        presence "traceroute input";
        description
          "Trace route destination";
        uses TRACEROUTE-OPTIONS;
        uses IPV6-SPECIFIC-OPTIONS;
      }
      container ipv4 {
        presence "ipv4 traceroute";
        description
          "Trace route IPv4";
        uses TRACEROUTE-OPTIONS;
      }
      container ipv6 {
        presence "ipv6 traceroute";
        description
          "Trace route IPv6";
        uses IPV6-TRACEROUTE-INPUT;
      }
    }
    output {
      container traceroute-response {
        description
          "Trace route response";
        container ipv4 {
          presence "ipv4 traceroute output";
          description
            "Trace route IPv4 response";
          uses TRACEROUTE-OUTPUT;
        }
        container ipv6 {
          presence "ipv6 traceroute output";
          description
            "Trace route IPv6 response";
          uses TRACEROUTE-OUTPUT;
        }
      }
    }
  }
}
