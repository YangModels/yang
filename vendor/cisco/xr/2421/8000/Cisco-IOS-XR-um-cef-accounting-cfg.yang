module Cisco-IOS-XR-um-cef-accounting-cfg {
  namespace "http://cisco.com/ns/yang/Cisco-IOS-XR-um-cef-accounting-cfg";
  prefix um-cef-accounting-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cef-accounting package configuration.
     
     This YANG module augments the
     modules with configuration data.
     
     Copyright (c) 2021-2024 by Cisco Systems, Inc.
     All rights reserved.";

  revision 2024-03-13 {
    description
      "Changed description of HLB min-paths Leaf";
  }
  revision 2024-02-03 {
    description
      "Added container and leaf for load-balancing oor";
  }
  revision 2023-02-13 {
    description
      "Added container prefixes for srv6 accounting";
  }
  revision 2022-06-21 {
    description
      "Added container hierarchical-load-balancing";
  }
  revision 2021-02-10 {
    description
      "Initial release";
  }

  container cef {
    description
      "CEF configuration";
    container adjacency {
      description
        "Adjacency configuration";
      container route {
        description
          "Adjacency route configuration";
        container override {
          description
            "Set override options for adjacency routes";
          container rib {
            presence "Indicates a rib node is configured.";
            description
              "Set options for adjacency routes overriding RIB routes";
          }
        }
      }
    }
    container pbts {
      description
        "PBTS configuration";
      container class {
        description
          "Forward class configuration";
        list forward-class {
          must
            "fallback-to/fallback-class-number or fallback-to/any or
             fallback-to/drop";
          key "forward-class-number";
          description
            "Forward Class number";
          leaf forward-class-number {
            type union {
              type enumeration {
                enum "any" {
                  value 8;
                  description
                    "Any forward class";
                }
              }
              type uint32 {
                range "0..7" {
                  description
                    "Forward Class number";
                }
              }
            }
            description
              "Forward Class number";
          }
          container fallback-to {
            description
              "Fallback to configuration";
            leaf-list fallback-class-number {
              type uint32 {
                range "0..7" {
                  description
                    "Fallback Class number";
                }
              }
              must "not(../any or ../drop)";
              max-elements "7";
              description
                "Fallback to configuration";
            }
            container any {
              must "not(../fallback-class-number or ../drop)";
              presence "Indicates a any node is configured.";
              description
                "Fallback to any class";
            }
            container drop {
              must "not(../any or ../fallback-class-number)";
              presence "Indicates a drop node is configured.";
              description
                "Fallback to drop";
            }
          }
        }
      }
    }
    container platform {
      description
        "Platform parameters";
      container lsm {
        description
          "Label-switched-multicast parameters";
        leaf frr-holdtime {
          type uint32 {
            range "3..180" {
              description
                "Time in seconds";
            }
          }
          description
            "Time to keep FRR slots programmed post FRR";
        }
      }
    }
    container retry {
      description
        "Retry parameters";
      leaf service-time {
        type uint32 {
          range "1..15000" {
            description
              "Time in msec";
          }
        }
        description
          "Retry service time (default 50 msec)";
      }
      leaf timeout {
        type uint32 {
          range "1..30000" {
            description
              "Time in msec";
          }
        }
        description
          "Retry timeout (default 15 msec)";
      }
      leaf syslog-timer {
        type uint32 {
          range "0..86400" {
            description
              "Time in seconds (default 120 seconds)";
          }
        }
        description
          "Syslog timer in seconds(default 120 seconds), 0 to disable";
      }
    }
    container encap-sharing {
      description
        "Disable MPLS encapsulation sharing";
      container disable {
        presence "Indicates a disable node is configured.";
        description
          "Use this in conjunction with BGP per-prefix label mode";
      }
    }
    container consistent-hashing {
      description
        "Load balancing consistent hashing";
      container auto-recovery {
        presence "Indicates a auto-recovery node is configured.";
        description
          "Automatically recover to previous hash state";
      }
    }
    container proactive-arp-nd {
      description
        "Proactive ARP/ND";
      container enable {
        presence "Indicates a enable node is configured.";
        description
          "Enable proactive ARP/ND feature";
      }
    }
    leaf ltrace-multiplier {
      type uint32 {
        range "1..16" {
          description
            "numeric value of the multiplier";
        }
      }
      description
        "ltrace multiplier";
    }
    container load-balancing {
      description
        "Load balance parameters";
      container mode {
        description
          "Specify the mode";
        container hierarchical {
          description
            "Hierarchical";
          container ecmp {
            presence "Indicates a ecmp node is configured.";
            description
              "ecmp hierarchical-load-balancing";
            leaf min-paths {
              type uint32 {
                range "1..128" {
                  description
                    "Number of paths";
                }
              }
              description
                "Minimum paths for qualifying HLB. Paths exceeding the configured value will be installed in HLB mode";
            }
          }
          container ucmp {
            must "not(../ecmp)";
            presence "Indicates a ucmp node is configured.";
            description
              "ucmp hierarchical-load-balancing";
            leaf group-size {
              type uint32 {
                range "1..128" {
                  description
                    "Number of paths";
                }
              }
              description
                "UCMP group size for HLB";
            }
          }
        }
      }
      container recursive {
        presence "Indicates a recursive node is configured.";
        description
          "recursive route configuration";
        container oor {
          description
            "OOR configuration";
          container mode {
            description
              "Specify the mode";
            container dampening-and-dlb {
              presence "Indicates a dampening-and-dlb node is configured.";
              description
                "OOR handling configuration";
              container dampening {
                description
                  "mbb parameter";
                leaf resource-threshold {
                  type uint32 {
                    range "1..99" {
                      description
                        "mbb percentage";
                    }
                  }
                  must "../../max-duration";
                  description
                    "percentage threshold parameter";
                }
              }
              container dlb {
                description
                  "dlb parameter";
                leaf resource-threshold {
                  type uint32 {
                    range "1..99" {
                      description
                        "dlb percentage";
                    }
                  }
                  must "../../max-duration";
                  must "../../dampening/resource-threshold";
                  description
                    "percentage threshold parameter";
                }
              }
              leaf max-duration {
                type uint32 {
                  range "1..600" {
                    description
                      "Time in sec";
                  }
                }
                description
                  "max-duration time configuration";
              }
            }
          }
        }
      }
    }
    container hierarchical-load-balancing {
      description
        "Hierarchical load balancing. Deprecated from 24.2.1";
    }
  }
  container accounting {
    presence "Indicates a accounting node is configured.";
    description
      "Enable accounting";
    container interfaces {
      presence "Indicates a interfaces node is configured.";
      description
        "Enable interfaces submode";
      container mpls {
        presence "Indicates a mpls node is configured.";
        description
          "Enable MPLS accounting";
        container ipv4 {
          description
            "Enable IPv4 accounting";
          container rsvp-te {
            presence "Indicates a rsvp-te node is configured.";
            description
              "Enable RSVP-TE accounting";
          }
        }
      }
      container segment-routing {
        description
          "Enable Segment-Routing (SR) accounting";
        container mpls {
          presence "Indicates a mpls node is configured.";
          description
            "Enable SR MPLS accounting";
          container ipv4 {
            presence "Indicates a ipv4 node is configured.";
            description
              "Enable IPv4 accounting";
          }
          container ipv6 {
            presence "Indicates a ipv6 node is configured.";
            description
              "Enable IPv6 accounting";
          }
        }
      }
    }
    container prefixes {
      description
        "Enter prefixes submode";
      container ipv6 {
        description
          "IPv6";
        container mode {
          presence "Indicates a mode node is configured.";
          description
            "Configure Accounting mode";
          container per-prefix {
            description
              "Enable Per-prefix accounting";
            container per-nexthop {
              presence "Indicates a per-nexthop node is configured.";
              description
                "Enable Per-prefix per-nexthop accounting";
              container srv6-locators {
                presence "Indicates a srv6-locators node is configured.";
                description
                  "Segment-routing SRv6 locator prefixes only";
              }
            }
          }
        }
      }
    }
  }
}
