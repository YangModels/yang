module Cisco-IOS-XR-um-lpts-pifib-domain-cfg {
  namespace "http://cisco.com/ns/yang/Cisco-IOS-XR-um-lpts-pifib-domain-cfg";
  prefix um-lpts-pifib-domain-cfg;

  import Cisco-IOS-XR-types {
    prefix xr;
  }
  import Cisco-IOS-XR-um-location-cfg {
    prefix location;
  }
  import Cisco-IOS-XR-um-lpts-pifib-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-pifib-domain package configuration.
     
     This YANG module augments the
     modules with configuration data.
     
     Copyright (c) 2021-2022 by Cisco Systems, Inc.
     All rights reserved.";

  revision 2022-07-28 {
    description
      "Added new nodes under flow/ipsec, l2tpv2, pim and udp";
  }
  revision 2022-07-11 {
    description
      "Added missing description statement to nodes";
  }
  revision 2021-07-14 {
    description
      "Added the new feature nodes cnbng-gtpu and cnbng-pfcp";
  }
  revision 2020-09-17 {
    description
      "Initial release";
  }

  feature pifib_domains_config_check {
    description
      "pifib domains config check";
  }

  feature pifib_xipc_throt_policer_config_check {
    description
      "pifib xipc throt policer config check";
  }

  grouping LPTS-POLICE {
    description
      "Grouping for lpts-police";
    container domains {
      description
        "ingress domains configuration command";
      list domain {
        key "domain-name";
        description
          "ingress domains configuration command";
        leaf domain-name {
          type xr:Cisco-ios-xr-string {
            length "1..32" {
              description
                "Domain name";
            }
            pattern "[a-z0-9A-Z][-_.:a-z0-9A-Z]*";
          }
          description
            "ingress domains configuration command";
        }
        container flow {
          description
            "lpts flow type";
          container fragment {
            description
              "Fragmented IP packets";
            leaf rate {
              type uint32 {
                range "0..4294967295" {
                  description
                    "Packets Per Second (actual Min and Max range depends on platform)";
                }
              }
              description
                "Rate in PPS";
            }
          }
          container ospf {
            description
              "OSPF ";
            container unicast {
              description
                "Unicast ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container multicast {
              description
                "Multicast";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
          }
          container isis {
            description
              "ISIS ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container bfd {
            description
              "BFD ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
            container multipath {
              description
                "Multipath ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container blb {
              description
                "BLB ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container singlepath {
              description
                "Singlepath ";
              leaf rate {
                type uint32 {
                  range "0..4294967295" {
                    description
                      "Packets Per Second (actual Min and Max range depends on platform)";
                  }
                }
                description
                  "Rate in PPS";
              }
            }
          }
          container bgp {
            description
              "BGP ";
            container known {
              description
                "Known ";
              leaf rate {
                type uint32 {
                  range "0..4294967295" {
                    description
                      "Packets Per Second (actual Min and Max range depends on platform)";
                  }
                }
                description
                  "Rate in PPS";
              }
            }
            container configured {
              description
                "Configured";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container pim {
            description
              "PIM ";
            container unicast {
              description
                "Unicast ";
              leaf rate {
                type uint32 {
                  range "0..4294967295" {
                    description
                      "Packets Per Second (actual Min and Max range depends on platform)";
                  }
                }
                description
                  "Rate in PPS";
              }
            }
            container multicast {
              description
                "Multicast ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
          }
          container igmp {
            description
              "IGMP ";
            leaf rate {
              type uint32 {
                range "0..4294967295" {
                  description
                    "Packets Per Second (actual Min and Max range depends on platform)";
                }
              }
              description
                "Rate in PPS";
            }
          }
          container icmp {
            description
              "ICMP ";
            container local {
              description
                "Local interest packets ";
              leaf rate {
                type uint32 {
                  range "0..4294967295" {
                    description
                      "Packets Per Second (actual Min and Max range depends on platform)";
                  }
                }
                description
                  "Rate in PPS";
              }
            }
            container application {
              description
                "Specific application packets ";
              leaf rate {
                type uint32 {
                  range "0..4294967295" {
                    description
                      "Packets Per Second (actual Min and Max range depends on platform)";
                  }
                }
                description
                  "Rate in PPS";
              }
            }
            container control {
              description
                "Control packets ";
              leaf rate {
                type uint32 {
                  range "0..4294967295" {
                    description
                      "Packets Per Second (actual Min and Max range depends on platform)";
                  }
                }
                description
                  "Rate in PPS";
              }
            }
            container default {
              description
                "Default packets ";
              leaf rate {
                type uint32 {
                  range "0..4294967295" {
                    description
                      "Packets Per Second (actual Min and Max range depends on platform)";
                  }
                }
                description
                  "Rate in PPS";
              }
            }
            container generic {
              description
                "Generic application packets ";
              container echo-reply {
                description
                  "Echo-reply packets ";
                leaf rate {
                  type uint32 {
                    range "0..4294967295" {
                      description
                        "Packets Per Second (actual Min and Max range depends on platform)";
                    }
                  }
                  description
                    "Rate in PPS";
                }
              }
            }
          }
          container ldp {
            description
              "LDP ";
            container tcp {
              description
                "TCP ";
              container known {
                description
                  "Known ";
                leaf rate {
                  type uint32 {
                    range "0..4294967295" {
                      description
                        "Packets Per Second (actual Min and Max range depends on platform)";
                    }
                  }
                  description
                    "Rate in PPS";
                }
              }
              container configured {
                description
                  "Configured";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container udp {
              description
                "UDP ";
              leaf rate {
                type uint32 {
                  range "0..4294967295" {
                    description
                      "Packets Per Second (actual Min and Max range depends on platform)";
                  }
                }
                description
                  "Rate in PPS";
              }
            }
          }
          container all-routers {
            description
              "All Routers";
            leaf rate {
              type uint32 {
                range "0..4294967295" {
                  description
                    "Packets Per Second (actual Min and Max range depends on platform)";
                }
              }
              description
                "Rate in PPS";
            }
          }
          container lmp {
            description
              "LMP ";
            container tcp {
              description
                "TCP ";
              container known {
                description
                  "Known ";
                leaf rate {
                  type uint32 {
                    range "0..4294967295" {
                      description
                        "Packets Per Second (actual Min and Max range depends on platform)";
                    }
                  }
                  description
                    "Rate in PPS";
                }
              }
              container configured {
                description
                  "Configured";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container udp {
              description
                "UDP ";
              leaf rate {
                type uint32 {
                  range "0..4294967295" {
                    description
                      "Packets Per Second (actual Min and Max range depends on platform)";
                  }
                }
                description
                  "Rate in PPS";
              }
            }
          }
          container rsvp {
            description
              "RSVP ";
            container default {
              description
                "RSVP Default ";
              leaf rate {
                type uint32 {
                  range "0..4294967295" {
                    description
                      "Packets Per Second (actual Min and Max range depends on platform)";
                  }
                }
                description
                  "Rate in PPS";
              }
            }
            container known {
              description
                "RSVP Known ";
              leaf rate {
                type uint32 {
                  range "0..4294967295" {
                    description
                      "Packets Per Second (actual Min and Max range depends on platform)";
                  }
                }
                description
                  "Rate in PPS";
              }
            }
            container udp {
              description
                "UDP";
              leaf rate {
                type uint32 {
                  range "0..4294967295" {
                    description
                      "Packets Per Second (actual Min and Max range depends on platform)";
                  }
                }
                description
                  "Rate in PPS";
              }
            }
          }
          container ike {
            description
              "IKE ";
            leaf rate {
              type uint32 {
                range "0..4294967295" {
                  description
                    "Packets Per Second (actual Min and Max range depends on platform)";
                }
              }
              description
                "Rate in PPS";
            }
          }
          container ipsec {
            description
              "IPSEC ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container msdp {
            description
              "MSDP ";
            container known {
              description
                "Known ";
              leaf rate {
                type uint32 {
                  range "0..4294967295" {
                    description
                      "Packets Per Second (actual Min and Max range depends on platform)";
                  }
                }
                description
                  "Rate in PPS";
              }
            }
            container configured {
              description
                "Configured";
              leaf rate {
                type uint32 {
                  range "0..4294967295" {
                    description
                      "Packets Per Second (actual Min and Max range depends on platform)";
                  }
                }
                description
                  "Rate in PPS";
              }
            }
            container default {
              description
                "Default";
              leaf rate {
                type uint32 {
                  range "0..4294967295" {
                    description
                      "Packets Per Second (actual Min and Max range depends on platform)";
                  }
                }
                description
                  "Rate in PPS";
              }
            }
          }
          container snmp {
            description
              "SNMP ";
            leaf rate {
              type uint32 {
                range "0..4294967295" {
                  description
                    "Packets Per Second (actual Min and Max range depends on platform)";
                }
              }
              description
                "Rate in PPS";
            }
          }
          container ssh {
            description
              "SSH ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container http {
            description
              "HTTP ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container shttp {
            description
              "SHTTP ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container telnet {
            description
              "TELNET ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container css {
            description
              "CSS ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container rsh {
            description
              "RSH ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container udp {
            description
              "UDP ";
            container known {
              description
                "Known ";
              leaf rate {
                type uint32 {
                  range "0..4294967295" {
                    description
                      "Packets Per Second (actual Min and Max range depends on platform)";
                  }
                }
                description
                  "Rate in PPS";
              }
            }
            container listen {
              description
                "Listen ";
              leaf rate {
                type uint32 {
                  range "0..4294967295" {
                    description
                      "Packets Per Second (actual Min and Max range depends on platform)";
                  }
                }
                description
                  "Rate in PPS";
              }
            }
            container configured {
              description
                "Config peer ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container tcp {
            description
              "TCP ";
            container known {
              description
                "Known ";
              leaf rate {
                type uint32 {
                  range "0..4294967295" {
                    description
                      "Packets Per Second (actual Min and Max range depends on platform)";
                  }
                }
                description
                  "Rate in PPS";
              }
            }
            container listen {
              description
                "Listen ";
              leaf rate {
                type uint32 {
                  range "0..4294967295" {
                    description
                      "Packets Per Second (actual Min and Max range depends on platform)";
                  }
                }
                description
                  "Rate in PPS";
              }
            }
            container configured {
              description
                "Configured ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container multicast {
            description
              "Multicast ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container raw {
            description
              "Raw ";
            container listen {
              description
                "Listen ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container ip-sla {
            description
              "IP-SLA ";
            leaf rate {
              type uint32 {
                range "0..4294967295" {
                  description
                    "Packets Per Second (actual Min and Max range depends on platform)";
                }
              }
              description
                "Rate in PPS";
            }
          }
          container eigrp {
            description
              "EIGRP ";
            leaf rate {
              type uint32 {
                range "0..4294967295" {
                  description
                    "Packets Per Second (actual Min and Max range depends on platform)";
                }
              }
              description
                "Rate in PPS";
            }
          }
          container rip {
            description
              "RIP ";
            leaf rate {
              type uint32 {
                range "0..4294967295" {
                  description
                    "Packets Per Second (actual Min and Max range depends on platform)";
                }
              }
              description
                "Rate in PPS";
            }
          }
          container l2tpv3 {
            description
              "L2TPv3 ";
            leaf rate {
              type uint32 {
                range "0..4294967295" {
                  description
                    "Packets Per Second (actual Min and Max range depends on platform)";
                }
              }
              description
                "Rate in PPS";
            }
          }
          container pcep {
            description
              "PCEP ";
            leaf rate {
              type uint32 {
                range "0..4294967295" {
                  description
                    "Packets Per Second (actual Min and Max range depends on platform)";
                }
              }
              description
                "Rate in PPS";
            }
          }
          container gre {
            description
              "GRE ";
            leaf rate {
              type uint32 {
                range "0..4294967295" {
                  description
                    "Packets Per Second (actual Min and Max range depends on platform)";
                }
              }
              description
                "Rate in PPS";
            }
          }
          container vrrp {
            description
              "VRRP ";
            leaf rate {
              type uint32 {
                range "0..4294967295" {
                  description
                    "Packets Per Second (actual Min and Max range depends on platform)";
                }
              }
              description
                "Rate in PPS";
            }
          }
          container hsrp {
            description
              "HSRP ";
            leaf rate {
              type uint32 {
                range "0..4294967295" {
                  description
                    "Packets Per Second (actual Min and Max range depends on platform)";
                }
              }
              description
                "Rate in PPS";
            }
          }
          container mpls {
            description
              "MPLS ";
            container oam {
              description
                "Oam ";
              leaf rate {
                type uint32 {
                  range "0..4294967295" {
                    description
                      "Packets Per Second (actual Min and Max range depends on platform)";
                  }
                }
                description
                  "Rate in PPS";
              }
            }
          }
          container l2tpv2 {
            description
              "L2TPv2 ";
            container default {
              description
                "Default ";
              leaf rate {
                type uint32 {
                  range "0..4294967295" {
                    description
                      "Packets Per Second (actual Min and Max range depends on platform)";
                  }
                }
                description
                  "Rate in PPS";
              }
            }
            container known {
              description
                "Known ";
              leaf rate {
                type uint32 {
                  range "0..4294967295" {
                    description
                      "Packets Per Second (actual Min and Max range depends on platform)";
                  }
                }
                description
                  "Rate in PPS";
              }
            }
            container fragment {
              description
                "Fragmented IP packets";
              leaf rate {
                type uint32 {
                  range "0..4294967295" {
                    description
                      "Packets Per Second (actual Min and Max range depends on platform)";
                  }
                }
                description
                  "Rate in PPS";
              }
            }
          }
          container dns {
            description
              "DNS ";
            leaf rate {
              type uint32 {
                range "0..4294967295" {
                  description
                    "Packets Per Second (actual Min and Max range depends on platform)";
                }
              }
              description
                "Rate in PPS";
            }
          }
          container radius {
            description
              "RADIUS ";
            leaf rate {
              type uint32 {
                range "0..4294967295" {
                  description
                    "Packets Per Second (actual Min and Max range depends on platform)";
                }
              }
              description
                "Rate in PPS";
            }
          }
          container tacacs {
            description
              "TACACS ";
            leaf rate {
              type uint32 {
                range "0..4294967295" {
                  description
                    "Packets Per Second (actual Min and Max range depends on platform)";
                }
              }
              description
                "Rate in PPS";
            }
          }
          container ntp {
            description
              "NTP ";
            container default {
              description
                "Default ";
              leaf rate {
                type uint32 {
                  range "0..4294967295" {
                    description
                      "Packets Per Second (actual Min and Max range depends on platform)";
                  }
                }
                description
                  "Rate in PPS";
              }
            }
            container known {
              description
                "Known ";
              leaf rate {
                type uint32 {
                  range "0..4294967295" {
                    description
                      "Packets Per Second (actual Min and Max range depends on platform)";
                  }
                }
                description
                  "Rate in PPS";
              }
            }
          }
          container mipv6 {
            description
              "MIPv6 ";
            leaf rate {
              type uint32 {
                range "0..4294967295" {
                  description
                    "Packets Per Second (actual Min and Max range depends on platform)";
                }
              }
              description
                "Rate in PPS";
            }
          }
          container amt {
            description
              "AMT ";
            leaf rate {
              type uint32 {
                range "0..4294967295" {
                  description
                    "Packets Per Second (actual Min and Max range depends on platform)";
                }
              }
              description
                "Rate in PPS";
            }
          }
          container sdac {
            description
              "SDAC-TCP ";
            leaf rate {
              type uint32 {
                range "0..4294967295" {
                  description
                    "Packets Per Second (actual Min and Max range depends on platform)";
                }
              }
              description
                "Rate in PPS";
            }
          }
          container radius-coa {
            description
              "RADIUS COA ";
            leaf rate {
              type uint32 {
                range "0..4294967295" {
                  description
                    "Packets Per Second (actual Min and Max range depends on platform)";
                }
              }
              description
                "Rate in PPS";
            }
          }
          container rel-udp {
            description
              "Syslog/netflow packets";
            leaf rate {
              type uint32 {
                range "0..4294967295" {
                  description
                    "Packets Per Second (actual Min and Max range depends on platform)";
                }
              }
              description
                "Rate in PPS";
            }
          }
          container dhcpv4 {
            description
              "DHCPv4 ";
            leaf rate {
              type uint32 {
                range "0..4294967295" {
                  description
                    "Packets Per Second (actual Min and Max range depends on platform)";
                }
              }
              description
                "Rate in PPS";
            }
          }
          container dhcpv6 {
            description
              "DHCPv6 ";
            leaf rate {
              type uint32 {
                range "0..4294967295" {
                  description
                    "Packets Per Second (actual Min and Max range depends on platform)";
                }
              }
              description
                "Rate in PPS";
            }
          }
          container onepk {
            description
              "ONEPK ";
            leaf rate {
              type uint32 {
                range "0..4294967295" {
                  description
                    "Packets Per Second (actual Min and Max range depends on platform)";
                }
              }
              description
                "Rate in PPS";
            }
          }
          container tpa {
            description
              "Third Party Applications";
            leaf rate {
              type uint32 {
                range "0..4294967295" {
                  description
                    "Packets Per Second (actual Min and Max range depends on platform)";
                }
              }
              description
                "Rate in PPS";
            }
          }
          container ietf-bob {
            description
              "IETF BOB Packets";
            leaf rate {
              type uint32 {
                range "0..4294967295" {
                  description
                    "Packets Per Second (actual Min and Max range depends on platform)";
                }
              }
              description
                "Rate in PPS";
            }
          }
          container xipc {
            if-feature "pifib_xipc_throt_policer_config_check";
            description
              "XIPC rate limit";
            leaf rate {
              type uint32 {
                range "0..4294967295" {
                  description
                    "Packets Per Second (actual Min and Max range depends on platform)";
                }
              }
              description
                "Rate in PPS";
            }
          }
          container pm-twamp {
            description
              "PM TWAMP Packets";
            leaf rate {
              type uint32 {
                range "0..4294967295" {
                  description
                    "Packets Per Second (actual Min and Max range depends on platform)";
                }
              }
              description
                "Rate in PPS";
            }
          }
          container cnbng-gtpu {
            description
              "CnBNG GTPU Packets";
            leaf rate {
              type uint32 {
                range "0..4294967295" {
                  description
                    "Packets Per Second (actual Min and Max range depends on platform)";
                }
              }
              description
                "Rate in PPS";
            }
          }
          container cnbng-pfcp {
            description
              "CnBNG PFCP Packets";
            leaf rate {
              type uint32 {
                range "0..4294967295" {
                  description
                    "Packets Per Second (actual Min and Max range depends on platform)";
                }
              }
              description
                "Rate in PPS";
            }
          }
        }
      }
    }
  }

  grouping LOCATION-BODY {
    description
      "Grouping for location";
    container domains {
      description
        "ingress domains configuration command";
      list domain {
        key "domain-name";
        description
          "ingress domains configuration command";
        leaf domain-name {
          type xr:Cisco-ios-xr-string {
            length "1..32" {
              description
                "Domain name";
            }
            pattern "[a-z0-9A-Z][-_.:a-z0-9A-Z]*";
          }
          description
            "ingress domains configuration command";
        }
        container flow {
          description
            "lpts flow type";
          container fragment {
            description
              "Fragmented IP packets";
            leaf rate {
              type uint32 {
                range "0..4294967295" {
                  description
                    "Packets Per Second (actual Min and Max range depends on platform)";
                }
              }
              description
                "Rate in PPS";
            }
          }
          container ospf {
            description
              "OSPF ";
            container unicast {
              description
                "Unicast ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container multicast {
              description
                "Multicast";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
          }
          container isis {
            description
              "ISIS ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container bfd {
            description
              "BFD ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
            container multipath {
              description
                "Multipath ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container blb {
              description
                "BLB ";
              container known {
                description
                  "Known ";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container singlepath {
              description
                "Singlepath ";
              leaf rate {
                type uint32 {
                  range "0..4294967295" {
                    description
                      "Packets Per Second (actual Min and Max range depends on platform)";
                  }
                }
                description
                  "Rate in PPS";
              }
            }
          }
          container bgp {
            description
              "BGP ";
            container known {
              description
                "Known ";
              leaf rate {
                type uint32 {
                  range "0..4294967295" {
                    description
                      "Packets Per Second (actual Min and Max range depends on platform)";
                  }
                }
                description
                  "Rate in PPS";
              }
            }
            container configured {
              description
                "Configured";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container pim {
            description
              "PIM ";
            container unicast {
              description
                "Unicast ";
              leaf rate {
                type uint32 {
                  range "0..4294967295" {
                    description
                      "Packets Per Second (actual Min and Max range depends on platform)";
                  }
                }
                description
                  "Rate in PPS";
              }
            }
          }
          container igmp {
            description
              "IGMP ";
            leaf rate {
              type uint32 {
                range "0..4294967295" {
                  description
                    "Packets Per Second (actual Min and Max range depends on platform)";
                }
              }
              description
                "Rate in PPS";
            }
          }
          container icmp {
            description
              "ICMP ";
            container local {
              description
                "Local interest packets ";
              leaf rate {
                type uint32 {
                  range "0..4294967295" {
                    description
                      "Packets Per Second (actual Min and Max range depends on platform)";
                  }
                }
                description
                  "Rate in PPS";
              }
            }
            container application {
              description
                "Specific application packets ";
              leaf rate {
                type uint32 {
                  range "0..4294967295" {
                    description
                      "Packets Per Second (actual Min and Max range depends on platform)";
                  }
                }
                description
                  "Rate in PPS";
              }
            }
            container control {
              description
                "Control packets ";
              leaf rate {
                type uint32 {
                  range "0..4294967295" {
                    description
                      "Packets Per Second (actual Min and Max range depends on platform)";
                  }
                }
                description
                  "Rate in PPS";
              }
            }
            container default {
              description
                "Default packets ";
              leaf rate {
                type uint32 {
                  range "0..4294967295" {
                    description
                      "Packets Per Second (actual Min and Max range depends on platform)";
                  }
                }
                description
                  "Rate in PPS";
              }
            }
            container generic {
              description
                "Generic application packets ";
              container echo-reply {
                description
                  "Echo-reply packets ";
                leaf rate {
                  type uint32 {
                    range "0..4294967295" {
                      description
                        "Packets Per Second (actual Min and Max range depends on platform)";
                    }
                  }
                  description
                    "Rate in PPS";
                }
              }
            }
          }
          container ldp {
            description
              "LDP ";
            container tcp {
              description
                "TCP ";
              container known {
                description
                  "Known ";
                leaf rate {
                  type uint32 {
                    range "0..4294967295" {
                      description
                        "Packets Per Second (actual Min and Max range depends on platform)";
                    }
                  }
                  description
                    "Rate in PPS";
                }
              }
              container configured {
                description
                  "Configured";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container udp {
              description
                "UDP ";
              leaf rate {
                type uint32 {
                  range "0..4294967295" {
                    description
                      "Packets Per Second (actual Min and Max range depends on platform)";
                  }
                }
                description
                  "Rate in PPS";
              }
            }
          }
          container all-routers {
            description
              "All Routers";
            leaf rate {
              type uint32 {
                range "0..4294967295" {
                  description
                    "Packets Per Second (actual Min and Max range depends on platform)";
                }
              }
              description
                "Rate in PPS";
            }
          }
          container lmp {
            description
              "LMP ";
            container tcp {
              description
                "TCP ";
              container known {
                description
                  "Known ";
                leaf rate {
                  type uint32 {
                    range "0..4294967295" {
                      description
                        "Packets Per Second (actual Min and Max range depends on platform)";
                    }
                  }
                  description
                    "Rate in PPS";
                }
              }
              container configured {
                description
                  "Configured";
                leaf rate {
                  type uint32 {
                    range "0..4294967295" {
                      description
                        "Packets Per Second (actual Min and Max range depends on platform)";
                    }
                  }
                  description
                    "Rate in PPS";
                }
              }
              container default {
                description
                  "Default ";
                leaf rate {
                  type uint32 {
                    range "0..4294967295" {
                      description
                        "Packets Per Second (actual Min and Max range depends on platform)";
                    }
                  }
                  description
                    "Rate in PPS";
                }
              }
            }
            container udp {
              description
                "UDP ";
              leaf rate {
                type uint32 {
                  range "0..4294967295" {
                    description
                      "Packets Per Second (actual Min and Max range depends on platform)";
                  }
                }
                description
                  "Rate in PPS";
              }
            }
          }
          container rsvp {
            description
              "RSVP ";
            container default {
              description
                "RSVP Default ";
              leaf rate {
                type uint32 {
                  range "0..4294967295" {
                    description
                      "Packets Per Second (actual Min and Max range depends on platform)";
                  }
                }
                description
                  "Rate in PPS";
              }
            }
            container known {
              description
                "RSVP Known ";
              leaf rate {
                type uint32 {
                  range "0..4294967295" {
                    description
                      "Packets Per Second (actual Min and Max range depends on platform)";
                  }
                }
                description
                  "Rate in PPS";
              }
            }
            container udp {
              description
                "UDP";
              leaf rate {
                type uint32 {
                  range "0..4294967295" {
                    description
                      "Packets Per Second (actual Min and Max range depends on platform)";
                  }
                }
                description
                  "Rate in PPS";
              }
            }
          }
          container ike {
            description
              "IKE ";
            leaf rate {
              type uint32 {
                range "0..4294967295" {
                  description
                    "Packets Per Second (actual Min and Max range depends on platform)";
                }
              }
              description
                "Rate in PPS";
            }
          }
          container ipsec {
            description
              "IPSEC ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
            container fragment {
              description
                "Fragmented IP packets";
              leaf rate {
                type uint32 {
                  range "0..4294967295" {
                    description
                      "Packets Per Second (actual Min and Max range depends on platform)";
                  }
                }
                description
                  "Rate in PPS";
              }
            }
          }
          container msdp {
            description
              "MSDP ";
            container known {
              description
                "Known ";
              leaf rate {
                type uint32 {
                  range "0..4294967295" {
                    description
                      "Packets Per Second (actual Min and Max range depends on platform)";
                  }
                }
                description
                  "Rate in PPS";
              }
            }
            container configured {
              description
                "Configured";
              leaf rate {
                type uint32 {
                  range "0..4294967295" {
                    description
                      "Packets Per Second (actual Min and Max range depends on platform)";
                  }
                }
                description
                  "Rate in PPS";
              }
            }
            container default {
              description
                "Default";
              leaf rate {
                type uint32 {
                  range "0..4294967295" {
                    description
                      "Packets Per Second (actual Min and Max range depends on platform)";
                  }
                }
                description
                  "Rate in PPS";
              }
            }
          }
          container snmp {
            description
              "SNMP ";
            leaf rate {
              type uint32 {
                range "0..4294967295" {
                  description
                    "Packets Per Second (actual Min and Max range depends on platform)";
                }
              }
              description
                "Rate in PPS";
            }
          }
          container ssh {
            description
              "SSH ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container http {
            description
              "HTTP ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container shttp {
            description
              "SHTTP ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container telnet {
            description
              "TELNET ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container css {
            description
              "CSS ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container rsh {
            description
              "RSH ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container udp {
            description
              "UDP ";
            container known {
              description
                "Known ";
              leaf rate {
                type uint32 {
                  range "0..4294967295" {
                    description
                      "Packets Per Second (actual Min and Max range depends on platform)";
                  }
                }
                description
                  "Rate in PPS";
              }
            }
            container listen {
              description
                "Listen ";
              leaf rate {
                type uint32 {
                  range "0..4294967295" {
                    description
                      "Packets Per Second (actual Min and Max range depends on platform)";
                  }
                }
                description
                  "Rate in PPS";
              }
            }
            container configured {
              description
                "Config peer ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container tcp {
            description
              "TCP ";
            container known {
              description
                "Known ";
              leaf rate {
                type uint32 {
                  range "0..4294967295" {
                    description
                      "Packets Per Second (actual Min and Max range depends on platform)";
                  }
                }
                description
                  "Rate in PPS";
              }
            }
            container listen {
              description
                "Listen ";
              leaf rate {
                type uint32 {
                  range "0..4294967295" {
                    description
                      "Packets Per Second (actual Min and Max range depends on platform)";
                  }
                }
                description
                  "Rate in PPS";
              }
            }
            container configured {
              description
                "Configured ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container multicast {
            description
              "Multicast ";
            container known {
              description
                "Known ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container raw {
            description
              "Raw ";
            container listen {
              description
                "Listen ";
              leaf rate {
                type uint32 {
                  range "0..4294967295" {
                    description
                      "Packets Per Second (actual Min and Max range depends on platform)";
                  }
                }
                description
                  "Rate in PPS";
              }
            }
            container default {
              description
                "Default ";
              leaf rate {
                type uint32 {
                  range "0..4294967295" {
                    description
                      "Packets Per Second (actual Min and Max range depends on platform)";
                  }
                }
                description
                  "Rate in PPS";
              }
            }
          }
          container ip-sla {
            description
              "IP-SLA ";
            leaf rate {
              type uint32 {
                range "0..4294967295" {
                  description
                    "Packets Per Second (actual Min and Max range depends on platform)";
                }
              }
              description
                "Rate in PPS";
            }
          }
          container eigrp {
            description
              "EIGRP ";
            leaf rate {
              type uint32 {
                range "0..4294967295" {
                  description
                    "Packets Per Second (actual Min and Max range depends on platform)";
                }
              }
              description
                "Rate in PPS";
            }
          }
          container rip {
            description
              "RIP ";
            leaf rate {
              type uint32 {
                range "0..4294967295" {
                  description
                    "Packets Per Second (actual Min and Max range depends on platform)";
                }
              }
              description
                "Rate in PPS";
            }
          }
          container l2tpv3 {
            description
              "L2TPv3 ";
            leaf rate {
              type uint32 {
                range "0..4294967295" {
                  description
                    "Packets Per Second (actual Min and Max range depends on platform)";
                }
              }
              description
                "Rate in PPS";
            }
          }
          container pcep {
            description
              "PCEP ";
            leaf rate {
              type uint32 {
                range "0..4294967295" {
                  description
                    "Packets Per Second (actual Min and Max range depends on platform)";
                }
              }
              description
                "Rate in PPS";
            }
          }
          container gre {
            description
              "GRE ";
            leaf rate {
              type uint32 {
                range "0..4294967295" {
                  description
                    "Packets Per Second (actual Min and Max range depends on platform)";
                }
              }
              description
                "Rate in PPS";
            }
          }
          container vrrp {
            description
              "VRRP ";
            leaf rate {
              type uint32 {
                range "0..4294967295" {
                  description
                    "Packets Per Second (actual Min and Max range depends on platform)";
                }
              }
              description
                "Rate in PPS";
            }
          }
          container hsrp {
            description
              "HSRP ";
            leaf rate {
              type uint32 {
                range "0..4294967295" {
                  description
                    "Packets Per Second (actual Min and Max range depends on platform)";
                }
              }
              description
                "Rate in PPS";
            }
          }
          container mpls {
            description
              "MPLS ";
            container oam {
              description
                "Oam ";
              leaf rate {
                type uint32 {
                  range "0..4294967295" {
                    description
                      "Packets Per Second (actual Min and Max range depends on platform)";
                  }
                }
                description
                  "Rate in PPS";
              }
            }
          }
          container l2tpv2 {
            description
              "L2TPv2 ";
            container default {
              description
                "Default ";
              leaf rate {
                type uint32 {
                  range "0..4294967295" {
                    description
                      "Packets Per Second (actual Min and Max range depends on platform)";
                  }
                }
                description
                  "Rate in PPS";
              }
            }
            container known {
              description
                "Known ";
              leaf rate {
                type uint32 {
                  range "0..4294967295" {
                    description
                      "Packets Per Second (actual Min and Max range depends on platform)";
                  }
                }
                description
                  "Rate in PPS";
              }
            }
          }
          container dns {
            description
              "DNS ";
            leaf rate {
              type uint32 {
                range "0..4294967295" {
                  description
                    "Packets Per Second (actual Min and Max range depends on platform)";
                }
              }
              description
                "Rate in PPS";
            }
          }
          container radius {
            description
              "RADIUS ";
            leaf rate {
              type uint32 {
                range "0..4294967295" {
                  description
                    "Packets Per Second (actual Min and Max range depends on platform)";
                }
              }
              description
                "Rate in PPS";
            }
          }
          container tacacs {
            description
              "TACACS ";
            leaf rate {
              type uint32 {
                range "0..4294967295" {
                  description
                    "Packets Per Second (actual Min and Max range depends on platform)";
                }
              }
              description
                "Rate in PPS";
            }
          }
          container ntp {
            description
              "NTP ";
            container default {
              description
                "Default ";
              leaf rate {
                type uint32 {
                  range "0..4294967295" {
                    description
                      "Packets Per Second (actual Min and Max range depends on platform)";
                  }
                }
                description
                  "Rate in PPS";
              }
            }
            container known {
              description
                "Known ";
              leaf rate {
                type uint32 {
                  range "0..4294967295" {
                    description
                      "Packets Per Second (actual Min and Max range depends on platform)";
                  }
                }
                description
                  "Rate in PPS";
              }
            }
          }
          container mipv6 {
            description
              "MIPv6 ";
            leaf rate {
              type uint32 {
                range "0..4294967295" {
                  description
                    "Packets Per Second (actual Min and Max range depends on platform)";
                }
              }
              description
                "Rate in PPS";
            }
          }
          container amt {
            description
              "AMT ";
            leaf rate {
              type uint32 {
                range "0..4294967295" {
                  description
                    "Packets Per Second (actual Min and Max range depends on platform)";
                }
              }
              description
                "Rate in PPS";
            }
          }
          container sdac {
            description
              "SDAC-TCP ";
            leaf rate {
              type uint32 {
                range "0..4294967295" {
                  description
                    "Packets Per Second (actual Min and Max range depends on platform)";
                }
              }
              description
                "Rate in PPS";
            }
          }
          container radius-coa {
            description
              "RADIUS COA ";
            leaf rate {
              type uint32 {
                range "0..4294967295" {
                  description
                    "Packets Per Second (actual Min and Max range depends on platform)";
                }
              }
              description
                "Rate in PPS";
            }
          }
          container rel-udp {
            description
              "Syslog/netflow packets";
            leaf rate {
              type uint32 {
                range "0..4294967295" {
                  description
                    "Packets Per Second (actual Min and Max range depends on platform)";
                }
              }
              description
                "Rate in PPS";
            }
          }
          container dhcpv4 {
            description
              "DHCPv4 ";
            leaf rate {
              type uint32 {
                range "0..4294967295" {
                  description
                    "Packets Per Second (actual Min and Max range depends on platform)";
                }
              }
              description
                "Rate in PPS";
            }
          }
          container dhcpv6 {
            description
              "DHCPv6 ";
            leaf rate {
              type uint32 {
                range "0..4294967295" {
                  description
                    "Packets Per Second (actual Min and Max range depends on platform)";
                }
              }
              description
                "Rate in PPS";
            }
          }
          container onepk {
            description
              "ONEPK ";
            leaf rate {
              type uint32 {
                range "0..4294967295" {
                  description
                    "Packets Per Second (actual Min and Max range depends on platform)";
                }
              }
              description
                "Rate in PPS";
            }
          }
          container tpa {
            description
              "Third Party Applications";
            leaf rate {
              type uint32 {
                range "0..4294967295" {
                  description
                    "Packets Per Second (actual Min and Max range depends on platform)";
                }
              }
              description
                "Rate in PPS";
            }
          }
          container ietf-bob {
            description
              "IETF BOB Packets";
            leaf rate {
              type uint32 {
                range "0..4294967295" {
                  description
                    "Packets Per Second (actual Min and Max range depends on platform)";
                }
              }
              description
                "Rate in PPS";
            }
          }
          container xipc {
            if-feature "pifib_xipc_throt_policer_config_check";
            description
              "XIPC rate limit";
            leaf rate {
              type uint32 {
                range "0..4294967295" {
                  description
                    "Packets Per Second (actual Min and Max range depends on platform)";
                }
              }
              description
                "Rate in PPS";
            }
          }
          container pm-twamp {
            description
              "PM TWAMP Packets";
            leaf rate {
              type uint32 {
                range "0..4294967295" {
                  description
                    "Packets Per Second (actual Min and Max range depends on platform)";
                }
              }
              description
                "Rate in PPS";
            }
          }
          container cnbng-gtpu {
            description
              "CnBNG GTPU Packets";
            leaf rate {
              type uint32 {
                range "0..4294967295" {
                  description
                    "Packets Per Second (actual Min and Max range depends on platform)";
                }
              }
              description
                "Rate in PPS";
            }
          }
          container cnbng-pfcp {
            description
              "CnBNG PFCP Packets";
            leaf rate {
              type uint32 {
                range "0..4294967295" {
                  description
                    "Packets Per Second (actual Min and Max range depends on platform)";
                }
              }
              description
                "Rate in PPS";
            }
          }
        }
      }
    }
  }

  augment "/a1:lpts/a1:pifib/a1:hardware/a1:police" {
    description
      "This augment extends lpts pifib hardware police nodes
       configuration";
    uses LPTS-POLICE;
  }
  augment "/location:locations/location:location/a1:lpts/a1:pifib/a1:hardware/a1:police" {
    description
      "This augment extends lpts pifib hardware police active nodes
       configuration";
    uses LOCATION-BODY;
  }
  augment "/location:locations/location:preconfigured-location/a1:lpts/a1:pifib/a1:hardware/a1:police" {
    description
      "This augment extends lpts pifib hardware police preconfigured nodes
       configuration";
    uses LOCATION-BODY;
  }
  augment "/a1:lpts/a1:pifib/a1:hardware" {
    description
      "This augment extends lpts pifib hardware nodes
       configuration";
    container domains {
      description
        "ingress domains configuration command";
      list domain {
        key "domain-name";
        description
          "ingress domains configuration command";
        leaf domain-name {
          type xr:Cisco-ios-xr-string {
            length "1..32" {
              description
                "Domain name";
            }
            pattern "[a-z0-9A-Z][-_.:a-z0-9A-Z]*";
          }
          description
            "ingress domains configuration command";
        }
        container interfaces {
          description
            "Add interface to domain";
          list interface {
            key "interface-name";
            description
              "Add interface to domain";
            leaf interface-name {
              type xr:Interface-name;
              description
                "Add interface to domain";
            }
          }
        }
      }
    }
  }
}
