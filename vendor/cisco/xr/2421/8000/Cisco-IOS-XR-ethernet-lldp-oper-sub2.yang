submodule Cisco-IOS-XR-ethernet-lldp-oper-sub2 {
  belongs-to Cisco-IOS-XR-ethernet-lldp-oper {
    prefix Cisco-IOS-XR-ethernet-lldp-oper;
  }

  import oc-xr-mapping {
    prefix emmi;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ethernet-lldp package operational data.
     
     Copyright (c) 2013-2017 by Cisco Systems, Inc.
     All rights reserved.";

  revision 2015-11-09 {
    description
      "IOS XR 6.0 revision.";
  }

  grouping LLDP-MGR-GLOBAL-INFO {
    description
      "LLDP global info";
    leaf chassis-id {
      type string;
      description
        "Chassis identifier";
      emmi:map-to {
        emmi:from {
          emmi:parent "/lldp/global-lldp/lldp-info";
          emmi:path "/oc-lldp:lldp/oc-lldp:state/oc-lldp:chassis-id";
        }
      }
    }
    leaf chassis-id-sub-type {
      type uint8;
      description
        "Chassis ID sub type";
      emmi:map-to {
        emmi:from {
          emmi:parent "/lldp/global-lldp/lldp-info";
          emmi:path "/oc-lldp:lldp/oc-lldp:state/oc-lldp:chassis-id-type";
        }
      }
    }
    leaf system-name {
      type string;
      description
        "System Name";
      emmi:map-to {
        emmi:from {
          emmi:parent "/lldp/global-lldp/lldp-info";
          emmi:path "/oc-lldp:lldp/oc-lldp:state/oc-lldp:system-name";
        }
      }
    }
    leaf timer {
      type uint32;
      description
        "Rate at which LLDP packets re sent (in sec)";
    }
    leaf hold-time {
      type uint32;
      description
        "Length  of time  (in sec)that receiver must keep
         thispacket";
    }
    leaf re-init {
      type uint32;
      description
        "Delay (in sec) for LLDPinitialization on
         anyinterface";
    }
  }
  emmi:mapping {
    emmi:package-name "oclldp";
    emmi:model-id "xr";
    emmi:module-id "cisco_ios_xr_ethernet_lldp_oper_sub2";
    emmi:target {
      emmi:model-id "oc";
      emmi:module-id "openconfig_lldp";
      emmi:namespace "if|urn:ietf:params:xml:ns:yang:ietf-interfaces";
      emmi:namespace "oc-if|http://openconfig.net/yang/interfaces";
      emmi:namespace "oc-lldp|http://openconfig.net/yang/lldp";
      emmi:namespace "oc-ext|http://openconfig.net/yang/openconfig-ext";
      emmi:namespace "yang|urn:ietf:params:xml:ns:yang:ietf-yang-types";
      emmi:namespace "oc-lldp-types|http://openconfig.net/yang/lldp/types";
    }
  }
}
