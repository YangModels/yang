module Cisco-IOS-XR-ip-domain-cfg {
  namespace "http://cisco.com/ns/yang/Cisco-IOS-XR-ip-domain-cfg";
  prefix ip-domain-cfg;

  import ietf-inet-types {
    prefix inet;
  }
  import Cisco-IOS-XR-types {
    prefix xr;
  }
  import cisco-semver {
    prefix semver;
  }
  import oc-xr-mapping {
    prefix emmi;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-domain package configuration.
     
     This module contains definitions
     for the following management objects:
       ip-domain: IP domain configuration
     
     Copyright (c) 2013-2019, 2022 by Cisco Systems, Inc.
     All rights reserved.";

  revision 2019-04-05 {
    description
      "Establish semantic version baseline.";
    semver:module-version "1.0.1";
  }
  revision 2019-02-19 {
    description
      "Domains default flows Disable support.";
  }
  revision 2017-09-07 {
    description
      "Fixed type translation error.";
  }
  revision 2015-05-13 {
    description
      "IOS XR 5.3.2 revision.";
  }
  revision 2015-01-07 {
    description
      "IOS XR 5.3.1 revision.";
  }

  container ip-domain {
    description
      "IP domain configuration";
    container vrfs {
      description
        "VRF table";
      list vrf {
        key "vrf-name";
        description
          "VRF specific data";
        container ipv6-hosts {
          description
            "IPv6 host";
          list ipv6-host {
            key "host-name";
            description
              "Host name and up to 4 host IPv6 addresses";
            leaf host-name {
              type string;
              description
                "A hostname";
              emmi:map-to {
                emmi:path "/oc-sys:system/oc-sys:dns/oc-sys:host-entries/oc-sys:host-entry/oc-sys:hostname" {
                  emmi:path-attributes {
                    emmi:node-key "true";
                  }
                }
                emmi:path "/oc-sys:system/oc-sys:dns/oc-sys:host-entries/oc-sys:host-entry/oc-sys:config/oc-sys:hostname";
              }
            }
            leaf-list address {
              type inet:ipv6-address-no-zone;
              min-elements 1;
              max-elements "4";
              description
                "Host IPv6 addresses";
              emmi:map-to {
                emmi:path "/oc-sys:system/oc-sys:dns/oc-sys:host-entries/oc-sys:host-entry/oc-sys:config/oc-sys:ipv6-address";
              }
            }
            emmi:map-to {
              emmi:path "/oc-sys:system/oc-sys:dns/oc-sys:host-entries/oc-sys:host-entry";
            }
          }
          emmi:map-to;
        }
        container servers {
          description
            "Name server addresses";
          list server {
            key "order server-address";
            description
              "Name server address";
            leaf order {
              type uint32;
              description
                "This is used to sort the servers in the
                 order of precedence";
            }
            leaf server-address {
              type inet:ip-address-no-zone;
              description
                "A name server address";
              emmi:map-to {
                emmi:function "" {
                  emmi:category "manual_function";
                }
                emmi:function "" {
                  emmi:category "manual_function";
                }
              }
            }
            emmi:map-to {
              emmi:path "/oc-sys:system/oc-sys:dns/oc-sys:servers/oc-sys:server";
            }
          }
          emmi:map-to;
        }
        container lists {
          description
            "Domain names to complete unqualified host
             names";
          list list {
            key "order list-name";
            description
              "Domain name to complete unqualified host
               names";
            leaf order {
              type uint32;
              description
                "This is used to sort the names in the order
                 of precedence";
            }
            leaf list-name {
              type xr:Cisco-ios-xr-string;
              description
                "A domain name";
              emmi:map-to {
                emmi:function "" {
                  emmi:category "manual_function";
                }
              }
            }
            emmi:map-to;
          }
          emmi:map-to;
        }
        container ipv4-hosts {
          description
            "IPv4 host";
          list ipv4-host {
            key "host-name";
            description
              "Host name and up to 8 host IPv4 addresses";
            leaf host-name {
              type string;
              description
                "A hostname";
              emmi:map-to {
                emmi:path "/oc-sys:system/oc-sys:dns/oc-sys:host-entries/oc-sys:host-entry/oc-sys:hostname" {
                  emmi:path-attributes {
                    emmi:node-key "true";
                  }
                }
                emmi:path "/oc-sys:system/oc-sys:dns/oc-sys:host-entries/oc-sys:host-entry/oc-sys:config/oc-sys:hostname";
              }
            }
            leaf-list address {
              type inet:ipv4-address-no-zone;
              min-elements 1;
              max-elements "8";
              description
                "Host IPv4 addresses";
              emmi:map-to {
                emmi:path "/oc-sys:system/oc-sys:dns/oc-sys:host-entries/oc-sys:host-entry/oc-sys:config/oc-sys:ipv4-address";
              }
            }
            emmi:map-to {
              emmi:path "/oc-sys:system/oc-sys:dns/oc-sys:host-entries/oc-sys:host-entry";
            }
          }
          emmi:map-to;
        }
        leaf lookup {
          type empty;
          description
            "Disable Domain Name System hostname
             translation";
        }
        leaf multicast-domain {
          type string;
          description
            "Default multicast domain name";
        }
        leaf source-interface {
          type xr:Interface-name;
          description
            "Specify interface for source address in
             connections";
        }
        leaf name {
          type string;
          description
            "Default domain name";
          emmi:map-to {
            emmi:function "" {
              emmi:category "manual_function";
            }
          }
        }
        leaf vrf-name {
          type xr:Cisco-ios-xr-string;
          description
            "Name of the VRF instance";
        }
        emmi:map-to {
          emmi:path "/oc-sys:system/oc-sys:config";
          emmi:path "/oc-sys:system/oc-sys:dns/oc-sys:config";
          emmi:path "/oc-sys:system/oc-sys:dns/oc-sys:servers";
          emmi:function "" {
            emmi:category "manual_function";
          }
        }
      }
      emmi:map-to;
    }
    leaf default-flows-disable {
      type empty;
      description
        "Disable default flows programming";
    }
    emmi:map-to;
  }
  emmi:mapping {
    emmi:package-name "ocsystem";
    emmi:model-id "xr";
    emmi:module-id "cisco_ios_xr_ip_domain_cfg";
    emmi:target {
      emmi:model-id "oc";
      emmi:module-id "openconfig_system";
      emmi:namespace "oc-sys-mgmt|http://openconfig.net/yang/system/management";
      emmi:namespace "oc-messages|http://openconfig.net/yang/messages";
      emmi:namespace "oc-aaa|http://openconfig.net/yang/aaa";
      emmi:namespace "oc-term-ext|http://cisco.com/ns/yang/Cisco-IOS-XR-openconfig-system-terminal-ext";
      emmi:namespace "oc-proc|http://openconfig.net/yang/system/procmon";
      emmi:namespace "oc-ext|http://openconfig.net/yang/openconfig-ext";
      emmi:namespace "oc-sys|http://openconfig.net/yang/system";
      emmi:namespace "oc-inet|http://openconfig.net/yang/types/inet";
      emmi:namespace "oc-sys-term|http://openconfig.net/yang/system/terminal";
      emmi:namespace "oc-alarms|http://openconfig.net/yang/alarms";
      emmi:namespace "oc-log|http://openconfig.net/yang/system/logging";
      emmi:namespace "oc-types|http://openconfig.net/yang/openconfig-types";
      emmi:namespace "oc-yang|http://openconfig.net/yang/types/yang";
      emmi:namespace "oc-aaa-types|http://openconfig.net/yang/aaa/types";
    }
  }
}
