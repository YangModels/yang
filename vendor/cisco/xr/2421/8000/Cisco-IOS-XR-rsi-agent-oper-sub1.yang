submodule Cisco-IOS-XR-rsi-agent-oper-sub1 {
  belongs-to Cisco-IOS-XR-rsi-agent-oper {
    prefix Cisco-IOS-XR-rsi-agent-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR rsi-agent package operational data.
     
     Copyright (c) 2013-2017 by Cisco Systems, Inc.
     All rights reserved.";

  revision 2015-11-09 {
    description
      "IOS XR 6.0 revision.";
  }

  typedef Rsi-vr-id {
    type uint32;
    description
      "Rsi vr id";
  }

  typedef Rsi-vrf-id {
    type uint32;
    description
      "Rsi vrf id";
  }

  typedef Rsi-tbl-id {
    type uint32;
    description
      "Rsi tbl id";
  }

  typedef Rsi-safi {
    type enumeration {
      enum "mgmt-rsi-safi-ucast" {
        value 1;
        description
          "Unicast";
      }
      enum "mgmt-rsi-safi-mcast" {
        value 2;
        description
          "Multicast";
      }
    }
    description
      "RSI SAFI type";
  }

  typedef Rsi-afi {
    type enumeration {
      enum "mgmt-rsi-afi-ipv4" {
        value 1;
        description
          "IPv4";
      }
      enum "mgmt-rsi-afi-ipv6" {
        value 2;
        description
          "IPv6";
      }
    }
    description
      "RSI AFI type";
  }

  grouping RSI-AGENT-INTF {
    description
      "RSI AGENT INTF";
    leaf ifhandle {
      type xr:Interface-name;
      description
        "Ifhandle";
    }
    leaf ifname {
      type string;
      description
        "Ifname";
    }
    leaf vrf-id {
      type Rsi-vrf-id;
      description
        "VRF ID";
    }
    leaf vrf-name-xr {
      type string;
      description
        "VRF Name";
    }
    leaf vr-id {
      type Rsi-vr-id;
      description
        "VR ID";
    }
    leaf vr-name {
      type string;
      description
        "VR Name";
    }
    leaf is-virtual {
      type boolean;
      description
        "Virtual";
    }
    leaf is-local {
      type boolean;
      description
        "Local";
    }
    leaf is-licensed {
      type boolean;
      description
        "Licensed";
    }
    leaf flags {
      type uint32;
      description
        "flags";
    }
    leaf refcount {
      type int32;
      description
        "Refcount";
    }
    leaf intf-by-ifh-regs {
      type int32;
      description
        "intf by ifh reg cnt";
    }
    leaf intf-tbl-by-ifh-regs {
      type int32;
      description
        "intf tbl by ifh reg cnt";
    }
    leaf-list ra-tbl-set {
      type uint8;
      description
        "ra tbl set";
    }
  }

  grouping RA-NOTIF-REG-BY-INTF {
    description
      "RA NOTIF REG BY INTF";
    leaf mdb-type {
      type uint32;
      description
        "mdb type";
    }
    leaf reg-hd {
      type uint64;
      description
        "reg hd";
    }
    leaf num-notifs-dispatched {
      type uint32;
      description
        "num notifs dispatched";
    }
    leaf ifname {
      type string;
      description
        "ifname";
    }
    leaf ifhandle {
      type xr:Interface-name;
      description
        "ifhandle";
    }
    leaf afi-filter {
      type uint32;
      description
        "afi filter";
    }
    leaf safi-filter {
      type uint32;
      description
        "safi filter";
    }
    leaf tbl-name {
      type string;
      description
        "tbl name";
    }
    leaf global {
      type boolean;
      description
        "Global";
    }
    leaf reg-flags {
      type uint32;
      description
        "reg flags";
    }
  }

  grouping RA-NOTIF-REG-BY-TBL {
    description
      "RA NOTIF REG BY TBL";
    leaf mdb-type {
      type uint32;
      description
        "mdb type";
    }
    leaf reg-hd {
      type uint64;
      description
        "reg hd";
    }
    leaf num-notifs-dispatched {
      type uint32;
      description
        "num notifs dispatched";
    }
    leaf tbl-name {
      type string;
      description
        "tbl name";
    }
    leaf tbl-id {
      type Rsi-tbl-id;
      description
        "tbl id";
    }
  }

  grouping RA-NOTIF-REG-BY-VPN {
    description
      "RA NOTIF REG BY VPN";
    container vpn-id {
      description
        "vpn id";
      uses RSI-VPNID;
    }
    leaf mdb-type {
      type uint32;
      description
        "mdb type";
    }
    leaf reg-hd {
      type uint32;
      description
        "reg hd";
    }
    leaf num-notifs-dispatched {
      type uint32;
      description
        "num notifs dispatched";
    }
  }

  grouping RA-NOTIF-REG-BY-VRF {
    description
      "RA NOTIF REG BY VRF";
    leaf mdb-type {
      type uint32;
      description
        "mdb type";
    }
    leaf reg-hd {
      type uint64;
      description
        "reg hd";
    }
    leaf num-notifs-dispatched {
      type uint32;
      description
        "num notifs dispatched";
    }
    leaf vrf-name {
      type string;
      description
        "vrf name";
    }
    leaf vrf-id {
      type uint32;
      description
        "vrf id";
    }
  }

  grouping RA-NOTIF-REG-BY-VR {
    description
      "RA NOTIF REG BY VR";
    leaf mdb-type {
      type uint32;
      description
        "mdb type";
    }
    leaf reg-hd {
      type uint64;
      description
        "reg hd";
    }
    leaf num-notifs-dispatched {
      type uint32;
      description
        "num notifs dispatched";
    }
    leaf vr-name {
      type string;
      description
        "vr name";
    }
    leaf vr-id {
      type uint32;
      description
        "vr id";
    }
    leaf flags {
      type uint32;
      description
        "flags";
    }
  }

  grouping RA-NOTIF-REG-BY-STATE {
    description
      "RA NOTIF REG BY STATE";
    leaf mdb-type {
      type uint32;
      description
        "mdb type";
    }
    leaf reg-hd {
      type uint64;
      description
        "reg hd";
    }
    leaf num-notifs-dispatched {
      type uint32;
      description
        "num notifs dispatched";
    }
    leaf state-id {
      type uint64;
      description
        "state id";
    }
  }

  grouping RA-NOTIF-REG-ALL {
    description
      "RA NOTIF REG ALL";
    leaf mdb-type {
      type uint32;
      description
        "mdb type";
    }
    leaf reg-hd {
      type uint64;
      description
        "reg hd";
    }
    leaf num-notifs-dispatched {
      type uint32;
      description
        "num notifs dispatched";
    }
    leaf flags {
      type uint32;
      description
        "flags";
    }
  }

  grouping RSI-AGENT-CLIENT {
    description
      "RSI AGENT CLIENT";
    leaf name {
      type string;
      description
        "Client Name";
    }
    leaf client-ptr {
      type uint64;
      description
        "client ptr";
    }
    leaf client-type {
      type uint32;
      description
        "client type";
    }
    leaf zombied {
      type boolean;
      description
        "Zombie flag";
    }
    leaf mdbs-processed {
      type uint32;
      description
        "mdbs processed";
    }
    leaf msgs-received {
      type uint32;
      description
        "msgs received";
    }
    leaf num-lookups-done {
      type uint32;
      description
        "num lookups done";
    }
    leaf num-failed-lookups {
      type uint32;
      description
        "num failed lookups";
    }
    leaf num-failed-regs {
      type uint32;
      description
        "num failed regs";
    }
    leaf num-auto-purges {
      type uint32;
      description
        "num auto purges";
    }
    leaf num-small-reply-buf {
      type uint32;
      description
        "num small reply buf";
    }
    leaf proc-name {
      type string;
      description
        "";
    }
    leaf pid {
      type uint32;
      description
        "pid";
    }
    leaf scoid {
      type int32;
      description
        "scoid";
    }
    leaf coid {
      type int32;
      description
        "coid";
    }
    leaf up-time-secs {
      type uint32;
      description
        "connected time in sec";
    }
    leaf zombie-secs {
      type uint32;
      description
        "Zombie for sec";
    }
    leaf last-rx-msg-type {
      type uint32;
      description
        "last rx msg type";
    }
    leaf pulse-count {
      type uint32;
      description
        "pulse count";
    }
    leaf async-q-size {
      type uint32;
      description
        "async q size";
    }
    leaf async-q-size-max {
      type uint32;
      description
        "async q size max";
    }
    leaf sync-items-returned {
      type uint32;
      description
        "sync items returned";
    }
    leaf async-items-returned {
      type uint32;
      description
        "async items returned";
    }
    leaf batch-enabled {
      type boolean;
      description
        "Batch enable flag";
    }
    leaf batch-size {
      type uint32;
      description
        "batch size";
    }
    leaf num-active-regs {
      type uint32;
      description
        "num active regs";
    }
    leaf num-owned-objs-tdl {
      type uint32;
      description
        "TDLs owned by producer client";
    }
    leaf-list local-tbl-buf {
      type Rsi-tbl-id;
      description
        "LTBLs owned by producer client";
    }
    list by-all {
      description
        "by all";
      uses RA-NOTIF-REG-ALL;
    }
    list by-state {
      description
        "by state";
      uses RA-NOTIF-REG-BY-STATE;
    }
    list by-vr {
      description
        "by vr";
      uses RA-NOTIF-REG-BY-VR;
    }
    list by-vrf {
      description
        "by vrf";
      uses RA-NOTIF-REG-BY-VRF;
    }
    list by-vpn {
      description
        "by vpn";
      uses RA-NOTIF-REG-BY-VPN;
    }
    list by-tbl {
      description
        "by tbl";
      uses RA-NOTIF-REG-BY-TBL;
    }
    list by-intf {
      description
        "by intf";
      uses RA-NOTIF-REG-BY-INTF;
    }
  }

  grouping RSI-AGENT-STATE {
    description
      "RSI AGENT STATE";
    leaf state-id {
      type uint32;
      description
        "state id";
    }
    leaf state-val {
      type uint32;
      description
        "state val";
    }
    leaf svd-is-enabled {
      type uint32;
      description
        "svd is enabled";
    }
    leaf intf-caps-v4-count {
      type uint32;
      description
        "intf caps v4 count";
    }
    leaf intf-caps-v6-count {
      type uint32;
      description
        "intf caps v6 count";
    }
    leaf vrf-intf-caps-v4-count {
      type uint32;
      description
        "vrf intf caps v4 count";
    }
    leaf vrf-intf-caps-v6-count {
      type uint32;
      description
        "vrf intf caps v6 count";
    }
    leaf-list state-ctx {
      type uint32;
      description
        "state ctx";
    }
  }

  grouping RSI-AGENT-PROD {
    description
      "RSI AGENT PROD";
    leaf item-id {
      type uint32;
      description
        "item id";
    }
    leaf name {
      type string;
      description
        "name";
    }
    leaf flags {
      type uint32;
      description
        "flags";
    }
    leaf num-owned-objs-vr {
      type uint32;
      description
        "num owned objs vr";
    }
    leaf num-owned-objs-vrf {
      type uint32;
      description
        "num owned objs vrf";
    }
    leaf num-owned-objs-tbl {
      type uint32;
      description
        "num owned objs tbl";
    }
    leaf num-owned-objs-intf {
      type uint32;
      description
        "num owned objs intf";
    }
    leaf num-owned-objs-tdl {
      type uint32;
      description
        "num owned objs tdl";
    }
    leaf num-saved-msgs {
      type uint32;
      description
        "num saved msgs";
    }
  }

  grouping RSI-AGENT-TBL-REF {
    description
      "RSI AGENT TBL REF";
    leaf vrf-tbl-idx {
      type uint32;
      description
        "VRF Table Index";
    }
    leaf afi {
      type Rsi-afi;
      description
        "AFI";
    }
    leaf safi {
      type Rsi-safi;
      description
        "SAFI";
    }
    leaf tbl-name {
      type string;
      description
        "Table Name";
    }
  }

  grouping RSI-VPNID {
    description
      "RSI VPNID";
    leaf oui {
      type uint32;
      description
        "VPNID OUI";
    }
    leaf index {
      type uint32;
      description
        "VPNID Index";
    }
  }

  grouping RSI-AGENT-VRF {
    description
      "RSI AGENT VRF";
    container vpn-id {
      description
        "VPN ID";
      uses RSI-VPNID;
    }
    leaf vrf-name {
      type string;
      description
        "VRF Name";
    }
    leaf vrf-id {
      type uint32;
      description
        "VRF ID";
    }
    leaf vr-id {
      type uint32;
      description
        "VR ID";
    }
    leaf submode-flag {
      type uint32;
      description
        "Submode Flag";
    }
    leaf fallback-vrf-name {
      type string;
      description
        "Fallback VRF_Name";
    }
    leaf vr-name {
      type string;
      description
        "VR Name";
    }
    leaf refcount {
      type int32;
      description
        "Refcount";
    }
    leaf intf-count-local {
      type int32;
      description
        "Locally significant Intf Count";
    }
    leaf intf-count-global {
      type int32;
      description
        "Total Interfaces";
    }
    leaf num-real-tbls {
      type int32;
      description
        "Tbl Count";
    }
    leaf num-fwd-ref-tbls {
      type int32;
      description
        "Fwd Ref Tbl Count";
    }
    leaf vrf-by-vrf-id-regs {
      type int32;
      description
        "vrf by vrf id reg cnt";
    }
    leaf vrf-by-vrf-name-regs {
      type int32;
      description
        "vrf by vrf name reg cnt";
    }
    leaf tbl-by-vrf-regs {
      type int32;
      description
        "tbl by vrf reg cnt";
    }
    leaf tbl-by-vrf-name-regs {
      type int32;
      description
        "tbl by vrf name reg cnt";
    }
    leaf vrf-flags {
      type uint32;
      description
        "VRF Flags";
    }
    leaf intf-cnt-local {
      type uint32;
      description
        "Local Intf Count";
    }
    leaf vrf-groups {
      type uint32;
      description
        "Number of VRF groups";
    }
    leaf parentvrf-cnt {
      type uint32;
      description
        "Number of parent VRF";
    }
    list table-array {
      description
        "Array of tables in VRF";
      uses RSI-AGENT-TBL-REF;
    }
  }

  grouping RSI-AGENT-VR {
    description
      "RSI AGENT VR";
    leaf vr-name-xr {
      type string;
      description
        "VR Name";
    }
    leaf vr-id {
      type uint32;
      description
        "VR ID";
    }
    leaf refcount {
      type int32;
      description
        "Refcount";
    }
    leaf num-real-vrfs {
      type int32;
      description
        "Num real vrfs";
    }
    leaf num-fwd-ref-vrfs {
      type int32;
      description
        "Fwd ref vrfs";
    }
    leaf vr-by-vr-id-regs {
      type int32;
      description
        "vr by vr id regs";
    }
    leaf vr-by-vr-name-regs {
      type int32;
      description
        "vr by vr name regs";
    }
    leaf vrf-by-vr-regs {
      type int32;
      description
        "vrf by vr regs";
    }
    leaf tbl-by-vr-regs {
      type int32;
      description
        "tbl by vr regs";
    }
    leaf vrf-cnt-local {
      type int32;
      description
        "vrf cnt local";
    }
  }
}
