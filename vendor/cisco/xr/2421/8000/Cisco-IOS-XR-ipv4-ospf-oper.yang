module Cisco-IOS-XR-ipv4-ospf-oper {
  namespace "http://cisco.com/ns/yang/Cisco-IOS-XR-ipv4-ospf-oper";
  prefix ipv4-ospf-oper;

  import ietf-inet-types {
    prefix inet;
  }
  import Cisco-IOS-XR-types {
    prefix xr;
  }
  import cisco-semver {
    prefix semver;
  }
  include Cisco-IOS-XR-ipv4-ospf-oper-sub3 {
    revision-date 2021-06-01;
  }
  include Cisco-IOS-XR-ipv4-ospf-oper-sub1 {
    revision-date 2021-06-01;
  }
  include Cisco-IOS-XR-ipv4-ospf-oper-sub2 {
    revision-date 2021-06-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-ospf package operational data.
     
     This module contains definitions
     for the following management objects:
       ospf: OSPF operational data
     
     Copyright (c) 2013-2022 by Cisco Systems, Inc.
     All rights reserved.";

  revision 2021-06-01 {
    description
      "Added changes to show if a FAD contains unknown parameters, option to enable SR forwarding MPLS, changes in neighbor sham link or virtual link name";
    semver:module-version "2.2.0";
  }
  revision 2020-03-19 {
    description
      "Added changes for Delay Normalization
       2020-02-04
        Added changes for Conditional Advertising
       2019-09-30
        Added changes for Weighted SRLG";
    semver:module-version "2.0.0";
  }
  revision 2019-07-26 {
    description
      "Added new fields in redistribution container to display more information.";
    semver:module-version "1.1.0";
  }
  revision 2019-04-05 {
    description
      "Establish semantic version baseline.";
    semver:module-version "1.0.0";
  }
  revision 2019-01-07 {
    description
      "Modified for Programmability 2.0";
  }
  revision 2018-04-18 {
    description
      "Added keychain name to be displayed in show ospf interface bag";
  }
  revision 2017-10-26 {
    description
      "Fixed some field name and values for better interpretation";
  }
  revision 2017-09-07 {
    description
      "Fixed type translation error.";
  }
  revision 2017-05-01 {
    description
      "Fixing backward compatibility error in module.";
  }
  revision 2017-01-02 {
    description
      "IOS XR 6.2.1 revision.";
  }
  revision 2015-11-09 {
    description
      "IOS XR 6.0 revision.";
  }

  typedef Ospf-prefix-length {
    type uint32 {
      range "0..32";
    }
    description
      "Ospf prefix length";
  }

  typedef Ospf-ls {
    type enumeration {
      enum "router" {
        value 1;
        description
          "Router LSA";
      }
      enum "network" {
        value 2;
        description
          "Network LSA";
      }
      enum "summary" {
        value 3;
        description
          "Summary LSA";
      }
      enum "asbr-summary" {
        value 4;
        description
          "ASBR-Summary LSA";
      }
      enum "external" {
        value 5;
        description
          "External LSA";
      }
      enum "nssa-external" {
        value 7;
        description
          "NSSA External LSA";
      }
      enum "opaque-link" {
        value 9;
        description
          "Opaque LSALink Scope";
      }
      enum "opaque-area" {
        value 10;
        description
          "Opaque LSA Area Scope";
      }
      enum "opaque-as" {
        value 11;
        description
          "Opaque LSA AS Scope";
      }
    }
    description
      "Ospf ls";
  }

  grouping ROUTE {
    description
      "Common node of route-table,
       multicast-intact-route-table";
    list route {
      description
        "An OSPF route";
      leaf prefix {
        type inet:ipv4-address-no-zone;
        description
          "IPv4 Prefix";
      }
      leaf prefix-length {
        type Ospf-prefix-length;
        description
          "Length of the subnet prefix";
      }
      uses OSPF-SH-TOPOLOGY;
    }
  }

  grouping FLOOD-LIST {
    description
      "Common node of flood-list-table,
       flood-list-area-table";
    list flood {
      key "interface-name";
      description
        "Flooding information for a specific interface";
      leaf interface-name {
        type xr:Interface-name;
        description
          "Name of the Interface";
      }
      uses OSPF-SH-FLOOD-LIST;
    }
  }

  grouping BORDER-ROUTER-TABLE {
    description
      "Common node of default-vrf, vrf";
    container border-routers {
      description
        "Border router table";
      list border-router {
        key "border-router-id";
        description
          "Information for a particular border router";
        leaf border-router-id {
          type inet:ipv4-address-no-zone;
          description
            "Router address";
        }
        uses OSPF-SH-BORDER-ROUTER;
      }
    }
  }

  grouping SEGMENT-ROUTING {
    description
      "Common node of default-vrf, vrf";
    container segment-routing {
      description
        "Container for Segment Routing";
      container adjacency-sids {
        description
          "Container for SR Adjacency SIDs";
        list adjacency-sid {
          key "adj-sid";
          description
            "SR Adj SID Bag";
          leaf adj-sid {
            type uint32 {
              range "0..1048575";
            }
            description
              "Adjacency SID";
          }
          uses OSPF-SH-ADJ-SID;
        }
      }
      container sr-endpoint-policies {
        description
          "Container for SR Policies";
        list sr-endpoint-policy {
          key "endpoint-ip";
          description
            "SR Endpoint Policy Bag";
          leaf endpoint-ip {
            type inet:ip-address-no-zone;
            description
              "Endpoint IP Address";
          }
          uses OSPF-SH-SR-ENDPOINT;
        }
      }
    }
  }

  grouping AREA-TABLE {
    description
      "Common node of default-vrf, vrf";
    container areas {
      description
        "Area table";
      list area {
        key "area-id";
        description
          "Container for per area data";
        container flood-list-area-table {
          description
            "Area specific flood list table";
          uses FLOOD-LIST;
        }
        container area-statistics {
          description
            "Container for Statistics";
          uses INTERFACE-STATS-TABLE;
        }
        leaf area-id {
          type uint32 {
            range "0..4294967295";
          }
          description
            "Area ID";
        }
        uses NEIGHBOR-TABLE;
        uses INTERFACE-BRIEF-TABLE;
        uses REQUEST-LIST-TABLE;
        uses RETRANSMISSION-LIST-TABLE;
        uses NEIGHBOR-DETAIL-TABLE;
        uses INTERFACE-TABLE;
      }
    }
  }

  grouping INTERFACE-STATS-TABLE {
    description
      "Common node of statistics, area-statistics";
    container interface-stats-entries {
      description
        "Statistics innformation Interface table";
      list interface-stats-entry {
        key "interface-name";
        description
          "Statistics information for a specific interface";
        leaf interface-name {
          type xr:Interface-name;
          description
            "Name of the Interface";
        }
        uses OSPF-SH-IF-STATS;
      }
    }
  }

  grouping STATISTICS {
    description
      "Common node of default-vrf, vrf";
    container statistics {
      description
        "Container for Statistics";
      container spf-stats {
        description
          "OSPF SPF statistics";
        uses OSPF-SH-STATS-SPF;
      }
      container rib-batch-stats {
        description
          "Stats concerning RIB route updates using the
           Batching API";
        uses OSPF-SH-RIB-BATCH-PRIORITY-QUEUES;
      }
      container issu-stats {
        description
          "OSPF ISSU statistics";
        uses OSPF-SH-NSR-STATS;
      }
      container rib-lc-stats {
        description
          "OSPF RIB Linecard node information";
        uses OSPF-SH-STATS-RIB-LC;
      }
      container rib-thread-stats {
        description
          "OSPF RIB thread statistics";
        uses OSPF-SH-STATS-WORK-QUEUES;
      }
      container nsr-pl-stats {
        description
          "OSPF NSR packet library statistics";
        uses OSPF-SH-NCD-STATS;
      }
      container nsr-stats {
        description
          "OSPF NSR thread statistics";
        uses OSPF-SH-NSR-STATS;
      }
      container frr-stats {
        description
          "OSPF fast-reroute statistics";
        uses OSPF-SH-IPFRR-STATS;
      }
      container te-stats {
        description
          "OSPF TE IO statistics";
        uses OSPF-SH-TE-STATS;
      }
      container protocol-stats {
        description
          "OSPF Protocol statistics";
        uses OSPF-SH-PROTOPKT-STATS;
      }
      container raw-io-stats {
        description
          "OSPF RAW IO statistics";
        uses OSPF-SH-RAW-STATS;
      }
      uses INTERFACE-STATS-TABLE;
    }
  }

  grouping OSPF-SUMMARY {
    description
      "Common node of default-vrf, vrf";
    container ospf-summary {
      description
        "Fast-reroute topology information";
      uses OSPF-SH-STATS-AGGT;
    }
  }

  grouping PROCESS-INFORMATION {
    description
      "Common node of default-vrf, vrf";
    container process-information {
      description
        "Container for OSPF Process information";
      container protocol-areas {
        description
          "Protocol Area table";
        list protocol-area {
          description
            "Area information";
          leaf area-id {
            type uint32 {
              range "0..4294967295";
            }
            description
              "Area ID if in integer format";
          }
          leaf address {
            type inet:ipv4-address-no-zone;
            description
              "Area ID if in IP address format";
          }
          uses OSPF-SH-PROTO-AREA;
        }
      }
      container protocol-summary {
        description
          "Basic OSPF protocol information";
        uses OSPF-SH-PROTOCOL;
      }
      container redistributions {
        description
          "Redistribution information table";
        list redistribution {
          description
            "Redistribution information";
          leaf protocol-name {
            type xr:Cisco-ios-xr-string;
            description
              "Name of the protocol being redistributed";
          }
          leaf process-name {
            type xr:Cisco-ios-xr-string;
            description
              "Process/Instance name of the protocol being
               redistributed";
          }
          uses OSPF-SH-REDIST;
        }
      }
      container process-areas {
        description
          "Process Area table";
        list process-area {
          description
            "Detailed information for a particular area";
          leaf area-id {
            type uint32 {
              range "0..4294967295";
            }
            description
              "Area ID if in integer format";
          }
          leaf address {
            type inet:ipv4-address-no-zone;
            description
              "Area ID if in IP address format";
          }
          uses OSPF-SH-AREA;
        }
      }
      container process-summary {
        description
          "Basic OSPF summary information";
        uses OSPF-SH-SUMMARY;
      }
    }
  }

  grouping ADJACENCY-INFORMATION {
    description
      "Common node of default-vrf, vrf";
    container adjacency-information {
      description
        "Container for OSPF Interfaces";
      uses NEIGHBOR-TABLE;
      uses REQUEST-LIST-TABLE;
      uses RETRANSMISSION-LIST-TABLE;
      uses NEIGHBOR-DETAIL-TABLE;
    }
  }

  grouping RETRANSMISSION-LIST-TABLE {
    description
      "Common node of adjacency-information, area";
    container retransmissions {
      description
        "Retransmission list table";
      list retransmission {
        description
          "Retransmission list for a particular adjacency";
        leaf interface-name {
          type xr:Interface-name;
          description
            "Name of the Interface";
        }
        leaf neighbor-address {
          type inet:ipv4-address-no-zone;
          description
            "IPv4 address of the neighbor";
        }
        uses OSPF-SH-RETRANS-LIST;
      }
    }
  }

  grouping LSA-SUMMARY-TABLE {
    description
      "Common node of database, database-area";
    container lsa-summaries {
      description
        "Link state advertisement summary table";
      list lsa-summary {
        description
          "LSA summary information";
        leaf area-id {
          type uint32 {
            range "0..4294967295";
          }
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Router ID of the Advertising Router";
        }
        leaf interface-name {
          type xr:Interface-name;
          description
            "Name of the Interface";
        }
        uses OSPF-SH-DATABASE;
      }
    }
  }

  grouping ROUTE-INFORMATION {
    description
      "Common node of default-vrf, vrf";
    container route-information {
      description
        "Container for OSPF routing tables";
      container backup-routes {
        description
          "OSPF Route Table Including Backup Paths";
        list backup-route {
          description
            "OSPF route including backup paths";
          leaf prefix {
            type inet:ipv4-address-no-zone;
            description
              "IPv4 Prefix";
          }
          leaf prefix-length {
            type Ospf-prefix-length;
            description
              "Length of the subnet prefix";
          }
          uses OSPF-SH-TOPOLOGY-BACKUP;
        }
      }
      container multicast-intact-route-table {
        description
          "OSPF Route Table including multicast-intact
           routes";
        uses ROUTE;
      }
      container multicast-intact-backup-routes {
        description
          "OSPF Route Table Including Multicast intact
           Backup Paths";
        list multicast-intact-backup-route {
          description
            "OSPF route including multicast backup paths";
          leaf prefix {
            type inet:ipv4-address-no-zone;
            description
              "IPv4 Prefix";
          }
          leaf prefix-length {
            type Ospf-prefix-length;
            description
              "Length of the subnet prefix";
          }
          uses OSPF-SH-TOPOLOGY-BACKUP;
        }
      }
      container summary-information {
        description
          "OSPF route summary statistics";
        uses OSPF-SH-ROUTE-SUMMARY;
      }
      container connected-routes {
        description
          "OSPF Connected Route Table";
        list connected-route {
          description
            "This is a Connected route";
          leaf prefix {
            type inet:ipv4-address-no-zone;
            description
              "IPv4 Prefix";
          }
          leaf prefix-length {
            type Ospf-prefix-length;
            description
              "Length of the subnet prefix";
          }
          uses OSPF-SH-TOPOLOGY;
        }
      }
      container local-routes {
        description
          "OSPF Local Route Table";
        list local-route {
          description
            "This is a Local route";
          leaf prefix {
            type inet:ipv4-address-no-zone;
            description
              "IPv4 Prefix";
          }
          leaf prefix-length {
            type Ospf-prefix-length;
            description
              "Length of the subnet prefix";
          }
          uses OSPF-SH-TOPOLOGY;
        }
      }
      container route-areas {
        description
          "OSPF Area Route Table";
        list route-area {
          key "area-id";
          description
            "OSPF Area Route";
          container multicast-intact-backup-route-areas {
            description
              "OSPF Route Table Including Multicast Intace
               Backup Paths in an area";
            list multicast-intact-backup-route-area {
              description
                "OSPF route including Multicast intact backup
                 paths";
              leaf prefix {
                type inet:ipv4-address-no-zone;
                description
                  "IPv4 Prefix";
              }
              leaf prefix-length {
                type Ospf-prefix-length;
                description
                  "Length of the subnet prefix";
              }
              uses OSPF-SH-TOPOLOGY-BACKUP;
            }
          }
          container connected-route-areas {
            description
              "OSPF Connected Route Table in an area";
            list connected-route-area {
              description
                "Connected route";
              leaf prefix {
                type inet:ipv4-address-no-zone;
                description
                  "IPv4 Prefix";
              }
              leaf prefix-length {
                type Ospf-prefix-length;
                description
                  "Length of the subnet prefix";
              }
              uses OSPF-SH-TOPOLOGY;
            }
          }
          container backup-route-areas {
            description
              "OSPF Route Table Including Backup Paths in an
               area";
            list backup-route-area {
              description
                "OSPF route including backup paths";
              leaf prefix {
                type inet:ipv4-address-no-zone;
                description
                  "IPv4 Prefix";
              }
              leaf prefix-length {
                type Ospf-prefix-length;
                description
                  "Length of the subnet prefix";
              }
              uses OSPF-SH-TOPOLOGY-BACKUP;
            }
          }
          container route-area-informations {
            description
              "OSPF Area Route Entry";
            list route-area-information {
              description
                "An OSPF route";
              leaf prefix {
                type inet:ipv4-address-no-zone;
                description
                  "IPv4 Prefix";
              }
              leaf prefix-length {
                type Ospf-prefix-length;
                description
                  "Length of the subnet prefix";
              }
              uses OSPF-SH-TOPOLOGY;
            }
          }
          container multicast-intact-route-areas {
            description
              "OSPF Area multicast-intact included route
               entry";
            list multicast-intact-route-area {
              description
                "A Muliticast OSPF route in an area";
              leaf prefix {
                type inet:ipv4-address-no-zone;
                description
                  "IPv4 Prefix";
              }
              leaf prefix-length {
                type Ospf-prefix-length;
                description
                  "Length of the subnet prefix";
              }
              uses OSPF-SH-TOPOLOGY;
            }
          }
          container summary-area-information {
            description
              "OSPF route summary statistics";
            uses OSPF-SH-ROUTE-SUMMARY;
          }
          container local-route-areas {
            description
              "OSPF Local Route Table";
            list local-route-area {
              description
                "Local route";
              leaf prefix {
                type inet:ipv4-address-no-zone;
                description
                  "IPv4 Prefix";
              }
              leaf prefix-length {
                type Ospf-prefix-length;
                description
                  "Length of the subnet prefix";
              }
              uses OSPF-SH-TOPOLOGY;
            }
          }
          leaf area-id {
            type uint32 {
              range "0..4294967295";
            }
            description
              "Area ID";
          }
        }
      }
      container route-table {
        description
          "OSPF Route Table";
        uses ROUTE;
      }
      container external-routes {
        description
          "OSPF External Route Table";
        list external-route {
          description
            "This is an OSPF external route";
          leaf prefix {
            type inet:ipv4-address-no-zone;
            description
              "IPv4 Prefix";
          }
          leaf prefix-length {
            type Ospf-prefix-length;
            description
              "Length of the subnet prefix";
          }
          uses OSPF-SH-ROUTE-EXT;
        }
      }
    }
  }

  grouping FAST-REROUTE {
    description
      "Common node of default-vrf, vrf";
    container fast-reroute {
      description
        "Container for FastReroute";
      container topologies {
        description
          "Fast-reroute topology information table";
        list topology {
          key "remote-router-id area-id";
          description
            "Fast-reroute topology information";
          leaf remote-router-id {
            type inet:ipv4-address-no-zone;
            description
              "Remote Node Router ID";
          }
          leaf area-id {
            type uint32 {
              range "0..4294967295";
            }
            description
              "Area ID";
          }
          uses OSPF-SH-IPFRR-TOPO;
        }
      }
    }
  }

  grouping POLICY-MI {
    description
      "Common node of policy-ipv4-active,
       policy-ipv4-backup";
    list policy-mi {
      key "mi-id";
      description
        "Mapping Item";
      leaf mi-id {
        type xr:Cisco-ios-xr-string;
        description
          "Mapping Item ID (0, 1, 2, ...)";
      }
      uses SRMS-MI-T-B;
    }
  }

  grouping MPLS-TE {
    description
      "Common node of default-vrf, vrf";
    container mpls-te {
      description
        "Container for MPLS TE";
      container mpls-te-links {
        description
          "MPLS TE link information table";
        list mpls-te-link {
          key "area-id";
          description
            "MPLS TE link information";
          leaf area-id {
            type uint32 {
              range "0..4294967295";
            }
            description
              "Area ID";
          }
          uses OSPF-SH-MPLS;
        }
      }
      container mpls-te-fragments {
        description
          "MPLS TE Fragment information table";
        list mpls-te-fragment {
          key "area-id";
          description
            "MPLS TE Fragment";
          leaf area-id {
            type uint32 {
              range "0..4294967295";
            }
            description
              "Area ID";
          }
          uses OSPF-SH-MPLS;
        }
      }
    }
  }

  grouping FLOOD-LIST-TABLE {
    description
      "Common node of default-vrf, vrf";
    container flood-list-table {
      description
        "List of LSAs being flooded";
      uses FLOOD-LIST;
    }
  }

  grouping SUMMARY-PREFIX-TABLE {
    description
      "Common node of default-vrf, vrf";
    container summary-prefixes {
      description
        "Summary prefix table";
      list summary-prefix {
        description
          "Summary prefix information";
        leaf prefix {
          type inet:ipv4-address-no-zone;
          description
            "Summary Prefix";
        }
        leaf netmask {
          type inet:ipv4-address-no-zone;
          description
            "Summary Mask";
        }
        uses OSPF-SH-SUMMARY-ADDRESS;
      }
    }
  }

  grouping NEIGHBOR-DETAIL-TABLE {
    description
      "Common node of adjacency-information, area";
    container neighbor-details {
      description
        "Neighbor detail table";
      list neighbor-detail {
        description
          "A single neighbor's detail information";
        leaf interface-name {
          type xr:Interface-name;
          description
            "Name of the Interface";
        }
        leaf neighbor-address {
          type inet:ipv4-address-no-zone;
          description
            "IPv4 address of the neighbor";
        }
        uses OSPF-SH-NEIGHBOR-DETAIL;
      }
    }
  }

  grouping REQUEST-LIST-TABLE {
    description
      "Common node of adjacency-information, area";
    container requests {
      description
        "Request List table";
      list request {
        description
          "Request list for a particular adjacency";
        leaf interface-name {
          type xr:Interface-name;
          description
            "Interface";
        }
        leaf neighbor-address {
          type inet:ipv4-address-no-zone;
          description
            "IPv4 address of the neighbor";
        }
        uses OSPF-SH-REQUEST-LIST;
      }
    }
  }

  grouping INTERFACE-TABLE {
    description
      "Common node of interface-information, area";
    container interfaces {
      description
        "OSPF Interface Table";
      list interface {
        key "interface-name";
        description
          "OSPF interface information";
        leaf interface-name {
          type xr:Interface-name;
          description
            "Name of the Interface";
        }
        uses OSPF-SH-INTERFACE;
      }
    }
  }

  grouping INTERFACE-BRIEF-TABLE {
    description
      "Common node of interface-information, area";
    container interface-briefs {
      description
        "OSPF Interface Brief Table";
      list interface-brief {
        key "interface-name";
        description
          "OSPF interface brief information";
        leaf interface-name {
          type xr:Interface-name;
          description
            "Interface";
        }
        uses OSPF-SH-IF-BRIEF;
      }
    }
  }

  grouping DATABASE {
    description
      "Common node of default-vrf, vrf";
    container database {
      description
        "OSPF Link State Database";
      container database-areas {
        description
          "Per-Area view of Link state database";
        list database-area {
          key "area-id";
          description
            "Per-Area Link State Database data";
          leaf area-id {
            type uint32 {
              range "0..4294967295";
            }
            description
              "Area ID";
          }
          uses LSA-TABLE;
          uses LSA-SUMMARY-TABLE;
        }
      }
      container database-summaries {
        description
          "Link State database summary table";
        list database-summary {
          key "area-id";
          description
            "Link State Database summary for a particular
             area";
          leaf area-id {
            type uint32 {
              range "0..4294967295";
            }
            description
              "Area ID";
          }
          uses OSPF-SH-DB-AREA-SUM;
        }
      }
      container database-summary-as {
        description
          "Link State Database summary for the AS";
        uses OSPF-SH-DB-AS-SUM;
      }
      uses LSA-TABLE;
      uses LSA-SUMMARY-TABLE;
    }
  }

  grouping INTERFACE-INFORMATION {
    description
      "Common node of default-vrf, vrf";
    container interface-information {
      description
        "Container for OSPF Interfaces/links";
      container virtual-links {
        description
          "Virtual Link table";
        list virtual-link {
          key "virtual-link-name";
          description
            "Information for one Virtual link";
          leaf virtual-link-name {
            type xr:Cisco-ios-xr-string;
            description
              "Virtual link";
          }
          uses OSPF-SH-VIRTUAL-LINKS;
        }
      }
      uses INTERFACE-BRIEF-TABLE;
      uses INTERFACE-TABLE;
    }
  }

  grouping NEIGHBOR-TABLE {
    description
      "Common node of adjacency-information, area";
    container neighbors {
      description
        "Neighbor table";
      list neighbor {
        description
          "Neighbor information";
        leaf interface-name {
          type xr:Interface-name;
          description
            "Name of the Interface";
        }
        leaf neighbor-address {
          type inet:ipv4-address-no-zone;
          description
            "IPv4 address of the neighbor";
        }
        uses OSPF-SH-NEIGHBOR;
      }
    }
  }

  grouping LSA-TABLE {
    description
      "Common node of database-area, database";
    container lsas {
      description
        "Link State Database Table";
      list lsa {
        description
          "Link State Advertisement information";
        leaf area-id {
          type uint32 {
            range "0..4294967295";
          }
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Router ID of the Advertising Router";
        }
        leaf interface-name {
          type xr:Interface-name;
          description
            "Name of the Interface";
        }
        uses OSPF-SH-DATABASE-DETAIL;
      }
    }
  }

  container ospf {
    config false;
    description
      "OSPF operational data";
    container processes {
      description
        "Table for each process";
      list process {
        key "process-name";
        description
          "Operational data for a particular OSPF process";
        container vrfs {
          description
            "Table for each VRF";
          list vrf {
            key "vrf-name";
            description
              "Operational data for a particular VRF
               (instance) in the OSPF process";
            container interface-vrf-information {
              description
                "Container for OSPF Interfaces/links under a
                 VRF";
              container sham-links {
                description
                  "Sham Link table";
                list sham-link {
                  key "sham-link-name";
                  description
                    "Information for one Sham link";
                  leaf sham-link-name {
                    type xr:Cisco-ios-xr-string;
                    description
                      "Sham link";
                  }
                  uses OSPF-SH-SHAM-LINKS;
                }
              }
            }
            leaf vrf-name {
              type xr:Cisco-ios-xr-string;
              description
                "VRF Name";
            }
            uses FLOOD-LIST-TABLE;
            uses SEGMENT-ROUTING;
            uses MPLS-TE;
            uses STATISTICS;
            uses ADJACENCY-INFORMATION;
            uses ROUTE-INFORMATION;
            uses INTERFACE-INFORMATION;
            uses BORDER-ROUTER-TABLE;
            uses PROCESS-INFORMATION;
            uses AREA-TABLE;
            uses DATABASE;
            uses SUMMARY-PREFIX-TABLE;
            uses OSPF-SUMMARY;
            uses FAST-REROUTE;
          }
        }
        container srms {
          description
            "Segment Routing Mapping Server operational
             data";
          container policy {
            description
              "Policy operational data";
            container policy-ipv4 {
              description
                "IPv4 policy operational data";
              container policy-ipv4-backup {
                description
                  "IPv4 backup policy operational data";
                uses POLICY-MI;
              }
              container policy-ipv4-active {
                description
                  "IPv4 active policy operational data";
                uses POLICY-MI;
              }
            }
          }
        }
        container default-vrf {
          description
            "Operational data for the default VRF
             (instance) in the OSPF process";
          container srlgs {
            description
              "Container for Weighted SRLG information";
            list srlg {
              key "srlg-name";
              description
                "Information for a particular SRLG";
              leaf srlg-name {
                type xr:Cisco-ios-xr-string;
                description
                  "Name of SRLG configured";
              }
              uses OSPF-SH-WSRLG;
            }
          }
          uses FLOOD-LIST-TABLE;
          uses SEGMENT-ROUTING;
          uses MPLS-TE;
          uses STATISTICS;
          uses ADJACENCY-INFORMATION;
          uses ROUTE-INFORMATION;
          uses INTERFACE-INFORMATION;
          uses BORDER-ROUTER-TABLE;
          uses PROCESS-INFORMATION;
          uses AREA-TABLE;
          uses DATABASE;
          uses SUMMARY-PREFIX-TABLE;
          uses OSPF-SUMMARY;
          uses FAST-REROUTE;
        }
        leaf process-name {
          type xr:Cisco-ios-xr-string;
          description
            "OSPF process";
        }
      }
    }
  }
}
