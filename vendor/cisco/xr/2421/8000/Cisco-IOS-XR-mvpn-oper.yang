module Cisco-IOS-XR-mvpn-oper {
  namespace "http://cisco.com/ns/yang/Cisco-IOS-XR-mvpn-oper";
  prefix mvpn-oper;

  import ietf-inet-types {
    prefix inet;
  }
  import Cisco-IOS-XR-types {
    prefix xr;
  }
  import cisco-semver {
    prefix semver;
  }
  include Cisco-IOS-XR-mvpn-oper-sub1 {
    revision-date 2021-08-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mvpn package operational data.
     
     This module contains definitions
     for the following management objects:
       mvpn: MVPN operational data
       ipv6-mvpn: IPv6 MVPN operational data
     
     Copyright (c) 2013-2022 by Cisco Systems, Inc.
     All rights reserved.";

  revision 2021-08-17 {
    description
      "backward compatible addition, in leaf discovery-type was made";
    semver:module-version "2.1.0";
  }
  revision 2020-04-02 {
    description
      "MVPN TreeSID information added.";
    semver:module-version "2.0.0";
  }
  revision 2019-08-27 {
    description
      "Providing MVPN information.";
    semver:module-version "1.0.0";
  }
  revision 2019-04-05 {
    description
      "Establish semantic version baseline.";
  }
  revision 2015-11-09 {
    description
      "IOS XR 6.0 revision.";
  }

  typedef Pim-mldp-opaque {
    type enumeration {
      enum "mldp-global-identifier" {
        value 1;
        description
          "Opaque Global Identifier";
      }
      enum "mldpvpn-identifier" {
        value 2;
        description
          "Opaque VPN Identifier";
      }
    }
    description
      "Pim mldp opaque";
  }

  typedef Pim-mdt-mldp {
    type enumeration {
      enum "mldpp2mp" {
        value 6;
        description
          "P2MP Tree";
      }
      enum "mldpmp2mp" {
        value 8;
        description
          "MP2MP Tree";
      }
    }
    description
      "Pim mdt mldp";
  }

  typedef Mdt-core {
    type enumeration {
      enum "inband" {
        value 0;
        description
          "Inband MDT Type";
      }
      enum "gre" {
        value 1;
        description
          "GRE MDT Type";
      }
      enum "mldp" {
        value 2;
        description
          "MLDP MDT Type";
      }
      enum "rsvp-te" {
        value 3;
        description
          "RSVP_TE MDT Type";
      }
      enum "ir" {
        value 4;
        description
          "IR MDT Type";
      }
      enum "vxlan" {
        value 5;
        description
          "VXLAN MDT Type";
      }
      enum "g-inband" {
        value 6;
        description
          "G_Inband MDT Type";
      }
      enum "max" {
        value 8;
        description
          "MAX MDT Type";
      }
    }
    description
      "Mdt core";
  }

  typedef Route-distinguisher {
    type string;
    description
      "Route distinguisher";
  }

  grouping LOCAL-ENTRY-TABLE {
    description
      "Common node of vrf, default-context";
    container local-entries {
      description
        "PIM MDT mldp local table";
      list local-entry {
        key "tree-type opaque-type oui vpn-index core-id";
        description
          "PIM MDT mldp local table";
        leaf tree-type {
          type Pim-mdt-mldp;
          description
            "Tree Type";
        }
        leaf opaque-type {
          type Pim-mldp-opaque;
          description
            "Opaque Type";
        }
        leaf oui {
          type uint32;
          description
            "OUI";
        }
        leaf vpn-index {
          type uint32;
          description
            "VPN Index";
        }
        leaf core-id {
          type uint32;
          description
            "Core ID";
        }
        uses PIM-MDT-DATA-MLDP-BAG;
      }
    }
  }

  grouping AUTO-RP {
    description
      "Common node of vrf, default-context";
    container auto-rp {
      description
        "PIM Auto-RP information";
      uses RP-RELAY-TABLE;
    }
  }

  grouping MDT-CACHE-TABLE {
    description
      "Common node of vrf, default-context";
    container mdt-caches {
      description
        "PIM MDT cache";
      list mdt-cache {
        key "core-type core-source-address customer-source-address customer-group-address";
        description
          "PIM MDT cache information";
        leaf core-type {
          type Mdt-core;
          description
            "MDT Core type";
        }
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-IR-LOCAL-ENTRY-TABLE {
    description
      "Common node of vrf, default-context";
    container ir-local-entries {
      description
        "PIM MDT ir local table";
      list ir-local-entry {
        key "core-id";
        description
          "PIM MDT ir local table";
        leaf core-id {
          type uint32;
          description
            "Core ID";
        }
        uses PIM-MDT-DATA-IR-BAG;
      }
    }
  }

  grouping MDT-RSVP-TE-CACHE-TABLE {
    description
      "Common node of vrf, default-context";
    container mdt-rsvp-te-caches {
      description
        "RSVPTE MDT cache";
      list mdt-rsvp-te-cache {
        key "core-source-address customer-source-address customer-group-address";
        description
          "RSVPTE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-INTERFACE {
    description
      "Common node of vrf, default-context";
    container mdt-interface {
      description
        "MDT interface information";
      uses PIM-MDT-INTERFACE-BAG;
    }
  }

  grouping MDT-GRE-CACHE-TABLE {
    description
      "Common node of vrf, default-context";
    container mdt-gre-caches {
      description
        "GRE MDT cache";
      list mdt-gre-cache {
        key "core-source-address customer-source-address customer-group-address";
        description
          "GRE MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping BGP-AF-TABLE {
    description
      "Common node of vrf, default-context";
    container bgp-afs {
      description
        "PIM BGP SAFI table";
      list bgp-af {
        key "source-address group-address";
        description
          "PIM BGP SAFI information";
        leaf source-address {
          type inet:ip-address-no-zone;
          description
            "Source IP address";
        }
        leaf group-address {
          type inet:ip-address-no-zone;
          description
            "Group IP address";
        }
        uses PIM-BGP-SAFI-BAG;
      }
    }
  }

  grouping VRF-TABLE {
    description
      "Common node of active, standby";
    container vrfs {
      description
        "VRF Table";
      list vrf {
        key "vrf-name";
        description
          "VRF name";
        container mvpn-sr-p2mp-entries {
          description
            "MVPN SR P2MP database table";
          list mvpn-sr-p2mp-entry {
            key "policy-name";
            description
              "MVPN SR P2MP database entry";
            leaf policy-name {
              type xr:Cisco-ios-xr-string;
              description
                "Policy Name";
            }
            uses PIM-SRP2MP-MDT-TUNNEL-DB-BAG;
          }
        }
        container mvpn-database-segment-routing {
          description
            "MVPN MDT Segment Routing tunnel database";
          uses PIM-TREESID-MDT-TUNNEL-DB-BAG;
        }
        container mvpn-database-rsvp-te {
          description
            "MVPN MDT RSVPTE tunnel database";
          uses PIM-P2MPTE-MDT-TUNNEL-DB-BAG;
        }
        container mvpn-context {
          description
            "MVPN context information";
          uses PIM-CONTEXT-BAG;
        }
        container mvpn-pes {
          description
            "MVPN PE Information";
          list mvpn-pe {
            key "pe-prefix";
            description
              "MVPN PE Address information";
            leaf pe-prefix {
              type inet:ip-address-no-zone;
              description
                "PE address";
            }
            uses PIM-PE-BAG;
          }
        }
        container mvpn-database-ir {
          description
            "MVPN MDT IR tunnel database";
          uses PIM-MDT-TUNNEL-DB-BAG;
        }
        leaf vrf-name {
          type xr:Cisco-ios-xr-string {
            length "1..32";
          }
          description
            "VRF name ";
        }
        uses MDT-INTERFACE;
        uses LOCAL-ENTRY-TABLE;
        uses MDT-RSVP-TE-REMOTE-ENTRY-TABLE;
        uses MDT-CACHE-SUMMARY;
        uses MDT-DATABASE-IR;
        uses MDT-GRE-CACHE-TABLE;
        uses MDT-IR-REMOTE-ENTRY-TABLE;
        uses MDT-DATABASE-RSVP-TE;
        uses BSR;
        uses BGP-AF-TABLE;
        uses MDT-RSVP-TE-LOCAL-ENTRY-TABLE;
        uses MDT-PREFIX-REMOTE-TABLE;
        uses MDT-CACHE-TABLE;
        uses MDT-RSVP-TE-CACHE-TABLE;
        uses AUTO-RP;
        uses MDT-SEGMENT-ROUTING-LOCAL-ENTRY-TABLE;
        uses REMOTE-ENTRY-TABLE;
        uses MDT-IR-CACHE-TABLE;
        uses PE-TABLE;
        uses MDT-SEGMENT-ROUTING-REMOTE-ENTRY-TABLE;
        uses MDT-MLDP-CACHE-TABLE;
        uses MDT-IR-LOCAL-ENTRY-TABLE;
        uses MDT-PREFIX-LOCAL-TABLE;
      }
    }
  }

  grouping BSR {
    description
      "Common node of vrf, default-context";
    container bsr {
      description
        "PIM BSR information";
      uses RP-RELAY-TABLE;
    }
  }

  grouping MDT-IR-CACHE-TABLE {
    description
      "Common node of vrf, default-context";
    container mdt-ir-caches {
      description
        "IR MDT cache";
      list mdt-ir-cache {
        key "core-source-address customer-source-address customer-group-address";
        description
          "IR MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping MDT-PREFIX-REMOTE-TABLE {
    description
      "Common node of vrf, default-context";
    container mdt-prefix-remotes {
      description
        "PIM MDT prefix remote table";
      list mdt-prefix-remote {
        key "mdt-prefix";
        description
          "PIM MDT prefix information";
        leaf mdt-prefix {
          type inet:ip-address-no-zone;
          description
            "MDT data prefix address";
        }
        uses PIM-MDT-DATA-PFX-BAG;
      }
    }
  }

  grouping MDT-DATABASE-RSVP-TE {
    description
      "Common node of vrf, default-context";
    container mdt-database-rsvp-te {
      description
        "PIM MDT RSVPTE tunnel database";
      uses PIM-P2MPTE-MDT-TUNNEL-DB-BAG;
    }
  }

  grouping PROCESS {
    description
      "Common node of active, standby";
    container process {
      description
        "Process";
      container mvpn-identifiers {
        description
          "MVPN Identifier Table";
        list mvpn-identifier {
          key "mvpn-identifier";
          description
            "MVPN Identifier";
          leaf mvpn-identifier {
            type uint32;
            description
              "MVPN Identifier";
          }
          uses PIM-MVPN-ID-INFO;
        }
      }
      container mvpn-segmenteds {
        description
          "MVPN SEGMENT DB Table";
        list mvpn-segmented {
          key "rd network";
          description
            "MVPN SEGMENT DB Entry";
          leaf rd {
            type Route-distinguisher;
            description
              "Route Distinguisher value";
          }
          leaf network {
            type inet:ip-prefix;
            description
              "Network in prefix/length format";
          }
          uses PIM-SEGMENT-DB-BAG;
        }
      }
    }
  }

  grouping MDT-IR-REMOTE-ENTRY-TABLE {
    description
      "Common node of vrf, default-context";
    container ir-remote-entries {
      description
        "PIM MDT ir remote table";
      list ir-remote-entry {
        key "tunnel-type label";
        description
          "PIM MDT ir remote table";
        leaf tunnel-type {
          type uint32;
          description
            "Tunnel Type";
        }
        leaf label {
          type uint32;
          description
            "Label";
        }
        uses PIM-MDT-DATA-IR-BAG;
      }
    }
  }

  grouping MDT-RSVP-TE-LOCAL-ENTRY-TABLE {
    description
      "Common node of vrf, default-context";
    container rsvp-te-local-entries {
      description
        "PIM MDT RSVP-TE local table";
      list rsvp-te-local-entry {
        key "p2mp-id tunnel-id extended-tunnel-d core-id";
        description
          "PIM MDT RSVP-TE local table";
        leaf p2mp-id {
          type uint32;
          description
            "Core ID";
        }
        leaf tunnel-id {
          type uint32;
          description
            "Tunnel ID";
        }
        leaf extended-tunnel-d {
          type inet:ip-address-no-zone;
          description
            "Extended Tunnel ID";
        }
        leaf core-id {
          type uint32;
          description
            "Core ID";
        }
        uses PIM-MDT-DATA-RSVPTE-BAG;
      }
    }
  }

  grouping MDT-PREFIX-LOCAL-TABLE {
    description
      "Common node of vrf, default-context";
    container mdt-prefix-locals {
      description
        "PIM MDT prefix local table";
      list mdt-prefix-local {
        key "mdt-prefix";
        description
          "PIM MDT prefix information";
        leaf mdt-prefix {
          type inet:ip-address-no-zone;
          description
            "MDT data prefix address";
        }
        uses PIM-MDT-DATA-PFX-BAG;
      }
    }
  }

  grouping MDT-MLDP-CACHE-TABLE {
    description
      "Common node of vrf, default-context";
    container mdt-mldp-caches {
      description
        "MLDP MDT cache";
      list mdt-mldp-cache {
        key "core-source-address customer-source-address customer-group-address";
        description
          "MLDP MDT cache information";
        leaf core-source-address {
          type inet:ip-address-no-zone;
          description
            "Core source IP address";
        }
        leaf customer-source-address {
          type inet:ip-address-no-zone;
          description
            "Customer source IP address";
        }
        leaf customer-group-address {
          type inet:ip-address-no-zone;
          description
            "Customer group IP address";
        }
        uses PIM-MDT-CACHE-BAG;
      }
    }
  }

  grouping PE-TABLE {
    description
      "Common node of vrf, default-context";
    container pes {
      description
        "PIM MVPN PE Information";
      list pe {
        key "pe-prefix";
        description
          "PIM PE Address information";
        leaf pe-prefix {
          type inet:ip-address-no-zone;
          description
            "PE address";
        }
        uses PIM-PE-BAG;
      }
    }
  }

  grouping RP-RELAY-TABLE {
    description
      "Common node of auto-rp, bsr";
    container rp-relays {
      description
        "PIM rp-relay database";
      list rp-relay {
        key "vrf-name";
        description
          "PIM Relay";
        leaf vrf-name {
          type xr:Cisco-ios-xr-string {
            length "1..32";
          }
          description
            "VRF name ";
        }
        uses PIM-RELAY-BAG;
      }
    }
  }

  grouping ACTIVE {
    description
      "Common node of mvpn, ipv6-mvpn";
    container active {
      description
        "Active Process";
      uses VRF-TABLE;
      uses DEFAULT-CONTEXT;
      uses PROCESS;
    }
  }

  grouping MDT-RSVP-TE-REMOTE-ENTRY-TABLE {
    description
      "Common node of vrf, default-context";
    container rsvp-te-remote-entries {
      description
        "PIM MDT RSVP-TE remote table";
      list rsvp-te-remote-entry {
        key "p2mp-id tunnel-id extended-tunnel-id";
        description
          "PIM MDT RSVP-TE remote table";
        leaf p2mp-id {
          type uint32;
          description
            "Core ID";
        }
        leaf tunnel-id {
          type uint32;
          description
            "Tunnel ID";
        }
        leaf extended-tunnel-id {
          type inet:ip-address-no-zone;
          description
            "Extended Tunnel ID";
        }
        uses PIM-MDT-DATA-RSVPTE-BAG;
      }
    }
  }

  grouping MDT-DATABASE-IR {
    description
      "Common node of vrf, default-context";
    container mdt-database-ir {
      description
        "PIM MDT IR tunnel database";
      uses PIM-MDT-TUNNEL-DB-BAG;
    }
  }

  grouping REMOTE-ENTRY-TABLE {
    description
      "Common node of vrf, default-context";
    container remote-entries {
      description
        "PIM MDT mldp remote table";
      list remote-entry {
        key "tree-type opaque-type oui vpn-index core-id";
        description
          "PIM MDT mldp remote table";
        leaf tree-type {
          type Pim-mdt-mldp;
          description
            "Tree Type";
        }
        leaf opaque-type {
          type Pim-mldp-opaque;
          description
            "Opaque Type";
        }
        leaf oui {
          type uint32;
          description
            "OUI";
        }
        leaf vpn-index {
          type uint32;
          description
            "VPN Index";
        }
        leaf core-id {
          type uint32;
          description
            "Core ID";
        }
        uses PIM-MDT-DATA-MLDP-BAG;
      }
    }
  }

  grouping MDT-SEGMENT-ROUTING-LOCAL-ENTRY-TABLE {
    description
      "Common node of vrf, default-context";
    container mdt-segment-routing-local-entries {
      description
        "PIM MDT Segment Routing local table";
      list mdt-segment-routing-local-entry {
        key "tree-id";
        description
          "PIM MDT Segment Routing local entry";
        leaf tree-id {
          type uint32;
          description
            "Tree ID";
        }
        uses PIM-MDT-DATA-TREESID-BAG;
      }
    }
  }

  grouping DEFAULT-CONTEXT {
    description
      "Common node of active, standby";
    container default-context {
      description
        "Default Context";
      uses MDT-INTERFACE;
      uses LOCAL-ENTRY-TABLE;
      uses MDT-RSVP-TE-REMOTE-ENTRY-TABLE;
      uses MDT-CACHE-SUMMARY;
      uses MDT-DATABASE-IR;
      uses MDT-GRE-CACHE-TABLE;
      uses MDT-IR-REMOTE-ENTRY-TABLE;
      uses MDT-DATABASE-RSVP-TE;
      uses BSR;
      uses BGP-AF-TABLE;
      uses MDT-RSVP-TE-LOCAL-ENTRY-TABLE;
      uses MDT-PREFIX-REMOTE-TABLE;
      uses MDT-CACHE-TABLE;
      uses MDT-RSVP-TE-CACHE-TABLE;
      uses AUTO-RP;
      uses MDT-SEGMENT-ROUTING-LOCAL-ENTRY-TABLE;
      uses REMOTE-ENTRY-TABLE;
      uses MDT-IR-CACHE-TABLE;
      uses PE-TABLE;
      uses MDT-SEGMENT-ROUTING-REMOTE-ENTRY-TABLE;
      uses MDT-MLDP-CACHE-TABLE;
      uses MDT-IR-LOCAL-ENTRY-TABLE;
      uses MDT-PREFIX-LOCAL-TABLE;
    }
  }

  grouping MDT-CACHE-SUMMARY {
    description
      "Common node of vrf, default-context";
    container mdt-cache-summary {
      description
        "PIM MDT cache summary";
      uses PIM-MDT-CACHE-SUMM-BAG;
    }
  }

  grouping STANDBY {
    description
      "Common node of mvpn, ipv6-mvpn";
    container standby {
      description
        "Standby Process";
      uses VRF-TABLE;
      uses DEFAULT-CONTEXT;
      uses PROCESS;
    }
  }

  grouping MDT-SEGMENT-ROUTING-REMOTE-ENTRY-TABLE {
    description
      "Common node of vrf, default-context";
    container mdt-segment-routing-remote-entries {
      description
        "PIM MDT Segment Routing remote table";
      list mdt-segment-routing-remote-entry {
        key "tree-id";
        description
          "PIM MDT Segment Routing remote table";
        leaf tree-id {
          type uint32;
          description
            "Tree ID";
        }
        uses PIM-MDT-DATA-TREESID-BAG;
      }
    }
  }

  container mvpn {
    config false;
    description
      "MVPN operational data";
    uses ACTIVE;
    uses STANDBY;
  }
  container ipv6-mvpn {
    config false;
    description
      "IPv6 MVPN operational data";
    uses ACTIVE;
    uses STANDBY;
  }
}
