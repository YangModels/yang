module Cisco-IOS-XR-um-traps-mpls-ldp-cfg {
  namespace "http://cisco.com/ns/yang/Cisco-IOS-XR-um-traps-mpls-ldp-cfg";
  prefix um-traps-mpls-ldp-cfg;

  import cisco-semver {
    prefix semver;
  }
  import Cisco-IOS-XR-um-snmp-server-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR traps mpls-ldp package configuration.
     
     This YANG module augments the
     modules with configuration data.
     
     Copyright (c) 2019, 2022 by Cisco Systems, Inc.
     All rights reserved.";

  revision 2019-10-10 {
    description
      "Initial version";
    semver:module-version "1.0.0";
  }

  augment "/a1:snmp-server/a1:traps" {
    container mpls {
      description
        "Enable SNMP MPLS traps";
      container ldp {
        description
          "Enable MPLS LDP traps";
        container down {
          presence "Indicates a down node is configured.";
          description
            "Enable MPLS LDP session down traps";
        }
        container up {
          presence "Indicates a up node is configured.";
          description
            "Enable MPLS LDP session up traps";
        }
        container threshold {
          presence "Indicates a threshold node is configured.";
          description
            "Enable MPLS LDP threshold traps";
        }
      }
    }
  }
}
