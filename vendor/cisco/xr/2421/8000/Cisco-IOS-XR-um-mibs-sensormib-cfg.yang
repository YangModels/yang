module Cisco-IOS-XR-um-mibs-sensormib-cfg {
  namespace "http://cisco.com/ns/yang/Cisco-IOS-XR-um-mibs-sensormib-cfg";
  prefix um-mibs-sensormib-cfg;

  import Cisco-IOS-XR-um-snmp-server-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mibs-sensormib package configuration.
     
     This YANG module augments the
     modules with configuration data.
     
     Copyright (c) 2020-2022 by Cisco Systems, Inc.
     All rights reserved.";

  revision 2022-07-11 {
    description
      "Added missing description statement to nodes";
  }
  revision 2020-03-23 {
    description
      "Initial release";
  }

  augment "/a1:snmp-server/a1:traps" {
    description
      "This augment extends snmp-server traps nodes
       configuration";
    container sensor {
      presence "Indicates a sensor node is configured.";
      description
        "Enable SNMP entity sensor traps";
    }
  }
  augment "/a1:snmp-server-mibs" {
    description
      "This augment extends snmp-server-mibs nodes
       configuration";
    container sensormib {
      description
        "sensormib related config";
      container cache {
        presence "Indicates a cache node is configured.";
        description
          "Enables sensormib caching";
      }
    }
  }
}
