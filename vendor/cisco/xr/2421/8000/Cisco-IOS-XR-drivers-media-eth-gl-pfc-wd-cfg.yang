module Cisco-IOS-XR-drivers-media-eth-gl-pfc-wd-cfg {
  namespace "http://cisco.com/ns/yang/Cisco-IOS-XR-drivers-media-eth-gl-pfc-wd-cfg";
  prefix drivers-media-eth-gl-pfc-wd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-media-eth-gl-pfc-wd package configuration.
     
     This module contains definitions
     for the following management objects:
       priority-flow-control-watchdog: Global Priority Flow Control
         Watchdog options
     
     Copyright (c) 2013-2019, 2022 by Cisco Systems, Inc.
     All rights reserved.";

  revision 2019-08-15 {
    description
      "Global pfc watchdog configuration.";
    semver:module-version "1.0.0";
  }
  revision 2019-04-05 {
    description
      "Establish semantic version baseline.";
  }
  revision 2015-11-09 {
    description
      "IOS XR 6.0 revision.";
  }

  typedef Ethernet-pfcgwd {
    type enumeration {
      enum "off" {
        value 0;
        description
          "Disable priority flow control watchdog";
      }
      enum "on" {
        value 1;
        description
          "Enable priority flow control watchdog";
      }
    }
    description
      "Ethernet pfcgwd";
  }

  container priority-flow-control-watchdog {
    description
      "Global Priority Flow Control Watchdog options";
    leaf auto-restore-multiplier {
      type uint32 {
        range "0..100";
      }
      description
        "Configure global priority flow-control watchdog
         Auto Restore Multiplier";
    }
    leaf interval {
      type uint32 {
        range "100..1000";
      }
      description
        "Configure global priority flow-control watchdog
         interval";
    }
    leaf shutdown-multiplier {
      type uint32 {
        range "1..10";
      }
      description
        "Configure global priority flow-control watchdog
         interval multiplier";
    }
    leaf mode {
      type Ethernet-pfcgwd;
      description
        "Configure global priority flow-control watchdog
         mode";
    }
  }
}
