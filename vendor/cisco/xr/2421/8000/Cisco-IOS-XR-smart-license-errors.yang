submodule Cisco-IOS-XR-smart-license-errors {
  belongs-to Cisco-IOS-XR-smart-license-act {
    prefix smart-license-act;
  }

  organization
    "Cisco Systems, Inc.";
  contact
    "Cisco Systems, Inc.
     Customer Service
     Postal: 170 W Tasman Drive
     San Jose, CA 95134
     Tel: +1 1800 553-NETS
     E-mail: cs-yang@cisco.com";
  description
    "Smart licensing error codes.
     
     Copyright (c) 2016-2020 by Cisco Systems, Inc.
     All rights reserved.";

  revision 2020-02-03 {
    description
      "Added support for policies & usage reporting.
       deprecated some functionality.";
    reference "https://software.cisco.com/";
  }
  revision 2017-10-11 {
    description
      "Initial Revision of the error codes";
    reference "https://software.cisco.com/";
  }

  typedef error-enum {
    type enumeration {
      enum "success" {
        value 0;
        description
          "Success";
      }
      enum "malloc" {
        value 1;
        description
          "Malloc Error";
      }
      enum "nullpointer" {
        value 2;
        description
          "Null pointer Error,
           it may also mean non existence of file
           in cases where files are provided as input";
      }
      enum "error3" {
        value 3;
        description
          "deprecated DO NOT remove";
      }
      enum "error4" {
        value 4;
        description
          "deprecated DO NOT remove";
      }
      enum "error5" {
        value 5;
        description
          "deprecated DO NOT remove";
      }
      enum "BadInputParams" {
        value 6;
        description
          "Bad input parameter";
      }
      enum "error7" {
        value 7;
        description
          "deprecated DO NOT remove";
      }
      enum "badhandle" {
        value 8;
        description
          "Bad handle";
      }
      enum "notfound" {
        value 9;
        description
          "The requested item was not found";
      }
      enum "notsupported" {
        value 10;
        description
          "The requested operation is not supported";
      }
      enum "alreadyinit" {
        value 11;
        description
          "Init failed because the agent is already initialized";
      }
      enum "notinit" {
        value 12;
        description
          "API failed because the agent is not initialized";
      }
      enum "smfailtocreate" {
        value 13;
        description
          "State machine creation failed";
      }
      enum "smfailtorun" {
        value 14;
        description
          "State machine not running";
      }
      enum "smfailtoinit" {
        value 15;
        description
          "State machine failed to init";
      }
      enum "smfailtodestroy" {
        value 16;
        description
          "State machine failed to destroy";
      }
      enum "msgparse" {
        value 17;
        description
          "message parsing error";
      }
      enum "msgbuild" {
        value 18;
        description
          "message building error";
      }
      enum "notenabled" {
        value 19;
        description
          "Smart Agent not enabled";
      }
      enum "invalidrequest" {
        value 20;
        description
          "Smart Agent request invalid";
      }
      enum "init" {
        value 21;
        description
          "General initialization error. We call a number of
           system routines to
           initialize system resources and we can't translate their error
           codes to Smart Agent error codes. The log should have a detailed
           description of the error.";
      }
      enum "failtosetstate" {
        value 22;
        description
          "Smart Agent Fail to set state";
      }
      enum "unsupportedresponse" {
        value 23;
        description
          "Unsupported response type";
      }
      enum "invalidresponse" {
        value 24;
        description
          "Invalid response type";
      }
      enum "storagefailtostore" {
        value 25;
        description
          "Smart Agent Trusted Storage failed to store*";
      }
      enum "storagefailtoretrieve" {
        value 26;
        description
          "Smart Agent Trusted Storage failed to retrieve*";
      }
      enum "nullccoidtoken" {
        value 27;
        description
          "Null CCOId and IdToken";
      }
      enum "matchidentifier" {
        value 28;
        description
          "Product Instance identifier failed to match";
      }
      enum "matchvendor" {
        value 29;
        description
          "Vendor string failed to match";
      }
      enum "matchnonce" {
        value 30;
        description
          "nonce failed to match";
      }
      enum "commdisabled" {
        value 31;
        description
          "communication channel error. Comm layer (call home) is disabled ";
      }
      enum "commsend" {
        value 32;
        description
          "Call Home message send error. probably a timeout so we
           will retry the send. any other error from the comm send should
           be a permanent failure";
      }
      enum "commresponse" {
        value 33;
        description
          "Call Home message send response error";
      }
      enum "communkown" {
        value 34;
        description
          "Call Home unknown error";
      }
      enum "smpostnotallow" {
        value 35;
        description
          "State machine Operation not permitted";
      }
      enum "reqmsgmissingmandatoryfield" {
        value 36;
        description
          "Missing mandatory field in request message";
      }
      enum "responsefailed" {
        value 37;
        description
          "We received a failure status in a response message.
           The log will contain a error message";
      }
      enum "pinotinit" {
        value 38;
        description
          "PI not initialized ";
      }
      enum "alreadyenabled" {
        value 39;
        description
          "The agent cannot be enabled more than once";
      }
      enum "alreadyregistered" {
        value 40;
        description
          "The agent is already registered";
      }
      enum "certinvalid" {
        value 41;
        description
          "The certificate is invalid ";
      }
      enum "certexpired" {
        value 42;
        description
          "The certificate has expired ";
      }
      enum "notregistered" {
        value 43;
        description
          "The agent is not registered ";
      }
      enum "csrgenerationfailed" {
        value 44;
        description
          "The CSR generation failed ";
      }
      enum "verifysignaturefailed" {
        value 45;
        description
          "Signature Verification failed ";
      }
      enum "generatesignaturefailed" {
        value 46;
        description
          "Signature Generation failed ";
      }
      enum "signcertverificationfailed" {
        value 47;
        description
          "Signing Certificate Verification failed ";
      }
      enum "nodecertverificationfailed" {
        value 48;
        description
          "Node Certificate Verification failed ";
      }
      enum "parsecertificatefailed" {
        value 49;
        description
          "Certificate Parsing failed ";
      }
      enum "cryptorootcaimportfailed" {
        value 50;
        description
          "Root Certificate Import failed ";
      }
      enum "taginvalid" {
        value 51;
        description
          "The tag is invalid ";
      }
      enum "standby" {
        value 52;
        description
          "Smart agent is running on a standby RP ";
      }
      enum "registrationinprogress" {
        value 53;
        description
          "Smart agent id token registration is in progress";
      }
      enum "commretry" {
        value 54;
        description
          "Call Home is not ready because it is in restart ipc";
      }
      enum "authrenewinprogress" {
        value 55;
        description
          "Smart agent authorization renew is in progress";
      }
      enum "idcertrenewinprogress" {
        value 56;
        description
          "Smart agent id certificate renew is in progress";
      }
      enum "noudichange" {
        value 57;
        description
          "Udi List Has Not been changed ";
      }
      enum "callhomeserviceoff" {
        value 58;
        description
          "Call home service cannot be turned on. ";
      }
      enum "msgexecinprogress" {
        value 59;
        description
          "message execution already in progress";
      }
      enum "msgexecinproglocked" {
        value 60;
        description
          "message execution in progress flag is locked";
      }
      enum "certmatchessubsetudis" {
        value 61;
        description
          "The ID cert only matches some of the system Udi's";
      }
      enum "storagegroupchangeincomplete" {
        value 62;
        description
          "A Storage group has not all been changed";
      }
      enum "storagemgmtnotinit" {
        value 63;
        description
          "Storage Management is not Init";
      }
      enum "tspathnotchanged" {
        value 64;
        description
          "TS System Path list is not changed ";
      }
      enum "cryptoinitnotcompleted" {
        value 65;
        description
          "Crypto Initialization is not completed";
      }
      enum "notinunidentified" {
        value 66;
        description
          "The agent is not in unidentified state ";
      }
      enum "platformpathinvalid" {
        value 67;
        description
          "The platform provided path is invalid ";
      }
      enum "platformudiinvalid" {
        value 68;
        description
          "The platform provided UDI is invalid ";
      }
      enum "storageobjfailtocreate" {
        value 69;
        description
          "failed to create Trusted Store object ";
      }
      enum "storageobjfailtoerase" {
        value 70;
        description
          "failed to erase trusted store object ";
      }
      enum "storageobjdoesnotexist" {
        value 71;
        description
          "trusted storage object/file does not exist";
      }
      enum "messageeventexceedspeer" {
        value 72;
        description
          "The message event is beyond the peer ";
      }
      enum "codevalidationfailed" {
        value 73;
        description
          "Validation of the authorization key failed.
           It probably does not match the UDI. The device will go to
           the unidentified state (not registered)";
      }
      enum "reserved" {
        value 74;
        description
          "operation not supported because the agent is running in
           permanent License reservation mode";
      }
      enum "noreservationinprogress" {
        value 75;
        description
          "No license reservation is in progress ";
      }
      enum "noauthorizationinstalled" {
        value 76;
        description
          "No authorization code instaled in device ";
      }
      enum "reservationmismatch" {
        value 77;
        description
          "The reservation authorization code does not match the
           reservation request code";
      }
      enum "notreservationmode" {
        value 78;
        description
          "not in license reservation mode ";
      }
      enum "reservationerror" {
        value 79;
        description
          " General reservation error. This is used with the API
           functions that are called by the CLI. the API will return a
           very specific displayString that describes the error.";
      }
      enum "sysmgrinit" {
        value 80;
        description
          "Sysmgr Init Failed ";
      }
      enum "alreadyexists" {
        value 81;
        description
          "Generic error for something already existing ";
      }
      enum "listinsertfailed" {
        value 82;
        description
          "Error in object insert to xos list ";
      }
      enum "sessionmgmtnotinit" {
        value 83;
        description
          "Session management not initialized";
      }
      enum "listinitfailed" {
        value 84;
        description
          "Error Creating Linked List";
      }
      enum "listbusy" {
        value 85;
        description
          "List in use";
      }
      enum "noclients" {
        value 86;
        description
          "No Connected Clients ";
      }
      enum "ipc" {
        value 87;
        description
          "Generic IPC layer error ";
      }
      enum "ipcopen" {
        value 88;
        description
          "The IPC socket open error ";
      }
      enum "ipcinit" {
        value 89;
        description
          "The IPC Initialization error ";
      }
      enum "ipcconnect" {
        value 90;
        description
          "The IPC Connection error ";
      }
      enum "ipcevents" {
        value 91;
        description
          "The IPC Server Event error ";
      }
      enum "ipcmgmt" {
        value 92;
        description
          "The IPC Management error ";
      }
      enum "ipcsend" {
        value 93;
        description
          "The IPC Send error ";
      }
      enum "ipcreceive" {
        value 94;
        description
          "The IPC Receive error ";
      }
      enum "ipctimeout" {
        value 95;
        description
          "The IPC timeout error ";
      }
      enum "enqueuefailed" {
        value 96;
        description
          "Failed to enqueue a message to the IPC Queue";
      }
      enum "dequeuefailed" {
        value 97;
        description
          "Failed to dequeue a message from the IPC queue";
      }
      enum "shuttingdown" {
        value 98;
        description
          "Fail because we are about to shutdown and we need
           to stop processing any more messages or responses";
      }
      enum "couldnotvalidatetrustchain" {
        value 99;
        description
          "Could not validate Trust Chain";
      }
      enum "reservationalreadyinstalled" {
        value 100;
        description
          "The reservation authorization code is already installed ";
      }
      enum "reservationinstallparsefail" {
        value 101;
        description
          "Failed to parse reservation authorization code ";
      }
      enum "base64encoding" {
        value 102;
        description
          "Base64 encoding failed ";
      }
      enum "base64decoding" {
        value 103;
        description
          "Base64 decoding failed ";
      }
      enum "invalidsoftwareidtag" {
        value 104;
        description
          "Failed to find UUID inside software id tag ";
      }
      enum "certificatemismatch" {
        value 105;
        description
          "Development certificates are being used with Production
           Root certificate ";
      }
      enum "noreservation" {
        value 106;
        description
          "No License Reservation ";
      }
      enum "agentunreachable" {
        value 107;
        description
          "the agent Daemon is unreachable ";
      }
      enum "ignoreevent" {
        value 108;
        description
          "the agent ignores event ";
      }
      enum "b58overflow" {
        value 109;
        description
          "Base58 overflow, number too large. ";
      }
      enum "b58decode" {
        value 110;
        description
          "Base58 decode error. ";
      }
      enum "b58badlen" {
        value 111;
        description
          "Bad base58 length. ";
      }
      enum "b58invdigit" {
        value 112;
        description
          "Invalid base58 digit. ";
      }
      enum "b58decodeoverflow" {
        value 113;
        description
          "Overflow detected during base58 decode. ";
      }
      enum "reservationversionoutofbound" {
        value 114;
        description
          "Reservation version out of bound ";
      }
      enum "base58encode" {
        value 115;
        description
          "General Base58 encoding error ";
      }
      enum "duplicatedentry" {
        value 116;
        description
          "General error code for adding item that already exists.
           Used in App HA setup when adding an HA peer device info that
           is already added ";
      }
      enum "missingentry" {
        value 117;
        description
          "General error code for trying to remove item that do
           not exist. Used in App HA setup when removing an HA peer device
           info that does not exist";
      }
      enum "badpeerinfoformat" {
        value 118;
        description
          "The given peer info contain incorrect data format ";
      }
      enum "badapplicationhaattributedataset" {
        value 119;
        description
          "The given handle attribute list contains incomplete
           application HA attributes";
      }
      enum "reservationinprogress" {
        value 120;
        description
          "license reservation is in progress ";
      }
      enum "xdmcreatehandle" {
        value 121;
        description
          "The xos_dm_create() failure causes this error code to be return ";
      }
      enum "versionmismatchinentitlementrsp" {
        value 122;
        description
          "Version in entitlement response message does not match
           with the
           one already saved from last completed response message. We need
           to send entitlement request again with proper version and data";
      }
      enum "harolenotsupported" {
        value 123;
        description
          "Given valid HA Role is not supported by this operation.
           For Application HA valid roles are Active or Standby.";
      }
      enum "apphainvalidcharacter" {
        value 124;
        description
          "Application HA attribute contains invalid character.
           Character set supported is alphanumeric.";
      }
      enum "apphaaddpeerfromsamedevice" {
        value 125;
        description
          "The peer info given is from the same device. ";
      }
      enum "apphaappduplicatedinstance" {
        value 126;
        description
          "When setting Application HA Attribute, a different
           handle with exactly
           same tag, app ha name, app ha id exists in the agent.";
      }
      enum "versionmismatchinregresponse" {
        value 127;
        description
          "Backend server does not support AppHA enabled message
           version. So
           registration response (from backend) received with status set as
           FAILED or VERSION_TOO_HIGH.";
      }
      enum "conversionnocb" {
        value 128;
        description
          "Migration function was called but there are no i
           call backs registered ";
      }
      enum "conversionnotallowed" {
        value 129;
        description
          "Migration was not enabled with the
           MIGRATION_ALLOWED property ";
      }
      enum "conversioninprogress" {
        value 130;
        description
          "Migration is in progress ";
      }
      enum "conversionalreadystarted" {
        value 131;
        description
          "Migration has already been started ";
      }
      enum "conversionnotenabled" {
        value 132;
        description
          "Migration is not enabled ";
      }
      enum "versionconversionnotsupported" {
        value 133;
        description
          "The backend server this device is connected to does
           not support conversion";
      }
      enum "noconversioninprogress" {
        value 134;
        description
          "No conversion in progress";
      }
      enum "cryptoversionmismatch" {
        value 135;
        description
          "Loaded OpenSSL version is not the same as used for
           development";
      }
      enum "conversionstoppedpartially" {
        value 136;
        description
          "Some Smart Licensing Conversion jobs stopped successfully";
      }
      enum "utilityenabled" {
        value 137;
        description
          "Operation is not supported because Utility management
           is enabled";
      }
      enum "utilitynotenabled" {
        value 138;
        description
          "Utility is not enabled";
      }
      enum "transportnotavailable" {
        value 139;
        description
          "Transport layer not abvailable";
      }
      enum "fqdn" {
        value 140;
        description
          "Unable to get FQDN";
      }
      enum "thirdparty" {
        value 141;
        description
          "The current transport type does not support this feature";
      }
      enum "transporttype" {
        value 142;
        description
          "The transport type needed is not configured";
      }
      enum "transportconfig" {
        value 143;
        description
          "A feature required a specific transport configuration
           which is not configured";
      }
      enum "IPCMsgVersion" {
        value 144;
        description
          "Internal IPC error indicating an IPC version mismatch";
      }
      enum "IPCFeatureDisabled" {
        value 145;
        description
          "Internal IPC error.
           The feature related to the IPC message is not available";
      }
      enum "IPCErrorCode" {
        value 146;
        description
          "Internal IPC error.
           The other side does not understand this error code";
      }
      enum "NotAuthorized" {
        value 147;
        description
          "Entitlement not authorized.
           Returned from the entitlement request call if the
           entitlement tag (license) cannot be authorized.
           The feature should not run if it gets this return code.
           This error code will only be returned under the
           following conditions:
            - Specific License Reservation (SLR) mode is in use
              - The authorization code installed does not contain
                the requested entitlement tag.
              - The authorization code installed does not contain
                enough counts to satisfy the request.
            - The entitlement tag is export restricted and is
              not export authorized.";
      }
      enum "ExportAllowed" {
        value 148;
        description
          "When the global export compliance flag is set to true,
           this error code be returned when calling export control
           APIs functions";
      }
      enum "NotExportRestricted" {
        value 149;
        description
          "This error code will be returned when calling export
           control API functions to request or return export
           authorization key for a feature
           that is not export restricted.";
      }
      enum "NoKey" {
        value 150;
        description
          "No authorization key to be returned.
           This error code will be returned when there is a
           request for export return key but the authorization
           key for the feature does not exist.";
      }
      enum "OperationInProgress" {
        value 151;
        description
          "The requested operation is already in progress";
      }
      enum "ReservationNoAuthCodeFound" {
        value 152;
        description
          "No authorization code found in meta file for the devices
           in this High Availability (HA) stack.
           Returned from the reservation install routine.";
      }
      enum "PreviouslyInstalled" {
        value 153;
        description
          "The user tried to install a reservation authorization
           code but it has been used previously";
      }
      enum "IsExportRestricted" {
        value 154;
        description
          "The Entitlement tag is export restricted";
      }
      enum "ExportRestrictedAuth" {
        value 155;
        description
          "Export authorization keys are installed";
      }
      enum "NoOperation" {
        value 156;
        description
          "There is no export key request or export return request
           in progress.";
      }
      enum "MsgSizeExceed" {
        value 157;
        description
          "Message size exceed the limit";
      }
      enum "TelemetryNotEnabled" {
        value 158;
        description
          "Telemetry not enabled";
      }
      enum "NoURL" {
        value 159;
        description
          "No URL is configured";
      }
      enum "AuthKeyRequestInProgress" {
        value 160;
        description
          "The export authorization key request is in progress";
      }
      enum "AuthKeyReturnInProgress" {
        value 161;
        description
          "The export authorization key return is in progress";
      }
      enum "ErrorOkTryAgain" {
        value 162;
        description
          "CSSM requested to try again";
      }
      enum "MismatchEntitlementRequest" {
        value 163;
        description
          "Mismatch in the entitlement request";
      }
      enum "InvalidAuthCodeType" {
        value 164;
        description
          "Invalid authorization code type for a particular operation";
      }
      enum "InvalidXML" {
        value 165;
        description
          "XML PArser fails to get an expected Node";
      }
      enum "ThreadDeadLock" {
        value 166;
        description
          "Mutex Error, This Thread already owns this lock";
      }
      enum "MutexPreviouslyInit" {
        value 167;
        description
          "Mutex Error. This Mutex was previously initialized";
      }
      enum "MutexInvalid" {
        value 168;
        description
          "Mutex Error, This is an invalid Mutex";
      }
      enum "MutexBusy" {
        value 169;
        description
          "Mutex Error. This Mutex is still busy and canot be destroyed";
      }
      enum "MutexNotOwner" {
        value 170;
        description
          "Mutex Error. The current thread is not the owner of the mutex";
      }
      enum "LicenseInUse" {
        value 171;
        description
          "Enforced/ExportRestricted License is in use";
      }
      enum "FailedToStoreInTheFile" {
        value 172;
        description
          "Error if it failed to store the data in the given file path";
      }
      enum "TrustCodeAlreadyInstalled" {
        value 173;
        description
          "Error if the user tries to generate trust request
           but trust code has already been installed";
      }
      enum "ErrorMax" {
        description
          "max error code";
      }
    }
    description
      "Smart License error codes returned by
       Smart Licensing RPC calls";
  }
}
