module Cisco-IOS-XR-man-http-lighttpd-yang-cfg {
  namespace "http://cisco.com/ns/yang/Cisco-IOS-XR-man-http-lighttpd-yang-cfg";
  prefix man-http-lighttpd-yang-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR man-http-lighttpd-yang package configuration.
     
     This module contains definitions
     for the following management objects:
       web: Webserver configuration commands
     
     Copyright (c) 2013-2019, 2022 by Cisco Systems, Inc.
     All rights reserved.";

  revision 2019-04-05 {
    description
      "Establish semantic version baseline.";
    semver:module-version "1.0.0";
  }
  revision 2017-09-07 {
    description
      "Fixed type translation error.";
  }
  revision 2015-11-09 {
    description
      "IOS XR 6.0 revision.";
  }

  container web {
    description
      "Webserver configuration commands";
    container server {
      description
        "Webserver configuration commands";
      container service {
        description
          "Web Service that needs to be activated";
        container restconf {
          presence "Indicates a restconf node is configured.";
          description
            "Restconf specific configurations";
          leaf http-port {
            type uint32;
            description
              "Port number http server is listening on";
          }
          leaf http-enable {
            type empty;
            description
              "Enable http connection in addition to https";
          }
          leaf https-port {
            type uint32;
            description
              "Port number https server is listening on";
          }
          leaf enable {
            type empty;
            mandatory true;
            description
              "Enable RESTCONF Service";
          }
        }
      }
    }
  }
}
