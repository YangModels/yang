module Cisco-IOS-XR-optics-driver-quad-cfg {
  namespace "http://cisco.com/ns/yang/Cisco-IOS-XR-optics-driver-quad-cfg";
  prefix optics-driver-quad-cfg;

  import cisco-semver {
    prefix semver;
  }
  import Cisco-IOS-XR-config-mda-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-driver-quad package configuration.
     
     This YANG module augments the
       Cisco-IOS-XR-config-mda-cfg
     module with configuration data.
     
     Copyright (c) 2013-2022 by Cisco Systems, Inc.
     All rights reserved.";

  revision 2021-03-02 {
    description
      "Augment MDA schema";
    semver:module-version "3.0.0";
  }
  revision 2019-04-05 {
    description
      "Establish semantic version baseline.";
    semver:module-version "1.0.1";
  }
  revision 2018-07-21 {
    description
      "Schema added.";
  }
  revision 2015-11-09 {
    description
      "IOS XR 6.0 revision.";
  }

  grouping QUAD-CONFIG-TABLE {
    description
      "Common node of active-node, preconfigured-node";
    container instances {
      description
        "quad configuration";
      list instance {
        key "inst-id";
        description
          "0 for LC ports, 1+ for MPA instances";
        leaf inst-id {
          type uint32 {
            range "0..5";
          }
          description
            "Instance number";
        }
        list quad-config {
          key "quad-id";
          description
            "none";
          container mode {
            description
              "select mode 10g or 25g for a quad(group of 2
               or 4 ports).";
            leaf speed {
              type string;
              description
                "speed 10g or 25g";
            }
          }
          leaf quad-id {
            type uint32 {
              range "0..11";
            }
            description
              "Quad number";
          }
        }
      }
    }
  }

  augment "/a1:preconfigured-nodes/a1:preconfigured-node" {
    description
      "This augment extends the configuration data of
       'Cisco-IOS-XR-config-mda-cfg'";
    uses QUAD-CONFIG-TABLE;
  }
  augment "/a1:active-nodes/a1:active-node" {
    description
      "This augment extends the configuration data of
       'Cisco-IOS-XR-config-mda-cfg'";
    uses QUAD-CONFIG-TABLE;
  }
}
