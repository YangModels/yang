module Cisco-IOS-XR-controller-ots-cfg {
  namespace "http://cisco.com/ns/yang/Cisco-IOS-XR-controller-ots-cfg";
  prefix controller-ots-cfg;

  import cisco-semver {
    prefix semver;
  }
  import Cisco-IOS-XR-ifmgr-cfg {
    prefix a1;
  }
  import oc-xr-mapping {
    prefix emmi;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ots package configuration.
     
     This YANG module augments the
       Cisco-IOS-XR-ifmgr-cfg
     module with configuration data.
     
     Copyright (c) 2013-2022 by Cisco Systems, Inc.
     All rights reserved.";

  revision 2021-06-01 {
    description
      "Added OTS TX Voa Attenuation and changed range for Ingress and Egress Ampli Gain Params";
    semver:module-version "1.0.0";
  }
  revision 2021-03-16 {
    description
      "Ingress/Egress Channel Attenuation config Params added for Ots Controller";
  }
  revision 2021-02-17 {
    description
      "Raman safety config Params added";
  }
  revision 2021-02-08 {
    description
      "Ingress/Egress safety config Params added";
  }
  revision 2020-09-02 {
    description
      "Raman Transmit Params added for Ots Controller";
  }
  revision 2020-08-21 {
    description
      "New Cfg Model Added for Ots Controller";
  }
  revision 2019-04-05 {
    description
      "Establish semantic version baseline.";
  }
  revision 2015-11-09 {
    description
      "IOS XR 6.0 revision.";
  }

  typedef Ots-ingress-egress-ampli-gain-range {
    type enumeration {
      enum "normal" {
        value 1;
        description
          "Normal Amplifier Gain Range";
      }
      enum "extended" {
        value 2;
        description
          "Extended Amplifier Gain Range";
      }
    }
    description
      "Ots ingress egress ampli gain range";
  }

  typedef Ots-back-reflection-state {
    type enumeration {
      enum "disable" {
        value 0;
        description
          "Back Reflection State, Disable";
      }
      enum "enable" {
        value 1;
        description
          "Back Reflection State, Enable";
      }
    }
    description
      "Ots back reflection state";
  }

  typedef Ots-safety-control-mode {
    type enumeration {
      enum "auto" {
        value 1;
        description
          "Automatic Safety Control Mode";
      }
      enum "disabled" {
        value 2;
        description
          "Disable Safety Control Mode";
      }
    }
    description
      "Ots safety control mode";
  }

  augment "/a1:interface-configurations/a1:interface-configuration" {
    description
      "This augment extends the configuration data of
       'Cisco-IOS-XR-ifmgr-cfg'";
    container ots {
      description
        "Ots controller configuration";
      container ingress-channel-slice-attns {
        description
          "Configure Ingress Channel Slice";
        list ingress-channel-slice-attn {
          key "ingress-channel-slice-attn";
          description
            "Configure Ingress Channel Slice Attenuation
             Value";
          leaf ingress-channel-slice-attn {
            type uint32 {
              range "1..1548";
            }
            description
              "Ingress Channel Slice Attenuation";
          }
          leaf ingress-channel-slice-attnvalue {
            type uint32 {
              range "0..250";
            }
            mandatory true;
            description
              "Ingress Channel Slice Attenuation Value";
          }
        }
      }
      container raman-tx-powers {
        description
          "Configure Raman Transmit Power Parameter";
        list raman-tx-power {
          key "raman-tx-power-instance";
          description
            "Configure RamanTxPower Value";
          leaf raman-tx-power-instance {
            type uint32 {
              range "1..5";
            }
            description
              "Raman Tx Power Instance";
          }
          leaf raman-tx-power-value {
            type uint32 {
              range "3500..36000";
            }
            mandatory true;
            description
              "Raman Tx Power value";
          }
        }
      }
      container egress-channel-slice-attns {
        description
          "Configure Egress Channel Slice";
        list egress-channel-slice-attn {
          key "egress-channel-slice-attn";
          description
            "Configure Egress Channel Slice Attenuation
             Value";
          leaf egress-channel-slice-attn {
            type uint32 {
              range "1..1548";
            }
            description
              "Egress Channel Slice Attenuation";
          }
          leaf egress-channel-slice-attnvalue {
            type uint32 {
              range "0..250";
            }
            mandatory true;
            description
              "Egress Channel Slice Attenuation Value";
          }
        }
      }
      leaf ots-raman-br-high-threshold {
        type int32 {
          range "-500..300";
        }
        description
          "Select Raman Back Reflection High Threshold(in
           units of 0.1dBm)";
      }
      leaf ots-egress-safety-control-mode {
        type Ots-safety-control-mode;
        description
          "Configure Egress safety Control Mode";
      }
      leaf ots-ingress-amplifier-gain {
        type uint32 {
          range "80..380";
        }
        description
          "Select Amplifier Gain value(in units of 0.1dBm)";
      }
      leaf ots-raman-br {
        type Ots-back-reflection-state;
        description
          "Select Raman Back Reflection as Enable or
           Disable";
      }
      leaf ots-ingress-osri {
        type boolean;
        description
          "Configure Ingress Optical safety remote
           interlock (OSRI)";
      }
      leaf ots-ingress-amplifier-gain-degrade-high-threshold {
        type uint32 {
          range "0..500";
        }
        description
          "Select Ingress Amplifier Gain Degrade High
           Threshold(in units of 0.1dBm)";
      }
      leaf ots-tx-voa-attenuation {
        type uint32 {
          range "0..200";
        }
        description
          "Select TX Voa Attenuation Setpoint(in units of
           0.1dBm)";
        emmi:map-to {
          emmi:function "oc_opt_att_cfg_attenuation_to_high" {
            emmi:category "manual_function";
          }
        }
      }
      leaf ots-ingress-safety-control-mode {
        type Ots-safety-control-mode;
        description
          "Configure Ingress safety Control Mode";
      }
      leaf ots-ingress-force-apr {
        type boolean;
        description
          "Configure Ingress Optical Force Automatic Power
           Reduction";
      }
      leaf ots-raman-force-apr {
        type boolean;
        description
          "Configure Raman Optical Force Automatic Power
           Reduction";
      }
      leaf ots-egress-amplifier-gain-degrade-low-threshold {
        type uint32 {
          range "0..500";
        }
        description
          "Select Egress Amplifier Gain Degrade Low
           Threshold(in units of 0.1dBm)";
      }
      leaf ots-egress-ampli-br-high-threshold {
        type int32 {
          range "-500..300";
        }
        description
          "Select Egress Ampli Back Reflection High
           Threshold(in units of 0.1dBm)";
      }
      leaf ots-ingress-amplifier-gain-degrade-low-threshold {
        type uint32 {
          range "0..500";
        }
        description
          "Select Ingress Amplifier Gain Degrade Low
           Threshold(in units of 0.1dBm)";
      }
      leaf ots-egress-amplifier-tilt {
        type int32 {
          range "-50..50";
        }
        description
          "Select Amplifier Tilt value(in units of 0.1dB)";
      }
      leaf ots-raman-safety-control-mode {
        type Ots-safety-control-mode;
        description
          "Configure Raman safety Control Mode";
      }
      leaf ots-egress-amplifier-gain {
        type uint32 {
          range "80..380";
        }
        description
          "Select Amplifier Gain value(in units of 0.1dBm)";
      }
      leaf ots-egress-amplifier-gain-degrade-high-threshold {
        type uint32 {
          range "0..500";
        }
        description
          "Select Egress Amplifier Gain Degrade High
           Threshold(in units of 0.1dBm)";
      }
      leaf ots-raman-osri {
        type boolean;
        description
          "Configure Optical safety remote interlock
           (OSRI)";
      }
      leaf ots-egress-osri {
        type boolean;
        description
          "Configure Egress Optical safety remote
           interlock (OSRI)";
      }
      leaf ots-egress-ampli-br {
        type Ots-back-reflection-state;
        description
          "Configure Optical Egress Ampli Back Reflection
           as Enable or Disable";
      }
      leaf ots-egress-amplifier-gain-range {
        type Ots-ingress-egress-ampli-gain-range;
        description
          "Configure EGRESS AMPLIFIER GAIN Range";
      }
      leaf ots-ingress-amplifier-gain-range {
        type Ots-ingress-egress-ampli-gain-range;
        description
          "Configure INGRESS AMPLIFIER GAIN Range";
      }
      leaf ots-ingress-amplifier-tilt {
        type int32 {
          range "-50..50";
        }
        description
          "Select Amplifier Tilt value(in units of 0.1dB)";
      }
      leaf ots-egress-force-apr {
        type boolean;
        description
          "Configure Egress Optical Force Automatic Power
           Reduction";
      }
      emmi:map-to;
    }
    emmi:map-to;
  }
  emmi:mapping {
    emmi:package-name "ocopticalattenuator";
    emmi:model-id "xr";
    emmi:module-id "cisco_ios_xr_controller_ots_cfg";
    emmi:target {
      emmi:model-id "oc";
      emmi:module-id "openconfig_optical_attenuator";
      emmi:namespace "oc-types|http://openconfig.net/yang/openconfig-types";
      emmi:namespace "oc-opt-att|http://openconfig.net/yang/optical-attenuator";
      emmi:namespace "oc-platform|http://openconfig.net/yang/platform";
      emmi:namespace "oc-ext|http://openconfig.net/yang/openconfig-ext";
      emmi:namespace "oc-ext|http://openconfig.net/yang/openconfig-ext";
      emmi:namespace "oc-platform|http://openconfig.net/yang/platform";
      emmi:namespace "oc-yang|http://openconfig.net/yang/types/yang";
      emmi:namespace "oc-platform-types|http://openconfig.net/yang/platform-types";
      emmi:namespace "oc-alarm-types|http://openconfig.net/yang/alarms/types";
    }
  }
}
