module Cisco-IOS-XR-um-cont-optics-speed-cfg {
  namespace "http://cisco.com/ns/yang/Cisco-IOS-XR-um-cont-optics-speed-cfg";
  prefix um-cont-optics-speed-cfg;

  import Cisco-IOS-XR-types {
    prefix xr;
  }
  import Cisco-IOS-XR-um-interface-cfg {
    prefix a1;
  }
  import tailf-common {
    prefix tailf;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-optics-speed package configuration.
     
     This YANG module augments the
     modules with configuration data.
     
     Copyright (c) 2022 by Cisco Systems, Inc.
     All rights reserved.";

  revision 2022-07-11 {
    description
      "Added missing description statement to nodes";
  }
  revision 2022-06-01 {
    description
      "Adjusted controller augmentation hierarchy";
  }
  revision 2022-02-03 {
    description
      "Initial release";
  }

  feature optics {
    description
      "optics";
  }

  grouping CONT-BODY {
    description
      "Grouping for controller";
    leaf speed {
      when "../a1:controller-name[starts-with(text(),'Optics')]" {
        tailf:dependency "../a1:controller-name";
      }
      if-feature "optics";
      type xr:Cisco-ios-xr-string {
        length "1..800" {
          description
            "1g | 10g | 25g | 40g | 50g | 100g | 200g | 400g | none";
        }
      }
      description
        "Configure port speed";
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
