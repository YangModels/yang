module Cisco-IOS-XR-um-clock-cfg {
  namespace "http://cisco.com/ns/yang/Cisco-IOS-XR-um-clock-cfg";
  prefix um-clock-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clock package configuration.
     
     This YANG module augments the
     modules with configuration data.
     
     Copyright (c) 2020, 2022 by Cisco Systems, Inc.
     All rights reserved.";

  revision 2020-07-07 {
    description
      "Initial release";
  }

  container clock {
    description
      "Configure time-of-day clock";
    container timezone {
      description
        "Configure time zone";
      container Africa-Accra {
        presence "Indicates this node is configured.";
        description
          "GMT Africa/Accra 0:00";
      }
      container Africa-Addis_Ababa {
        presence "Indicates this node is configured.";
        description
          "EAT Africa/Addis_Ababa 3:00";
      }
      container Africa-Algiers {
        presence "Indicates this node is configured.";
        description
          "CET Africa/Algiers 1:00";
      }
      container Africa-Asmara {
        presence "Indicates this node is configured.";
        description
          "EAT Africa/Asmara 3:00";
      }
      container Africa-Asmera {
        presence "Indicates this node is configured.";
        description
          "EAT Africa/Asmera 3:00";
      }
      container Africa-Bamako {
        presence "Indicates this node is configured.";
        description
          "GMT Africa/Bamako 0:00";
      }
      container Africa-Bangui {
        presence "Indicates this node is configured.";
        description
          "WAT Africa/Bangui 1:00";
      }
      container Africa-Banjul {
        presence "Indicates this node is configured.";
        description
          "GMT Africa/Banjul 0:00";
      }
      container Africa-Bissau {
        presence "Indicates this node is configured.";
        description
          "GMT Africa/Bissau 0:00";
      }
      container Africa-Blantyre {
        presence "Indicates this node is configured.";
        description
          "CAT Africa/Blantyre 2:00";
      }
      container Africa-Brazzaville {
        presence "Indicates this node is configured.";
        description
          "WAT Africa/Brazzaville 1:00";
      }
      container Africa-Bujumbura {
        presence "Indicates this node is configured.";
        description
          "CAT Africa/Bujumbura 2:00";
      }
      container Africa-Cairo {
        presence "Indicates this node is configured.";
        description
          "EET Africa/Cairo 2:00";
      }
      container Africa-Casablanca {
        presence "Indicates this node is configured.";
        description
          "+01 Africa/Casablanca 1:00";
      }
      container Africa-Ceuta {
        presence "Indicates this node is configured.";
        description
          "CET Africa/Ceuta 1:00";
      }
      container Africa-Conakry {
        presence "Indicates this node is configured.";
        description
          "GMT Africa/Conakry 0:00";
      }
      container Africa-Dakar {
        presence "Indicates this node is configured.";
        description
          "GMT Africa/Dakar 0:00";
      }
      container Africa-Dar_es_Salaam {
        presence "Indicates this node is configured.";
        description
          "EAT Africa/Dar_es_Salaam 3:00";
      }
      container Africa-Djibouti {
        presence "Indicates this node is configured.";
        description
          "EAT Africa/Djibouti 3:00";
      }
      container Africa-Douala {
        presence "Indicates this node is configured.";
        description
          "WAT Africa/Douala 1:00";
      }
      container Africa-El_Aaiun {
        presence "Indicates this node is configured.";
        description
          "+01 Africa/El_Aaiun 1:00";
      }
      container Africa-Freetown {
        presence "Indicates this node is configured.";
        description
          "GMT Africa/Freetown 0:00";
      }
      container Africa-Gaborone {
        presence "Indicates this node is configured.";
        description
          "CAT Africa/Gaborone 2:00";
      }
      container Africa-Harare {
        presence "Indicates this node is configured.";
        description
          "CAT Africa/Harare 2:00";
      }
      container Africa-Johannesburg {
        presence "Indicates this node is configured.";
        description
          "SAST Africa/Johannesburg 2:00";
      }
      container Africa-Juba {
        presence "Indicates this node is configured.";
        description
          "EAT Africa/Juba 3:00";
      }
      container Africa-Kampala {
        presence "Indicates this node is configured.";
        description
          "EAT Africa/Kampala 3:00";
      }
      container Africa-Khartoum {
        presence "Indicates this node is configured.";
        description
          "CAT Africa/Khartoum 2:00";
      }
      container Africa-Kigali {
        presence "Indicates this node is configured.";
        description
          "CAT Africa/Kigali 2:00";
      }
      container Africa-Kinshasa {
        presence "Indicates this node is configured.";
        description
          "WAT Africa/Kinshasa 1:00";
      }
      container Africa-Lagos {
        presence "Indicates this node is configured.";
        description
          "WAT Africa/Lagos 1:00";
      }
      container Africa-Libreville {
        presence "Indicates this node is configured.";
        description
          "WAT Africa/Libreville 1:00";
      }
      container Africa-Lome {
        presence "Indicates this node is configured.";
        description
          "GMT Africa/Lome 0:00";
      }
      container Africa-Luanda {
        presence "Indicates this node is configured.";
        description
          "WAT Africa/Luanda 1:00";
      }
      container Africa-Lubumbashi {
        presence "Indicates this node is configured.";
        description
          "CAT Africa/Lubumbashi 2:00";
      }
      container Africa-Lusaka {
        presence "Indicates this node is configured.";
        description
          "CAT Africa/Lusaka 2:00";
      }
      container Africa-Malabo {
        presence "Indicates this node is configured.";
        description
          "WAT Africa/Malabo 1:00";
      }
      container Africa-Maputo {
        presence "Indicates this node is configured.";
        description
          "CAT Africa/Maputo 2:00";
      }
      container Africa-Maseru {
        presence "Indicates this node is configured.";
        description
          "SAST Africa/Maseru 2:00";
      }
      container Africa-Mbabane {
        presence "Indicates this node is configured.";
        description
          "SAST Africa/Mbabane 2:00";
      }
      container Africa-Mogadishu {
        presence "Indicates this node is configured.";
        description
          "EAT Africa/Mogadishu 3:00";
      }
      container Africa-Monrovia {
        presence "Indicates this node is configured.";
        description
          "GMT Africa/Monrovia 0:00";
      }
      container Africa-Nairobi {
        presence "Indicates this node is configured.";
        description
          "EAT Africa/Nairobi 3:00";
      }
      container Africa-Ndjamena {
        presence "Indicates this node is configured.";
        description
          "WAT Africa/Ndjamena 1:00";
      }
      container Africa-Niamey {
        presence "Indicates this node is configured.";
        description
          "WAT Africa/Niamey 1:00";
      }
      container Africa-Nouakchott {
        presence "Indicates this node is configured.";
        description
          "GMT Africa/Nouakchott 0:00";
      }
      container Africa-Ouagadougou {
        presence "Indicates this node is configured.";
        description
          "GMT Africa/Ouagadougou 0:00";
      }
      container Africa-Porto-Novo {
        presence "Indicates this node is configured.";
        description
          "WAT Africa/Porto-Novo 1:00";
      }
      container Africa-Sao_Tome {
        presence "Indicates this node is configured.";
        description
          "GMT Africa/Sao_Tome 0:00";
      }
      container Africa-Timbuktu {
        presence "Indicates this node is configured.";
        description
          "GMT Africa/Timbuktu 0:00";
      }
      container Africa-Tripoli {
        presence "Indicates this node is configured.";
        description
          "EET Africa/Tripoli 2:00";
      }
      container Africa-Tunis {
        presence "Indicates this node is configured.";
        description
          "CET Africa/Tunis 1:00";
      }
      container Africa-Windhoek {
        presence "Indicates this node is configured.";
        description
          "CAT Africa/Windhoek 2:00";
      }
      container America-Adak {
        presence "Indicates this node is configured.";
        description
          "HST America/Adak -10:00";
      }
      container America-Anchorage {
        presence "Indicates this node is configured.";
        description
          "AKST America/Anchorage -9:00";
      }
      container America-Anguilla {
        presence "Indicates this node is configured.";
        description
          "AST America/Anguilla -4:00";
      }
      container America-Antigua {
        presence "Indicates this node is configured.";
        description
          "AST America/Antigua -4:00";
      }
      container America-Araguaina {
        presence "Indicates this node is configured.";
        description
          "-03 America/Araguaina -3:00";
      }
      container America-Argentina-Buenos_Aires {
        presence "Indicates this node is configured.";
        description
          "-03 America/Argentina/Buenos_Aires -3:00";
      }
      container America-Argentina-Catamarca {
        presence "Indicates this node is configured.";
        description
          "-03 America/Argentina/Catamarca -3:00";
      }
      container America-Argentina-ComodRivadavia {
        presence "Indicates this node is configured.";
        description
          "-03 America/Argentina/ComodRivadavia -3:00";
      }
      container America-Argentina-Cordoba {
        presence "Indicates this node is configured.";
        description
          "-03 America/Argentina/Cordoba -3:00";
      }
      container America-Argentina-Jujuy {
        presence "Indicates this node is configured.";
        description
          "-03 America/Argentina/Jujuy -3:00";
      }
      container America-Argentina-La_Rioja {
        presence "Indicates this node is configured.";
        description
          "-03 America/Argentina/La_Rioja -3:00";
      }
      container America-Argentina-Mendoza {
        presence "Indicates this node is configured.";
        description
          "-03 America/Argentina/Mendoza -3:00";
      }
      container America-Argentina-Rio_Gallegos {
        presence "Indicates this node is configured.";
        description
          "-03 America/Argentina/Rio_Gallegos -3:00";
      }
      container America-Argentina-Salta {
        presence "Indicates this node is configured.";
        description
          "-03 America/Argentina/Salta -3:00";
      }
      container America-Argentina-San_Juan {
        presence "Indicates this node is configured.";
        description
          "-03 America/Argentina/San_Juan -3:00";
      }
      container America-Argentina-San_Luis {
        presence "Indicates this node is configured.";
        description
          "-03 America/Argentina/San_Luis -3:00";
      }
      container America-Argentina-Tucuman {
        presence "Indicates this node is configured.";
        description
          "-03 America/Argentina/Tucuman -3:00";
      }
      container America-Argentina-Argentina-Ushuaia {
        presence "Indicates this node is configured.";
        description
          "-03 America/Argentina/Argentina/Ushuaia -3:00";
      }
      container America-Aruba {
        presence "Indicates this node is configured.";
        description
          "AST America/Aruba -4:00";
      }
      container America-Atikokan {
        presence "Indicates this node is configured.";
        description
          "EST America/Atikokan -5:00";
      }
      container America-Atka {
        presence "Indicates this node is configured.";
        description
          "HST America/Atka -10:00";
      }
      container America-Bahia {
        presence "Indicates this node is configured.";
        description
          "-03 America/Bahia -3:00";
      }
      container America-Bahia_Banderas {
        presence "Indicates this node is configured.";
        description
          "CST America/Bahia_Banderas -6:00";
      }
      container America-Barbados {
        presence "Indicates this node is configured.";
        description
          "AST America/Barbados -4:00";
      }
      container America-Belem {
        presence "Indicates this node is configured.";
        description
          "-03 America/Belem -3:00";
      }
      container America-Belize {
        presence "Indicates this node is configured.";
        description
          "CST America/Belize -6:00";
      }
      container America-Blanc-Sablon {
        presence "Indicates this node is configured.";
        description
          "AST America/Blanc-Sablon -4:00";
      }
      container America-Boa_Vista {
        presence "Indicates this node is configured.";
        description
          "-04 America/Boa_Vista -4:00";
      }
      container America-Bogota {
        presence "Indicates this node is configured.";
        description
          "-05 America/Bogota -5:00";
      }
      container America-Boise {
        presence "Indicates this node is configured.";
        description
          "MST America/Boise -7:00";
      }
      container America-Buenos_Aires {
        presence "Indicates this node is configured.";
        description
          "-03 America/Buenos_Aires -3:00";
      }
      container America-Cambridge_Bay {
        presence "Indicates this node is configured.";
        description
          "MST America/Cambridge_Bay -7:00";
      }
      container America-Campo_Grande {
        presence "Indicates this node is configured.";
        description
          "-04 America/Campo_Grande -4:00";
      }
      container America-Cancun {
        presence "Indicates this node is configured.";
        description
          "EST America/Cancun -5:00";
      }
      container America-Caracas {
        presence "Indicates this node is configured.";
        description
          "-04 America/Caracas -4:00";
      }
      container America-Catamarca {
        presence "Indicates this node is configured.";
        description
          "-03 America/Catamarca -3:00";
      }
      container America-Cayenne {
        presence "Indicates this node is configured.";
        description
          "-03 America/Cayenne -3:00";
      }
      container America-Cayman {
        presence "Indicates this node is configured.";
        description
          "EST America/Cayman -5:00";
      }
      container America-Chicago {
        presence "Indicates this node is configured.";
        description
          "CST America/Chicago -6:00";
      }
      container America-Chihuahua {
        presence "Indicates this node is configured.";
        description
          "MST America/Chihuahua -7:00";
      }
      container America-Coral_Harbour {
        presence "Indicates this node is configured.";
        description
          "EST America/Coral_Harbour -5:00";
      }
      container America-Cordoba {
        presence "Indicates this node is configured.";
        description
          "-03 America/Cordoba -3:00";
      }
      container America-Costa_Rica {
        presence "Indicates this node is configured.";
        description
          "CST America/Costa_Rica -6:00";
      }
      container America-Creston {
        presence "Indicates this node is configured.";
        description
          "MST America/Creston -7:00";
      }
      container America-Cuiaba {
        presence "Indicates this node is configured.";
        description
          "-04 America/Cuiaba -4:00";
      }
      container America-Curacao {
        presence "Indicates this node is configured.";
        description
          "AST America/Curacao -4:00";
      }
      container America-Danmarkshavn {
        presence "Indicates this node is configured.";
        description
          "GMT America/Danmarkshavn 0:00";
      }
      container America-Dawson {
        presence "Indicates this node is configured.";
        description
          "PST America/Dawson -8:00";
      }
      container America-Dawson_Creek {
        presence "Indicates this node is configured.";
        description
          "MST America/Dawson_Creek -7:00";
      }
      container America-Denver {
        presence "Indicates this node is configured.";
        description
          "MST America/Denver -7:00";
      }
      container America-Detroit {
        presence "Indicates this node is configured.";
        description
          "EST America/Detroit -5:00";
      }
      container America-Dominica {
        presence "Indicates this node is configured.";
        description
          "AST America/Dominica -4:00";
      }
      container America-Edmonton {
        presence "Indicates this node is configured.";
        description
          "MST America/Edmonton -7:00";
      }
      container America-Eirunepe {
        presence "Indicates this node is configured.";
        description
          "-05 America/Eirunepe -5:00";
      }
      container America-El_Salvador {
        presence "Indicates this node is configured.";
        description
          "CST America/El_Salvador -6:00";
      }
      container America-Ensenada {
        presence "Indicates this node is configured.";
        description
          "PST America/Ensenada -8:00";
      }
      container America-Fort_Nelson {
        presence "Indicates this node is configured.";
        description
          "MST America/Fort_Nelson -7:00";
      }
      container America-Fort_Wayne {
        presence "Indicates this node is configured.";
        description
          "EST America/Fort_Wayne -5:00";
      }
      container America-Fortaleza {
        presence "Indicates this node is configured.";
        description
          "-03 America/Fortaleza  -3:00";
      }
      container America-Glace_Bay {
        presence "Indicates this node is configured.";
        description
          "AST America/Glace_Bay -4:00";
      }
      container America-Godthab {
        presence "Indicates this node is configured.";
        description
          "-03 America/Godthab -3:00";
      }
      container America-Goose_Bay {
        presence "Indicates this node is configured.";
        description
          "AST America/Goose_Bay -4:00";
      }
      container America-Grand_Turk {
        presence "Indicates this node is configured.";
        description
          "EST America/Grand_Turk -5:00";
      }
      container America-Grenada {
        presence "Indicates this node is configured.";
        description
          "AST America/Grenada -4:00";
      }
      container America-Guadeloupe {
        presence "Indicates this node is configured.";
        description
          "AST America/Guadeloupe -4:00";
      }
      container America-Guatemala {
        presence "Indicates this node is configured.";
        description
          "CST America/Guatemala -6:00";
      }
      container America-Guayaquil {
        presence "Indicates this node is configured.";
        description
          "-05 America/Guayaquil -5:00";
      }
      container America-Guyana {
        presence "Indicates this node is configured.";
        description
          "-04 America/Guyana -4:00";
      }
      container America-Halifax {
        presence "Indicates this node is configured.";
        description
          "AST America/Halifax -4:00";
      }
      container America-Havana {
        presence "Indicates this node is configured.";
        description
          "CST America/Havana -6:00";
      }
      container America-Hermosillo {
        presence "Indicates this node is configured.";
        description
          "MST America/Hermosillo -7:00";
      }
      container America-Indiana-Indianapolis {
        presence "Indicates this node is configured.";
        description
          "EST America/Indiana/Indianapolis -5:00";
      }
      container America-Indiana-Knox {
        presence "Indicates this node is configured.";
        description
          "CST America/Indiana/Knox -6:00";
      }
      container America-Indiana-Marengo {
        presence "Indicates this node is configured.";
        description
          "EST America/Indiana/Marengo -5:00";
      }
      container America-Indiana-Petersburg {
        presence "Indicates this node is configured.";
        description
          "EST America/Indiana/Petersburg -5:00";
      }
      container America-Indiana-Tell_City {
        presence "Indicates this node is configured.";
        description
          "CST America/Indiana/Tell_City -6:00";
      }
      container America-Indiana-Vevay {
        presence "Indicates this node is configured.";
        description
          "EST America/Indiana/Vevay -5:00";
      }
      container America-Indiana-Vincennes {
        presence "Indicates this node is configured.";
        description
          "EST America/Indiana/Vincennes -5:00";
      }
      container America-Indiana-Winamac {
        presence "Indicates this node is configured.";
        description
          "EST America/Indiana/Winamac -5:00";
      }
      container America-Indianapolis {
        presence "Indicates this node is configured.";
        description
          "EST America/Indianapolis -5:00";
      }
      container America-Inuvik {
        presence "Indicates this node is configured.";
        description
          "MST America/Inuvik -7:00";
      }
      container America-Iqaluit {
        presence "Indicates this node is configured.";
        description
          "EST America/Iqaluit -5:00";
      }
      container America-Jamaica {
        presence "Indicates this node is configured.";
        description
          "EST America/Jamaica -5:00";
      }
      container America-Jujuy {
        presence "Indicates this node is configured.";
        description
          "-03 America/Jujuy -3:00";
      }
      container America-Juneau {
        presence "Indicates this node is configured.";
        description
          "AKST America/Juneau -9:00";
      }
      container America-Kentucky-Louisville {
        presence "Indicates this node is configured.";
        description
          "EST America/Kentucky/Louisville -5:00";
      }
      container America-Kentucky-Monticello {
        presence "Indicates this node is configured.";
        description
          "EST America/Kentucky/Monticello -5:00";
      }
      container America-Knox_IN {
        presence "Indicates this node is configured.";
        description
          "CST America/Knox_IN -6:00";
      }
      container America-Kralendijk {
        presence "Indicates this node is configured.";
        description
          "AST America/Kralendijk -4:00";
      }
      container America-La_Paz {
        presence "Indicates this node is configured.";
        description
          "-04 America/La_Paz -4:00";
      }
      container America-Lima {
        presence "Indicates this node is configured.";
        description
          "-05 America/Lima -5:00";
      }
      container America-Los_Angeles {
        presence "Indicates this node is configured.";
        description
          "PST America/Los_Angeles -8:00";
      }
      container America-Louisville {
        presence "Indicates this node is configured.";
        description
          "EST America/Louisville -5:00";
      }
      container America-Lower_Princes {
        presence "Indicates this node is configured.";
        description
          "AST America/Lower_Princes -4:00";
      }
      container America-Maceio {
        presence "Indicates this node is configured.";
        description
          "-03 America/Maceio -3:00";
      }
      container America-Managua {
        presence "Indicates this node is configured.";
        description
          "CST America/Managua -6:00";
      }
      container America-Manaus {
        presence "Indicates this node is configured.";
        description
          "-04 America/Manaus -4:00";
      }
      container America-Marigot {
        presence "Indicates this node is configured.";
        description
          "AST America/Marigot -4:00";
      }
      container America-Martinique {
        presence "Indicates this node is configured.";
        description
          "AST America/Martinique -4:00";
      }
      container America-Matamoros {
        presence "Indicates this node is configured.";
        description
          "CST America/Matamoros -6:00";
      }
      container America-Mazatlan {
        presence "Indicates this node is configured.";
        description
          "MST America/Mazatlan -7:00";
      }
      container America-Mendoza {
        presence "Indicates this node is configured.";
        description
          "-03 America/Mendoza -3:00";
      }
      container America-Menominee {
        presence "Indicates this node is configured.";
        description
          "CST America/Menominee -6:00";
      }
      container America-Merida {
        presence "Indicates this node is configured.";
        description
          "CST America/Merida -6:00";
      }
      container America-Metlakatla {
        presence "Indicates this node is configured.";
        description
          "AKST America/Metlakatla -9:00";
      }
      container America-Mexico_City {
        presence "Indicates this node is configured.";
        description
          "CST America/Mexico_City -6:00";
      }
      container America-Miquelon {
        presence "Indicates this node is configured.";
        description
          "-03 America/Miquelon -3:00";
      }
      container America-Moncton {
        presence "Indicates this node is configured.";
        description
          "AST America/Moncton -4:00";
      }
      container America-Monterrey {
        presence "Indicates this node is configured.";
        description
          "CST America/Monterrey -6:00";
      }
      container America-Montevideo {
        presence "Indicates this node is configured.";
        description
          "-03 America/Montevideo -3:00";
      }
      container America-Montreal {
        presence "Indicates this node is configured.";
        description
          "EST America/Montreal -5:00";
      }
      container America-Montserrat {
        presence "Indicates this node is configured.";
        description
          "AST America/Montserrat -4:00";
      }
      container America-Nassau {
        presence "Indicates this node is configured.";
        description
          "EST America/Nassau -5:00";
      }
      container America-New_York {
        presence "Indicates this node is configured.";
        description
          "EST America/New_York -5:00";
      }
      container America-Nipigon {
        presence "Indicates this node is configured.";
        description
          "EST America/Nipigon -5:00";
      }
      container America-Nome {
        presence "Indicates this node is configured.";
        description
          "AKST America/Nome -9:00";
      }
      container America-Noronha {
        presence "Indicates this node is configured.";
        description
          "-02 America/Noronha -2:00";
      }
      container America-North_Dakota-Beulah {
        presence "Indicates this node is configured.";
        description
          "CST America/North_Dakota/Beulah -6:00";
      }
      container America-North_Dakota-Center {
        presence "Indicates this node is configured.";
        description
          "CST America/North_Dakota/Center -6:00";
      }
      container America-North_Dakota-New_Salem {
        presence "Indicates this node is configured.";
        description
          "CST America/North_Dakota/New_Salem -6:00";
      }
      container America-Ojinaga {
        presence "Indicates this node is configured.";
        description
          "MST America/Ojinaga -7:00";
      }
      container America-Panama {
        presence "Indicates this node is configured.";
        description
          "EST America/Panama -5:00";
      }
      container America-Pangnirtung {
        presence "Indicates this node is configured.";
        description
          "EST America/Pangnirtung -5:00";
      }
      container America-Paramaribo {
        presence "Indicates this node is configured.";
        description
          "-03 America/Paramaribo -3:00";
      }
      container America-Phoenix {
        presence "Indicates this node is configured.";
        description
          "MST America/Phoenix -7:00";
      }
      container America-Port-au-Prince {
        presence "Indicates this node is configured.";
        description
          "EST America/Port-au-Prince -5:00";
      }
      container America-Port_of_Spain {
        presence "Indicates this node is configured.";
        description
          "AST America/Port_of_Spain -4:00";
      }
      container America-Porto_Acre {
        presence "Indicates this node is configured.";
        description
          "-05 America/Porto_Acre -5:00";
      }
      container America-Porto_Velho {
        presence "Indicates this node is configured.";
        description
          "-04 America/Porto_Velho -4:00";
      }
      container America-Puerto_Rico {
        presence "Indicates this node is configured.";
        description
          "AST America/Puerto_Rico -4:00";
      }
      container America-Punta_Arenas {
        presence "Indicates this node is configured.";
        description
          "-03 America/Punta_Arenas -3:00";
      }
      container America-Rainy_River {
        presence "Indicates this node is configured.";
        description
          "CST America/Rainy_River -6:00";
      }
      container America-Rankin_Inlet {
        presence "Indicates this node is configured.";
        description
          "CST America/Rankin_Inlet -6:00";
      }
      container America-Recife {
        presence "Indicates this node is configured.";
        description
          "-03 America/Recife -3:00";
      }
      container America-Regina {
        presence "Indicates this node is configured.";
        description
          "CST America/Regina -6:00";
      }
      container America-Resolute {
        presence "Indicates this node is configured.";
        description
          "CST America/Resolute -6:00";
      }
      container America-Rio_Branco {
        presence "Indicates this node is configured.";
        description
          "-05 America/Rio_Branco -5:00";
      }
      container America-Rosario {
        presence "Indicates this node is configured.";
        description
          "-03 America/Rosario -3:00";
      }
      container America-Santa_Isabel {
        presence "Indicates this node is configured.";
        description
          "PST America/Santa_Isabel -8:00";
      }
      container America-Santarem {
        presence "Indicates this node is configured.";
        description
          "-03 America/Santarem -3:00";
      }
      container America-Santiago {
        presence "Indicates this node is configured.";
        description
          "-04 America/Santiago -4:00";
      }
      container America-Santo_Domingo {
        presence "Indicates this node is configured.";
        description
          "AST America/Santo_Domingo -4:00";
      }
      container America-Sao_Paulo {
        presence "Indicates this node is configured.";
        description
          "-03 America/Sao_Paulo -3:00";
      }
      container America-Scoresbysund {
        presence "Indicates this node is configured.";
        description
          "-01 America/Scoresbysund -1:00";
      }
      container America-Shiprock {
        presence "Indicates this node is configured.";
        description
          "MST America/Shiprock -7:00";
      }
      container America-Sitka {
        presence "Indicates this node is configured.";
        description
          "AKST America/Sitka -9:00";
      }
      container America-St_Barthelemy {
        presence "Indicates this node is configured.";
        description
          "AST America/St_Barthelemy -4:00";
      }
      container America-St_Johns {
        presence "Indicates this node is configured.";
        description
          "NST America/St_Johns -3:30";
      }
      container America-St_Kitts {
        presence "Indicates this node is configured.";
        description
          "AST America/St_Kitts -4:00";
      }
      container America-St_Lucia {
        presence "Indicates this node is configured.";
        description
          "AST America/St_Lucia -4:00";
      }
      container America-St_Thomas {
        presence "Indicates this node is configured.";
        description
          "AST America/St_Thomas -4:00";
      }
      container America-St_Vincent {
        presence "Indicates this node is configured.";
        description
          "AST America/St_Vincent -4:00";
      }
      container America-Swift_Current {
        presence "Indicates this node is configured.";
        description
          "CST America/Swift_Current -6:00";
      }
      container America-Tegucigalpa {
        presence "Indicates this node is configured.";
        description
          "CST America/Tegucigalpa -6:00";
      }
      container America-Thule {
        presence "Indicates this node is configured.";
        description
          "AST America/Thule -4:00";
      }
      container America-Thunder_Bay {
        presence "Indicates this node is configured.";
        description
          "EST America/Thunder_Bay -5:00";
      }
      container America-Tijuana {
        presence "Indicates this node is configured.";
        description
          "PST America/Tijuana -8:00";
      }
      container America-Toronto {
        presence "Indicates this node is configured.";
        description
          "EST America/Toronto -5:00";
      }
      container America-Tortola {
        presence "Indicates this node is configured.";
        description
          "AST America/Tortola -4:00";
      }
      container America-Vancouver {
        presence "Indicates this node is configured.";
        description
          "PST America/Vancouver -8:00";
      }
      container America-Virgin {
        presence "Indicates this node is configured.";
        description
          "AST America/Virgin -4:00";
      }
      container America-Whitehorse {
        presence "Indicates this node is configured.";
        description
          "PST America/Whitehorse -8:00";
      }
      container America-Winnipeg {
        presence "Indicates this node is configured.";
        description
          "CST America/Winnipeg -6:00";
      }
      container America-Yakutat {
        presence "Indicates this node is configured.";
        description
          "AKST America/Yakutat -9:00";
      }
      container America-Yellowknife {
        presence "Indicates this node is configured.";
        description
          "MST America/Yellowknife -7:00";
      }
      container Antarctica-Casey {
        presence "Indicates this node is configured.";
        description
          "+08 Antarctica/Casey 8:00";
      }
      container Antarctica-Davis {
        presence "Indicates this node is configured.";
        description
          "+07 Antarctica/Davis 7:00";
      }
      container Antarctica-DumontDUrville {
        presence "Indicates this node is configured.";
        description
          "+10 Antarctica/DumontDUrville 10:00";
      }
      container Antarctica-Macquarie {
        presence "Indicates this node is configured.";
        description
          "+11 Antarctica/Macquarie 11:00";
      }
      container Antarctica-Mawson {
        presence "Indicates this node is configured.";
        description
          "+05 Antarctica/Mawson 5:00";
      }
      container Antarctica-McMurdo {
        presence "Indicates this node is configured.";
        description
          "NZST Antarctica/McMurdo 12:00";
      }
      container Antarctica-Palmer {
        presence "Indicates this node is configured.";
        description
          "-03 Antarctica/Palmer -3:00";
      }
      container Antarctica-Rothera {
        presence "Indicates this node is configured.";
        description
          "-03 Antarctica/Rothera -3:00";
      }
      container Antarctica-South_Pole {
        presence "Indicates this node is configured.";
        description
          "NZST Antarctica/South_Pole 12:00";
      }
      container Antarctica-Syowa {
        presence "Indicates this node is configured.";
        description
          "+03 Antarctica/Syowa 3:00";
      }
      container Antarctica-Troll {
        presence "Indicates this node is configured.";
        description
          "+00 Antarctica/Troll 0:00";
      }
      container Antarctica-Vostok {
        presence "Indicates this node is configured.";
        description
          "+06 Antarctica/Vostok 6:00";
      }
      container Asia-Aden {
        presence "Indicates this node is configured.";
        description
          "+03 Asia/Aden 3:00";
      }
      container Asia-Almaty {
        presence "Indicates this node is configured.";
        description
          "+06 Asia/Almaty 6:00";
      }
      container Asia-Amman {
        presence "Indicates this node is configured.";
        description
          "EET Asia/Amman 2:00";
      }
      container Asia-Anadyr {
        presence "Indicates this node is configured.";
        description
          "+12 Asia/Anadyr 12:00";
      }
      container Asia-Aqtau {
        presence "Indicates this node is configured.";
        description
          "+05 Asia/Aqtau 5:00";
      }
      container Asia-Aqtobe {
        presence "Indicates this node is configured.";
        description
          "+05 Asia/Aqtobe 5:00";
      }
      container Asia-Ashgabat {
        presence "Indicates this node is configured.";
        description
          "+05 Asia/Ashgabat 5:00";
      }
      container Asia-Ashkhabad {
        presence "Indicates this node is configured.";
        description
          "+05 Asia/Ashkhabad 5:00";
      }
      container Asia-Atyrau {
        presence "Indicates this node is configured.";
        description
          "+05 Asia/Atyrau 5:00";
      }
      container Asia-Baghdad {
        presence "Indicates this node is configured.";
        description
          "+03 Asia/Baghdad 3:00";
      }
      container Asia-Bahrain {
        presence "Indicates this node is configured.";
        description
          "+03 Asia/Bahrain 3:00";
      }
      container Asia-Baku {
        presence "Indicates this node is configured.";
        description
          "+04 Asia/Baku 4:00";
      }
      container Asia-Bangkok {
        presence "Indicates this node is configured.";
        description
          "+07 Asia/Bangkok 7:00";
      }
      container Asia-Barnaul {
        presence "Indicates this node is configured.";
        description
          "+07 Asia/Barnaul 7:00";
      }
      container Asia-Beirut {
        presence "Indicates this node is configured.";
        description
          "EET Asia/Beirut 2:00";
      }
      container Asia-Bishkek {
        presence "Indicates this node is configured.";
        description
          "+06 Asia/Bishkek 6:00";
      }
      container Asia-Brunei {
        presence "Indicates this node is configured.";
        description
          "+08 Asia/Brunei 8:00";
      }
      container Asia-Calcutta {
        presence "Indicates this node is configured.";
        description
          "IST Asia/Calcutta 5:30";
      }
      container Asia-Chita {
        presence "Indicates this node is configured.";
        description
          "+09 Asia/Chita 9:00";
      }
      container Asia-Choibalsan {
        presence "Indicates this node is configured.";
        description
          "+08 Asia/Choibalsan 8:00";
      }
      container Asia-Chongqing {
        presence "Indicates this node is configured.";
        description
          "CST Asia/Chongqing 8:00";
      }
      container Asia-Chungking {
        presence "Indicates this node is configured.";
        description
          "CST Asia/Chungking 8:00";
      }
      container Asia-Colombo {
        presence "Indicates this node is configured.";
        description
          "+0530 Asia/Colombo 5:30";
      }
      container Asia-Dacca {
        presence "Indicates this node is configured.";
        description
          "+06 Asia/Dacca 6:00";
      }
      container Asia-Damascus {
        presence "Indicates this node is configured.";
        description
          "EET Asia/Damascus 2:00";
      }
      container Asia-Dhaka {
        presence "Indicates this node is configured.";
        description
          "+06 Asia/Dhaka 6:00";
      }
      container Asia-Dili {
        presence "Indicates this node is configured.";
        description
          "+09 Asia/Dili 9:00";
      }
      container Asia-Dubai {
        presence "Indicates this node is configured.";
        description
          "+04 Asia/Dubai 4:00";
      }
      container Asia-Dushanbe {
        presence "Indicates this node is configured.";
        description
          "+05 Asia/Dushanbe 5:00";
      }
      container Asia-Famagusta {
        presence "Indicates this node is configured.";
        description
          "EET Asia/Famagusta 2:00";
      }
      container Asia-Gaza {
        presence "Indicates this node is configured.";
        description
          "EET Asia/Gaza 2:00";
      }
      container Asia-Harbin {
        presence "Indicates this node is configured.";
        description
          "CST Asia/Harbin 8:00";
      }
      container Asia-Hebron {
        presence "Indicates this node is configured.";
        description
          "EET Asia/Hebron 2:00";
      }
      container Asia-Ho_Chi_Minh {
        presence "Indicates this node is configured.";
        description
          "+07 Asia/Ho_Chi_Minh 7:00";
      }
      container Asia-Hong_Kong {
        presence "Indicates this node is configured.";
        description
          "HKT Asia/Hong_Kong 8:00";
      }
      container Asia-Hovd {
        presence "Indicates this node is configured.";
        description
          "+07 Asia/Hovd 7:00";
      }
      container Asia-Irkutsk {
        presence "Indicates this node is configured.";
        description
          "+08 Asia/Irkutsk 8:00";
      }
      container Asia-Istanbul {
        presence "Indicates this node is configured.";
        description
          "+03 Asia/Istanbul 3:00";
      }
      container Asia-Jakarta {
        presence "Indicates this node is configured.";
        description
          "WIB Asia/Jakarta 7:00";
      }
      container Asia-Jayapura {
        presence "Indicates this node is configured.";
        description
          "WIT Asia/Jayapura 9:00";
      }
      container Asia-Jerusalem {
        presence "Indicates this node is configured.";
        description
          "IST Asia/Jerusalem 5:30";
      }
      container Asia-Kabul {
        presence "Indicates this node is configured.";
        description
          "+0430 Asia/Kabul 4:30";
      }
      container Asia-Kamchatka {
        presence "Indicates this node is configured.";
        description
          "+12 Asia/Kamchatka 12:00";
      }
      container Asia-Karachi {
        presence "Indicates this node is configured.";
        description
          "PKT Asia/Karachi 5:00";
      }
      container Asia-Kashgar {
        presence "Indicates this node is configured.";
        description
          "+06 Asia/Kashgar 6:00";
      }
      container Asia-Kathmandu {
        presence "Indicates this node is configured.";
        description
          "+0545 Asia/Kathmandu 05:45";
      }
      container Asia-Katmandu {
        presence "Indicates this node is configured.";
        description
          "+0545 Asia/Katmandu 05:45";
      }
      container Asia-Khandyga {
        presence "Indicates this node is configured.";
        description
          "+09 Asia/Khandyga 9:00";
      }
      container Asia-Kolkata {
        presence "Indicates this node is configured.";
        description
          "IST Asia/Kolkata 5:30";
      }
      container Asia-Krasnoyarsk {
        presence "Indicates this node is configured.";
        description
          "+07 Asia/Krasnoyarsk 7:00";
      }
      container Asia-Kuala_Lumpur {
        presence "Indicates this node is configured.";
        description
          "+08 Asia/Kuala_Lumpur 8:00";
      }
      container Asia-Kuching {
        presence "Indicates this node is configured.";
        description
          "+08 Asia/Kuching 8:00";
      }
      container Asia-Kuwait {
        presence "Indicates this node is configured.";
        description
          "+03 Asia/Kuwait 3:00";
      }
      container Asia-Macao {
        presence "Indicates this node is configured.";
        description
          "CST Asia/Macao 8:00";
      }
      container Asia-Macau {
        presence "Indicates this node is configured.";
        description
          "CST Asia/Macau 8:00";
      }
      container Asia-Magadan {
        presence "Indicates this node is configured.";
        description
          "+11 Asia/Magadan 11:00";
      }
      container Asia-Makassar {
        presence "Indicates this node is configured.";
        description
          "WITA Asia/Makassar 8:00";
      }
      container Asia-Manila {
        presence "Indicates this node is configured.";
        description
          "PST Asia/Manila 8:00";
      }
      container Asia-Muscat {
        presence "Indicates this node is configured.";
        description
          "+04 Asia/Muscat 4:00";
      }
      container Asia-Nicosia {
        presence "Indicates this node is configured.";
        description
          "EET Asia/Nicosia 2:00";
      }
      container Asia-Novokuznetsk {
        presence "Indicates this node is configured.";
        description
          "+07 Asia/Novokuznetsk 7:00";
      }
      container Asia-Novosibirsk {
        presence "Indicates this node is configured.";
        description
          "+07 Asia/Novosibirsk 7:00";
      }
      container Asia-Omsk {
        presence "Indicates this node is configured.";
        description
          "+06 Asia/Omsk 6:00";
      }
      container Asia-Oral {
        presence "Indicates this node is configured.";
        description
          "+05 Asia/Oral 5:00";
      }
      container Asia-Phnom_Penh {
        presence "Indicates this node is configured.";
        description
          "+07 Asia/Phnom_Penh 7:00";
      }
      container Asia-Pontianak {
        presence "Indicates this node is configured.";
        description
          "WIB Asia/Pontianak 7:00";
      }
      container Asia-Pyongyang {
        presence "Indicates this node is configured.";
        description
          "KST Asia/Pyongyang 9:00";
      }
      container Asia-Qatar {
        presence "Indicates this node is configured.";
        description
          "+03 Asia/Qatar 3:00";
      }
      container Asia-Qostanay {
        presence "Indicates this node is configured.";
        description
          "+06 Asia/Qostanay 6:00";
      }
      container Asia-Qyzylorda {
        presence "Indicates this node is configured.";
        description
          "+05 Asia/Qyzylorda 5:00";
      }
      container Asia-Rangoon {
        presence "Indicates this node is configured.";
        description
          "+0630 Asia/Rangoon 06:30";
      }
      container Asia-Riyadh {
        presence "Indicates this node is configured.";
        description
          "+03 Asia/Riyadh 3:00";
      }
      container Asia-Saigon {
        presence "Indicates this node is configured.";
        description
          "+07 Asia/Saigon 7:00";
      }
      container Asia-Sakhalin {
        presence "Indicates this node is configured.";
        description
          "+11 Asia/Sakhalin 11:00";
      }
      container Asia-Samarkand {
        presence "Indicates this node is configured.";
        description
          "+05 Asia/Samarkand 5:00";
      }
      container Asia-Seoul {
        presence "Indicates this node is configured.";
        description
          "KST Asia/Seoul 9:00";
      }
      container Asia-Shanghai {
        presence "Indicates this node is configured.";
        description
          "CST Asia/Shanghai 8:00";
      }
      container Asia-Singapore {
        presence "Indicates this node is configured.";
        description
          "+08 Asia/Singapore 8:00";
      }
      container Asia-Srednekolymsk {
        presence "Indicates this node is configured.";
        description
          "+11 Asia/Srednekolymsk 11:00";
      }
      container Asia-Ujung_Pandang {
        presence "Indicates this node is configured.";
        description
          "WITA Asia/Ujung_Pandang 8:00";
      }
      container Asia-Ulaanbaatar {
        presence "Indicates this node is configured.";
        description
          "+08 Asia/Ulaanbaatar 8:00";
      }
      container Asia-Ulan_Bator {
        presence "Indicates this node is configured.";
        description
          "+08 Asia/Ulan_Bator 8:00";
      }
      container Asia-Urumqi {
        presence "Indicates this node is configured.";
        description
          "+06 Asia/Urumqi 6:00";
      }
      container Asia-Ust-Nera {
        presence "Indicates this node is configured.";
        description
          "+10 Asia/Ust-Nera 10:00";
      }
      container Asia-Taipei {
        presence "Indicates this node is configured.";
        description
          "CST Asia/Taipei 8:00";
      }
      container Asia-Tashkent {
        presence "Indicates this node is configured.";
        description
          "+05 Asia/Tashkent 5:00";
      }
      container Asia-Tbilisi {
        presence "Indicates this node is configured.";
        description
          "+04 Asia/Tbilisi 4:00";
      }
      container Asia-Tehran {
        presence "Indicates this node is configured.";
        description
          "+0330 Asia/Tehran 3:30";
      }
      container Asia-Tel_Aviv {
        presence "Indicates this node is configured.";
        description
          "IST Asia/Tel_Aviv 2:00";
      }
      container Asia-Thimbu {
        presence "Indicates this node is configured.";
        description
          "+06 Asia/Thimbu 6:00";
      }
      container Asia-Thimphu {
        presence "Indicates this node is configured.";
        description
          "+06 Asia/Thimphu 6:00";
      }
      container Asia-Tokyo {
        presence "Indicates this node is configured.";
        description
          "JST Asia/Tokyo 9:00";
      }
      container Asia-Tomsk {
        presence "Indicates this node is configured.";
        description
          "+07 Asia/Tomsk 7:00";
      }
      container Asia-Vientiane {
        presence "Indicates this node is configured.";
        description
          "+07 Asia/Vientiane 7:00";
      }
      container Asia-Vladivostok {
        presence "Indicates this node is configured.";
        description
          "+10 Asia/Vladivostok 10:00";
      }
      container Asia-Yakutsk {
        presence "Indicates this node is configured.";
        description
          "+09 Asia/Yakutsk 9:00";
      }
      container Asia-Yangon {
        presence "Indicates this node is configured.";
        description
          "+0630 Asia/Yangon 06:30";
      }
      container Asia-Yekaterinburg {
        presence "Indicates this node is configured.";
        description
          "+05 Asia/Yekaterinburg 5:00";
      }
      container Asia-Yerevan {
        presence "Indicates this node is configured.";
        description
          "+04 Asia/Yerevan 4:00";
      }
      container Atlantic-Azores {
        presence "Indicates this node is configured.";
        description
          "-01 Atlantic/Azores -1:00";
      }
      container Atlantic-Bermuda {
        presence "Indicates this node is configured.";
        description
          "AST Atlantic/Bermuda -4:00";
      }
      container Atlantic-Canary {
        presence "Indicates this node is configured.";
        description
          "WET Atlantic/Canary 0:00";
      }
      container Atlantic-Cape_Verde {
        presence "Indicates this node is configured.";
        description
          "-01 Atlantic/Cape_Verde -1:00";
      }
      container Atlantic-Faeroe {
        presence "Indicates this node is configured.";
        description
          "WET Atlantic/Faeroe 0:00";
      }
      container Atlantic-Faroe {
        presence "Indicates this node is configured.";
        description
          "WET Atlantic/Faroe 0:00";
      }
      container Atlantic-Jan_Mayen {
        presence "Indicates this node is configured.";
        description
          "CET Atlantic/Jan_Mayen 1:00";
      }
      container Atlantic-Madeira {
        presence "Indicates this node is configured.";
        description
          "WET Atlantic/Madeira 0:00";
      }
      container Atlantic-Reykjavik {
        presence "Indicates this node is configured.";
        description
          "GMT Atlantic/Reykjavik 0:00";
      }
      container Atlantic-South_Georgia {
        presence "Indicates this node is configured.";
        description
          "-02 Atlantic/South_Georgia -2:00";
      }
      container Atlantic-St_Helena {
        presence "Indicates this node is configured.";
        description
          "GMT Atlantic/St_Helena 0:00";
      }
      container Atlantic-Stanley {
        presence "Indicates this node is configured.";
        description
          "-03 Atlantic/Stanley -3:00";
      }
      container Australia-ACT {
        presence "Indicates this node is configured.";
        description
          "AEST Australia/ACT 10:00";
      }
      container Australia-Adelaide {
        presence "Indicates this node is configured.";
        description
          "ACST Australia/Adelaide 9:30";
      }
      container Australia-Brisbane {
        presence "Indicates this node is configured.";
        description
          "AEST Australia/Brisbane 10:00";
      }
      container Australia-Broken_Hill {
        presence "Indicates this node is configured.";
        description
          "ACST Australia/Broken_Hill 9:30";
      }
      container Australia-Canberra {
        presence "Indicates this node is configured.";
        description
          "AEST Australia/Canberra 10:00";
      }
      container Australia-Currie {
        presence "Indicates this node is configured.";
        description
          "AEST Australia/Currie 10:00";
      }
      container Australia-Darwin {
        presence "Indicates this node is configured.";
        description
          "ACST Australia/Darwin 9:30";
      }
      container Australia-Eucla {
        presence "Indicates this node is configured.";
        description
          "+0845 Australia/Eucla 8:45";
      }
      container Australia-Hobart {
        presence "Indicates this node is configured.";
        description
          "AEST Australia/Hobart 10:00";
      }
      container Australia-LHI {
        presence "Indicates this node is configured.";
        description
          "+1030 Australia/LHI 10:30";
      }
      container Australia-Lindeman {
        presence "Indicates this node is configured.";
        description
          "AEST Australia/Lindeman 10:00";
      }
      container Australia-Lord_Howe {
        presence "Indicates this node is configured.";
        description
          "+1030 Australia/Lord_Howe 10:30";
      }
      container Australia-Melbourne {
        presence "Indicates this node is configured.";
        description
          "AEST Australia/Melbourne 10:00";
      }
      container Australia-North {
        presence "Indicates this node is configured.";
        description
          "ACST Australia/North 9:30";
      }
      container Australia-Perth {
        presence "Indicates this node is configured.";
        description
          "AWST Australia/Perth 8:00";
      }
      container Australia-Queensland {
        presence "Indicates this node is configured.";
        description
          "AEST Australia/Queensland 10:00";
      }
      container Australia-South {
        presence "Indicates this node is configured.";
        description
          "ACST Australia/South 9:30";
      }
      container Australia-Sydney {
        presence "Indicates this node is configured.";
        description
          "AEST Australia/Sydney 10:00";
      }
      container Australia-Tasmania {
        presence "Indicates this node is configured.";
        description
          "AEST Australia/Tasmania 10:00";
      }
      container Australia-Victoria {
        presence "Indicates this node is configured.";
        description
          "AEST Australia/Victoria 10:00";
      }
      container Australia-West {
        presence "Indicates this node is configured.";
        description
          "AWST Australia/West 8:00";
      }
      container Australia-Yancowinna {
        presence "Indicates this node is configured.";
        description
          "ACST Australia/Yancowinna 9:30";
      }
      container Brazil-Acre {
        presence "Indicates this node is configured.";
        description
          "-05 Brazil/Acre -5:00";
      }
      container Brazil-DeNoronha {
        presence "Indicates this node is configured.";
        description
          "-02 Brazil/DeNoronha -2:00";
      }
      container Brazil-East {
        presence "Indicates this node is configured.";
        description
          "-03 Brazil/East -3:00";
      }
      container Brazil-West {
        presence "Indicates this node is configured.";
        description
          "-04 Brazil/West -4:00";
      }
      container CET {
        presence "Indicates this node is configured.";
        description
          "CET CET 1:00";
      }
      container CST6CDT {
        presence "Indicates this node is configured.";
        description
          "CST CST6CDT -6:00";
      }
      container Canada-Atlantic {
        presence "Indicates this node is configured.";
        description
          "AST Canada/Atlantic -4:00";
      }
      container Canada-Central {
        presence "Indicates this node is configured.";
        description
          "CST Canada/Central -6:00";
      }
      container Canada-Eastern {
        presence "Indicates this node is configured.";
        description
          "EST Canada/Eastern -5:00";
      }
      container Canada-Mountain {
        presence "Indicates this node is configured.";
        description
          "MST Canada/Mountain -7:00";
      }
      container Canada-Newfoundland {
        presence "Indicates this node is configured.";
        description
          "NST Canada/Newfoundland -3:30";
      }
      container Canada-Pacific {
        presence "Indicates this node is configured.";
        description
          "PST Canada/Pacific -8:00";
      }
      container Canada-Saskatchewan {
        presence "Indicates this node is configured.";
        description
          "CST Canada/Saskatchewan -6:00";
      }
      container Canada-Yukon {
        presence "Indicates this node is configured.";
        description
          "PST Canada/Yukon -8:00";
      }
      container Chile-Continental {
        presence "Indicates this node is configured.";
        description
          "-04 Chile/Continental -4:00";
      }
      container Chile-EasterIsland {
        presence "Indicates this node is configured.";
        description
          "-06 Chile/EasterIsland -6:00";
      }
      container Cuba {
        presence "Indicates this node is configured.";
        description
          "CST Cuba -6:00";
      }
      container EET {
        presence "Indicates this node is configured.";
        description
          "EET EET 2:00";
      }
      container EST {
        presence "Indicates this node is configured.";
        description
          "EST EST -5:00";
      }
      container EST5EDT {
        presence "Indicates this node is configured.";
        description
          "EST EST5EDT -5:00";
      }
      container Egypt {
        presence "Indicates this node is configured.";
        description
          "EET Egypt 2:00";
      }
      container Eire {
        presence "Indicates this node is configured.";
        description
          "IST Eire 1:00";
      }
      container Etc-GMT {
        presence "Indicates this node is configured.";
        description
          "GMT Etc/GMT 0:00";
      }
      container Etc-GMT-plus-0 {
        presence "Indicates this node is configured.";
        description
          "GMT Etc/GMT+0 0:00";
      }
      container Etc-GMT-plus-1 {
        presence "Indicates this node is configured.";
        description
          "-01 Etc/GMT+1 -1:00";
      }
      container Etc-GMT-plus-2 {
        presence "Indicates this node is configured.";
        description
          "-02 Etc/GMT+2 -2:00";
      }
      container Etc-GMT-plus-3 {
        presence "Indicates this node is configured.";
        description
          "-03 Etc/GMT+3 -3:00";
      }
      container Etc-GMT-plus-4 {
        presence "Indicates this node is configured.";
        description
          "-04 Etc/GMT+4 -4:00";
      }
      container Etc-GMT-plus-5 {
        presence "Indicates this node is configured.";
        description
          "-05 Etc/GMT+5 -5:00";
      }
      container Etc-GMT-plus-6 {
        presence "Indicates this node is configured.";
        description
          "-06 Etc/GMT+6 -6:00";
      }
      container Etc-GMT-plus-7 {
        presence "Indicates this node is configured.";
        description
          "-07 Etc/GMT+7 -7:00";
      }
      container Etc-GMT-plus-8 {
        presence "Indicates this node is configured.";
        description
          "-08 Etc/GMT+8 -8:00";
      }
      container Etc-GMT-plus-9 {
        presence "Indicates this node is configured.";
        description
          "-09 Etc/GMT+9 -9:00";
      }
      container Etc-GMT-plus-10 {
        presence "Indicates this node is configured.";
        description
          "-10 Etc/GMT+10 -10:00";
      }
      container Etc-GMT-plus-11 {
        presence "Indicates this node is configured.";
        description
          "-11 Etc/GMT+11 -11:00";
      }
      container Etc-GMT-plus-12 {
        presence "Indicates this node is configured.";
        description
          "-12 Etc/GMT+12 -12:00";
      }
      container Etc-GMT-0 {
        presence "Indicates this node is configured.";
        description
          "GMT Etc/GMT-0 0:00";
      }
      container Etc-GMT-1 {
        presence "Indicates this node is configured.";
        description
          "+01 Etc/GMT-1 1:00";
      }
      container Etc-GMT-2 {
        presence "Indicates this node is configured.";
        description
          "+02 Etc/GMT-2 2:00";
      }
      container Etc-GMT-3 {
        presence "Indicates this node is configured.";
        description
          "+03 Etc/GMT-3 3:00";
      }
      container Etc-GMT-4 {
        presence "Indicates this node is configured.";
        description
          "+04 Etc/GMT-4 4:00";
      }
      container Etc-GMT-5 {
        presence "Indicates this node is configured.";
        description
          "+05 Etc/GMT-5 5:00";
      }
      container Etc-GMT-6 {
        presence "Indicates this node is configured.";
        description
          "+06 Etc/GMT-6 6:00";
      }
      container Etc-GMT-7 {
        presence "Indicates this node is configured.";
        description
          "+07 Etc/GMT-7 7:00";
      }
      container Etc-GMT-8 {
        presence "Indicates this node is configured.";
        description
          "+08 Etc/GMT-8 8:00";
      }
      container Etc-GMT-9 {
        presence "Indicates this node is configured.";
        description
          "+09 Etc/GMT-9 9:00";
      }
      container Etc-GMT-10 {
        presence "Indicates this node is configured.";
        description
          "+10 Etc/GMT-10 10:00";
      }
      container Etc-GMT-11 {
        presence "Indicates this node is configured.";
        description
          "+11 Etc/GMT-11 11:00";
      }
      container Etc-GMT-12 {
        presence "Indicates this node is configured.";
        description
          "+12 Etc/GMT-12 12:00";
      }
      container Etc-GMT0 {
        presence "Indicates this node is configured.";
        description
          "GMT Etc/GMT0 0:00";
      }
      container Etc-Greenwich {
        presence "Indicates this node is configured.";
        description
          "GMT Etc/Greenwich 0:00";
      }
      container Etc-UCT {
        presence "Indicates this node is configured.";
        description
          "UCT Etc/UCT 0:00";
      }
      container Etc-UTC {
        presence "Indicates this node is configured.";
        description
          "UTC Etc/UTC 0:00";
      }
      container Etc-Universal {
        presence "Indicates this node is configured.";
        description
          "UTC Etc/Universal 0:00";
      }
      container Etc-Zulu {
        presence "Indicates this node is configured.";
        description
          "UTC Etc/Zulu 0:00";
      }
      container Europe-Amsterdam {
        presence "Indicates this node is configured.";
        description
          "CET Europe/Amsterdam 1:00";
      }
      container Europe-Andorra {
        presence "Indicates this node is configured.";
        description
          "CET Europe/Andorra 1:00";
      }
      container Europe-Astrakhan {
        presence "Indicates this node is configured.";
        description
          "+04 Europe/Astrakhan 4:00";
      }
      container Europe-Athens {
        presence "Indicates this node is configured.";
        description
          "EET Europe/Athens 2:00";
      }
      container Europe-Belfast {
        presence "Indicates this node is configured.";
        description
          "GMT Europe/Belfast 0:00";
      }
      container Europe-Belgrade {
        presence "Indicates this node is configured.";
        description
          "CET Europe/Belgrade 1:00";
      }
      container Europe-Berlin {
        presence "Indicates this node is configured.";
        description
          "CET Europe/Berlin 1:00";
      }
      container Europe-Bratislava {
        presence "Indicates this node is configured.";
        description
          "CET Europe/Bratislava 1:00";
      }
      container Europe-Brussels {
        presence "Indicates this node is configured.";
        description
          "CET Europe/Brussels 1:00";
      }
      container Europe-Bucharest {
        presence "Indicates this node is configured.";
        description
          "EET Europe/Bucharest 2:00";
      }
      container Europe-Budapest {
        presence "Indicates this node is configured.";
        description
          "CET Europe/Budapest 1:00";
      }
      container Europe-Busingen {
        presence "Indicates this node is configured.";
        description
          "CET Europe/Busingen 1:00";
      }
      container Europe-Chisinau {
        presence "Indicates this node is configured.";
        description
          "EET Europe/Chisinau 2:00";
      }
      container Europe-Copenhagen {
        presence "Indicates this node is configured.";
        description
          "CET Europe/Copenhagen 1:00";
      }
      container Europe-Dublin {
        presence "Indicates this node is configured.";
        description
          "IST Europe/Dublin 1:00";
      }
      container Europe-Gibraltar {
        presence "Indicates this node is configured.";
        description
          "CET Europe/Gibraltar 1:00";
      }
      container Europe-Guernsey {
        presence "Indicates this node is configured.";
        description
          "GMT Europe/Guernsey 0:00";
      }
      container Europe-Helsinki {
        presence "Indicates this node is configured.";
        description
          "EET Europe/Helsinki 2:00";
      }
      container Europe-Isle_of_Man {
        presence "Indicates this node is configured.";
        description
          "GMT Europe/Isle_of_Man 0:00";
      }
      container Europe-Istanbul {
        presence "Indicates this node is configured.";
        description
          "+03 Europe/Istanbul 3:00";
      }
      container Europe-Jersey {
        presence "Indicates this node is configured.";
        description
          "GMT Europe/Jersey 0:00";
      }
      container Europe-Kaliningrad {
        presence "Indicates this node is configured.";
        description
          "EET Europe/Kaliningrad 2:00";
      }
      container Europe-Kiev {
        presence "Indicates this node is configured.";
        description
          "EET Europe/Kiev 2:00";
      }
      container Europe-Kirov {
        presence "Indicates this node is configured.";
        description
          "+03 Europe/Kirov 3:00";
      }
      container Europe-Lisbon {
        presence "Indicates this node is configured.";
        description
          "WET Europe/Lisbon 0:00";
      }
      container Europe-Ljubljana {
        presence "Indicates this node is configured.";
        description
          "CET Europe/Ljubljana 1:00";
      }
      container Europe-London {
        presence "Indicates this node is configured.";
        description
          "GMT Europe/London 0:00";
      }
      container Europe-Luxembourg {
        presence "Indicates this node is configured.";
        description
          "CET Europe/Luxembourg 1:00";
      }
      container Europe-Madrid {
        presence "Indicates this node is configured.";
        description
          "CET Europe/Madrid 1:00";
      }
      container Europe-Malta {
        presence "Indicates this node is configured.";
        description
          "CET Europe/Malta 1:00";
      }
      container Europe-Mariehamn {
        presence "Indicates this node is configured.";
        description
          "EET Europe/Mariehamn 2:00";
      }
      container Europe-Minsk {
        presence "Indicates this node is configured.";
        description
          "+03 Europe/Minsk 3:00";
      }
      container Europe-Monaco {
        presence "Indicates this node is configured.";
        description
          "CET Europe/Monaco 1:00";
      }
      container Europe-Moscow {
        presence "Indicates this node is configured.";
        description
          "MSK Europe/Moscow 3:00";
      }
      container Europe-Nicosia {
        presence "Indicates this node is configured.";
        description
          "EET Europe/Nicosia 2:00";
      }
      container Europe-Oslo {
        presence "Indicates this node is configured.";
        description
          "CET Europe/Oslo 1:00";
      }
      container Europe-Paris {
        presence "Indicates this node is configured.";
        description
          "CET Europe/Paris 1:00";
      }
      container Europe-Podgorica {
        presence "Indicates this node is configured.";
        description
          "CET Europe/Podgorica 1:00";
      }
      container Europe-Prague {
        presence "Indicates this node is configured.";
        description
          "CET Europe/Prague 1:00";
      }
      container Europe-Riga {
        presence "Indicates this node is configured.";
        description
          "EET Europe/Riga 2:00";
      }
      container Europe-Rome {
        presence "Indicates this node is configured.";
        description
          "CET Europe/Rome 1:00";
      }
      container Europe-Samara {
        presence "Indicates this node is configured.";
        description
          "+04 Europe/Samara 4:00";
      }
      container Europe-San_Marino {
        presence "Indicates this node is configured.";
        description
          "CET Europe/San_Marino 1:00";
      }
      container Europe-Sarajevo {
        presence "Indicates this node is configured.";
        description
          "CET Europe/Sarajevo 1:00";
      }
      container Europe-Saratov {
        presence "Indicates this node is configured.";
        description
          "+04 Europe/Saratov 4:00";
      }
      container Europe-Simferopol {
        presence "Indicates this node is configured.";
        description
          "MSK Europe/Simferopol 3:00";
      }
      container Europe-Skopje {
        presence "Indicates this node is configured.";
        description
          "CET Europe/Skopje 1:00";
      }
      container Europe-Sofia {
        presence "Indicates this node is configured.";
        description
          "EET Europe/Sofia 2:00";
      }
      container Europe-Stockholm {
        presence "Indicates this node is configured.";
        description
          "CET Europe/Stockholm 1:00";
      }
      container Europe-Tallinn {
        presence "Indicates this node is configured.";
        description
          "EET Europe/Tallinn 2:00";
      }
      container Europe-Tirane {
        presence "Indicates this node is configured.";
        description
          "CET Europe/Tirane 1:00";
      }
      container Europe-Tiraspol {
        presence "Indicates this node is configured.";
        description
          "EET Europe/Tiraspol 2:00";
      }
      container Europe-Ulyanovsk {
        presence "Indicates this node is configured.";
        description
          "+04 Europe/Ulyanovsk 4:00";
      }
      container Europe-Uzhgorod {
        presence "Indicates this node is configured.";
        description
          "EET Europe/Uzhgorod 2:00";
      }
      container Europe-Vatican {
        presence "Indicates this node is configured.";
        description
          "CET Europe/Vatican 1:00";
      }
      container Europe-Vienna {
        presence "Indicates this node is configured.";
        description
          "CET Europe/Vienna 1:00";
      }
      container Europe-Vilnius {
        presence "Indicates this node is configured.";
        description
          "EET Europe/Vilnius 2:00";
      }
      container Europe-Volgograd {
        presence "Indicates this node is configured.";
        description
          "+04 Europe/Volgograd 4:00";
      }
      container Europe-Warsaw {
        presence "Indicates this node is configured.";
        description
          "CET Europe/Warsaw 1:00";
      }
      container Europe-Zagreb {
        presence "Indicates this node is configured.";
        description
          "CET Europe/Zagreb 1:00";
      }
      container Europe-Zaporozhye {
        presence "Indicates this node is configured.";
        description
          "EET Europe/Zaporozhye 2:00";
      }
      container Europe-Zurich {
        presence "Indicates this node is configured.";
        description
          "CET Europe/Zurich 1:00";
      }
      container GB {
        presence "Indicates this node is configured.";
        description
          "GMT GB 0:00";
      }
      container GB-Eire {
        presence "Indicates this node is configured.";
        description
          "GMT GB-Eire 0:00";
      }
      container GMT {
        presence "Indicates this node is configured.";
        description
          "GMT GMT 0:00";
      }
      container GMT-plus-0 {
        presence "Indicates this node is configured.";
        description
          "GMT GMT+0 0:00";
      }
      container GMT-0 {
        presence "Indicates this node is configured.";
        description
          "GMT GMT-0 0:00";
      }
      container GMT0 {
        presence "Indicates this node is configured.";
        description
          "GMT GMT0 0:00";
      }
      container Greenwich {
        presence "Indicates this node is configured.";
        description
          "GMT Greenwich 0:00";
      }
      container HST {
        presence "Indicates this node is configured.";
        description
          "HST HST -10:00";
      }
      container Hongkong {
        presence "Indicates this node is configured.";
        description
          "HKT Hongkong 8:00";
      }
      container Iceland {
        presence "Indicates this node is configured.";
        description
          "GMT Iceland 0:00";
      }
      container Indian-Antananarivo {
        presence "Indicates this node is configured.";
        description
          "EAT Indian/Antananarivo 3:00";
      }
      container Indian-Chagos {
        presence "Indicates this node is configured.";
        description
          "+06 Indian/Chagos 6:00";
      }
      container Indian-Christmas {
        presence "Indicates this node is configured.";
        description
          "+07 Indian/Christmas 7:00";
      }
      container Indian-Cocos {
        presence "Indicates this node is configured.";
        description
          "+0630 Indian/Cocos 06:30";
      }
      container Indian-Comoro {
        presence "Indicates this node is configured.";
        description
          "EAT Indian/Comoro 3:00";
      }
      container Indian-Kerguelen {
        presence "Indicates this node is configured.";
        description
          "+05 Indian/Kerguelen 5:00";
      }
      container Indian-Mahe {
        presence "Indicates this node is configured.";
        description
          "+04 Indian/Mahe 4:00";
      }
      container Indian-Maldives {
        presence "Indicates this node is configured.";
        description
          "+05 Indian/Maldives 5:00";
      }
      container Indian-Mauritius {
        presence "Indicates this node is configured.";
        description
          "+04 Indian/Mauritius 4:00";
      }
      container Indian-Mayotte {
        presence "Indicates this node is configured.";
        description
          "EAT Indian/Mayotte 3:00";
      }
      container Indian-Reunion {
        presence "Indicates this node is configured.";
        description
          "+04 Indian/Reunion 4:00";
      }
      container Iran {
        presence "Indicates this node is configured.";
        description
          "+0330 Iran 3:30";
      }
      container Israel {
        presence "Indicates this node is configured.";
        description
          "IST Israel 2:00";
      }
      container Jamaica {
        presence "Indicates this node is configured.";
        description
          "EST Jamaica -5:00";
      }
      container Japan {
        presence "Indicates this node is configured.";
        description
          "JST Japan 9:00";
      }
      container Kwajalein {
        presence "Indicates this node is configured.";
        description
          "+12 Kwajalein 12:00";
      }
      container Libya {
        presence "Indicates this node is configured.";
        description
          "EET Libya 2:00";
      }
      container MET {
        presence "Indicates this node is configured.";
        description
          "MET MET 1:00";
      }
      container MST {
        presence "Indicates this node is configured.";
        description
          "MST MST -7:00";
      }
      container MST7MDT {
        presence "Indicates this node is configured.";
        description
          "MST MST7MDT -7:00";
      }
      container Mexico-BajaNorte {
        presence "Indicates this node is configured.";
        description
          "PST Mexico/BajaNorte -8:00";
      }
      container Mexico-BajaSur {
        presence "Indicates this node is configured.";
        description
          "MST Mexico/BajaSur -7:00";
      }
      container Mexico-General {
        presence "Indicates this node is configured.";
        description
          "CST Mexico/General -6:00";
      }
      container NZ {
        presence "Indicates this node is configured.";
        description
          "NZST NZ 12:00";
      }
      container NZ-CHAT {
        presence "Indicates this node is configured.";
        description
          "+1245 NZ-CHAT 12:45";
      }
      container Navajo {
        presence "Indicates this node is configured.";
        description
          "MST Navajo -7:00";
      }
      container PRC {
        presence "Indicates this node is configured.";
        description
          "CST PRC -6:00";
      }
      container PST8PDT {
        presence "Indicates this node is configured.";
        description
          "PST PST8PDT -8:00";
      }
      container Pacific-Apia {
        presence "Indicates this node is configured.";
        description
          "+13 Pacific/Apia 13:00";
      }
      container Pacific-Auckland {
        presence "Indicates this node is configured.";
        description
          "NZST Pacific/Auckland 12:00";
      }
      container Pacific-Bougainville {
        presence "Indicates this node is configured.";
        description
          "+11 Pacific/Bougainville 11:00";
      }
      container Pacific-Chatham {
        presence "Indicates this node is configured.";
        description
          "+1245 Pacific/Chatham 12:45";
      }
      container Pacific-Chuuk {
        presence "Indicates this node is configured.";
        description
          "+10 Pacific/Chuuk 10:00";
      }
      container Pacific-Easter {
        presence "Indicates this node is configured.";
        description
          "-06 Pacific/Easter -6:00";
      }
      container Pacific-Efate {
        presence "Indicates this node is configured.";
        description
          "+11 Pacific/Efate 11:00";
      }
      container Pacific-Enderbury {
        presence "Indicates this node is configured.";
        description
          "+13 Pacific/Enderbury 13:00";
      }
      container Pacific-Fakaofo {
        presence "Indicates this node is configured.";
        description
          "+13 Pacific/Fakaofo 13:00";
      }
      container Pacific-Fiji {
        presence "Indicates this node is configured.";
        description
          "+12 Pacific/Fiji 12:00";
      }
      container Pacific-Funafuti {
        presence "Indicates this node is configured.";
        description
          "+12 Pacific/Funafuti 12:00";
      }
      container Pacific-Galapagos {
        presence "Indicates this node is configured.";
        description
          "-06 Pacific/Galapagos -6:00";
      }
      container Pacific-Gambier {
        presence "Indicates this node is configured.";
        description
          "-09 Pacific/Gambier -9:00";
      }
      container Pacific-Guadalcanal {
        presence "Indicates this node is configured.";
        description
          "+11 Pacific/Guadalcanal 11:00";
      }
      container Pacific-Guam {
        presence "Indicates this node is configured.";
        description
          "ChST Pacific/Guam 10:00";
      }
      container Pacific-Honolulu {
        presence "Indicates this node is configured.";
        description
          "HST Pacific/Honolulu -10:00";
      }
      container Pacific-Johnston {
        presence "Indicates this node is configured.";
        description
          "HST Pacific/Johnston -10:00";
      }
      container Pacific-Kiritimati {
        presence "Indicates this node is configured.";
        description
          "+14 Pacific/Kiritimati 14:00";
      }
      container Pacific-Kosrae {
        presence "Indicates this node is configured.";
        description
          "+11 Pacific/Kosrae 11:00";
      }
      container Pacific-Kwajalein {
        presence "Indicates this node is configured.";
        description
          "+12 Pacific/Kwajalein 12:00";
      }
      container Pacific-Majuro {
        presence "Indicates this node is configured.";
        description
          "+12 Pacific/Majuro 12:00";
      }
      container Pacific-Marquesas {
        presence "Indicates this node is configured.";
        description
          "-0930 Pacific/Marquesas -09:30";
      }
      container Pacific-Midwy {
        presence "Indicates this node is configured.";
        description
          "SST Pacific/Midwy -11:00";
      }
      container Pacific-Nauru {
        presence "Indicates this node is configured.";
        description
          "+12 Pacific/Nauru 12:00";
      }
      container Pacific-Niue {
        presence "Indicates this node is configured.";
        description
          "-11 Pacific/Niue -11:00";
      }
      container Pacific-Norfolk {
        presence "Indicates this node is configured.";
        description
          "+11 Pacific/Norfolk 11:00";
      }
      container Pacific-Noumea {
        presence "Indicates this node is configured.";
        description
          "+11 Pacific/Noumea 11:00";
      }
      container Pacific-Pago_Pago {
        presence "Indicates this node is configured.";
        description
          "SST Pacific/Pago_Pago -11:00";
      }
      container Pacific-Palau {
        presence "Indicates this node is configured.";
        description
          "+09 Pacific/Palau 9:00";
      }
      container Pacific-Pitcairn {
        presence "Indicates this node is configured.";
        description
          "-08 Pacific/Pitcairn -8:00";
      }
      container Pacific-Pohnpei {
        presence "Indicates this node is configured.";
        description
          "+11 Pacific/Pohnpei 11:00";
      }
      container Pacific-Ponape {
        presence "Indicates this node is configured.";
        description
          "+11 Pacific/Ponape 11:00";
      }
      container Pacific-Port_Moresby {
        presence "Indicates this node is configured.";
        description
          "+10 Pacific/Port_Moresby 10:00";
      }
      container Pacific-Rarotonga {
        presence "Indicates this node is configured.";
        description
          "-10 Pacific/Rarotonga -10:00";
      }
      container Pacific-Saipan {
        presence "Indicates this node is configured.";
        description
          "ChST Pacific/Saipan 10:00";
      }
      container Pacific-Samoa {
        presence "Indicates this node is configured.";
        description
          "SST Pacific/Samoa -11:00";
      }
      container Pacific-Tahiti {
        presence "Indicates this node is configured.";
        description
          "-10 Pacific/Tahiti -10:00";
      }
      container Pacific-Tarawa {
        presence "Indicates this node is configured.";
        description
          "+12 Pacific/Tarawa 12:00";
      }
      container Pacific-Tongatapu {
        presence "Indicates this node is configured.";
        description
          "+13 Pacific/Tongatapu 13:00";
      }
      container Pacific-Truk {
        presence "Indicates this node is configured.";
        description
          "+10 Pacific/Truk 10:00";
      }
      container Pacific-Wake {
        presence "Indicates this node is configured.";
        description
          "+12 Pacific/Wake 12:00";
      }
      container Pacific-Wallis {
        presence "Indicates this node is configured.";
        description
          "+12 Pacific/Wallis 12:00";
      }
      container Pacific-Yap {
        presence "Indicates this node is configured.";
        description
          "+10 Pacific/Yap 10:00";
      }
      container Poland {
        presence "Indicates this node is configured.";
        description
          "CET Poland 1:00";
      }
      container Portugal {
        presence "Indicates this node is configured.";
        description
          "WET Portugal 0:00";
      }
      container ROC {
        presence "Indicates this node is configured.";
        description
          "CST ROC -6:00";
      }
      container ROK {
        presence "Indicates this node is configured.";
        description
          "KST ROK 9:00";
      }
      container Singapore {
        presence "Indicates this node is configured.";
        description
          "+08 Singapore 8:00";
      }
      container Turkey {
        presence "Indicates this node is configured.";
        description
          "+03 Turkey 3:00";
      }
      container UCT {
        presence "Indicates this node is configured.";
        description
          "UCT UCT 0:00";
      }
      container US-Alaska {
        presence "Indicates this node is configured.";
        description
          "AKST US/Alaska -9:00";
      }
      container US-Arizona {
        presence "Indicates this node is configured.";
        description
          "MST US/Arizona -7:00";
      }
      container US-Central {
        presence "Indicates this node is configured.";
        description
          "CST US/Central -6:00";
      }
      container US-East-Indiana {
        presence "Indicates this node is configured.";
        description
          "EST US/East-Indiana -5:00";
      }
      container US-Eastern {
        presence "Indicates this node is configured.";
        description
          "EST US/Eastern -5:00";
      }
      container US-Hawaii {
        presence "Indicates this node is configured.";
        description
          "HST US/Hawaii -10:00";
      }
      container US-Indiana-Starke {
        presence "Indicates this node is configured.";
        description
          "CST US/Indiana-Starke -6:00";
      }
      container US-Michigan {
        presence "Indicates this node is configured.";
        description
          "EST US/Michigan -5:00";
      }
      container US-Mountain {
        presence "Indicates this node is configured.";
        description
          "MST US/Mountain -7:00";
      }
      container US-Pacific {
        presence "Indicates this node is configured.";
        description
          "PST US/Pacific -8:00";
      }
      container US-Samoa {
        presence "Indicates this node is configured.";
        description
          "SST US/Samoa -11:00";
      }
      container UTC {
        presence "Indicates this node is configured.";
        description
          "UTC UTC 0:00";
      }
      container Universal {
        presence "Indicates this node is configured.";
        description
          "UTC Universal 0:00";
      }
      container W-SU {
        presence "Indicates this node is configured.";
        description
          "MSK W-SU 3:00";
      }
      container WET {
        presence "Indicates this node is configured.";
        description
          "WET WET 0:00";
      }
      container Zulu {
        presence "Indicates this node is configured.";
        description
          "UTC Zulu 0:00";
      }
      container zone1970.tab {
        presence "Indicates this node is configured.";
        description
          "zone zone1970.tab -24:00";
      }
    }
  }
}
