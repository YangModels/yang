//*************  DO-NOT EDIT  **************
//*********** Auto-generated file ********** 

 module cisco-xr-openconfig-vlan-deviations {


  namespace "http://cisco.com/ns/yang/cisco-xr-openconfig-vlan-deviations";
  prefix  "vlandevs";

  import openconfig-vlan { prefix oc-vlan; }
  import openconfig-interfaces { prefix oc-if; }
  import openconfig-if-ethernet { prefix oc-eth; }
  import openconfig-if-aggregate { prefix oc-lag; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-vlan.yang@2015-10-09 

     on Cisco IOS-XR devices.

     Copyright (c) 2016-2019 by Cisco Systems, Inc.
     All rights reserved.";

  revision "2019-04-18" {
    description
      "vlan-id tag is supported for the state 
       (previously only marked as supported for config)";
  }

  revision "2018-07-04" {
    description
      "Revision applicable to IOS-XR 6.5.1";
  }

  revision "2016-07-08" {
    description
      "Initial revision applicable to IOS-XR 6.1.1";
  }

  deviation /oc-vlan:vlans/oc-vlan:vlan {
    deviate not-supported;
  }

  deviation /oc-if:interfaces/oc-if:interface/oc-eth:ethernet/oc-vlan:switched-vlan/oc-vlan:config/oc-vlan:interface-mode {
    deviate not-supported;
  }

  deviation /oc-if:interfaces/oc-if:interface/oc-eth:ethernet/oc-vlan:switched-vlan/oc-vlan:config/oc-vlan:native-vlan {
    deviate not-supported;
  }

  deviation /oc-if:interfaces/oc-if:interface/oc-eth:ethernet/oc-vlan:switched-vlan/oc-vlan:config/oc-vlan:access-vlan {
    deviate not-supported;
  }

  deviation /oc-if:interfaces/oc-if:interface/oc-eth:ethernet/oc-vlan:switched-vlan/oc-vlan:config/oc-vlan:trunk-vlans {
    deviate not-supported;
  }

  deviation /oc-if:interfaces/oc-if:interface/oc-eth:ethernet/oc-vlan:switched-vlan/oc-vlan:state/oc-vlan:interface-mode {
    deviate not-supported;
  }

  deviation /oc-if:interfaces/oc-if:interface/oc-eth:ethernet/oc-vlan:switched-vlan/oc-vlan:state/oc-vlan:native-vlan {
    deviate not-supported;
  }

  deviation /oc-if:interfaces/oc-if:interface/oc-eth:ethernet/oc-vlan:switched-vlan/oc-vlan:state/oc-vlan:access-vlan {
    deviate not-supported;
  }

  deviation /oc-if:interfaces/oc-if:interface/oc-eth:ethernet/oc-vlan:switched-vlan/oc-vlan:state/oc-vlan:trunk-vlans {
    deviate not-supported;
  }

  deviation /oc-if:interfaces/oc-if:interface/oc-lag:aggregation/oc-vlan:switched-vlan/oc-vlan:config/oc-vlan:interface-mode {
    deviate not-supported;
  }

  deviation /oc-if:interfaces/oc-if:interface/oc-lag:aggregation/oc-vlan:switched-vlan/oc-vlan:config/oc-vlan:native-vlan {
    deviate not-supported;
  }

  deviation /oc-if:interfaces/oc-if:interface/oc-lag:aggregation/oc-vlan:switched-vlan/oc-vlan:config/oc-vlan:access-vlan {
    deviate not-supported;
  }

  deviation /oc-if:interfaces/oc-if:interface/oc-lag:aggregation/oc-vlan:switched-vlan/oc-vlan:config/oc-vlan:trunk-vlans {
    deviate not-supported;
  }

  deviation /oc-if:interfaces/oc-if:interface/oc-lag:aggregation/oc-vlan:switched-vlan/oc-vlan:state/oc-vlan:interface-mode {
    deviate not-supported;
  }

  deviation /oc-if:interfaces/oc-if:interface/oc-lag:aggregation/oc-vlan:switched-vlan/oc-vlan:state/oc-vlan:native-vlan {
    deviate not-supported;
  }

  deviation /oc-if:interfaces/oc-if:interface/oc-lag:aggregation/oc-vlan:switched-vlan/oc-vlan:state/oc-vlan:access-vlan {
    deviate not-supported;
  }

  deviation /oc-if:interfaces/oc-if:interface/oc-lag:aggregation/oc-vlan:switched-vlan/oc-vlan:state/oc-vlan:trunk-vlans {
    deviate not-supported;
  }

  deviation /oc-if:interfaces/oc-if:interface/oc-vlan:routed-vlan/oc-vlan:config/oc-vlan:vlan {
    deviate not-supported;
  }

  deviation /oc-if:interfaces/oc-if:interface/oc-vlan:routed-vlan/oc-vlan:state/oc-vlan:vlan {
    deviate not-supported;
  }


}
//total deviations:21
