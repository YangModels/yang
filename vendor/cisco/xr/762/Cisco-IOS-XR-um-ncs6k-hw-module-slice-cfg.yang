module Cisco-IOS-XR-um-ncs6k-hw-module-slice-cfg {
  namespace "http://cisco.com/ns/yang/Cisco-IOS-XR-um-ncs6k-hw-module-slice-cfg";
  prefix um-ncs6k-hw-module-slice-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs6k-hw-module-slice package configuration.
     
     This YANG module augments the
     modules with configuration data.
     
     Copyright (c) 2020 by Cisco Systems, Inc.
     All rights reserved.";

  revision 2020-09-15 {
    description
      "Initial release";
    semver:module-version "1.0.0";
  }

  grouping LOCATION-BODY {
    container location {
      description
        "Fully qualified location specification";
      container slices {
        description
          "Configure slice h/w module";
        list slice {
          key "slice-id";
          description
            "Configure slice h/w module";
          leaf slice-id {
            type uint32 {
              range "0..4" {
                description
                  "Slice number";
              }
            }
            description
              "Configure slice h/w module";
          }
          container shutdown {
            presence "Indicates a shutdown node is configured.";
            description
              "Shutdown the slice";
          }
          container breakout {
            description
              "Configure slice in breakout mode";
            container ten-g {
              presence "Indicates a ten-g node is configured.";
              description
                "config slice in 10G breakout mode";
            }
          }
          container framer-mode {
            description
              "Configure framer mode for the slice (Ethernet is default)";
            container otu4 {
              presence "Indicates a otu4 node is configured.";
              description
                "config slice in OTN (G.709-OTU4) 100G mode";
            }
          }
          container reset {
            description
              "Slice reset feature";
            container auto {
              description
                "Automatic slice reset on system errors";
              container disable {
                presence "Indicates a disable node is configured.";
                description
                  "Disable slice reset due to system faults";
              }
            }
          }
        }
      }
    }
  }

  augment "/location:locations/location:location" {
    uses LOCATION-BODY;
  }
  augment "/location:locations/location:preconfigured-location" {
    uses LOCATION-BODY;
  }
}
