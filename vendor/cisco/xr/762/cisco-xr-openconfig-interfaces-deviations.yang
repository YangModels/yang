module cisco-xr-openconfig-interfaces-deviations {


  namespace "http://cisco.com/ns/yang/cisco-xr-openconfig-interfaces-deviations";
  prefix  "ocifdevs";

  import openconfig-interfaces { prefix oc-if; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-interfaces.yang@2015-11-20 

     on Cisco IOS-XR devices.

     Copyright (c) 2016-2017, 2019 by Cisco Systems, Inc.
     All rights reserved.";

  revision "2016-05-16" {
    description
      "Initial revision applicable to IOS-XR 6.1.1";
  }

  deviation /oc-if:interfaces/oc-if:interface/oc-if:config/oc-if:enabled {
    deviate delete {
        default true;
    }
  }

  deviation /oc-if:interfaces/oc-if:interface/oc-if:state/oc-if:enabled {
    deviate delete {
        default true;
    }
  }

}
//total deviations:2
