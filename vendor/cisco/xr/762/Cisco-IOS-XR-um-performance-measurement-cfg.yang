module Cisco-IOS-XR-um-performance-measurement-cfg {
  namespace "http://cisco.com/ns/yang/Cisco-IOS-XR-um-performance-measurement-cfg";
  prefix um-performance-measurement-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR performance-measurement package configuration.
     
     This YANG module augments the
     modules with configuration data.
     
     Copyright (c) 2021 by Cisco Systems, Inc.
     All rights reserved.";

  revision 2021-12-08 {
    description
      "Added name and tx-interval nodes support under delay-profile and liveness-profile";
    semver:module-version "1.1.0";
  }
  revision 2021-06-29 {
    description
      "Initial release";
    semver:module-version "1.0.0";
  }

  container performance-measurement {
    presence "Indicates a performance-measurement node is configured.";
    description
      "Enter the Performance Measurement submode";
    container interfaces {
      description
        "Enable Performance Measurement on an interface";
      list interface {
        key "interface-name";
        description
          "Enable Performance Measurement on an interface";
        leaf interface-name {
          type xr:Interface-name;
          description
            "Enable Performance Measurement on an interface";
        }
        container delay-measurement {
          presence "Indicates a delay-measurement node is configured.";
          description
            "Enable delay-measurement on the interface";
          leaf advertise-delay {
            type uint32 {
              range "1..16777215" {
                description
                  "Advertisement delay (uSec)";
              }
            }
            description
              "Advertisement delay";
          }
          container delay-profile {
            description
              "Interface delay profile";
            leaf name {
              type xr:Cisco-ios-xr-string {
                length "1..256" {
                  description
                    "Profile name";
                }
              }
              description
                "Profile name";
            }
          }
        }
        container next-hop {
          description
            "next-hop address";
          leaf ipv4 {
            type inet:ipv4-address-no-zone;
            must "not(../ipv6)";
            description
              "IPv4 address";
          }
          leaf ipv6 {
            type inet:ipv6-address-no-zone;
            must "not(../ipv4)";
            description
              "IPv6 address";
          }
        }
      }
    }
    container endpoint {
      description
        "Enable Performance Measurement for an endpoint";
      container ipv4s {
        description
          "IPv4 endpoint";
        list ipv4 {
          must "vrf";
          key "address";
          description
            "IPv4 endpoint";
          leaf address {
            type inet:ipv4-address-no-zone;
            description
              "IPv4 endpoint";
          }
          list vrf {
            key "vrf-name";
            description
              "Endpoint vrf table";
            leaf vrf-name {
              type union {
                type string {
                  pattern "default" {
                    description
                      "Default VRF name";
                  }
                }
                type xr:Cisco-ios-xr-string {
                  length "1..32" {
                    description
                      "VRF name";
                  }
                }
              }
              description
                "endpoint vrf table";
            }
            container source-address {
              description
                "Source address of the endpoint";
              leaf ipv4 {
                type inet:ipv4-address-no-zone;
                description
                  "IPv4 address";
              }
            }
            leaf description {
              type string {
                length "1..255" {
                  description
                    "Description of the endpoint";
                }
              }
              description
                "Description of the endpoint";
            }
            container delay-measurement {
              presence "Indicates a delay-measurement node is configured.";
              description
                "Enable delay-measurement on the endpoint";
              container delay-profile {
                description
                  "Endpoint delay profile name";
                leaf name {
                  type xr:Cisco-ios-xr-string {
                    length "1..256" {
                      description
                        "Profile name";
                    }
                  }
                  description
                    "Profile name";
                }
              }
            }
            container segment-list {
              description
                "Enable segment list on the endpoint";
              container names {
                description
                  "Segment-list name";
                list name {
                  key "list-name";
                  description
                    "Segment-list name";
                  leaf list-name {
                    type xr:Cisco-ios-xr-string {
                      length "1..128" {
                        description
                          "Identifying name for segment-list";
                      }
                    }
                    description
                      "Segment-list name";
                  }
                }
              }
            }
            container liveness-detection {
              presence "Indicates a liveness-detection node is configured.";
              description
                "Enable liveness-detection on the endpoint";
              container liveness-profile {
                description
                  "Endpoint liveness profile name";
                leaf name {
                  type xr:Cisco-ios-xr-string {
                    length "1..256" {
                      description
                        "Profile name";
                    }
                  }
                  description
                    "Profile name";
                }
              }
            }
          }
        }
      }
      container ipv6s {
        description
          "IPv6 endpoint";
        list ipv6 {
          must "vrf";
          key "address";
          description
            "IPv6 endpoint";
          leaf address {
            type inet:ipv6-address-no-zone;
            description
              "IPv6 endpoint";
          }
          list vrf {
            key "vrf-name";
            description
              "Endpoint vrf table";
            leaf vrf-name {
              type union {
                type string {
                  pattern "default" {
                    description
                      "Default VRF name";
                  }
                }
                type xr:Cisco-ios-xr-string {
                  length "1..32" {
                    description
                      "VRF name";
                  }
                }
              }
              description
                "endpoint vrf table";
            }
            container source-address {
              description
                "Source address of the endpoint";
              leaf ipv6 {
                type inet:ipv6-address-no-zone;
                description
                  "IPv6 address";
              }
            }
            leaf description {
              type string {
                length "1..255" {
                  description
                    "Description of the endpoint";
                }
              }
              description
                "Description of the endpoint";
            }
            container delay-measurement {
              presence "Indicates a delay-measurement node is configured.";
              description
                "Enable delay-measurement on the endpoint";
              container delay-profile {
                description
                  "Endpoint delay profile name";
                leaf name {
                  type xr:Cisco-ios-xr-string {
                    length "1..256" {
                      description
                        "Profile name";
                    }
                  }
                  description
                    "Profile name";
                }
              }
            }
            container segment-list {
              description
                "Enable segment list on the endpoint";
              container names {
                description
                  "Segment-list name";
                list name {
                  key "list-name";
                  description
                    "Segment-list name";
                  leaf list-name {
                    type xr:Cisco-ios-xr-string {
                      length "1..128" {
                        description
                          "Identifying name for segment-list";
                      }
                    }
                    description
                      "Segment-list name";
                  }
                }
              }
            }
            container liveness-detection {
              presence "Indicates a liveness-detection node is configured.";
              description
                "Enable liveness-detection on the endpoint";
              container liveness-profile {
                description
                  "Endpoint liveness profile name";
                leaf name {
                  type xr:Cisco-ios-xr-string {
                    length "1..256" {
                      description
                        "Profile name";
                    }
                  }
                  description
                    "Profile name";
                }
              }
            }
          }
        }
      }
    }
    container delay-profile {
      description
        "Delay profile";
      container interfaces {
        description
          "Enter interface delay profile submode";
        container names {
          description
            "Deprecated in IOS-XR 7.6.1. Please use 'delay-profile name' instead";
          list name {
            key "profile-name";
            description
              "Deprecated in IOS-XR 7.6.1. Please use 'delay-profile name' instead";
            leaf profile-name {
              type string {
                length "1..256" {
                  description
                    "Profile name";
                }
              }
              description
                "Deprecated in IOS-XR 7.6.1. Please use 'delay-profile name' instead";
            }
            container probe {
              description
                "Enter interface delay probe submode";
              leaf computation-interval {
                type uint32 {
                  range "1..3600" {
                    description
                      "Computation interval (seconds)";
                  }
                }
                description
                  "Interval for metric computation";
              }
              leaf burst-interval {
                type uint32 {
                  range "30..15000" {
                    description
                      "Burst interval (msec) (Deprecated in IOS-XR 7.6.1. Please use tx-interval.)";
                  }
                }
                description
                  "Burst interval (Deprecated in IOS-XR 7.6.1. Please use tx-interval.)";
              }
              leaf tx-interval {
                type uint32 {
                  range "30000..15000000" {
                    description
                      "TX interval (usec)";
                  }
                }
                description
                  "TX interval";
              }
              container protocol {
                description
                  "Configure protocol type for delay measurement probe messages";
                container pm-mpls {
                  must "not(../twamp-light)";
                  presence "Indicates a pm-mpls node is configured.";
                  description
                    "Interface delay measurement using RFC6374 with MPLS encap";
                }
                container twamp-light {
                  must "not(../pm-mpls)";
                  presence "Indicates a twamp-light node is configured.";
                  description
                    "Interface delay measurement using RFC5357";
                }
              }
              container tos {
                description
                  "Enter interface delay probe type of service submode";
                leaf traffic-class {
                  type uint32 {
                    range "0..7" {
                      description
                        "Traffic Class value";
                    }
                  }
                  description
                    "Traffic Class value indicating TOS level used by protocol pm-mpls";
                }
                leaf dscp {
                  type uint32 {
                    range "0..63" {
                      description
                        "DSCP value";
                    }
                  }
                  description
                    "DSCP value indicating TOS level used by protocol twamp-light";
                }
              }
              container measurement-mode {
                description
                  "Delay measurement mode";
                container one-way {
                  must "not(../two-way)";
                  presence "Indicates a one-way node is configured.";
                  description
                    "Measure one way delay with timestamp 1 and 2";
                }
                container two-way {
                  must "not(../one-way)";
                  presence "Indicates a two-way node is configured.";
                  description
                    "Measure one way delay with timestamp 1, 2, 3 and 4 without clock synchronization";
                }
              }
            }
            container advertisement {
              description
                "Enter interface delay profile advertisement submode";
              container periodic {
                description
                  "Go into interface delay periodic advertisement submode";
                container disabled {
                  presence "Indicates a disabled node is configured.";
                  description
                    "Periodic advertisement disabled";
                }
                leaf interval {
                  type uint32 {
                    range "30..3600" {
                      description
                        "Periodic advertisement and metric aggregation interval (seconds)";
                    }
                  }
                  description
                    "Periodic advertisement and metric aggregation interval";
                }
                leaf threshold {
                  type uint32 {
                    range "0..100" {
                      description
                        "Periodic advertisement threshold percentage change (compared to last advertisement)";
                    }
                  }
                  description
                    "Periodic advertisement threshold (compared to last advertisement)";
                }
                leaf minimum-change {
                  type uint32 {
                    range "0..100000" {
                      description
                        "Periodic advertisement minimum change in uSec (compared to last advertisement)";
                    }
                  }
                  description
                    "Periodic advertisement minimum change (compared to last advertisement)";
                }
              }
              container logging {
                description
                  "Enter interface delay profile advertisement logging submode";
                container delay-exceeded {
                  presence "Indicates a delay-exceeded node is configured.";
                  description
                    "Emit syslog when the delay exceeds the threshold";
                }
              }
              container accelerated {
                presence "Indicates a accelerated node is configured.";
                description
                  "Enter interface delay profile advertisement accelerated submode";
                leaf threshold {
                  type uint32 {
                    range "0..100" {
                      description
                        "Accelerated advertisement threshold percentage change";
                    }
                  }
                  description
                    "Accelerated advertisement threshold";
                }
                leaf minimum-change {
                  type uint32 {
                    range "0..100000" {
                      description
                        "Accelerated advertisement minimum change (uSec)";
                    }
                  }
                  description
                    "Accelerated advertisement minimum change";
                }
              }
              container anomaly-check {
                presence "Indicates a anomaly-check node is configured.";
                description
                  "Enter interface delay profile advertisement anomaly submode";
                leaf upper-bound {
                  type uint32 {
                    range "0..200000" {
                      description
                        "Anomaly Check advertisement upper-bound (uSec)";
                    }
                  }
                  must "../lower-bound";
                  must "../lower-bound";
                  description
                    "Anomaly Check advertisement upper-bound";
                }
                leaf lower-bound {
                  type uint32 {
                    range "0..200000" {
                      description
                        "Anomaly Check advertisement lower-bound (uSec)";
                    }
                  }
                  must "../upper-bound";
                  must "../upper-bound";
                  description
                    "Anomaly Check advertisement lower-bound";
                }
              }
            }
          }
        }
        container default {
          presence "Indicates a default node is configured.";
          description
            "Default profile";
          container probe {
            description
              "Enter interface delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            container protocol {
              description
                "Configure protocol type for delay measurement probe messages";
              container pm-mpls {
                must "not(../twamp-light)";
                presence "Indicates a pm-mpls node is configured.";
                description
                  "Interface delay measurement using RFC6374 with MPLS encap";
              }
              container twamp-light {
                must "not(../pm-mpls)";
                presence "Indicates a twamp-light node is configured.";
                description
                  "Interface delay measurement using RFC5357";
              }
            }
            container tos {
              description
                "Enter interface delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
          }
          container advertisement {
            description
              "Enter interface delay profile advertisement submode";
            container periodic {
              description
                "Go into interface delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container logging {
              description
                "Enter interface delay profile advertisement logging submode";
              container delay-exceeded {
                presence "Indicates a delay-exceeded node is configured.";
                description
                  "Emit syslog when the delay exceeds the threshold";
              }
            }
            container accelerated {
              presence "Indicates a accelerated node is configured.";
              description
                "Enter interface delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter interface delay profile advertisement anomaly submode";
              leaf upper-bound {
                type uint32 {
                  range "0..200000" {
                    description
                      "Anomaly Check advertisement upper-bound (uSec)";
                  }
                }
                must "../lower-bound";
                must "../lower-bound";
                description
                  "Anomaly Check advertisement upper-bound";
              }
              leaf lower-bound {
                type uint32 {
                  range "0..200000" {
                    description
                      "Anomaly Check advertisement lower-bound (uSec)";
                  }
                }
                must "../upper-bound";
                must "../upper-bound";
                description
                  "Anomaly Check advertisement lower-bound";
              }
            }
          }
        }
      }
      container rsvp-te {
        description
          "Enter RSVP-TE delay profile submode";
        container default {
          presence "Indicates a default node is configured.";
          description
            "Default profile";
          container probe {
            description
              "Enter RSVP-TE delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            container protocol {
              description
                "Configure protocol type for delay measurement probe messages";
              container pm-mpls {
                must "not(../twamp-light)";
                presence "Indicates a pm-mpls node is configured.";
                description
                  "RSVP-TE tunnel delay measurement using RFC6374 with MPLS encap";
              }
              container twamp-light {
                must "not(../pm-mpls)";
                presence "Indicates a twamp-light node is configured.";
                description
                  "RSVP-TE tunnel delay measurement using RFC5357";
              }
            }
            container tos {
              description
                "Enter RSVP-TE delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../loopback)";
                presence "Indicates a one-way node is configured.";
                description
                  "Measure one way delay with timestamp 1 and 2";
              }
              container loopback {
                must "not(../one-way)";
                presence "Indicates a loopback node is configured.";
                description
                  "Loopback the probe packet collecting only timestamp 1 and 4";
              }
            }
          }
          container advertisement {
            description
              "Enter RSVP-TE delay profile advertisement submode";
            container periodic {
              description
                "Go into RSVP-TE delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container logging {
              description
                "Enter RSVP-TE delay profile advertisement logging submode";
              container delay-exceeded {
                presence "Indicates a delay-exceeded node is configured.";
                description
                  "Emit syslog when the delay exceeds the threshold";
              }
            }
            container accelerated {
              presence "Indicates a accelerated node is configured.";
              description
                "Enter RSVP-TE delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
          }
        }
      }
      container sr-policy {
        description
          "Enter SR Policy delay profile submode";
        container names {
          description
            "Deprecated in IOS-XR 7.6.1. Please use 'delay-profile name' instead";
          list name {
            key "profile-name";
            description
              "Deprecated in IOS-XR 7.6.1. Please use 'delay-profile name' instead";
            leaf profile-name {
              type string {
                length "1..256" {
                  description
                    "Profile name";
                }
              }
              description
                "Deprecated in IOS-XR 7.6.1. Please use 'delay-profile name' instead";
            }
            container probe {
              description
                "Enter SR Policy delay probe submode";
              leaf computation-interval {
                type uint32 {
                  range "1..3600" {
                    description
                      "Computation interval (seconds)";
                  }
                }
                description
                  "Interval for metric computation";
              }
              leaf burst-interval {
                type uint32 {
                  range "30..15000" {
                    description
                      "Burst interval (msec) (Deprecated in IOS-XR 7.6.1. Please use tx-interval.)";
                  }
                }
                description
                  "Burst interval (Deprecated in IOS-XR 7.6.1. Please use tx-interval.)";
              }
              leaf tx-interval {
                type uint32 {
                  range "30000..15000000" {
                    description
                      "TX interval (usec)";
                  }
                }
                description
                  "TX interval";
              }
              container sweep {
                description
                  "Enable ECMP hashing by sweeping a field in the probe packet";
                container destination {
                  description
                    "Sweep a range of IP destination addresses";
                  leaf ipv4 {
                    type inet:ipv4-address-no-zone;
                    must "../range";
                    description
                      "Start of the IPv4 address range, used by IPv4, IPv6 and NULL endpoint SR Policy";
                  }
                  leaf range {
                    type uint32 {
                      range "0..128" {
                        description
                          "Sweeping range (Should fully be in the 127.0.0.0/8 space)";
                      }
                    }
                    must "../ipv4";
                    description
                      "Number of IP addresses to sweep ";
                  }
                }
              }
              container protocol {
                description
                  "Configure protocol type for delay measurement probe messages";
                container pm-mpls {
                  must "not(../twamp-light)";
                  presence "Indicates a pm-mpls node is configured.";
                  description
                    "SR Policy delay measurement using RFC6374 with MPLS encap";
                }
                container twamp-light {
                  must "not(../pm-mpls)";
                  presence "Indicates a twamp-light node is configured.";
                  description
                    "SR Policy delay measurement using RFC5357";
                }
              }
              container tos {
                description
                  "Enter SR Policy delay probe type of service submode";
                leaf traffic-class {
                  type uint32 {
                    range "0..7" {
                      description
                        "Traffic Class value";
                    }
                  }
                  description
                    "Traffic Class value indicating TOS level used by protocol pm-mpls";
                }
                leaf dscp {
                  type uint32 {
                    range "0..63" {
                      description
                        "DSCP value";
                    }
                  }
                  description
                    "DSCP value indicating TOS level used by protocol twamp-light";
                }
              }
              container measurement-mode {
                description
                  "Delay measurement mode";
                container one-way {
                  must "not(../two-way or ../loopback)";
                  presence "Indicates a one-way node is configured.";
                  description
                    "Measure one way delay with timestamp 1 and 2";
                }
                container two-way {
                  must "not(../one-way or ../loopback)";
                  presence "Indicates a two-way node is configured.";
                  description
                    "Measure one way delay with timestamp 1, 2, 3 and 4 without clock synchronization";
                }
                container loopback {
                  must "not(../one-way or ../two-way)";
                  presence "Indicates a loopback node is configured.";
                  description
                    "Loopback the probe packet collecting only timestamp 1 and 4 (reverse-path must be configured for SR Policy with RFC6374 MPLS encap)";
                }
              }
            }
            container advertisement {
              description
                "Enter SR Policy delay profile advertisement submode";
              container logging {
                description
                  "Enter SR Policy delay profile advertisement logging submode";
                container delay-exceeded {
                  presence "Indicates a delay-exceeded node is configured.";
                  description
                    "Emit syslog when the delay exceeds the threshold";
                }
              }
              container threshold-check {
                description
                  "Configure threshold-check for delay measurement advertisement (default: maximum-delay)";
                container average-delay {
                  presence "Indicates a average-delay node is configured.";
                  description
                    "Enable average-delay threshold-check";
                }
                container minimum-delay {
                  presence "Indicates a minimum-delay node is configured.";
                  description
                    "Enable minimum-delay threshold-check";
                }
                container maximum-delay {
                  presence "Indicates a maximum-delay node is configured.";
                  description
                    "Enable maximum-delay threshold-check";
                }
              }
              container periodic {
                description
                  "Go into SR Policy delay periodic advertisement submode";
                container disabled {
                  presence "Indicates a disabled node is configured.";
                  description
                    "Periodic advertisement disabled";
                }
                leaf interval {
                  type uint32 {
                    range "30..3600" {
                      description
                        "Periodic advertisement and metric aggregation interval (seconds)";
                    }
                  }
                  description
                    "Periodic advertisement and metric aggregation interval";
                }
                leaf threshold {
                  type uint32 {
                    range "0..100" {
                      description
                        "Periodic advertisement threshold percentage change (compared to last advertisement)";
                    }
                  }
                  description
                    "Periodic advertisement threshold (compared to last advertisement)";
                }
                leaf minimum-change {
                  type uint32 {
                    range "0..100000" {
                      description
                        "Periodic advertisement minimum change in uSec (compared to last advertisement)";
                    }
                  }
                  description
                    "Periodic advertisement minimum change (compared to last advertisement)";
                }
              }
              container accelerated {
                presence "Indicates a accelerated node is configured.";
                description
                  "Enter SR Policy delay profile advertisement accelerated submode";
                leaf threshold {
                  type uint32 {
                    range "0..100" {
                      description
                        "Accelerated advertisement threshold percentage change";
                    }
                  }
                  description
                    "Accelerated advertisement threshold";
                }
                leaf minimum-change {
                  type uint32 {
                    range "0..100000" {
                      description
                        "Accelerated advertisement minimum change (uSec)";
                    }
                  }
                  description
                    "Accelerated advertisement minimum change";
                }
              }
              container anomaly-check {
                presence "Indicates a anomaly-check node is configured.";
                description
                  "Enter SR Policy delay profile advertisement anomaly submode";
                leaf upper-bound {
                  type uint32 {
                    range "0..200000" {
                      description
                        "Anomaly Check advertisement upper-bound (uSec)";
                    }
                  }
                  must "../lower-bound";
                  must "../lower-bound";
                  description
                    "Anomaly Check advertisement upper-bound";
                }
                leaf lower-bound {
                  type uint32 {
                    range "0..200000" {
                      description
                        "Anomaly Check advertisement lower-bound (uSec)";
                    }
                  }
                  must "../upper-bound";
                  must "../upper-bound";
                  description
                    "Anomaly Check advertisement lower-bound";
                }
              }
            }
          }
        }
        container default {
          presence "Indicates a default node is configured.";
          description
            "Default profile";
          container probe {
            description
              "Enter SR Policy delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container protocol {
              description
                "Configure protocol type for delay measurement probe messages";
              container pm-mpls {
                must "not(../twamp-light)";
                presence "Indicates a pm-mpls node is configured.";
                description
                  "SR Policy delay measurement using RFC6374 with MPLS encap";
              }
              container twamp-light {
                must "not(../pm-mpls)";
                presence "Indicates a twamp-light node is configured.";
                description
                  "SR Policy delay measurement using RFC5357";
              }
            }
            container tos {
              description
                "Enter SR Policy delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way or ../loopback)";
                presence "Indicates a one-way node is configured.";
                description
                  "Measure one way delay with timestamp 1 and 2";
              }
              container two-way {
                must "not(../one-way or ../loopback)";
                presence "Indicates a two-way node is configured.";
                description
                  "Measure one way delay with timestamp 1, 2, 3 and 4 without clock synchronization";
              }
              container loopback {
                must "not(../one-way or ../two-way)";
                presence "Indicates a loopback node is configured.";
                description
                  "Loopback the probe packet collecting only timestamp 1 and 4 (reverse-path must be configured for SR Policy with RFC6374 MPLS encap)";
              }
            }
          }
          container advertisement {
            description
              "Enter SR Policy delay profile advertisement submode";
            container logging {
              description
                "Enter SR Policy delay profile advertisement logging submode";
              container delay-exceeded {
                presence "Indicates a delay-exceeded node is configured.";
                description
                  "Emit syslog when the delay exceeds the threshold";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Go into SR Policy delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter SR Policy delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter SR Policy delay profile advertisement anomaly submode";
              leaf upper-bound {
                type uint32 {
                  range "0..200000" {
                    description
                      "Anomaly Check advertisement upper-bound (uSec)";
                  }
                }
                must "../lower-bound";
                must "../lower-bound";
                description
                  "Anomaly Check advertisement upper-bound";
              }
              leaf lower-bound {
                type uint32 {
                  range "0..200000" {
                    description
                      "Anomaly Check advertisement lower-bound (uSec)";
                  }
                }
                must "../upper-bound";
                must "../upper-bound";
                description
                  "Anomaly Check advertisement lower-bound";
              }
            }
          }
        }
      }
      container endpoint {
        description
          "Enter endpoint delay profile submode";
        container names {
          description
            "Deprecated in IOS-XR 7.6.1. Please use 'delay-profile name' instead";
          list name {
            key "profile-name";
            description
              "Deprecated in IOS-XR 7.6.1. Please use 'delay-profile name' instead";
            leaf profile-name {
              type string {
                length "1..256" {
                  description
                    "Profile name";
                }
              }
              description
                "Deprecated in IOS-XR 7.6.1. Please use 'delay-profile name' instead";
            }
            container probe {
              description
                "Enter endpoint delay probe submode";
              leaf burst-interval {
                type uint32 {
                  range "30..15000" {
                    description
                      "Burst interval (msec) (Deprecated in IOS-XR 7.6.1. Please use tx-interval.)";
                  }
                }
                description
                  "Burst interval (Deprecated in IOS-XR 7.6.1. Please use tx-interval.)";
              }
              leaf tx-interval {
                type uint32 {
                  range "30000..15000000" {
                    description
                      "TX interval (usec)";
                  }
                }
                description
                  "TX interval";
              }
              leaf computation-interval {
                type uint32 {
                  range "1..3600" {
                    description
                      "Computation interval (seconds)";
                  }
                }
                description
                  "Interval for metric computation";
              }
              container measurement-mode {
                description
                  "Delay measurement mode";
                container one-way {
                  must "not(../two-way or ../loopback)";
                  presence "Indicates a one-way node is configured.";
                  description
                    "Measure one way delay with timestamp 1 and 2";
                }
                container two-way {
                  must "not(../one-way or ../loopback)";
                  presence "Indicates a two-way node is configured.";
                  description
                    "Measure one way delay with timestamp 1, 2, 3 and 4 without clock synchronization";
                }
                container loopback {
                  must "not(../one-way or ../two-way)";
                  presence "Indicates a loopback node is configured.";
                  description
                    "Loopback the probe packet collecting only timestamp 1 and 4";
                }
              }
              container tos {
                description
                  "Enter endpoint delay probe type of service submode";
                leaf dscp {
                  type uint32 {
                    range "0..63" {
                      description
                        "DSCP value";
                    }
                  }
                  description
                    "DSCP value indicating TOS level used by protocol twamp-light";
                }
              }
            }
            container advertisement {
              description
                "Enter endpoint delay profile advertisement submode";
              container logging {
                description
                  "Enter Endpoint delay profile advertisement logging submode";
                container delay-exceeded {
                  presence "Indicates a delay-exceeded node is configured.";
                  description
                    "Emit syslog when the delay exceeds the threshold";
                }
              }
              container threshold-check {
                description
                  "Configure threshold-check for delay measurement advertisement (default: maximum-delay)";
                container average-delay {
                  presence "Indicates a average-delay node is configured.";
                  description
                    "Enable average-delay threshold-check";
                }
                container minimum-delay {
                  presence "Indicates a minimum-delay node is configured.";
                  description
                    "Enable minimum-delay threshold-check";
                }
                container maximum-delay {
                  presence "Indicates a maximum-delay node is configured.";
                  description
                    "Enable maximum-delay threshold-check";
                }
              }
              container periodic {
                description
                  "Enter endpoint delay periodic advertisement submode";
                container disabled {
                  presence "Indicates a disabled node is configured.";
                  description
                    "Periodic advertisement disabled";
                }
                leaf interval {
                  type uint32 {
                    range "30..3600" {
                      description
                        "Periodic advertisement and metric aggregation interval (seconds)";
                    }
                  }
                  description
                    "Periodic advertisement and metric aggregation interval";
                }
                leaf threshold {
                  type uint32 {
                    range "0..100" {
                      description
                        "Periodic advertisement threshold percentage change (compared to last advertisement)";
                    }
                  }
                  description
                    "Periodic advertisement threshold (compared to last advertisement)";
                }
                leaf minimum-change {
                  type uint32 {
                    range "0..100000" {
                      description
                        "Periodic advertisement minimum change in uSec (compared to last advertisement)";
                    }
                  }
                  description
                    "Periodic advertisement minimum change (compared to last advertisement)";
                }
              }
              container accelerated {
                presence "Indicates a accelerated node is configured.";
                description
                  "Enter endpoint delay profile advertisement accelerated submode";
                leaf threshold {
                  type uint32 {
                    range "0..100" {
                      description
                        "Accelerated advertisement threshold percentage change";
                    }
                  }
                  description
                    "Accelerated advertisement threshold";
                }
                leaf minimum-change {
                  type uint32 {
                    range "0..100000" {
                      description
                        "Accelerated advertisement minimum change (uSec)";
                    }
                  }
                  description
                    "Accelerated advertisement minimum change";
                }
              }
            }
          }
        }
        container default {
          presence "Indicates a default node is configured.";
          description
            "Default profile";
          container probe {
            description
              "Enter endpoint delay probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            leaf computation-interval {
              type uint32 {
                range "1..3600" {
                  description
                    "Computation interval (seconds)";
                }
              }
              description
                "Interval for metric computation";
            }
            container measurement-mode {
              description
                "Delay measurement mode";
              container one-way {
                must "not(../two-way or ../loopback)";
                presence "Indicates a one-way node is configured.";
                description
                  "Measure one way delay with timestamp 1 and 2";
              }
              container two-way {
                must "not(../one-way or ../loopback)";
                presence "Indicates a two-way node is configured.";
                description
                  "Measure one way delay with timestamp 1, 2, 3 and 4 without clock synchronization";
              }
              container loopback {
                must "not(../one-way or ../two-way)";
                presence "Indicates a loopback node is configured.";
                description
                  "Loopback the probe packet collecting only timestamp 1 and 4";
              }
            }
            container tos {
              description
                "Enter endpoint delay probe type of service submode";
              leaf dscp {
                type uint32 {
                  range "0..63" {
                    description
                      "DSCP value";
                  }
                }
                description
                  "DSCP value indicating TOS level used by protocol twamp-light";
              }
            }
          }
          container advertisement {
            description
              "Enter endpoint delay profile advertisement submode";
            container logging {
              description
                "Enter Endpoint delay profile advertisement logging submode";
              container delay-exceeded {
                presence "Indicates a delay-exceeded node is configured.";
                description
                  "Emit syslog when the delay exceeds the threshold";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Enter endpoint delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter endpoint delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
          }
        }
      }
      container names {
        description
          "Delay profile name";
        list name {
          key "profile-name";
          description
            "delay-profile name";
          leaf profile-name {
            type xr:Cisco-ios-xr-string {
              length "1..256" {
                description
                  "Profile name";
              }
            }
            description
              "Profile name";
          }
          container probe {
            description
              "Enter delay probe submode";
            leaf computation-interval {
              type uint32 {
                range "1..3600" {
                  description
                    "Computation interval (seconds)";
                }
              }
              description
                "Interval for metric computation";
            }
            leaf tx-interval {
              type uint32 {
                range "30000..15000000" {
                  description
                    "TX interval (usec)";
                }
              }
              description
                "TX interval";
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint";
                }
                leaf range {
                  type uint32 {
                    range "0..128" {
                      description
                        "Sweeping range (Should fully be in the 127.0.0.0/8 space)";
                    }
                  }
                  must "../ipv4";
                  description
                    "Number of IP addresses to sweep ";
                }
              }
            }
            container protocol {
              description
                "Configure protocol type for delay measurement probe messages";
              container pm-mpls {
                must "not(../twamp-light)";
                presence "Indicates a pm-mpls node is configured.";
                description
                  "Delay measurement using RFC6374 with MPLS encap. Only applicable for interface and SR policy delay measurement";
              }
              container twamp-light {
                must "not(../pm-mpls)";
                presence "Indicates a twamp-light node is configured.";
                description
                  "Delay measurement using RFC5357";
              }
            }
            container tos {
              description
                "Enter delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
          }
          container advertisement {
            description
              "Enter delay profile advertisement submode";
            container logging {
              description
                "Enter delay profile advertisement logging submode";
              container delay-exceeded {
                presence "Indicates a delay-exceeded node is configured.";
                description
                  "Emit syslog when the delay exceeds the threshold";
              }
            }
            container threshold-check {
              description
                "Configure threshold-check for delay measurement advertisement";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter delay profile advertisement anomaly submode";
              leaf upper-bound {
                type uint32 {
                  range "0..200000" {
                    description
                      "Anomaly Check advertisement upper-bound (uSec)";
                  }
                }
                must "../lower-bound";
                description
                  "Anomaly Check advertisement upper-bound";
              }
              leaf lower-bound {
                type uint32 {
                  range "0..200000" {
                    description
                      "Anomaly Check advertisement lower-bound (uSec)";
                  }
                }
                must "../upper-bound";
                description
                  "Anomaly Check advertisement lower-bound";
              }
            }
          }
        }
      }
    }
    container liveness-profile {
      description
        "Liveness profile";
      container sr-policy {
        description
          "Enter SR Policy delay profile submode";
        container names {
          description
            "Deprecated in IOS-XR 7.6.1. Please use 'liveness-profile name' instead";
          list name {
            key "profile-name";
            description
              "Deprecated in IOS-XR 7.6.1. Please use 'liveness-profile name' instead";
            leaf profile-name {
              type string {
                length "1..256" {
                  description
                    "Profile name";
                }
              }
              description
                "Deprecated in IOS-XR 7.6.1. Please use 'liveness-profile name' instead";
            }
            container liveness-detection {
              description
                "Enter SR Policy liveness detection submode";
              leaf multiplier {
                type uint32 {
                  range "2..10" {
                    description
                      "Detect multiplier";
                  }
                }
                description
                  "Configure detect multiplier";
              }
            }
            container probe {
              description
                "Enter SR Policy liveness detection probe submode";
              leaf burst-interval {
                type uint32 {
                  range "30..15000" {
                    description
                      "Burst interval (msec) (Deprecated in IOS-XR 7.6.1. Please use tx-interval.)";
                  }
                }
                description
                  "Burst interval (Deprecated in IOS-XR 7.6.1. Please use tx-interval.)";
              }
              leaf tx-interval {
                type uint32 {
                  range "30000..15000000" {
                    description
                      "TX interval (usec)";
                  }
                }
                description
                  "TX interval";
              }
              container measurement-mode {
                description
                  "Deprecated in release 7.6.1";
                container loopback {
                  presence "Indicates a loopback node is configured.";
                  description
                    "Loopback the probe packet collecting only timestamp 1 and 4 (reverse-path must be configured for SR Policy with RFC6374 MPLS encap)";
                }
              }
              container sweep {
                description
                  "Enable ECMP hashing by sweeping a field in the probe packet";
                container destination {
                  description
                    "Sweep a range of IP destination addresses";
                  leaf ipv4 {
                    type inet:ipv4-address-no-zone;
                    must "../range";
                    description
                      "Start of the IPv4 address range, used by IPv4, IPv6 and NULL endpoint SR Policy";
                  }
                  leaf range {
                    type uint32 {
                      range "0..128" {
                        description
                          "Sweeping range (Should fully be in the 127.0.0.0/8 space)";
                      }
                    }
                    must "../ipv4";
                    description
                      "Number of IP addresses to sweep ";
                  }
                }
              }
              container tos {
                description
                  "SR Policy liveness probe type of service";
                leaf dscp {
                  type uint32 {
                    range "0..63" {
                      description
                        "DSCP value";
                    }
                  }
                  description
                    "DSCP value indicating TOS level used by protocol twamp-light";
                }
              }
            }
          }
        }
        container default {
          presence "Indicates a default node is configured.";
          description
            "Default profile";
          container liveness-detection {
            description
              "Enter SR Policy liveness detection submode";
            leaf multiplier {
              type uint32 {
                range "2..10" {
                  description
                    "Detect multiplier";
                }
              }
              description
                "Configure detect multiplier";
            }
          }
          container probe {
            description
              "Enter SR Policy liveness detection probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            container measurement-mode {
              description
                "Deprecated in release 7.6.1";
              container loopback {
                presence "Indicates a loopback node is configured.";
                description
                  "Loopback the probe packet collecting only timestamp 1 and 4 (reverse-path must be configured for SR Policy with RFC6374 MPLS encap)";
              }
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container tos {
              description
                "SR Policy liveness probe type of service";
              leaf dscp {
                type uint32 {
                  range "0..63" {
                    description
                      "DSCP value";
                  }
                }
                description
                  "DSCP value indicating TOS level used by protocol twamp-light";
              }
            }
          }
        }
      }
      container endpoint {
        description
          "Enter endpoint liveness profile submode";
        container names {
          description
            "Deprecated in IOS-XR 7.6.1. Please use 'liveness-profile name' instead";
          list name {
            key "profile-name";
            description
              "Deprecated in IOS-XR 7.6.1. Please use 'liveness-profile name' instead";
            leaf profile-name {
              type string {
                length "1..256" {
                  description
                    "Profile name";
                }
              }
              description
                "Deprecated in IOS-XR 7.6.1. Please use 'liveness-profile name' instead";
            }
            container probe {
              description
                "Enter endpoint liveness detection probe submode";
              leaf burst-interval {
                type uint32 {
                  range "30..15000" {
                    description
                      "Burst interval (msec) (Deprecated in IOS-XR 7.6.1. Please use tx-interval.)";
                  }
                }
                description
                  "Burst interval (Deprecated in IOS-XR 7.6.1. Please use tx-interval.)";
              }
              leaf tx-interval {
                type uint32 {
                  range "30000..15000000" {
                    description
                      "TX interval (usec)";
                  }
                }
                description
                  "TX interval";
              }
              container measurement-mode {
                description
                  "Deprecated in release 7.6.1";
                container loopback {
                  presence "Indicates a loopback node is configured.";
                  description
                    "Loopback the probe packet collecting only timestamp 1 and 4";
                }
              }
              container tos {
                description
                  "Endpoint liveness probe type of service";
                leaf dscp {
                  type uint32 {
                    range "0..63" {
                      description
                        "DSCP value";
                    }
                  }
                  description
                    "DSCP value indicating TOS level used by protocol twamp-light";
                }
              }
            }
            container liveness-detection {
              description
                "Enter endpoint liveness detection submode";
              leaf multiplier {
                type uint32 {
                  range "2..10" {
                    description
                      "Detect multiplier";
                  }
                }
                description
                  "Configure detect multiplier";
              }
              container logging {
                description
                  "Endpoint liveness logging";
                container state-change {
                  presence "Indicates a state-change node is configured.";
                  description
                    "Emit syslog when the liveness state change detected";
                }
              }
            }
          }
        }
        container default {
          presence "Indicates a default node is configured.";
          description
            "Default profile";
          container probe {
            description
              "Enter endpoint liveness detection probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec)";
                }
              }
              description
                "TX interval";
            }
            container measurement-mode {
              description
                "Deprecated in release 7.6.1";
              container loopback {
                presence "Indicates a loopback node is configured.";
                description
                  "Loopback the probe packet collecting only timestamp 1 and 4";
              }
            }
            container tos {
              description
                "Endpoint liveness probe type of service";
              leaf dscp {
                type uint32 {
                  range "0..63" {
                    description
                      "DSCP value";
                  }
                }
                description
                  "DSCP value indicating TOS level used by protocol twamp-light";
              }
            }
          }
          container liveness-detection {
            description
              "Enter endpoint liveness detection submode";
            leaf multiplier {
              type uint32 {
                range "2..10" {
                  description
                    "Detect multiplier";
                }
              }
              description
                "Configure detect multiplier";
            }
            container logging {
              description
                "Endpoint liveness logging";
              container state-change {
                presence "Indicates a state-change node is configured.";
                description
                  "Emit syslog when the liveness state change detected";
              }
            }
          }
        }
      }
      container names {
        description
          "Liveness profile name";
        list name {
          key "profile-name";
          description
            "liveness-profile name";
          leaf profile-name {
            type string {
              length "1..256" {
                description
                  "Profile name";
              }
            }
            description
              "liveness-profile name";
          }
          container liveness-detection {
            description
              "Enter liveness detection submode";
            leaf multiplier {
              type uint32 {
                range "2..10" {
                  description
                    "Detect multiplier";
                }
              }
              description
                "Configure detect multiplier";
            }
            container logging {
              description
                "Liveness logging";
              container state-change {
                presence "Indicates a state-change node is configured.";
                description
                  "Emit syslog when the liveness state change detected";
              }
            }
          }
          container probe {
            description
              "Enter liveness detection probe submode";
            leaf tx-interval {
              type uint32 {
                range "30000..15000000" {
                  description
                    "TX interval (usec)";
                }
              }
              description
                "TX interval";
            }
            container sweep {
              description
                "Enable ECMP hashing by sweeping a field in the probe packet";
              container destination {
                description
                  "Sweep a range of destination IP addresses";
                leaf ipv4 {
                  type inet:ipv4-address-no-zone;
                  must "../range";
                  description
                    "Start of the IPv4 address range, used by IPv4, IPv6 and NULL endpoint";
                }
                leaf range {
                  type uint32 {
                    range "0..128" {
                      description
                        "Sweeping range (Should fully be in the 127.0.0.0/8 space)";
                    }
                  }
                  must "../ipv4";
                  description
                    "Number of IP addresses to sweep ";
                }
              }
            }
            container tos {
              description
                "Liveness probe type of service";
              leaf dscp {
                type uint32 {
                  range "0..63" {
                    description
                      "DSCP value";
                  }
                }
                description
                  "DSCP value indicating TOS level used by protocol twamp-light";
              }
            }
          }
        }
      }
    }
    container protocol {
      description
        "Supported protocols";
      container twamp-light {
        description
          "Enter twamp-light protocol submode";
        container measurement {
          description
            "Supported measurement types";
          container delay {
            description
              "Enter delay measurement submode";
            container unauthenticated {
              description
                "Enter unauthenticated submode";
              leaf querier-dst-port {
                type uint32 {
                  range "862|1024..14999" {
                    description
                      "Port number. 862 is default TWAMP reserved UDP destination port";
                  }
                }
                description
                  "Port number";
              }
              leaf querier-src-port {
                type uint32 {
                  range "1024..14999" {
                    description
                      "Port number";
                  }
                }
                description
                  "UDP port opened on Route Processor to be used as source port in queries";
              }
              container ipv4 {
                description
                  "timestamp for ipv4 packet";
                container timestamp1 {
                  description
                    "timestamp 1";
                  leaf label {
                    type uint32 {
                      range "256..23999" {
                        description
                          "label";
                      }
                    }
                    description
                      "label";
                  }
                }
                container timestamp2 {
                  description
                    "timestamp 2";
                  leaf label {
                    type uint32 {
                      range "256..23999" {
                        description
                          "label";
                      }
                    }
                    description
                      "label";
                  }
                }
              }
              container ipv6 {
                description
                  "timestamp for ipv6 packet";
                container timestamp1 {
                  description
                    "timestamp 1";
                  leaf label {
                    type uint32 {
                      range "256..23999" {
                        description
                          "label";
                      }
                    }
                    description
                      "label";
                  }
                }
                container timestamp2 {
                  description
                    "timestamp 2";
                  leaf label {
                    type uint32 {
                      range "256..23999" {
                        description
                          "label";
                      }
                    }
                    description
                      "label";
                  }
                }
              }
            }
          }
        }
      }
    }
    container distribute-sessions {
      description
        "Distribute SR Policy DM sessions to linecards";
      container enable {
        must "not(../disable)";
        presence "Indicates a enable node is configured.";
        description
          "Enable distribute SR Policy DM sessions to linecards";
      }
      container disable {
        must "not(../enable)";
        presence "Indicates a disable node is configured.";
        description
          "Disable distribute SR Policy DM sessions to linecards (default)";
      }
    }
  }
}
