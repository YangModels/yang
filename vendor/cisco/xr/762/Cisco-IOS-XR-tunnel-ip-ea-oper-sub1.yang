submodule Cisco-IOS-XR-tunnel-ip-ea-oper-sub1 {
  belongs-to Cisco-IOS-XR-tunnel-ip-ea-oper {
    prefix Cisco-IOS-XR-tunnel-ip-ea-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tunnel-ip-ea package operational data.
     
     Copyright (c) 2013-2021 by Cisco Systems, Inc.
     All rights reserved.";

  revision 2021-10-19 {
    description
      "Added an entry for ipsec and changed ea_flags datatype in bag";
    semver:module-version "2.0.0";
  }
  revision 2019-04-05 {
    description
      "Establish semantic version baseline.";
    semver:module-version "1.0.1";
  }
  revision 2015-11-09 {
    description
      "IOS XR 6.0 revision.";
  }

  typedef Tunl-gre-plat-upd {
    type enumeration {
      enum "tunl-gre-plat-upd-all" {
        value -1;
        description
          "tunl gre plat upd all";
      }
      enum "tunl-gre-plat-upd-none" {
        value 0;
        description
          "tunl gre plat upd none";
      }
      enum "tunl-gre-plat-upd-mode" {
        value 1;
        description
          "tunl gre plat upd mode";
      }
      enum "tunl-gre-plat-upd-tunl-src-addr" {
        value 2;
        description
          "tunl gre plat upd tunl src addr";
      }
      enum "tunl-gre-plat-upd-tunl-dst-addr" {
        value 4;
        description
          "tunl gre plat upd tunl dst addr";
      }
      enum "tunl-gre-plat-upd-ttl" {
        value 8;
        description
          "tunl gre plat upd ttl";
      }
      enum "tunl-gre-plat-upd-tos-present" {
        value 16;
        description
          "tunl gre plat upd tos present";
      }
      enum "tunl-gre-plat-upd-tos" {
        value 32;
        description
          "tunl gre plat upd tos";
      }
      enum "tunl-gre-plat-upd-key-present" {
        value 64;
        description
          "tunl gre plat upd key present";
      }
      enum "tunl-gre-plat-upd-key" {
        value 128;
        description
          "tunl gre plat upd key";
      }
      enum "tunl-gre-plat-upd-enable-checksum" {
        value 256;
        description
          "tunl gre plat upd enable checksum";
      }
      enum "tunl-gre-plat-upd-ka-rx-enabled" {
        value 512;
        description
          "tunl gre plat upd ka rx enabled";
      }
      enum "tunl-gre-plat-upd-bandwidth" {
        value 1024;
        description
          "tunl gre plat upd bandwidth";
      }
      enum "tunl-gre-plat-upd-line-proto-up" {
        value 2048;
        description
          "tunl gre plat upd line proto up";
      }
      enum "tunl-gre-plat-upd-dfbit" {
        value 4096;
        description
          "tunl gre plat upd dfbit";
      }
      enum "tunl-gre-plat-upd-mtu" {
        value 8192;
        description
          "tunl gre plat upd mtu";
      }
      enum "tunl-gre-plat-upd-trans-vrf" {
        value 16384;
        description
          "tunl gre plat upd trans vrf";
      }
      enum "tunl-gre-plat-upd-key-enable" {
        value 32768;
        description
          "tunl gre plat upd key enable";
      }
      enum "tunl-gre-plat-upd-intf-ready" {
        value 65536;
        description
          "tunl gre plat upd intf ready";
      }
      enum "tunl-ip-plat-upd-output-if" {
        value 131072;
        description
          "tunl ip plat upd output if";
      }
      enum "tunl-ip-plat-upd-output-phy-if" {
        value 262144;
        description
          "tunl ip plat upd output phy if";
      }
      enum "tunl-ip-plat-upd-encap-in-sw" {
        value 524288;
        description
          "tunl ip plat upd encap in sw";
      }
      enum "tunl-ip-plat-upd-ipsec-enabled" {
        value 1048576;
        description
          "tunl ip plat upd ipsec enabled";
      }
    }
    description
      "Tunl gre plat upd";
  }

  typedef Tunl-ip-mode-dir {
    type enumeration {
      enum "tunl-ip-mode-dir-none" {
        description
          "tunl ip mode dir none";
      }
      enum "tunl-ip-mode-dir-decap" {
        description
          "tunl ip mode dir decap";
      }
      enum "tunl-ip-mode-dir-encap" {
        description
          "tunl ip mode dir encap";
      }
      enum "tunl-ip-mode-dir-max" {
        description
          "tunl ip mode dir max";
      }
    }
    description
      "Tunl ip mode dir";
  }

  typedef Tunl-in6-addr {
    type inet:ipv6-address;
    description
      "Tunl in6 addr";
  }

  typedef Tunl-in-addr {
    type inet:ipv4-address;
    description
      "Tunl in addr";
  }

  typedef Tunl-af-id {
    type enumeration {
      enum "tunl-af-id-none" {
        value 0;
        description
          "Unspecified AFI";
      }
      enum "tunl-af-id-ipv4" {
        value 2;
        description
          "IPv4 AFI";
      }
      enum "tunl-af-id-ipv6" {
        value 10;
        description
          "IPv6 AFI";
      }
    }
    description
      "Tunl af id";
  }

  typedef Tunl-ip-mode {
    type enumeration {
      enum "tunl-ip-mode-none" {
        value 0;
        description
          "tunl ip mode none";
      }
      enum "tunl-ip-mode-gr-eo-ipv4" {
        value 1;
        description
          "tunl ip mode gr eo ipv4";
      }
      enum "tunl-ip-mode-gr-eo-ipv6" {
        value 2;
        description
          "tunl ip mode gr eo ipv6";
      }
      enum "tunl-ip-mode-mgr-eo-ipv4" {
        value 3;
        description
          "tunl ip mode mgr eo ipv4";
      }
      enum "tunl-ip-mode-mgr-eo-ipv6" {
        value 4;
        description
          "tunl ip mode mgr eo ipv6";
      }
      enum "tunl-ip-mode-ipv4" {
        value 5;
        description
          "tunl ip mode ipv4";
      }
      enum "tunl-ip-mode-ipv6" {
        value 6;
        description
          "tunl ip mode ipv6";
      }
      enum "tunl-ip-mode-ipseco-ipv4" {
        value 7;
        description
          "tunl ip mode ipseco ipv4";
      }
      enum "tunl-ip-mode-max" {
        value 8;
        description
          "tunl ip mode max";
      }
    }
    description
      "Tunl ip mode";
  }

  grouping TUNL-IP-EA-EDM {
    description
      "TUNL IP EA EDM";
    container source-address-xr {
      description
        "Source Address";
      uses IP-ADDR-UNION;
    }
    container destination-address-xr {
      description
        "Destination Address";
      uses IP-ADDR-UNION;
    }
    leaf interface-type {
      type xr:Interface-name;
      description
        "Interface Type";
    }
    leaf destination-address-length {
      type uint8;
      description
        "Destination Address Length";
    }
    leaf tunnel-vrf-table-id {
      type uint32;
      description
        "Tunnel VRF table ID";
    }
    leaf tunnel-mode-xr {
      type Tunl-ip-mode;
      description
        "Mode of Tunnel";
    }
    leaf tunnel-mode-direction {
      type Tunl-ip-mode-dir;
      description
        "Mode direction";
    }
    leaf bandwidth {
      type uint32;
      description
        "Bandwidth";
    }
    leaf key {
      type uint32;
      description
        "Key Value for GRE Packet";
    }
    leaf key-entropy-length {
      type uint8;
      description
        "Key entropy length for GRE Packet";
    }
    leaf platform-tunnel-id {
      type uint16;
      description
        "Platform Tunnel ID";
    }
    leaf hw-retry-flags {
      type Tunl-gre-plat-upd;
      description
        "HW Retry Flags";
    }
    leaf flags {
      type uint32;
      description
        "Flags for don't fragment, TOS reflection";
    }
    leaf mtu {
      type uint16;
      description
        "Maximum Transmission Unit";
    }
    leaf tos {
      type uint8;
      description
        "Type Of Service";
    }
    leaf ttl {
      type uint8;
      description
        "Time To Live";
    }
    leaf encapsulation-state {
      type uint8;
      description
        "Encapsulation State";
    }
    leaf adjacent-flags {
      type uint32;
      description
        "Adjacent Flags";
    }
    leaf output-ifhandle {
      type xr:Interface-name;
      description
        "O/p Interface handle";
    }
    leaf next-pointer {
      type uint32;
      description
        "Pointer to next Node";
    }
    leaf ip-sec-enabled {
      type uint8;
      description
        "IPSec profile enabled";
    }
  }

  grouping TUNL-GRE-EA-SHM-EDM {
    description
      "TUNL GRE EA SHM EDM";
    leaf shm-intialized {
      type uint8;
      description
        "Shm Initialization";
    }
    leaf sh-mwin-id {
      type uint32;
      description
        "Shmwin Id";
    }
    leaf shm-version {
      type uint32;
      description
        "Shm Version";
    }
    leaf shm-base-addr {
      type uint32;
      description
        "Shm Base Address";
    }
    leaf platform-info {
      type uint64;
      description
        "Platform Info";
    }
    leaf tunnel-ipqt {
      type uint64;
      description
        "Tunnel IP QT";
    }
    leaf tunnel-idb {
      type uint64;
      description
        "Tunnel IP IDB";
    }
    leaf tunnel-idb-dummy {
      type uint64;
      description
        "Tunnel IP IDB Dummy";
    }
  }

  grouping TUNL-P2MP-EA-EDM-OVERLAY {
    description
      "TUNL P2MP EA EDM OVERLAY";
    container overlay-address {
      description
        "Overlay Address";
      uses IP-ADDR-UNION;
    }
    leaf adjacency {
      type uint32;
      description
        "Adjacency";
    }
    leaf stale-flag {
      type boolean;
      description
        "Stale Flag";
    }
  }

  grouping IP-ADDR-UNION {
    description
      "IP ADDR UNION";
    leaf afi {
      type Tunl-af-id;
      description
        "AFI";
    }
    leaf ipv4 {
      when "../afi = 'tunl-af-id-ipv4'" {
        description
          "../AFI = 'TUNL_AF_ID_IPV4'";
      }
      type Tunl-in-addr;
      description
        "IPv4 address type";
    }
    leaf ipv6 {
      when "../afi = 'tunl-af-id-ipv6'" {
        description
          "../AFI = 'TUNL_AF_ID_IPV6'";
      }
      type Tunl-in6-addr;
      description
        "IPv6 address type";
    }
  }

  grouping TUNL-P2MP-EA-EDM-TED-DB {
    description
      "TUNL P2MP EA EDM TED DB";
    container transport-address {
      description
        "Transport Address";
      uses IP-ADDR-UNION;
    }
    list overlay-array {
      description
        "Overlay Address";
      uses TUNL-P2MP-EA-EDM-OVERLAY;
    }
  }

  grouping TUNL-P2MP-EA-EDM-TED-DB-ARRAY {
    description
      "Array of TED DB entries BAG";
    leaf tunnel-id-xr {
      type uint32;
      description
        "Tunnel id";
    }
    leaf interface-type {
      type xr:Interface-name;
      description
        "Interface Type";
    }
    leaf tunnel-mode {
      type Tunl-ip-mode;
      description
        "Mode of Tunnel";
    }
    leaf endpt-count {
      type uint32;
      description
        "Endpoint count";
    }
    list ted-db-array {
      description
        "Array of EA TED DB";
      uses TUNL-P2MP-EA-EDM-TED-DB;
    }
  }

  grouping TUNL-IP-EA-SUM {
    description
      "TUNL IP EA SUM";
    leaf eaidb-count {
      type uint16;
      description
        "EA IDB count";
    }
    leaf eaqt-count {
      type uint16;
      description
        "EA QT count";
    }
    leaf num-idbs-to-retry-upd {
      type uint16;
      description
        "Number of IDBs to retry PD update";
    }
    leaf num-idbs-to-retry-del {
      type uint16;
      description
        "Number of IDBs to retry PD delete";
    }
    leaf num-idbs-retried-upd {
      type uint16;
      description
        "Number of IDBs retried PD update";
    }
    leaf num-idbs-retried-del {
      type uint16;
      description
        "Number of IDBs retried PD delete";
    }
    leaf num-idbs-retry-failed {
      type uint16;
      description
        "Number of IDBs retry failed";
    }
  }
}
