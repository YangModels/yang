module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2021-09-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2021 by Cisco Systems, Inc.
     All rights reserved.";

  revision 2021-09-22 {
    description
      "Removal of mplspweport OFA object IosSetYangSchemaRev Cisco-IOS-XR-platforms-ofa-table-stats-oper";
    semver:module-version "3.1.0";
  }
  revision 2020-06-19 {
    description
      "Bwalk Error Counters IosSetYangSchemaRev Cisco-IOS-XR-platforms-ofa-table-stats-oper";
    semver:module-version "3.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "test-ssm" {
        value 27;
        description
          "testssm";
      }
      enum "test-encap-mgr" {
        value 28;
        description
          "testencapmgr";
      }
      enum "test-mplsrte" {
        value 29;
        description
          "testmplsrte";
      }
      enum "sys" {
        value 30;
        description
          "sys";
      }
      enum "npu" {
        value 31;
        description
          "npu";
      }
      enum "npu-host-port" {
        value 32;
        description
          "npuhostport";
      }
      enum "npuhwid" {
        value 33;
        description
          "npuhwid";
      }
      enum "optics-port" {
        value 34;
        description
          "opticsport";
      }
      enum "gi-port" {
        value 35;
        description
          "giport";
      }
      enum "l1-port" {
        value 36;
        description
          "l1port";
      }
      enum "mac-port" {
        value 37;
        description
          "macport";
      }
      enum "l2-port" {
        value 38;
        description
          "l2port";
      }
      enum "eth-port" {
        value 39;
        description
          "ethport";
      }
      enum "eth-ports-tats" {
        value 40;
        description
          "ethportstats";
      }
      enum "l2intf" {
        value 41;
        description
          "l2intf";
      }
      enum "l2if" {
        value 42;
        description
          "l2if";
      }
      enum "mplspwe-port" {
        value 43;
        description
          "mplspweport";
      }
      enum "mhpwe-port" {
        value 44;
        description
          "mhpweport";
      }
      enum "l2xc" {
        value 45;
        description
          "l2xc";
      }
      enum "l2vpnstats" {
        value 46;
        description
          "l2vpnstats";
      }
      enum "l1-ports-tats" {
        value 47;
        description
          "l1portstats";
      }
      enum "mac-ports-tats" {
        value 48;
        description
          "macportstats";
      }
      enum "l3intf" {
        value 49;
        description
          "l3intf";
      }
      enum "l3if" {
        value 50;
        description
          "l3if";
      }
      enum "l3intfrxstats" {
        value 51;
        description
          "l3intfrxstats";
      }
      enum "ip-route" {
        value 52;
        description
          "iproute";
      }
      enum "ip6-route" {
        value 53;
        description
          "ip6route";
      }
      enum "punt-policy-stats" {
        value 54;
        description
          "puntpolicystats";
      }
      enum "lpts-policy-stats" {
        value 55;
        description
          "lptspolicystats";
      }
      enum "tep" {
        value 56;
        description
          "tep";
      }
      enum "ip-punt-policy" {
        value 57;
        description
          "ippuntpolicy";
      }
      enum "ip6-punt-policy" {
        value 58;
        description
          "ip6puntpolicy";
      }
      enum "iplpts-policy" {
        value 59;
        description
          "iplptspolicy";
      }
      enum "ip6lpts-policy" {
        value 60;
        description
          "ip6lptspolicy";
      }
      enum "isis-punt-policy" {
        value 61;
        description
          "isispuntpolicy";
      }
      enum "isislpts-policy" {
        value 62;
        description
          "isislptspolicy";
      }
      enum "nh-group" {
        value 63;
        description
          "nhgroup";
      }
      enum "ipnh-group" {
        value 64;
        description
          "ipnhgroup";
      }
      enum "ip6nh-group" {
        value 65;
        description
          "ip6nhgroup";
      }
      enum "ipnh" {
        value 66;
        description
          "ipnh";
      }
      enum "ip6nh" {
        value 67;
        description
          "ip6nh";
      }
      enum "ipvrf" {
        value 68;
        description
          "ipvrf";
      }
      enum "vrfid" {
        value 69;
        description
          "vrfid";
      }
      enum "mplsnh" {
        value 70;
        description
          "mplsnh";
      }
      enum "lspnh" {
        value 71;
        description
          "lspnh";
      }
      enum "encap-mgr" {
        value 72;
        description
          "encapmgr";
      }
      enum "mpls-label" {
        value 73;
        description
          "mplslabel";
      }
      enum "punt" {
        value 74;
        description
          "punt";
      }
      enum "punt-police-r" {
        value 75;
        description
          "puntpolicer";
      }
      enum "lpts-police-r" {
        value 76;
        description
          "lptspolicer";
      }
      enum "punt-lpts-police-r" {
        value 77;
        description
          "puntlptspolicer";
      }
      enum "punt-stats" {
        value 78;
        description
          "puntstats";
      }
      enum "tm-port" {
        value 79;
        description
          "tmport";
      }
      enum "span-session" {
        value 80;
        description
          "spansession";
      }
      enum "police-rstats" {
        value 81;
        description
          "policerstats";
      }
      enum "tm-ports-tats" {
        value 82;
        description
          "tmportstats";
      }
      enum "voq-grp" {
        value 83;
        description
          "voqgrp";
      }
      enum "l3intftxstats" {
        value 84;
        description
          "l3intftxstats";
      }
      enum "mplstetxstats" {
        value 85;
        description
          "mplstetxstats";
      }
      enum "mplslblstats" {
        value 86;
        description
          "mplslblstats";
      }
      enum "police-r" {
        value 87;
        description
          "policer";
      }
      enum "l2intfrxstats" {
        value 88;
        description
          "l2intfrxstats";
      }
      enum "l2intftxstats" {
        value 89;
        description
          "l2intftxstats";
      }
      enum "pbr-tt-ipv4" {
        value 90;
        description
          "pbr tt ipv4";
      }
      enum "pbr-tt-ipv6" {
        value 91;
        description
          "pbr tt ipv6";
      }
      enum "bfdhwoff" {
        value 92;
        description
          "bfdhwoff";
      }
      enum "bfdoff" {
        value 93;
        description
          "bfdoff";
      }
      enum "bfdoffstats" {
        value 94;
        description
          "bfdoffstats";
      }
      enum "global" {
        value 95;
        description
          "global";
      }
      enum "lag-port" {
        value 96;
        description
          "lagport";
      }
      enum "agg-port" {
        value 97;
        description
          "aggport";
      }
      enum "agg-member" {
        value 98;
        description
          "aggmember";
      }
      enum "qos-profile" {
        value 99;
        description
          "qosprofile";
      }
      enum "acl-profile" {
        value 100;
        description
          "acl profile";
      }
      enum "tmrate-profile" {
        value 101;
        description
          "tmrateprofile";
      }
      enum "ipacl" {
        value 102;
        description
          "ipacl";
      }
      enum "ip6acl" {
        value 103;
        description
          "ip6acl";
      }
      enum "sched-tree" {
        value 104;
        description
          "schedtree";
      }
      enum "tmcos" {
        value 105;
        description
          "tmcos";
      }
      enum "statsagg" {
        value 106;
        description
          "statsagg";
      }
      enum "nhprotect" {
        value 107;
        description
          "nhprotect";
      }
      enum "sampler" {
        value 108;
        description
          "sampler";
      }
      enum "l2qos" {
        value 109;
        description
          "l2qos";
      }
      enum "peer-qos" {
        value 110;
        description
          "peerqos";
      }
      enum "ipqos" {
        value 111;
        description
          "ipqos";
      }
      enum "ip6qos" {
        value 112;
        description
          "ip6qos";
      }
      enum "mplsqos" {
        value 113;
        description
          "mplsqos";
      }
      enum "qos-group" {
        value 114;
        description
          "qosgroup";
      }
      enum "qosid" {
        value 115;
        description
          "qosid";
      }
      enum "extlif" {
        value 116;
        description
          "extlif";
      }
      enum "elif" {
        value 117;
        description
          "elif";
      }
      enum "ingaclstats" {
        value 118;
        description
          "ingaclstats";
      }
      enum "egraclstats" {
        value 119;
        description
          "egraclstats";
      }
      enum "edpl" {
        value 120;
        description
          "edpl";
      }
      enum "l2protect" {
        value 121;
        description
          "l2protect";
      }
      enum "sat" {
        value 122;
        description
          "sat";
      }
      enum "satstats" {
        value 123;
        description
          "satstats";
      }
      enum "cfmoam-profile-def" {
        value 124;
        description
          "cfmoamprofiledef";
      }
      enum "cfmmaid" {
        value 125;
        description
          "cfmmaid";
      }
      enum "cfmdefmps" {
        value 126;
        description
          "cfmdefmps";
      }
      enum "cfmofflmep" {
        value 127;
        description
          "cfmofflmep";
      }
      enum "cfmoffrmep" {
        value 128;
        description
          "cfmoffrmep";
      }
      enum "cfmnonoff" {
        value 129;
        description
          "cfmnonoff";
      }
      enum "cfmhwoffrxstats" {
        value 130;
        description
          "cfmhwoffrxstats";
      }
      enum "cfmnonoff-load" {
        value 131;
        description
          "cfmnonoffload";
      }
      enum "cfm-default-s" {
        value 132;
        description
          "cfmdefaults";
      }
      enum "cfmmntassocid" {
        value 133;
        description
          "cfmmntassocid";
      }
      enum "ipmc-route" {
        value 134;
        description
          "ipmcroute";
      }
      enum "l2ipmc-route" {
        value 135;
        description
          "l2ipmcroute";
      }
      enum "ipmco-list" {
        value 136;
        description
          "ipmcolist";
      }
      enum "l2mco-list" {
        value 137;
        description
          "l2mcolist";
      }
      enum "meshmc" {
        value 138;
        description
          "meshmc";
      }
      enum "l2-bridge" {
        value 139;
        description
          "l2bridge";
      }
      enum "l2-bridge-port" {
        value 140;
        description
          "l2bridgeport";
      }
      enum "l2-bridge-mac" {
        value 141;
        description
          "l2bridgemac";
      }
      enum "l2brmac" {
        value 142;
        description
          "l2brmac";
      }
      enum "ip-tunnel-decap" {
        value 143;
        description
          "iptunneldecap";
      }
      enum "l2vlan-range" {
        value 144;
        description
          "l2vlanrange";
      }
      enum "ip-tunnel-encap" {
        value 145;
        description
          "iptunnelencap";
      }
      enum "iptnl-encap" {
        value 146;
        description
          "iptnlencap";
      }
      enum "iptnldecap" {
        value 147;
        description
          "iptnldecap";
      }
      enum "iptnlnh" {
        value 148;
        description
          "iptnlnh";
      }
      enum "rawget" {
        value 149;
        description
          "rawget";
      }
      enum "ip6mc-route" {
        value 150;
        description
          "ip6mcroute";
      }
      enum "ip6mc-comp-grp" {
        value 151;
        description
          "ip6mc comp grp";
      }
      enum "l2evpnact-remote-peer-id" {
        value 152;
        description
          "l2evpnactremotepeerid";
      }
      enum "l2evpnact-local-shl" {
        value 153;
        description
          "l2evpnactlocalshl";
      }
      enum "l2evpnact-remote-shl" {
        value 154;
        description
          "l2evpnactremoteshl";
      }
      enum "evpn-iml-range" {
        value 155;
        description
          "evpn imlrange";
      }
      enum "l2-bridge-o-list" {
        value 156;
        description
          "l2bridgeolist";
      }
      enum "l2acl" {
        value 157;
        description
          "l2acl";
      }
      enum "l2evpn-nh" {
        value 158;
        description
          "l2evpn nh";
      }
      enum "l2-bridge-port-sc" {
        value 159;
        description
          "l2bridgeport sc";
      }
      enum "l3intfmctxstats" {
        value 160;
        description
          "l3intfmctxstats";
      }
      enum "tidl-sample" {
        value 161;
        description
          "tidl sample";
      }
      enum "tidl-ref-sample" {
        value 162;
        description
          "tidl ref sample";
      }
      enum "ipacl-prefix" {
        value 163;
        description
          "ipaclprefix";
      }
      enum "ip6acl-prefix" {
        value 164;
        description
          "ip6aclprefix";
      }
      enum "ipacl-port" {
        value 165;
        description
          "ipaclport";
      }
      enum "scaleacl" {
        value 166;
        description
          "scaleacl";
      }
      enum "ipmcf-hop" {
        value 167;
        description
          "ipmcfhop";
      }
      enum "bundle-swoff" {
        value 168;
        description
          "bundle swoff";
      }
      enum "mcidswoff" {
        value 169;
        description
          "mcidswoff";
      }
      enum "dest-map" {
        value 170;
        description
          "destmap";
      }
      enum "l2-bridge-port-pw" {
        value 171;
        description
          "l2bridgeport pw";
      }
      enum "l2evpnact-local-shlstats" {
        value 172;
        description
          "l2evpnactlocalshlstats";
      }
      enum "test-hidden" {
        value 173;
        description
          "testhidden";
      }
      enum "test-local" {
        value 174;
        description
          "testlocal";
      }
      enum "test-repeated" {
        value 175;
        description
          "testrepeated";
      }
      enum "limd" {
        value 176;
        description
          "limd";
      }
      enum "litap" {
        value 177;
        description
          "litap";
      }
      enum "l3ifstats" {
        value 178;
        description
          "l3ifstats";
      }
      enum "mplsstats" {
        value 179;
        description
          "mplsstats";
      }
      enum "sr-test-ats" {
        value 180;
        description
          "srtestats";
      }
      enum "srteifstats" {
        value 181;
        description
          "srteifstats";
      }
      enum "exception-nh" {
        value 182;
        description
          "exceptionnh";
      }
      enum "srv6-global" {
        value 183;
        description
          "srv6 global";
      }
      enum "srv6sid" {
        value 184;
        description
          "srv6sid";
      }
      enum "srv6nh" {
        value 185;
        description
          "srv6nh";
      }
      enum "sr6sid" {
        value 186;
        description
          "sr6sid";
      }
      enum "sr6nh" {
        value 187;
        description
          "sr6nh";
      }
      enum "sr6-global" {
        value 188;
        description
          "sr6 global";
      }
      enum "redirect-vrf" {
        value 189;
        description
          "redirectvrf";
      }
      enum "test-xtf" {
        value 190;
        description
          "test xtf";
      }
      enum "ippbr" {
        value 191;
        description
          "ippbr";
      }
      enum "ippbrstats" {
        value 192;
        description
          "ippbrstats";
      }
      enum "mpls-mdt-bud" {
        value 193;
        description
          "mplsmdtbud";
      }
      enum "mpls-label-rxstats" {
        value 194;
        description
          "mplslabelrxstats";
      }
      enum "l2mac-static" {
        value 195;
        description
          "l2macstatic";
      }
      enum "dot1x" {
        value 196;
        description
          "dot1x";
      }
      enum "iprte" {
        value 197;
        description
          "iprte";
      }
      enum "ip6rte" {
        value 198;
        description
          "ip6rte";
      }
      enum "llnh" {
        value 199;
        description
          "llnh";
      }
      enum "urpfintf" {
        value 200;
        description
          "urpfintf";
      }
      enum "ipmcrxstats" {
        value 201;
        description
          "ipmcrxstats";
      }
      enum "mplsrte" {
        value 202;
        description
          "mplsrte";
      }
      enum "protectnh" {
        value 203;
        description
          "protectnh";
      }
      enum "ipllnh" {
        value 204;
        description
          "ipllnh";
      }
      enum "ip6llnh" {
        value 205;
        description
          "ip6llnh";
      }
      enum "macnh" {
        value 206;
        description
          "macnh";
      }
      enum "qos-match-stats" {
        value 207;
        description
          "qosmatchstats";
      }
      enum "ofal2xc" {
        value 208;
        description
          "ofal2xc";
      }
      enum "ofamplspwe-port" {
        value 209;
        description
          "ofamplspweport";
      }
      enum "pwenh" {
        value 210;
        description
          "pwenh";
      }
      enum "pwenh-group" {
        value 211;
        description
          "pwenhgroup";
      }
      enum "ipmcrte" {
        value 212;
        description
          "ipmcrte";
      }
      enum "ip6mcrte" {
        value 213;
        description
          "ip6mcrte";
      }
      enum "ipmcr-test-ats" {
        value 214;
        description
          "ipmcrtestats";
      }
      enum "ip6mcr-test-ats" {
        value 215;
        description
          "ip6mcrtestats";
      }
      enum "transport-nh" {
        value 216;
        description
          "transportnh";
      }
      enum "port-range" {
        value 217;
        description
          "portrange";
      }
      enum "mcid" {
        value 218;
        description
          "mcid";
      }
      enum "mc-gid" {
        value 219;
        description
          "mc gid";
      }
      enum "mcgidole" {
        value 220;
        description
          "mcgidole";
      }
      enum "mco-list" {
        value 221;
        description
          "mcolist";
      }
      enum "test-da" {
        value 222;
        description
          "testda";
      }
      enum "test-ca" {
        value 223;
        description
          "testca";
      }
      enum "test-ba" {
        value 224;
        description
          "testba";
      }
      enum "test-aa" {
        value 225;
        description
          "testaa";
      }
      enum "test-async-aa" {
        value 226;
        description
          "testasyncaa";
      }
      enum "test-reliable-notif" {
        value 227;
        description
          "testreliablenotif";
      }
      enum "test-de" {
        value 228;
        description
          "testde";
      }
      enum "test-ce" {
        value 229;
        description
          "testce";
      }
      enum "test-be" {
        value 230;
        description
          "testbe";
      }
      enum "test-db" {
        value 231;
        description
          "testdb";
      }
      enum "test-cb" {
        value 232;
        description
          "testcb";
      }
      enum "test-bb" {
        value 233;
        description
          "testbb";
      }
      enum "test-df" {
        value 234;
        description
          "testdf";
      }
      enum "test-cf" {
        value 235;
        description
          "testcf";
      }
      enum "test-bf" {
        value 236;
        description
          "testbf";
      }
      enum "test-af" {
        value 237;
        description
          "testaf";
      }
      enum "test-cz" {
        value 238;
        description
          "testcz";
      }
      enum "test-ax" {
        value 239;
        description
          "testax";
      }
      enum "test-ay" {
        value 240;
        description
          "testay";
      }
      enum "test-ef" {
        value 241;
        description
          "testef";
      }
      enum "test-ff" {
        value 242;
        description
          "testff";
      }
      enum "test-npurc" {
        value 243;
        description
          "testnpurc";
      }
      enum "test-gf" {
        value 244;
        description
          "testgf";
      }
      enum "test-eastwestscheduling" {
        value 245;
        description
          "testeastwestscheduling";
      }
      enum "test-transnh" {
        value 246;
        description
          "testtransnh";
      }
      enum "test-eth-port" {
        value 247;
        description
          "testethport";
      }
      enum "test-eastwest" {
        value 248;
        description
          "testeastwest";
      }
      enum "test-ifstats" {
        value 249;
        description
          "testifstats";
      }
      enum "test-async-oor" {
        value 250;
        description
          "testasyncoor";
      }
      enum "test-async-db" {
        value 251;
        description
          "testasyncdb";
      }
      enum "test-syncmcas-too-r" {
        value 252;
        description
          "testsyncmcastoor";
      }
      enum "test-syncdeviceoor" {
        value 253;
        description
          "testsyncdeviceoor";
      }
      enum "test-az" {
        value 254;
        description
          "testaz";
      }
      enum "test-by" {
        value 255;
        description
          "testby";
      }
      enum "police-r-group" {
        value 256;
        description
          "policergroup";
      }
      enum "meter-profile" {
        value 257;
        description
          "meterprofile";
      }
      enum "acl-mirror" {
        value 258;
        description
          "acl mirror";
      }
      enum "meter-action-profile" {
        value 259;
        description
          "meteractionprofile";
      }
      enum "voqrm" {
        value 260;
        description
          "voqrm";
      }
      enum "port-wfq-profile" {
        value 261;
        description
          "portwfqprofile";
      }
      enum "rpfif" {
        value 262;
        description
          "rpfif";
      }
      enum "brmac" {
        value 263;
        description
          "brmac";
      }
      enum "br-static-mac" {
        value 264;
        description
          "brstaticmac";
      }
      enum "xconnect" {
        value 265;
        description
          "xconnect";
      }
      enum "bridge" {
        value 266;
        description
          "bridge";
      }
      enum "pwe-port" {
        value 267;
        description
          "pweport";
      }
      enum "olist" {
        value 268;
        description
          "olist";
      }
      enum "lsmprotect" {
        value 269;
        description
          "lsmprotect";
      }
      enum "monitor-session" {
        value 270;
        description
          "monitorsession";
      }
      enum "monitor-session-stats" {
        value 271;
        description
          "monitorsessionstats";
      }
      enum "mplsmcast" {
        value 272;
        description
          "mplsmcast";
      }
      enum "l2ifstats" {
        value 273;
        description
          "l2ifstats";
      }
      enum "imlnh" {
        value 274;
        description
          "imlnh";
      }
      enum "evinh" {
        value 275;
        description
          "evinh";
      }
      enum "member-list" {
        value 276;
        description
          "memberlist";
      }
      enum "test-oor" {
        value 277;
        description
          "testoor";
      }
      enum "hwre-source-s-oor" {
        value 278;
        description
          "hwresources oor";
      }
      enum "qospfcstats" {
        value 279;
        description
          "qospfcstats";
      }
      enum "pfctc" {
        value 280;
        description
          "pfctc";
      }
      enum "pfc-watchdog" {
        value 281;
        description
          "pfc watchdog";
      }
      enum "qos-shared" {
        value 282;
        description
          "qosshared";
      }
      enum "ecntxstats" {
        value 283;
        description
          "ecntxstats";
      }
      enum "tm-remote-credit" {
        value 284;
        description
          "tmremotecredit";
      }
      enum "ipmcole" {
        value 285;
        description
          "ipmcole";
      }
      enum "ip6mcole" {
        value 286;
        description
          "ip6mcole";
      }
      enum "pbr" {
        value 287;
        description
          "pbr";
      }
      enum "pbrstats" {
        value 288;
        description
          "pbrstats";
      }
      enum "punt-stormcontrol" {
        value 289;
        description
          "puntstormcontrol";
      }
      enum "ip6mcrxstats" {
        value 290;
        description
          "ip6mcrxstats";
      }
      enum "ipmctxintf" {
        value 291;
        description
          "ipmctxintf";
      }
      enum "ipmc-mdt-encap" {
        value 292;
        description
          "ipmcmdtencap";
      }
      enum "ipmc-mdt-decap" {
        value 293;
        description
          "ipmcmdtdecap";
      }
      enum "op2tap" {
        value 294;
        description
          "op2tap";
      }
      enum "mplsole" {
        value 295;
        description
          "mplsole";
      }
      enum "syncrpc" {
        value 296;
        description
          "syncrpc";
      }
      enum "tnlstats" {
        value 297;
        description
          "tnlstats";
      }
      enum "l2dhcp" {
        value 298;
        description
          "l2dhcp";
      }
      enum "pbrsbf" {
        value 299;
        description
          "pbrsbf";
      }
      enum "statsrpc" {
        value 300;
        description
          "statsrpc";
      }
      enum "oglpts" {
        value 301;
        description
          "oglpts";
      }
      enum "oglpts-prefix" {
        value 302;
        description
          "oglptsprefix";
      }
      enum "og6lpts-prefix" {
        value 303;
        description
          "og6lptsprefix";
      }
      enum "stormcontrol" {
        value 304;
        description
          "stormcontrol";
      }
      enum "acl-police-r" {
        value 305;
        description
          "aclpolicer";
      }
      enum "acl-police-rstats" {
        value 306;
        description
          "aclpolicerstats";
      }
      enum "aclkey-profile" {
        value 307;
        description
          "aclkeyprofile";
      }
      enum "acl-action-profile" {
        value 308;
        description
          "aclactionprofile";
      }
      enum "dummytable" {
        value 309;
        description
          "dummytable";
      }
      enum "ip-sub" {
        value 310;
        description
          "ipsub";
      }
      enum "test-silverfoxsync" {
        value 311;
        description
          "testsilverfoxsync";
      }
      enum "test-statsreplication" {
        value 312;
        description
          "teststatsreplication";
      }
      enum "dot1x-mac" {
        value 313;
        description
          "dot1x mac";
      }
      enum "mpa" {
        value 314;
        description
          "mpa";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
