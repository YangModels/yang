module Cisco-IOS-XR-um-cont-stm-cfg {
  namespace "http://cisco.com/ns/yang/Cisco-IOS-XR-um-cont-stm-cfg";
  prefix um-cont-stm-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-stm package configuration.
     
     This YANG module augments the
     modules with configuration data.
     
     Copyright (c) 2021-2022 by Cisco Systems, Inc.
     All rights reserved.";

  revision 2022-05-13 {
    description
      "Added new leaf node sixtyfour-bytes under container overhead/j0/send and overhead/j0/expected";
    semver:module-version "1.1.0";
  }
  revision 2021-05-07 {
    description
      "Initial release";
    semver:module-version "1.0.0";
  }

  grouping CONT-BODY {
    container clock {
      description
        "Configure SONET/SDH port clock";
      leaf source {
        type enumeration {
          enum "internal" {
            value 0;
            description
              "Select internal clock";
          }
          enum "line" {
            value 1;
            description
              "Select clock recovered from line (default)";
          }
        }
        description
          "Configure SONET/SDH port TX clock source";
      }
    }
    container loopback {
      description
        "Configure SONET/SDH controller loopback mode";
      container internal {
        must "not(../line)";
        presence "Indicates a internal node is configured.";
        description
          "Select local (terminal) loopback";
      }
      container line {
        must "not(../internal)";
        presence "Indicates a line node is configured.";
        description
          "Select network (facility) loopback";
      }
    }
    container overhead {
      description
        "Configure SONET Section & Line or SDH Regeneration Section & Multiplex Section OH byte/bit values";
      container j0 {
        description
          "Specify SONET Section trace or SDH Regeneration Section identifier (J0/C1) ";
        container send {
          description
            "Set transmit trace Identifier";
          leaf one-byte {
            type uint32 {
              range "0..255" {
                description
                  "J0/C1 byte value (default 0x01)";
              }
            }
            must "not(../sixteen-bytes or ../sixtyfour-bytes)";
            description
              "Configure a 1 byte section or Regeneration section trace ";
          }
          leaf sixteen-bytes {
            type string {
              length "1..15" {
                description
                  "ASCII text ";
              }
            }
            must "not(../one-byte or ../sixtyfour-bytes)";
            description
              "Configure a 16 bytes section or Regeneration section trace";
          }
          leaf sixtyfour-bytes {
            type string {
              length "1..62" {
                description
                  "ASCII text ";
              }
            }
            must "not(../one-byte or ../sixteen-bytes)";
            description
              "Configure a Section layer/Regeneration layer trace, string of upto 62 characters accepted(<CR> & <LF> characters will be added at the end).";
          }
        }
        container expected {
          description
            "Set expected trace Identifier";
          leaf one-byte {
            type uint32 {
              range "0..255" {
                description
                  "J0/C1 byte value (default 0x01)";
              }
            }
            must "not(../sixteen-bytes or ../sixtyfour-bytes)";
            description
              "Configure a 1 byte section or Regeneration section trace ";
          }
          leaf sixteen-bytes {
            type string {
              length "1..15" {
                description
                  "ASCII text ";
              }
            }
            must "not(../one-byte or ../sixtyfour-bytes)";
            description
              "Configure a 16 bytes section or Regeneration section trace";
          }
          leaf sixtyfour-bytes {
            type string {
              length "1..62" {
                description
                  "ASCII text ";
              }
            }
            must "not(../one-byte or ../sixteen-bytes)";
            description
              "Configure a Section layer/Regeneration layer trace, string of upto 62 characters accepted(<CR> & <LF> characters will be added at the end).";
          }
        }
      }
    }
    container perf-mon {
      description
        "Enable/Disable Performance Monitoring";
      container disable {
        must "not(../enable)";
        presence "Indicates a disable node is configured.";
        description
          "Disable performance monitoring";
      }
      container enable {
        must "not(../disable)";
        presence "Indicates a enable node is configured.";
        description
          "Enable performance monitoring";
      }
    }
    container threshold {
      description
        "Configure SONET section/line or SDH Regeneration/Multiplex Section BER threshold values";
      leaf b1-tca {
        type uint32 {
          range "3..9" {
            description
              "Bit error rate (10 to the minus n) (default 6)";
          }
        }
        description
          "Set B1 BER Threshold Crossing Alert (TCA) threshold";
      }
      leaf b2-tca {
        type uint32 {
          range "3..9" {
            description
              "Bit error rate (10 to the minus n) (default 6)";
          }
        }
        description
          "Set B2 BER Threshold Crossing Alert (TCA) threshold";
      }
      leaf sd-ber {
        type uint32 {
          range "5..9" {
            description
              "Bit error rate (10 to the minus n) (default 6)";
          }
        }
        description
          "Set Signal Degrade BER threshold";
      }
      leaf sf-ber {
        type uint32 {
          range "3..5" {
            description
              "Bit error rate (10 to the minus n) (default 3)";
          }
        }
        description
          "Set Signal Fail BER threshold";
      }
    }
  }

  augment "/a1:interfaces/a1:controller" {
    uses CONT-BODY;
  }
  augment "/a1:interfaces/a1:controller-preconfigure" {
    uses CONT-BODY;
  }
}
