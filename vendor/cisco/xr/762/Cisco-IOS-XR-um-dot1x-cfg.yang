module Cisco-IOS-XR-um-dot1x-cfg {
  namespace "http://cisco.com/ns/yang/Cisco-IOS-XR-um-dot1x-cfg";
  prefix um-dot1x-cfg;

  import Cisco-IOS-XR-types {
    prefix xr;
  }
  import ietf-yang-types {
    prefix yang;
  }
  import Cisco-IOS-XR-um-interface-cfg {
    prefix a1;
  }
  import Cisco-IOS-XR-um-aaa-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dot1x package configuration.
     
     This YANG module augments the
     modules with configuration data.
     
     Copyright (c) 2022 by Cisco Systems, Inc.
     All rights reserved.";

  revision 2022-03-22 {
    description
      "Added Retry time for MAC Authentication Bypass feature";
    semver:module-version "1.2.0";
  }
  revision 2021-11-22 {
    description
      "Added container mab under dot1x";
    semver:module-version "1.1.0";
  }
  revision 2021-03-19 {
    description
      "Initial release";
    semver:module-version "1.0.0";
  }

  grouping IF-BODY {
    container dot1x {
      description
        "Interface Config Commands for IEEE 802.1X";
      leaf profile {
        type xr:Cisco-ios-xr-string {
          length "1..800" {
            description
              "String";
          }
        }
        description
          "Credentials profile configuration";
      }
    }
    container eapol {
      description
        "EAPOL configuration commands";
      container destination-address {
        description
          "Destination address for EAPoL frames transmission";
        leaf mac-address {
          type yang:mac-address;
          must
            "not(../bridge-group-address or ../broadcast-address
             or ../lldp-multicast-address)";
          description
            "configure this node";
        }
        container bridge-group-address {
          must
            "not(../mac-address or ../broadcast-address
             or ../lldp-multicast-address)";
          presence "Indicates a bridge-group-address node is configured.";
          description
            "Configure bridge group address";
        }
        container broadcast-address {
          must
            "not(../mac-address or ../bridge-group-address
             or ../lldp-multicast-address)";
          presence "Indicates a broadcast-address node is configured.";
          description
            "Configure broadcast MAC address";
        }
        container lldp-multicast-address {
          must
            "not(../mac-address or ../bridge-group-address
             or ../broadcast-address)";
          presence "Indicates a lldp-multicast-address node is configured.";
          description
            "Configure lldp multicast address";
        }
      }
      leaf eth-type {
        type enumeration {
          enum "876F" {
            value 34671;
            description
              "Value of Ethertype";
          }
        }
        description
          "EAPOL ethertype configuration";
      }
    }
  }

  grouping CONT-BODY {
    container dot1x {
      description
        "Interface Config Commands for IEEE 802.1X";
      leaf profile {
        type xr:Cisco-ios-xr-string {
          length "1..800" {
            description
              "String";
          }
        }
        description
          "Credentials profile configuration";
      }
    }
  }

  augment "/a1:interfaces/a1:interface" {
    uses IF-BODY;
  }
  augment "/a1:interfaces/a1:interface-preconfigure" {
    uses IF-BODY;
  }
  augment "/a1:interfaces/a1:controller" {
    uses CONT-BODY;
  }
  augment "/a1:interfaces/a1:controller-preconfigure" {
    uses CONT-BODY;
  }
  augment "/a2:aaa/a2:authentication" {
    container dot1x {
      description
        "Set authentication lists for Dot1x";
      container default {
        description
          "Default list name for AAA authentication";
        container group {
          description
            "Use Server-group";
          leaf use-list-of-all-radius-hosts {
            type enumeration {
              enum "radius" {
                value 3;
                description
                  "Use list of all RADIUS hosts";
              }
            }
            must "not(../server-group-name)";
            description
              "configure this node";
          }
          leaf server-group-name {
            type xr:Cisco-ios-xr-string {
              length "1..800" {
                description
                  "server-group name";
              }
            }
            must "not(../use-list-of-all-radius-hosts)";
            description
              "server-group name";
          }
        }
      }
      container aaa-authentication-names {
        description
          "List name for AAA authentication";
        list aaa-authentication-name {
          key "aaa-authentication-name";
          description
            "List name for AAA authentication";
          leaf aaa-authentication-name {
            type xr:Cisco-ios-xr-string {
              length "1..800" {
                description
                  "List name for AAA authentication";
              }
            }
            description
              "List name for AAA authentication";
          }
          container group {
            description
              "Use Server-group";
            leaf use-list-of-all-radius-hosts {
              type enumeration {
                enum "radius" {
                  value 3;
                  description
                    "Use list of all RADIUS hosts";
                }
              }
              must "not(../server-group-name)";
              description
                "configure this node";
            }
            leaf server-group-name {
              type xr:Cisco-ios-xr-string {
                length "1..800" {
                  description
                    "server-group name";
                }
              }
              must "not(../use-list-of-all-radius-hosts)";
              description
                "server-group name";
            }
          }
        }
      }
    }
  }
  container dot1x {
    description
      "IEEE 802.1X Global Configuration Commands";
    container profiles {
      description
        "Configure 802.1X profiles";
      list profile {
        key "profile-name";
        description
          "Configure 802.1X profiles";
        leaf profile-name {
          type xr:Cisco-ios-xr-string {
            length "1..63" {
              description
                "Specify a profile name (max 63 charecters)";
            }
          }
          description
            "Configure 802.1X profiles";
        }
        container pae {
          description
            "Set 802.1x pae type";
          container authenticator {
            must "not(../supplicant or ../both)";
            presence "Indicates a authenticator node is configured.";
            description
              "Set PAE Type as Authenticator";
          }
          container supplicant {
            must "not(../authenticator or ../both)";
            presence "Indicates a supplicant node is configured.";
            description
              "Set PAE Type as Supplicant";
          }
          container both {
            must "not(../authenticator or ../supplicant)";
            presence "Indicates a both node is configured.";
            description
              "Set PAE Type as both Supplicant and Authenticator";
          }
        }
        container mab {
          presence "Indicates a mab node is configured.";
          description
            "Enable MAC Authentication Bypass";
        }
        container supplicant {
          description
            "Enter in Supplicant submode";
          container eap {
            description
              "Configure EAP Supplicant Parameters";
            leaf profile {
              type xr:Cisco-ios-xr-string {
                length "1..63" {
                  description
                    "EAP Profile Name";
                }
              }
              description
                "EAP Profile Configuration";
            }
          }
        }
        container authenticator {
          description
            "Enter in Authenticator submode";
          container eap {
            description
              "enable local EAP server";
            leaf profile {
              type xr:Cisco-ios-xr-string {
                length "1..63" {
                  description
                    "EAP Profile Name";
                }
              }
              description
                "EAP Profile Configuration";
            }
          }
          container timer {
            description
              "Set various timeouts";
            container reauth-time {
              description
                "In seconds, after which an automatic reauth should be initiated";
              container server {
                presence "Indicates a server node is configured.";
                description
                  "server given re-auth timer value, min expected value is 60 sec, default: 1hr";
              }
              leaf timer-value {
                type uint32 {
                  range "60..5184000" {
                    description
                      "In seconds, admin configured reauth timer value, min:60, max:5184000 (2 months)";
                  }
                }
                description
                  "In seconds, admin configured reauth timer value, min:60, max:5184000 (2 months)";
              }
            }
            leaf mab-retry-time {
              type uint32 {
                range "60..300" {
                  description
                    "In seconds, min:60(default), max:300 (5 minutes)";
                }
              }
              description
                "In seconds, interval after which an auth attempt will be initiated for auth failed or server unreachable MAB clients";
            }
          }
          container server {
            description
              "Remote AAA server event";
            container dead {
              description
                "AAA server unreachable";
              container action {
                description
                  "dot1x authenticator action";
                container auth-fail {
                  must "not(../auth-retry)";
                  presence "Indicates a auth-fail node is configured.";
                  description
                    "declare authentication failure on server unreachability";
                }
                container auth-retry {
                  must "not(../auth-fail)";
                  presence "Indicates a auth-retry node is configured.";
                  description
                    "no auth fail declared, retry authentication with supplicant, until server is reachable.";
                }
              }
            }
          }
          container host-mode {
            description
              "set the host mode for authentication";
            container multi-auth {
              must "not(../multi-host or ../single-host)";
              presence "Indicates a multi-auth node is configured.";
              description
                "multiple authentication mode";
            }
            container multi-host {
              must "not(../multi-auth or ../single-host)";
              presence "Indicates a multi-host node is configured.";
              description
                "multiple host mode";
            }
            container single-host {
              must "not(../multi-auth or ../multi-host)";
              presence "Indicates a single-host node is configured.";
              description
                "single host mode";
            }
          }
        }
      }
    }
  }
  container eap {
    description
      "EAP Global Configuration Commands";
    container profiles {
      description
        "Configure EAP profiles";
      list profile {
        key "profile-name";
        description
          "Configure EAP profiles";
        leaf profile-name {
          type xr:Cisco-ios-xr-string {
            length "1..63" {
              description
                "Specify a profile name (max 63 characters)";
            }
          }
          description
            "Configure EAP profiles";
        }
        leaf identity {
          type xr:Cisco-ios-xr-string {
            length "1..63" {
              description
                "Specify EAP Identity or Username for authentication";
            }
          }
          description
            "identity name";
        }
        container method {
          description
            "Add an allowed method";
          container tls {
            description
              "EAP-TLS method allowed";
            leaf pki-trustpoint {
              type xr:Cisco-ios-xr-string {
                length "1..63" {
                  description
                    "Specify the pki trustpoint name";
                }
              }
              description
                "Set pki trustpoint";
            }
          }
          container ttls {
            description
              "EAP-TTLS method allowed";
            leaf pki-trustpoint {
              type xr:Cisco-ios-xr-string {
                length "1..63" {
                  description
                    "Specify the pki trustpoint name";
                }
              }
              description
                "Set pki trustpoint";
            }
          }
        }
        container allow-eap-tls-v1-0 {
          presence "Indicates a allow-eap-tls-v1-0 node is configured.";
          description
            "Allow EAP TLS v1.0";
        }
      }
    }
  }
}
