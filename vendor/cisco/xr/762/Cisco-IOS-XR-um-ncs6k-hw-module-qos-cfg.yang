module Cisco-IOS-XR-um-ncs6k-hw-module-qos-cfg {
  namespace "http://cisco.com/ns/yang/Cisco-IOS-XR-um-ncs6k-hw-module-qos-cfg";
  prefix um-ncs6k-hw-module-qos-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs6k-hw-module-qos package configuration.
     
     This YANG module augments the
     modules with configuration data.
     
     Copyright (c) 2020 by Cisco Systems, Inc.
     All rights reserved.";

  revision 2020-06-26 {
    description
      "Initial release";
    semver:module-version "1.0.0";
  }

  container hw-module {
    description
      "Configure h/w module";
    container all {
      description
        "all line cards";
      container qos-mode {
        description
          "Configure qos mode in HW Module port(s)";
        container aggregate-bundle-mode {
          presence "Indicates a aggregate-bundle-mode node is configured.";
          description
            "set aggregate bundle mode";
        }
      }
    }
  }
}
