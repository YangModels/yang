module Cisco-IOS-XR-um-ethernet-sla-cfg {
  namespace "http://cisco.com/ns/yang/Cisco-IOS-XR-um-ethernet-sla-cfg";
  prefix um-ethernet-sla-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-sla package configuration.
     
     This YANG module augments the
     modules with configuration data.
     
     Copyright (c) 2021-2022 by Cisco Systems, Inc.
     All rights reserved.";

  revision 2022-07-26 {
    description
      "Updated bins width options";
    semver:module-version "1.1.0";
  }
  revision 2021-01-28 {
    description
      "Initial release";
    semver:module-version "1.0.0";
  }

  container ethernet {
    description
      "Ethernet configuration commands";
    container sla {
      description
        "Service-Level Agreement configuration";
      container profiles {
        description
          "Per-profile configuration";
        list profile {
          key "profile-name";
          description
            "Per-profile configuration";
          leaf profile-name {
            type xr:Cisco-ios-xr-string {
              length "1..800" {
                description
                  "Profile name";
              }
            }
            description
              "Per-profile configuration";
          }
          leaf type {
            type string {
              pattern "(cfm-delay-measurement)|(cfm-delay-measurement-version-0)|(cfm-loopback)|(cfm-loss-measurement)|(cfm-synthetic-loss-measurement)";
            }
            mandatory true;
            description
              "Type of packet that operations using this profile will send";
          }
          container probe {
            description
              "SLA Probe configuration";
            container send {
              description
                "Configure properties of packets to send";
              container packet {
                description
                  "Send single packets";
                container once {
                  must "not(../every)";
                  must "not(../../burst/once or ../../burst/every)";
                  presence "Indicates a once node is configured.";
                  description
                    "Send a single packet";
                }
                container every {
                  must "not(../once)";
                  must "not(../../burst/once or ../../burst/every)";
                  presence "Indicates a every node is configured.";
                  description
                    "Specify how often packets within a probe should be sent";
                  leaf interval {
                    type uint32 {
                      range "1..10000" {
                        description
                          "Interval between packets";
                      }
                    }
                    must
                      "../milliseconds or ../seconds or ../minutes
                       or ../hours";
                    mandatory true;
                    description
                      "Specify how often packets within a probe should be sent";
                  }
                  container milliseconds {
                    must
                      "not(../seconds or ../minutes
                       or ../hours)";
                    presence "Indicates a milliseconds node is configured.";
                    description
                      "Time is in milliseconds";
                  }
                  container seconds {
                    must
                      "not(../milliseconds or ../minutes
                       or ../hours)";
                    presence "Indicates a seconds node is configured.";
                    description
                      "Time is in seconds";
                  }
                  container minutes {
                    must
                      "not(../milliseconds or ../seconds
                       or ../hours)";
                    presence "Indicates a minutes node is configured.";
                    description
                      "Time is in minutes";
                  }
                  container hours {
                    must
                      "not(../milliseconds or ../seconds
                       or ../minutes)";
                    presence "Indicates a hours node is configured.";
                    description
                      "Time is in hours";
                  }
                }
              }
              container burst {
                description
                  "Send bursts of packets";
                container once {
                  must "not(../every) and ../packet/count";
                  must "not(../../packet/once or ../../packet/every)";
                  presence "Indicates a once node is configured.";
                  description
                    "Send a single burst";
                }
                container every {
                  must "not(../once) and ../packet/count";
                  must "not(../../packet/once or ../../packet/every)";
                  presence "Indicates a every node is configured.";
                  description
                    "Specify how often bursts within a probe should be sent";
                  leaf interval {
                    type uint32 {
                      range "1..3600" {
                        description
                          "Interval between bursts";
                      }
                    }
                    must
                      "../seconds or ../minutes
                       or ../hours";
                    mandatory true;
                    description
                      "Specify how often bursts within a probe should be sent";
                  }
                  container seconds {
                    must "not(../minutes or ../hours)";
                    presence "Indicates a seconds node is configured.";
                    description
                      "Time is in seconds";
                  }
                  container minutes {
                    must "not(../seconds or ../hours)";
                    presence "Indicates a minutes node is configured.";
                    description
                      "Time is in minutes";
                  }
                  container hours {
                    must "not(../seconds or ../minutes)";
                    presence "Indicates a hours node is configured.";
                    description
                      "Time is in hours";
                  }
                }
                container packet {
                  description
                    "Configure properties of packets within each burst";
                  leaf count {
                    type uint32 {
                      range "2..1200" {
                        description
                          "Number of packets in each burst";
                      }
                    }
                    must "../interval-in-seconds or ../interval-in-milliseconds";
                    description
                      "Specify the number of packets in each burst";
                  }
                  leaf interval-in-seconds {
                    type uint32 {
                      range "1..30" {
                        description
                          "Interval between packets in each burst (in seconds)";
                      }
                    }
                    must "not(../interval-in-milliseconds)";
                    description
                      "Specify the interval between packets in each burst";
                  }
                  leaf interval-in-milliseconds {
                    type uint32 {
                      range "50..30000" {
                        description
                          "Interval between packets in each burst (in milliseconds)";
                      }
                    }
                    must "not(../interval-in-seconds)";
                    description
                      "Specify the interval between packets in each burst";
                  }
                }
              }
            }
            container packet {
              description
                "Configure properties of the packet";
              leaf size {
                type uint32 {
                  range "1..9000" {
                    description
                      "Size of each packet in the probe";
                  }
                }
                description
                  "Specify the minimum size of each packet in the probe (packets will be padded if needed)";
              }
              container test {
                description
                  "Specify a test pattern to pad the packets";
                container pattern {
                  description
                    "Specify a test pattern to pad the packets";
                  container pseudo-random {
                    must "not(../hex)";
                    presence "Indicates a pseudo-random node is configured.";
                    description
                      "Use a pseudo-random bit sequence for packet padding";
                  }
                  leaf hex {
                    type uint32 {
                      range "0..4294967295" {
                        description
                          "Pattern to be used for hex padding (format 0xHHHHHHHH)";
                      }
                    }
                    must "not(../pseudo-random)";
                    description
                      "Use an optionally specified hex pattern for packet padding";
                  }
                }
              }
            }
            leaf priority {
              type uint32 {
                range "0..7" {
                  description
                    "Packet priority of each packet in the probe";
                }
              }
              description
                "Specify the priority to use when sending packets";
            }
            container synthetic {
              description
                "Specify the number of packets used in each FLR calculation";
              container loss {
                description
                  "Specify the number of packets used in each FLR calculation";
                container calculation {
                  description
                    "Specify the number of packets used in each FLR calculation";
                  leaf packets {
                    type uint32 {
                      range "10..12096000" {
                        description
                          "Packet priority of each packet in the probe";
                      }
                    }
                    description
                      "Specify the number of packets used in each FLR calculation";
                  }
                }
              }
            }
          }
          container statistics {
            description
              "SLA Statistics-collection configuration";
            container measure {
              description
                "Specify the type of statistics to collect";
              list measure {
                key "type";
                description
                  "Specify the type of statistics to collect";
                leaf type {
                  type enumeration {
                    enum "one-way-delay-ds" {
                      value 3;
                      description
                        "Collect one-way (destination-to-source) delay";
                    }
                    enum "one-way-delay-sd" {
                      value 2;
                      description
                        "Collect one-way (source-to-destination) delay";
                    }
                    enum "one-way-jitter-ds" {
                      value 6;
                      description
                        "Collect one-way (destination-to-source) jitter";
                    }
                    enum "one-way-jitter-sd" {
                      value 5;
                      description
                        "Collect one-way (source-to-destination) jitter";
                    }
                    enum "round-trip-delay" {
                      value 1;
                      description
                        "Collect round-trip delay";
                    }
                    enum "round-trip-jitter" {
                      value 4;
                      description
                        "Collect round-trip jitter";
                    }
                    enum "one-way-loss-ds" {
                      value 8;
                      description
                        "Collect one-way (destination-to-source) loss";
                    }
                    enum "one-way-loss-sd" {
                      value 7;
                      description
                        "Collect one-way (source-to-destination) los";
                    }
                  }
                  description
                    "Specify the type of statistics to collect";
                }
                container aggregate {
                  description
                    "Specify how results should be aggregated";
                  container none {
                    must "not(../bins)";
                    presence "Indicates a none node is configured.";
                    description
                      "Perform no aggregation";
                  }
                  leaf bins {
                    type uint32 {
                      range "2..100" {
                        description
                          "Number of bins to distribute results between";
                      }
                    }
                    must "not(../none)";
                    description
                      "Aggregate results into a number of bins";
                  }
                  leaf width {
                    type uint32 {
                      range "1..10000000" {
                        description
                          "Width in percentage points, to an accuracy of one percentage point";
                      }
                    }
                    description
                      "Width in percentage points, to an accuracy of one percentage point";
                  }
                  leaf width-tenths {
                    type uint32 {
                      range "0..9" {
                        description
                          "Tenths of a percentage point";
                      }
                    }
                    description
                      "Tenths of a percentage point";
                  }
                  container usec {
                    presence "Indicates a usec node is configured.";
                    description
                      "Interpret the width in microseconds";
                  }
                }
                container buckets {
                  description
                    "Bucket configuration";
                  leaf size {
                    type uint32 {
                      range "1..100" {
                        description
                          "Size of each bucket (number of probes-per-bucket)";
                      }
                    }
                    description
                      "Configure the size of each bucket";
                  }
                  container probes {
                    presence "Indicates a probes node is configured.";
                    description
                      "Buckets span multiple probes";
                  }
                  leaf archive {
                    type uint32 {
                      range "1..100" {
                        description
                          "Number of buckets to store internally";
                      }
                    }
                    description
                      "Configure the number of buckets to store internally";
                  }
                }
                container thresholds {
                  description
                    "Ethernet SLA thresholds submode";
                  container type {
                    description
                      "Specify the type of the threshold";
                    container stateful {
                      description
                        "Set a 'stateful' threshold";
                      container log {
                        description
                          "Emit a syslog when the threshold is crossed";
                        container on {
                          description
                            "Specify the condition for crossing the threshold";
                          leaf max-value {
                            type uint32 {
                              range "1..2147483647" {
                                description
                                  "Threshold value. In microseconds for delay, millionths of a percent for loss";
                              }
                            }
                            description
                              "Threshold is breached when the maximum value crosses the configured threshold value";
                          }
                          leaf mean-value {
                            type uint32 {
                              range "1..2147483647" {
                                description
                                  "Threshold value. In microseconds for delay, millionths of a percent for loss";
                              }
                            }
                            description
                              "Threshold is breached when the mean value crosses the configured threshold value";
                          }
                          leaf sample-count {
                            type uint32 {
                              range "1..2147483647" {
                                description
                                  "Threshold sample count";
                              }
                            }
                            description
                              "Threshold is breached when the sample count in bins in and above a certain bin number crosses the configured sample count";
                          }
                          container in-and-above {
                            description
                              "Specify the bin number in-and-above which samples count towards the threshold sample count";
                            leaf bin {
                              type uint32 {
                                range "2..100" {
                                  description
                                    "Bin number";
                                }
                              }
                              description
                                "Specify the bin number in-and-above which samples count towards the threshold sample count";
                            }
                          }
                        }
                      }
                      container efd {
                        description
                          "Bring down the interface with EFD when the threshold is crossed";
                        container on {
                          description
                            "Specify the condition for crossing the threshold";
                          leaf max-value {
                            type uint32 {
                              range "1..2147483647" {
                                description
                                  "Threshold value. In microseconds for delay, millionths of a percent for loss";
                              }
                            }
                            description
                              "Threshold is breached when the maximum value crosses the configured threshold value";
                          }
                          leaf mean-value {
                            type uint32 {
                              range "1..2147483647" {
                                description
                                  "Threshold value. In microseconds for delay, millionths of a percent for loss";
                              }
                            }
                            description
                              "Threshold is breached when the mean value crosses the configured threshold value";
                          }
                          leaf sample-count {
                            type uint32 {
                              range "1..2147483647" {
                                description
                                  "Threshold sample count";
                              }
                            }
                            description
                              "Threshold is breached when the sample count in bins in and above a certain bin number crosses the configured sample count";
                          }
                          container in-and-above {
                            description
                              "Specify the bin number in-and-above which samples count towards the threshold sample count";
                            leaf bin {
                              type uint32 {
                                range "2..100" {
                                  description
                                    "Bin number";
                                }
                              }
                              description
                                "Specify the bin number in-and-above which samples count towards the threshold sample count";
                            }
                          }
                        }
                      }
                    }
                    container stateless {
                      description
                        "Set a 'stateless' threshold";
                      container log {
                        description
                          "Emit a syslog when the threshold is crossed";
                        container on {
                          description
                            "Specify the condition for crossing the threshold";
                          leaf max-value {
                            type uint32 {
                              range "1..2147483647" {
                                description
                                  "Threshold value. In microseconds for delay, millionths of a percent for loss";
                              }
                            }
                            description
                              "Threshold is breached when the maximum value crosses the configured threshold value";
                          }
                          leaf mean-value {
                            type uint32 {
                              range "1..2147483647" {
                                description
                                  "Threshold value. In microseconds for delay, millionths of a percent for loss";
                              }
                            }
                            description
                              "Threshold is breached when the mean value crosses the configured threshold value";
                          }
                          leaf sample-count {
                            type uint32 {
                              range "1..2147483647" {
                                description
                                  "Threshold sample count";
                              }
                            }
                            description
                              "Threshold is breached when the sample count in bins in and above a certain bin number crosses the configured sample count";
                          }
                          container in-and-above {
                            description
                              "Specify the bin number in-and-above which samples count towards the threshold sample count";
                            leaf bin {
                              type uint32 {
                                range "2..100" {
                                  description
                                    "Bin number";
                                }
                              }
                              description
                                "Specify the bin number in-and-above which samples count towards the threshold sample count";
                            }
                          }
                        }
                      }
                    }
                  }
                }
              }
            }
          }
          container schedule {
            description
              "SLA Schedule configuration";
            container every {
              description
                "Specify scheduling frequency";
              container week {
                presence "Indicates a week node is configured.";
                description
                  "Schedule once every week";
                leaf on {
                  type enumeration {
                    enum "monday" {
                      value 1;
                      description
                        "Schedule every Monday";
                    }
                    enum "tuesday" {
                      value 2;
                      description
                        "Schedule every Tuesday";
                    }
                    enum "wednesday" {
                      value 3;
                      description
                        "Schedule every Wednesday";
                    }
                    enum "thursday" {
                      value 4;
                      description
                        "Schedule every Thursday";
                    }
                    enum "friday" {
                      value 5;
                      description
                        "Schedule every Friday";
                    }
                    enum "saturday" {
                      value 6;
                      description
                        "Schedule every Saturday";
                    }
                    enum "sunday" {
                      value 7;
                      description
                        "Schedule every Sunday";
                    }
                  }
                  mandatory true;
                  description
                    "Specify day of week to schedule on";
                }
              }
              container day {
                presence "Indicates a day node is configured.";
                description
                  "Schedule once every day";
              }
              leaf interval-in-minutes {
                type uint32 {
                  range "1..90" {
                    description
                      "Interval between operations (minutes)";
                  }
                }
                description
                  "Interval between operations (minutes)";
              }
              leaf interval-in-hours {
                type uint32 {
                  range "1..90" {
                    description
                      "Interval between operations (hours)";
                  }
                }
                description
                  "Interval between operations (hours)";
              }
              container at {
                description
                  "Specify time of day (hh:mm UTC) at which (first) operation should be performed";
                leaf hours {
                  type uint32 {
                    range "0..23" {
                      description
                        "Hours (hh:mm UTC)";
                    }
                  }
                  must
                    "../minutes and
                     (../../week or ../../day or
                     ../../interval-in-minutes or ../../interval-in-hours)";
                  description
                    "Hours (hh:mm UTC)";
                }
                leaf minutes {
                  type uint32 {
                    range "0..59" {
                      description
                        "Minutes (hh:mm UTC)";
                    }
                  }
                  must "../hours";
                  description
                    "Minutes (hh:mm UTC)";
                }
              }
              container for {
                description
                  "Specify how long operations should keep running for";
                leaf time {
                  type uint32 {
                    range "1..3600" {
                      description
                        "Duration of operation (may be seconds, minutes, hours, days, or weeks)";
                    }
                  }
                  must
                    "../unit and
                     (../../week or ../../day or
                     ../../interval-in-minutes or ../../interval-in-hours)";
                  description
                    "Duration of operation (may be seconds, minutes, hours, days, or weeks)";
                }
                leaf unit {
                  type enumeration {
                    enum "seconds" {
                      value 3;
                      description
                        "Time is in seconds";
                    }
                    enum "minutes" {
                      value 4;
                      description
                        "Time is in minutes";
                    }
                    enum "hours" {
                      value 5;
                      description
                        "Time is in hours";
                    }
                    enum "day" {
                      value 6;
                      description
                        "Time is in days";
                    }
                    enum "week" {
                      value 7;
                      description
                        "Time is in weeks";
                    }
                  }
                  must "../time";
                }
              }
            }
          }
        }
      }
    }
  }
}
