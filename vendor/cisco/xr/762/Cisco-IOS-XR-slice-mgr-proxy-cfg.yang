module Cisco-IOS-XR-slice-mgr-proxy-cfg {
  namespace "http://cisco.com/ns/yang/Cisco-IOS-XR-slice-mgr-proxy-cfg";
  prefix slice-mgr-proxy-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR slice-mgr-proxy package configuration.
     
     This module contains definitions
     for the following management objects:
       node-path: Node act path
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container node-path {
    description
      "Node act path";
    list node {
      key "node-name";
      description
        "Node (Physical location of the node in R_S_I
         format)";
      container slice-ids {
        description
          "Slice";
        list slice-id {
          key "slice-id";
          description
            "Slice Id on which configuration will be
             applied";
          leaf state {
            type uint32;
            description
              "set val 0 to shutdown";
          }
          leaf breakout {
            type uint32;
            description
              "10G Breakout Config";
          }
          leaf mode {
            type uint32;
            description
              "set val 4 for OTU4 ";
          }
          leaf slice-id {
            type uint32 {
              range "0..4";
            }
            description
              "The identifier for this slice";
          }
        }
      }
      leaf node-name {
        type xr:Physical-allowed-node-id-string;
        description
          "Location in R_S_I format";
      }
    }
  }
}
