module Cisco-IOS-XR-infra-script-mgmt-oper {
  namespace "http://cisco.com/ns/yang/Cisco-IOS-XR-infra-script-mgmt-oper";
  prefix infra-script-mgmt-oper;

  import Cisco-IOS-XR-types {
    prefix xr;
  }
  import cisco-semver {
    prefix semver;
  }
  include Cisco-IOS-XR-infra-script-mgmt-oper-sub1 {
    revision-date 2022-11-21;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-script-mgmt package operational data.
     
     This module contains definitions
     for the following management objects:
       script: Script operational data
     
     Copyright (c) 2013-2022 by Cisco Systems, Inc.
     All rights reserved.";

  revision 2022-11-21 {
    description
      "Added script repo type to script status
       2022-05-24
         Added show-del for script execution
       2022-05-17
         Added show-del and other options for script status/execution
       2022-03-23
         Added precommit as a new script type supported by script management.
       2021-12-13
         Added snmp as a new script type supported by script management.";
    semver:module-version "2.0.1M";
  }
  revision 2021-04-08 {
    description
      "Removed Detail, Output, Error, Reverse, Last, classes under ShowDel.";
    semver:module-version "2.0.0";
  }
  revision 2019-04-05 {
    description
      "Establish semantic version baseline.";
  }
  revision 2015-11-09 {
    description
      "IOS XR 6.0 revision.";
  }

  grouping TYPE-SHOW-DEL {
    description
      "Common node of exec-script, process-script,
       config-script, eem-script, snmp-script,
       precommit-script";
    container type-show-del {
      description
        "Detailed deleted script status information of
         specified script type";
      container summary {
        description
          "Status Information about a particular script";
        uses SCRIPT-STATUS-SUMMARY;
      }
    }
  }

  grouping TYPE-LAST-TABLE {
    description
      "Common node of exec-script, process-script,
       config-script, eem-script, snmp-script,
       precommit-script";
    container lasts {
      description
        "Detailed script status information given last
         number of scripts";
      list last {
        key "last-num";
        description
          "Detailed script status information given last
           number of scripts";
        leaf last-num {
          type uint32;
          description
            "Last number of scripts";
        }
        uses SCRIPT-STATUS-DETAIL;
      }
    }
  }

  grouping REVERSE {
    description
      "Common node of exec-script, process-script,
       config-script, eem-script, snmp-script,
       precommit-script";
    container reverse {
      description
        "Detailed script status information reversed";
      uses SCRIPT-STATUS-DETAIL;
    }
  }

  grouping SHOW-DELETE {
    description
      "Common node of exec-script, process-script,
       config-script, eem-script, snmp-script,
       precommit-script";
    container show-delete {
      description
        "Detailed script status information reversed";
      uses SCRIPT-STATUS-DETAIL;
    }
  }

  grouping TYPE-NAME-TABLE {
    description
      "Common node of exec-script, process-script,
       config-script, eem-script, snmp-script,
       precommit-script";
    container type-names {
      description
        "Script status information given script type and
         script name";
      list type-name {
        key "name-str";
        description
          "Script Status Information about a particular
           script";
        container reverse {
          description
            "Detailed script status information reversed";
          uses SCRIPT-STATUS-DETAIL;
        }
        container detail {
          description
            "Detailed script status information";
          uses SCRIPT-STATUS-DETAIL;
        }
        container type-name-detail-show-del {
          description
            "Deleted information about a particular script";
          uses SCRIPT-STATUS-DETAIL;
        }
        container lasts {
          description
            "Detailed script status information given last
             number of scripts";
          list last {
            key "last-num";
            description
              "Detailed script status information given last
               number of scripts";
            leaf last-num {
              type uint32;
              description
                "Last number of scripts";
            }
            uses SCRIPT-STATUS-DETAIL;
          }
        }
        container type-name-detail-last-show-dels {
          description
            "Detailed information of a particular execution
             request";
          list type-name-detail-last-show-del {
            key "last-num";
            description
              "Detailed information of a particular
               execution request";
            leaf last-num {
              type uint32;
              description
                "Last number of scripts";
            }
            uses SCRIPT-STATUS-DETAIL;
          }
        }
        container summary {
          description
            "Status Information about a particular script";
          uses SCRIPT-STATUS-SUMMARY;
        }
        container type-name-show-del {
          description
            "Deleted information about a particular script";
          container summary {
            description
              "Status summary information about a particular
               script";
            uses SCRIPT-STATUS-SUMMARY;
          }
        }
        leaf name-str {
          type xr:Cisco-ios-xr-string;
          description
            "Script name";
        }
      }
    }
  }

  grouping DETAIL-SHOW-DEL {
    description
      "Common node of exec-script, process-script,
       config-script, eem-script, snmp-script,
       precommit-script";
    container detail-show-del {
      description
        "Deleted information about a particular script";
      uses SCRIPT-STATUS-DETAIL;
    }
  }

  grouping SUMMARY {
    description
      "Common node of exec-script, eem-script,
       process-script, config-script, snmp-script,
       precommit-script";
    container summary {
      description
        "Show script status information";
      uses SCRIPT-STATUS-SUMMARY;
    }
  }

  grouping DETAIL {
    description
      "Common node of exec-script, process-script,
       config-script, eem-script, snmp-script,
       precommit-script";
    container detail {
      description
        "Detailed script status information";
      uses SCRIPT-STATUS-DETAIL;
    }
  }

  container script {
    config false;
    description
      "Script operational data";
    container status {
      description
        "Script status information";
      container detail-reverse-showdel-table {
        description
          "Detailed information of a particular execution
           request";
        container detail-reverse-showdel {
          description
            "Detailed information of a particular execution
             request";
          uses SCRIPT-STATUS-DETAIL;
        }
      }
      container lasts {
        description
          "Detailed information of a particular execution
           request";
        list last {
          key "last-num";
          description
            "Detailed information of a particular execution
             request";
          leaf last-num {
            type uint32;
            description
              "Last number of scripts";
          }
          uses SCRIPT-STATUS-DETAIL;
        }
      }
      container detail-reverse-lasts {
        description
          "Detailed information of a particular execution
           request";
        list detail-reverse-last {
          key "last-num";
          description
            "Detailed information of a particular execution
             request";
          leaf last-num {
            type uint32;
            description
              "Last number of scripts";
          }
          uses SCRIPT-STATUS-DETAIL;
        }
      }
      container detail-last-show-dels {
        description
          "Detailed information of a particular execution
           request";
        list detail-last-show-del {
          key "last-num";
          description
            "Detailed information of a particular execution
             request";
          leaf last-num {
            type uint32;
            description
              "Last number of scripts";
          }
          uses SCRIPT-STATUS-DETAIL;
        }
      }
      container type {
        description
          "Show script status type information";
        container process-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
        container eem-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
        container config-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
        container precommit-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
        container exec-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
        container snmp-script {
          description
            "Show script status type information";
          uses TYPE-LAST-TABLE;
          uses TYPE-SHOW-DEL;
          uses SHOW-DELETE;
          uses REVERSE;
          uses DETAIL-SHOW-DEL;
          uses DETAIL;
          uses TYPE-NAME-TABLE;
          uses SUMMARY;
        }
      }
      container reverse {
        description
          "Detailed information of a particular execution
           request";
        uses SCRIPT-STATUS-DETAIL;
      }
      container status-names {
        description
          "Information about last request";
        list status-name {
          key "name-str";
          description
            "Status Information about a particular script";
          container status-name-detail-reverse-last-show-dels {
            description
              "Detailed information of a particular
               execution request";
            list status-name-detail-reverse-last-show-del {
              key "last-num";
              description
                "Detailed information of a particular
                 execution request";
              leaf last-num {
                type uint32;
                description
                  "Last number of scripts";
              }
              uses SCRIPT-STATUS-DETAIL;
            }
          }
          container show-delete {
            description
              "Detailed information of a particular
               execution request";
            uses SCRIPT-STATUS-DETAIL;
          }
          container reverse {
            description
              "Detailed information of a particular
               execution request";
            uses SCRIPT-STATUS-DETAIL;
          }
          container status-name-detail-reverse-show-del {
            description
              "Detailed information of a particular
               execution request";
            uses SCRIPT-STATUS-DETAIL;
          }
          container detail {
            description
              "Detailed information of a particular
               execution request";
            uses SCRIPT-STATUS-DETAIL;
          }
          container status-name-show-del {
            description
              "Show script status detail information";
            container summary {
              description
                "Detailed information of a particular
                 execution request";
              uses SCRIPT-STATUS-SUMMARY;
            }
          }
          container detail-last-show-dels {
            description
              "Detailed information of a particular
               execution request";
            list detail-last-show-del {
              key "last-num";
              description
                "Detailed information of a particular
                 execution request";
              leaf last-num {
                type uint32;
                description
                  "Last number of scripts";
              }
              uses SCRIPT-STATUS-DETAIL;
            }
          }
          container summary {
            description
              "Status Information about a particular script";
            uses SCRIPT-STATUS-SUMMARY;
          }
          container status-name-detail-reverse-lasts {
            description
              "Detailed information of a particular
               execution request";
            list status-name-detail-reverse-last {
              key "last-num";
              description
                "Detailed information of a particular
                 execution request";
              leaf last-num {
                type uint32;
                description
                  "Last number of scripts";
              }
              uses SCRIPT-STATUS-DETAIL;
            }
          }
          container lasts {
            description
              "Detailed information of a particular
               execution request";
            list last {
              key "last-num";
              description
                "Detailed information of a particular
                 execution request";
              leaf last-num {
                type uint32;
                description
                  "Last number of scripts";
              }
              uses SCRIPT-STATUS-DETAIL;
            }
          }
          container detail-showdel {
            description
              "Detailed information of a particular
               execution request";
            uses SCRIPT-STATUS-DETAIL;
          }
          leaf name-str {
            type xr:Cisco-ios-xr-string;
            description
              "Show Execution Name string";
          }
        }
      }
      container detail-reverse-last-show-dels {
        description
          "Detailed information of a particular execution
           request";
        list detail-reverse-last-show-del {
          key "last-num";
          description
            "Detailed information of a particular execution
             request";
          leaf last-num {
            type uint32;
            description
              "Last number of scripts";
          }
          uses SCRIPT-STATUS-DETAIL;
        }
      }
      container detail {
        description
          "Detailed information of a particular execution
           request";
        uses SCRIPT-STATUS-DETAIL;
      }
      container summary {
        description
          "Script status summary information";
        uses SCRIPT-STATUS-SUMMARY;
      }
      container show-del {
        description
          "Information about deleted scripts";
        container summary {
          description
            "Detailed information of a particular execution
             request";
          uses SCRIPT-STATUS-SUMMARY;
        }
      }
    }
    container execution {
      description
        "Information about script execution";
      container error-showdel {
        description
          "Error log for script execution";
        uses SCRIPT-EXECUTION-ERROR-LOG;
      }
      container lasts {
        description
          "Information about last request";
        list last {
          key "last-num";
          description
            "Information about last request";
          container output {
            description
              "Detailed output log for script execution";
            uses SCRIPT-EXECUTION-OUTPUT-LOG;
          }
          container last-names {
            description
              "Status Details about a particular execution
               request";
            list last-name {
              key "name-str";
              description
                "Information about a particular request";
              container last-name-show-del {
                description
                  "Status Details about a particular execution
                   request";
                container summary {
                  description
                    "Show execution request status summary
                     about a particular execution request";
                  uses SCRIPT-EXECUTION-SUMMARY;
                }
              }
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container last-name-detail-show-del {
                description
                  "Status Details about a particular execution
                   request";
                uses SCRIPT-EXECUTION-DETAIL;
              }
              container summary {
                description
                  "Show execution request status summary
                   about a particular execution request";
                uses SCRIPT-EXECUTION-SUMMARY;
              }
              container error {
                description
                  "Detailed error log for script execution";
                uses SCRIPT-EXECUTION-ERROR-LOG;
              }
              leaf name-str {
                type xr:Cisco-ios-xr-string;
                description
                  "Show Execution Name string";
              }
            }
          }
          container output-error {
            description
              "Detailed output and error log for script
               execution";
            uses SCRIPT-EXECUTION-LOG;
          }
          container detail {
            description
              "Detailed information of a particular
               execution request";
            uses SCRIPT-EXECUTION-DETAIL;
          }
          container summary {
            description
              "Information about script execution for last
               script request executed";
            uses SCRIPT-EXECUTION-SUMMARY;
          }
          container error {
            description
              "Detailed error log for script execution";
            uses SCRIPT-EXECUTION-ERROR-LOG;
          }
          container last-show-del {
            description
              "Status Reverse Details about a particular
               execution request";
            container summary {
              description
                "Show execution request status summary  about
                 a particular execution request";
              uses SCRIPT-EXECUTION-SUMMARY;
            }
          }
          leaf last-num {
            type uint32;
            description
              "Last given number of executed requests";
          }
        }
      }
      container output-showdel {
        description
          "Output log for script execution";
        uses SCRIPT-EXECUTION-OUTPUT-LOG;
      }
      container execution-statuses {
        description
          "Information about status of script execution";
        list execution-status {
          key "status-str";
          description
            "Status Information about request";
          container status-lasts {
            description
              "Status Reverse Details about a particular
               execution request";
            list status-last {
              key "last-num";
              description
                "Information about last request";
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container status-last-names {
                description
                  "Status Reverse Details about a particular
                   execution request";
                list status-last-name {
                  key "name-str";
                  description
                    "Information about a particular request";
                  container status-last-name-show-del {
                    description
                      "Status Reverse Details about a particular
                       execution request";
                    container summary {
                      description
                        "Show execution request status summary
                         about a particular execution request";
                      uses SCRIPT-EXECUTION-SUMMARY;
                    }
                  }
                  container output {
                    description
                      "Detailed output log for script execution";
                    uses SCRIPT-EXECUTION-OUTPUT-LOG;
                  }
                  container output-error {
                    description
                      "Detailed output and error log for script
                       execution";
                    uses SCRIPT-EXECUTION-LOG;
                  }
                  container detail {
                    description
                      "Show execution request status summary
                       about a particular execution request";
                    uses SCRIPT-EXECUTION-DETAIL;
                  }
                  container summary {
                    description
                      "Show execution request status summary
                       about a particular execution request";
                    uses SCRIPT-EXECUTION-SUMMARY;
                  }
                  container error {
                    description
                      "Detailed error log for script execution";
                    uses SCRIPT-EXECUTION-ERROR-LOG;
                  }
                  leaf name-str {
                    type xr:Cisco-ios-xr-string;
                    description
                      "Show Execution Name string";
                  }
                }
              }
              container summary {
                description
                  "Show execution request status summary
                   about a particular execution request";
                uses SCRIPT-EXECUTION-SUMMARY;
              }
              container error {
                description
                  "Detailed error log for script execution";
                uses SCRIPT-EXECUTION-ERROR-LOG;
              }
              leaf last-num {
                type uint32;
                description
                  "Last given number of executed requests";
              }
            }
          }
          container output {
            description
              "Detailed output log for script execution";
            uses SCRIPT-EXECUTION-OUTPUT-LOG;
          }
          container status-reverse {
            description
              "Status Details about a particular execution
               request";
            container output {
              description
                "Detailed output log for script execution";
              uses SCRIPT-EXECUTION-OUTPUT-LOG;
            }
            container output-error {
              description
                "Detailed output and error log for script
                 execution";
              uses SCRIPT-EXECUTION-LOG;
            }
            container detail {
              description
                "Show execution request status summary  about
                 a particular execution request";
              uses SCRIPT-EXECUTION-DETAIL;
            }
            container summary {
              description
                "Show execution request status summary  about
                 a particular execution request";
              uses SCRIPT-EXECUTION-SUMMARY;
            }
            container error {
              description
                "Detailed error log for script execution";
              uses SCRIPT-EXECUTION-ERROR-LOG;
            }
            container status-reverse-lasts {
              description
                "Status Details about a particular execution
                 request";
              list status-reverse-last {
                key "last-num";
                description
                  "Information about last request";
                container output {
                  description
                    "Detailed output log for script execution";
                  uses SCRIPT-EXECUTION-OUTPUT-LOG;
                }
                container output-error {
                  description
                    "Detailed output and error log for script
                     execution";
                  uses SCRIPT-EXECUTION-LOG;
                }
                container detail {
                  description
                    "Show execution request status summary
                     about a particular execution request";
                  uses SCRIPT-EXECUTION-DETAIL;
                }
                container summary {
                  description
                    "Show execution request status summary
                     about a particular execution request";
                  uses SCRIPT-EXECUTION-SUMMARY;
                }
                container status-reverse-last-names {
                  description
                    "Status Details about a particular
                     execution request";
                  list status-reverse-last-name {
                    key "name-str";
                    description
                      "Information about a particular request";
                    container status-reverse-last-name-show-del {
                      description
                        "Status Details about a particular
                         execution request";
                      container summary {
                        description
                          "Show execution request status summary
                           about a particular execution request";
                        uses SCRIPT-EXECUTION-SUMMARY;
                      }
                    }
                    container output {
                      description
                        "Detailed output log for script execution";
                      uses SCRIPT-EXECUTION-OUTPUT-LOG;
                    }
                    container output-error {
                      description
                        "Detailed output and error log for script
                         execution";
                      uses SCRIPT-EXECUTION-LOG;
                    }
                    container detail {
                      description
                        "Show execution request status summary
                         about a particular execution request";
                      uses SCRIPT-EXECUTION-DETAIL;
                    }
                    container summary {
                      description
                        "Show execution request status summary
                         about a particular execution request";
                      uses SCRIPT-EXECUTION-SUMMARY;
                    }
                    container error {
                      description
                        "Detailed error log for script execution";
                      uses SCRIPT-EXECUTION-ERROR-LOG;
                    }
                    leaf name-str {
                      type xr:Cisco-ios-xr-string;
                      description
                        "Show Execution Name string";
                    }
                  }
                }
                container error {
                  description
                    "Detailed error log for script execution";
                  uses SCRIPT-EXECUTION-ERROR-LOG;
                }
                leaf last-num {
                  type uint32;
                  description
                    "Last given number of executed requests";
                }
              }
            }
          }
          container status-show-del {
            description
              "Status Reverse Details about a particular
               execution request";
            container summary {
              description
                "Show execution request status summary  about
                 a particular execution request";
              uses SCRIPT-EXECUTION-SUMMARY;
            }
          }
          container output-error {
            description
              "Detailed output and error log for script
               execution";
            uses SCRIPT-EXECUTION-LOG;
          }
          container detail {
            description
              "Detailed information of a particular
               execution request";
            uses SCRIPT-EXECUTION-DETAIL;
          }
          container execution-status-names {
            description
              "Status Reverse Details about a particular
               execution request";
            list execution-status-name {
              key "name-str";
              description
                "Information about a particular request";
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container execution-status-name-show-del {
                description
                  "Status Reverse Details about a particular
                   execution request";
                container summary {
                  description
                    "Show execution request status summary
                     about a particular execution request";
                  uses SCRIPT-EXECUTION-SUMMARY;
                }
              }
              container summary {
                description
                  "Show execution request status summary
                   about a particular execution request";
                uses SCRIPT-EXECUTION-SUMMARY;
              }
              container error {
                description
                  "Detailed error log for script execution";
                uses SCRIPT-EXECUTION-ERROR-LOG;
              }
              leaf name-str {
                type xr:Cisco-ios-xr-string;
                description
                  "Show Execution Name string";
              }
            }
          }
          container summary {
            description
              "Status information for script execution";
            uses SCRIPT-EXECUTION-SUMMARY;
          }
          container error {
            description
              "Detailed error log for script execution";
            uses SCRIPT-EXECUTION-ERROR-LOG;
          }
          leaf status-str {
            type xr:Cisco-ios-xr-string;
            description
              "Status of given executed requests";
          }
        }
      }
      container output {
        description
          "Output log for script execution";
        uses SCRIPT-EXECUTION-OUTPUT-LOG;
      }
      container output-error-showdel {
        description
          "Output and Error log for script execution";
        uses SCRIPT-EXECUTION-LOG;
      }
      container output-error {
        description
          "Output and Error log for script execution";
        uses SCRIPT-EXECUTION-LOG;
      }
      container detail {
        description
          "Detailed information about script execution";
        uses SCRIPT-EXECUTION-DETAIL;
      }
      container requests {
        description
          "Information about script execution requests";
        list request {
          key "request-id";
          description
            "Information about a particular request";
          container request-statuses {
            description
              "Status Details about a particular execution
               request";
            list request-status {
              key "status-str";
              description
                "Status Information about request";
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container request-status-reverse {
                description
                  "Status Reverse Details about a particular
                   execution request";
                container output {
                  description
                    "Detailed output log for script execution";
                  uses SCRIPT-EXECUTION-OUTPUT-LOG;
                }
                container output-error {
                  description
                    "Detailed output and error log for script
                     execution";
                  uses SCRIPT-EXECUTION-LOG;
                }
                container detail {
                  description
                    "Show execution request status summary
                     about a particular execution request";
                  uses SCRIPT-EXECUTION-DETAIL;
                }
                container request-status-reverse-lasts {
                  description
                    "Status Reverse Details about a particular
                     execution request";
                  list request-status-reverse-last {
                    key "last-num";
                    description
                      "Information about last request";
                    container request-status-reverse-last-names {
                      description
                        "Status Reverse Details about a
                         particular execution request";
                      list request-status-reverse-last-name {
                        key "name-str";
                        description
                          "Information about a particular request";
                        container request-status-reverse-last-name-show-del {
                          description
                            "Status Reverse Details about a
                             particular execution request";
                          container summary {
                            description
                              "Show execution request status summary
                               about a particular execution request";
                            uses SCRIPT-EXECUTION-SUMMARY;
                          }
                        }
                        container output {
                          description
                            "Detailed output log for script
                             execution";
                          uses SCRIPT-EXECUTION-OUTPUT-LOG;
                        }
                        container output-error {
                          description
                            "Detailed output and error log for
                             script execution";
                          uses SCRIPT-EXECUTION-LOG;
                        }
                        container detail {
                          description
                            "Show execution request status summary
                             about a particular execution request";
                          uses SCRIPT-EXECUTION-DETAIL;
                        }
                        container summary {
                          description
                            "Show execution request status summary
                             about a particular execution request";
                          uses SCRIPT-EXECUTION-SUMMARY;
                        }
                        container error {
                          description
                            "Detailed error log for script
                             execution";
                          uses SCRIPT-EXECUTION-ERROR-LOG;
                        }
                        leaf name-str {
                          type xr:Cisco-ios-xr-string;
                          description
                            "Show Execution Name string";
                        }
                      }
                    }
                    container output {
                      description
                        "Detailed output log for script execution";
                      uses SCRIPT-EXECUTION-OUTPUT-LOG;
                    }
                    container output-error {
                      description
                        "Detailed output and error log for script
                         execution";
                      uses SCRIPT-EXECUTION-LOG;
                    }
                    container detail {
                      description
                        "Show execution request status summary
                         about a particular execution request";
                      uses SCRIPT-EXECUTION-DETAIL;
                    }
                    container summary {
                      description
                        "Show execution request status summary
                         about a particular execution request";
                      uses SCRIPT-EXECUTION-SUMMARY;
                    }
                    container error {
                      description
                        "Detailed error log for script execution";
                      uses SCRIPT-EXECUTION-ERROR-LOG;
                    }
                    leaf last-num {
                      type uint32;
                      description
                        "Last given number of executed requests";
                    }
                  }
                }
                container summary {
                  description
                    "Show execution request status summary
                     about a particular execution request";
                  uses SCRIPT-EXECUTION-SUMMARY;
                }
                container error {
                  description
                    "Detailed error log for script execution";
                  uses SCRIPT-EXECUTION-ERROR-LOG;
                }
              }
              container summary {
                description
                  "Show execution request status summary
                   about a particular execution request";
                uses SCRIPT-EXECUTION-SUMMARY;
              }
              container error {
                description
                  "Detailed error log for script execution";
                uses SCRIPT-EXECUTION-ERROR-LOG;
              }
              leaf status-str {
                type xr:Cisco-ios-xr-string;
                description
                  "Status of given executed requests";
              }
            }
          }
          container request-names {
            description
              "Status Reverse Details about a particular
               execution request";
            list request-name {
              key "name-str";
              description
                "Information about a particular request";
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container request-name-show-del {
                description
                  "Status Reverse Details about a particular
                   execution request";
                container summary {
                  description
                    "Show execution request status summary
                     about a particular execution request";
                  uses SCRIPT-EXECUTION-SUMMARY;
                }
              }
              container summary {
                description
                  "Show execution request status summary
                   about a particular execution request";
                uses SCRIPT-EXECUTION-SUMMARY;
              }
              container error {
                description
                  "Detailed error log for script execution";
                uses SCRIPT-EXECUTION-ERROR-LOG;
              }
              leaf name-str {
                type xr:Cisco-ios-xr-string;
                description
                  "Show Execution Name string";
              }
            }
          }
          container request-reverse {
            description
              "Status Reverse Details about a particular
               execution request";
            container output {
              description
                "Detailed output log for script execution";
              uses SCRIPT-EXECUTION-OUTPUT-LOG;
            }
            container output-error {
              description
                "Detailed output and error log for script
                 execution";
              uses SCRIPT-EXECUTION-LOG;
            }
            container detail {
              description
                "Show execution request status summary  about
                 a particular execution request";
              uses SCRIPT-EXECUTION-DETAIL;
            }
            container summary {
              description
                "Show execution request status summary  about
                 a particular execution request";
              uses SCRIPT-EXECUTION-SUMMARY;
            }
            container error {
              description
                "Detailed error log for script execution";
              uses SCRIPT-EXECUTION-ERROR-LOG;
            }
            container req-rev-lasts {
              description
                "Status Reverse Details about a particular
                 execution request";
              list req-rev-last {
                key "last-num";
                description
                  "Information about last request";
                container req-rev-last-names {
                  description
                    "Status Reverse Details about a particular
                     execution request";
                  list req-rev-last-name {
                    key "name-str";
                    description
                      "Information about a particular request";
                    container output {
                      description
                        "Detailed output log for script execution";
                      uses SCRIPT-EXECUTION-OUTPUT-LOG;
                    }
                    container output-error {
                      description
                        "Detailed output and error log for script
                         execution";
                      uses SCRIPT-EXECUTION-LOG;
                    }
                    container detail {
                      description
                        "Show execution request status summary
                         about a particular execution request";
                      uses SCRIPT-EXECUTION-DETAIL;
                    }
                    container summary {
                      description
                        "Show execution request status summary
                         about a particular execution request";
                      uses SCRIPT-EXECUTION-SUMMARY;
                    }
                    container request-reverse-last-name-show-del {
                      description
                        "Status Reverse Details about a
                         particular execution request";
                      container summary {
                        description
                          "Show execution request status summary
                           about a particular execution request";
                        uses SCRIPT-EXECUTION-SUMMARY;
                      }
                    }
                    container error {
                      description
                        "Detailed error log for script execution";
                      uses SCRIPT-EXECUTION-ERROR-LOG;
                    }
                    leaf name-str {
                      type xr:Cisco-ios-xr-string;
                      description
                        "Show Execution Name string";
                    }
                  }
                }
                container output {
                  description
                    "Detailed output log for script execution";
                  uses SCRIPT-EXECUTION-OUTPUT-LOG;
                }
                container output-error {
                  description
                    "Detailed output and error log for script
                     execution";
                  uses SCRIPT-EXECUTION-LOG;
                }
                container detail {
                  description
                    "Show execution request status summary
                     about a particular execution request";
                  uses SCRIPT-EXECUTION-DETAIL;
                }
                container summary {
                  description
                    "Show execution request status summary
                     about a particular execution request";
                  uses SCRIPT-EXECUTION-SUMMARY;
                }
                container error {
                  description
                    "Detailed error log for script execution";
                  uses SCRIPT-EXECUTION-ERROR-LOG;
                }
                leaf last-num {
                  type uint32;
                  description
                    "Last given number of executed requests";
                }
              }
            }
          }
          container output {
            description
              "Detailed output log for script execution";
            uses SCRIPT-EXECUTION-OUTPUT-LOG;
          }
          container request-show-del {
            description
              "Status Reverse Details about a particular
               execution request";
            container summary {
              description
                "Show execution request status summary  about
                 a particular execution request";
              uses SCRIPT-EXECUTION-SUMMARY;
            }
          }
          container output-error {
            description
              "Detailed output and error log for script
               execution";
            uses SCRIPT-EXECUTION-LOG;
          }
          container detail {
            description
              "Show execution request status summary  about
               a particular execution request";
            uses SCRIPT-EXECUTION-DETAIL;
          }
          container request-lasts {
            description
              "Status Reverse Details about a particular
               execution request";
            list request-last {
              key "last-num";
              description
                "Information about last request";
              container output {
                description
                  "Detailed output log for script execution";
                uses SCRIPT-EXECUTION-OUTPUT-LOG;
              }
              container output-error {
                description
                  "Detailed output and error log for script
                   execution";
                uses SCRIPT-EXECUTION-LOG;
              }
              container detail {
                description
                  "Show execution request status summary
                   about a particular execution request";
                uses SCRIPT-EXECUTION-DETAIL;
              }
              container request-last-names {
                description
                  "Status Reverse Details about a particular
                   execution request";
                list request-last-name {
                  key "name-str";
                  description
                    "Information about a particular request";
                  container output {
                    description
                      "Detailed output log for script execution";
                    uses SCRIPT-EXECUTION-OUTPUT-LOG;
                  }
                  container output-error {
                    description
                      "Detailed output and error log for script
                       execution";
                    uses SCRIPT-EXECUTION-LOG;
                  }
                  container detail {
                    description
                      "Show execution request status summary
                       about a particular execution request";
                    uses SCRIPT-EXECUTION-DETAIL;
                  }
                  container summary {
                    description
                      "Show execution request status summary
                       about a particular execution request";
                    uses SCRIPT-EXECUTION-SUMMARY;
                  }
                  container request-last-name-show-del {
                    description
                      "Status Reverse Details about a particular
                       execution request";
                    container summary {
                      description
                        "Show execution request status summary
                         about a particular execution request";
                      uses SCRIPT-EXECUTION-SUMMARY;
                    }
                  }
                  container error {
                    description
                      "Detailed error log for script execution";
                    uses SCRIPT-EXECUTION-ERROR-LOG;
                  }
                  leaf name-str {
                    type xr:Cisco-ios-xr-string;
                    description
                      "Show Execution Name string";
                  }
                }
              }
              container summary {
                description
                  "Show execution request status summary
                   about a particular execution request";
                uses SCRIPT-EXECUTION-SUMMARY;
              }
              container error {
                description
                  "Detailed error log for script execution";
                uses SCRIPT-EXECUTION-ERROR-LOG;
              }
              leaf last-num {
                type uint32;
                description
                  "Last given number of executed requests";
              }
            }
          }
          container summary {
            description
              "Summary information of particular execution
               request id";
            uses SCRIPT-EXECUTION-SUMMARY;
          }
          container error {
            description
              "Detailed error log for script execution";
            uses SCRIPT-EXECUTION-ERROR-LOG;
          }
          leaf request-id {
            type xr:Cisco-ios-xr-string;
            description
              "Show Execution Request ID";
          }
        }
      }
      container names {
        description
          "Execution information about specific script";
        list name {
          key "name-str";
          description
            "Information about a particular request";
          container output {
            description
              "Detailed output log for script execution";
            uses SCRIPT-EXECUTION-OUTPUT-LOG;
          }
          container detail-show-del {
            description
              "Detailed information of a particular
               execution request";
            uses SCRIPT-EXECUTION-DETAIL;
          }
          container output-error {
            description
              "Detailed output and error log for script
               execution";
            uses SCRIPT-EXECUTION-LOG;
          }
          container detail {
            description
              "Detailed information of a particular
               execution request";
            uses SCRIPT-EXECUTION-DETAIL;
          }
          container name-show-del {
            description
              "Status Reverse Details about a particular
               execution request";
            container summary {
              description
                "Show execution request status summary  about
                 a particular execution request";
              uses SCRIPT-EXECUTION-SUMMARY;
            }
          }
          container summary {
            description
              "Information about script execution for a
               particular script";
            uses SCRIPT-EXECUTION-SUMMARY;
          }
          container error {
            description
              "Detailed error log for script execution";
            uses SCRIPT-EXECUTION-ERROR-LOG;
          }
          leaf name-str {
            type xr:Cisco-ios-xr-string;
            description
              "Show Execution Name string";
          }
        }
      }
      container reverse {
        description
          "Information about last request";
        container reverse-names {
          description
            "Status Reverse Details about a particular
             execution request";
          list reverse-name {
            key "name-str";
            description
              "Information about a particular request";
            container reverse-name-show-del {
              description
                "Status Reverse Details about a particular
                 execution request";
              container summary {
                description
                  "Show execution request status summary
                   about a particular execution request";
                uses SCRIPT-EXECUTION-SUMMARY;
              }
            }
            container output {
              description
                "Detailed output log for script execution";
              uses SCRIPT-EXECUTION-OUTPUT-LOG;
            }
            container output-error {
              description
                "Detailed output and error log for script
                 execution";
              uses SCRIPT-EXECUTION-LOG;
            }
            container detail {
              description
                "Show execution request status summary  about
                 a particular execution request";
              uses SCRIPT-EXECUTION-DETAIL;
            }
            container summary {
              description
                "Show execution request status summary  about
                 a particular execution request";
              uses SCRIPT-EXECUTION-SUMMARY;
            }
            container error {
              description
                "Detailed error log for script execution";
              uses SCRIPT-EXECUTION-ERROR-LOG;
            }
            leaf name-str {
              type xr:Cisco-ios-xr-string;
              description
                "Show Execution Name string";
            }
          }
        }
        container output {
          description
            "Detailed output log for script execution";
          uses SCRIPT-EXECUTION-OUTPUT-LOG;
        }
        container reverse-lasts {
          description
            "Status Reverse Details about a particular
             execution request";
          list reverse-last {
            key "last-num";
            description
              "Information about last request";
            container output {
              description
                "Detailed output log for script execution";
              uses SCRIPT-EXECUTION-OUTPUT-LOG;
            }
            container output-error {
              description
                "Detailed output and error log for script
                 execution";
              uses SCRIPT-EXECUTION-LOG;
            }
            container detail {
              description
                "Show execution request status summary  about
                 a particular execution request";
              uses SCRIPT-EXECUTION-DETAIL;
            }
            container reverse-last-names {
              description
                "Status Details about a particular execution
                 request";
              list reverse-last-name {
                key "name-str";
                description
                  "Information about a particular request";
                container reverse-last-name-show-del {
                  description
                    "Status Details about a particular
                     execution request";
                  container summary {
                    description
                      "Show execution request status summary
                       about a particular execution request";
                    uses SCRIPT-EXECUTION-SUMMARY;
                  }
                }
                container output {
                  description
                    "Detailed output log for script execution";
                  uses SCRIPT-EXECUTION-OUTPUT-LOG;
                }
                container output-error {
                  description
                    "Detailed output and error log for script
                     execution";
                  uses SCRIPT-EXECUTION-LOG;
                }
                container detail {
                  description
                    "Show execution request status summary
                     about a particular execution request";
                  uses SCRIPT-EXECUTION-DETAIL;
                }
                container summary {
                  description
                    "Show execution request status summary
                     about a particular execution request";
                  uses SCRIPT-EXECUTION-SUMMARY;
                }
                container error {
                  description
                    "Detailed error log for script execution";
                  uses SCRIPT-EXECUTION-ERROR-LOG;
                }
                leaf name-str {
                  type xr:Cisco-ios-xr-string;
                  description
                    "Show Execution Name string";
                }
              }
            }
            container summary {
              description
                "Show execution request status summary  about
                 a particular execution request";
              uses SCRIPT-EXECUTION-SUMMARY;
            }
            container error {
              description
                "Detailed error log for script execution";
              uses SCRIPT-EXECUTION-ERROR-LOG;
            }
            leaf last-num {
              type uint32;
              description
                "Last given number of executed requests";
            }
          }
        }
        container output-error {
          description
            "Detailed output and error log for script
             execution";
          uses SCRIPT-EXECUTION-LOG;
        }
        container detail {
          description
            "Detailed information of a particular execution
             request";
          uses SCRIPT-EXECUTION-DETAIL;
        }
        container summary {
          description
            "Information about script execution for last
             script request executed";
          uses SCRIPT-EXECUTION-SUMMARY;
        }
        container error {
          description
            "Detailed error log for script execution";
          uses SCRIPT-EXECUTION-ERROR-LOG;
        }
        container reverse-show-del {
          description
            "Status Reverse Details about a particular
             execution request";
          container summary {
            description
              "Show execution request status summary  about
               a particular execution request";
            uses SCRIPT-EXECUTION-SUMMARY;
          }
        }
      }
      container summary {
        description
          "Summary information about script execution";
        uses SCRIPT-EXECUTION-SUMMARY;
      }
      container error {
        description
          "Error log for script execution";
        uses SCRIPT-EXECUTION-ERROR-LOG;
      }
      container execution-show-del {
        description
          "Deleted information about script execution";
        container summary {
          description
            "Deleted information for script execution";
          uses SCRIPT-EXECUTION-SUMMARY;
        }
      }
      container detail-showdel {
        description
          "Detailed information about script execution";
        uses SCRIPT-EXECUTION-DETAIL;
      }
    }
  }
}
