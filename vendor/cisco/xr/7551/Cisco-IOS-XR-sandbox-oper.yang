module Cisco-IOS-XR-sandbox-oper {
  namespace "http://cisco.com/ns/yang/Cisco-IOS-XR-sandbox-oper";
  prefix sandbox-oper;

  import cisco-semver {
    prefix semver;
  }
  include Cisco-IOS-XR-sandbox-oper-sub1 {
    revision-date 2022-07-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sandbox package operational data.
     
     This module contains definitions
     for the following management objects:
       sandbox: Sandbox Operational data space
     
     Copyright (c) 2013-2022 by Cisco Systems, Inc.
     All rights reserved.";

  revision 2022-07-08 {
    description
      "sandbox show CLI added";
    semver:module-version "1.0.0";
  }
  revision 2019-04-05 {
    description
      "Establish semantic version baseline.";
  }
  revision 2015-11-09 {
    description
      "IOS XR 6.0 revision.";
  }

  container sandbox {
    config false;
    description
      "Sandbox Operational data space";
    container info {
      description
        "Info data bag";
      uses SANDBOXMGR-INTERNAL-INFO;
    }
    container detail {
      description
        "Detail data bag";
      uses SANDBOXMGR-DETAILS;
    }
    container services {
      description
        "Services data bag";
      uses SANDBOXMGR-SERVICES;
    }
  }
}
