module Cisco-IOS-XR-mpls-ldp-mldp-oper {
  namespace "http://cisco.com/ns/yang/Cisco-IOS-XR-mpls-ldp-mldp-oper";
  prefix mpls-ldp-mldp-oper;

  import ietf-inet-types {
    prefix inet;
  }
  import Cisco-IOS-XR-types {
    prefix xr;
  }
  import cisco-semver {
    prefix semver;
  }
  include Cisco-IOS-XR-mpls-ldp-mldp-oper-sub1 {
    revision-date 2022-01-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-ldp-mldp package operational data.
     
     This module contains definitions
     for the following management objects:
       mpls-mldp: MPLS MLDP operational data
     
     Copyright (c) 2013-2022 by Cisco Systems, Inc.
     All rights reserved.";

  revision 2022-01-27 {
    description
      "Modified arg type for mldp database root address in schema and bgen files. from ipaddress to string";
    semver:module-version "1.2.1m";
  }
  revision 2021-04-27 {
    description
      "Added mLDP flex-algo";
    semver:module-version "1.2.0";
  }
  revision 2020-10-18 {
    description
      "Backward compatible removal in telemetry event Cisco-IOS-XR-types, event-telemetry was removed.";
    semver:module-version "1.1.0";
  }
  revision 2019-04-05 {
    description
      "Establish semantic version baseline.";
    semver:module-version "1.1.0";
  }
  revision 2018-08-30 {
    description
      "Operational Yang model for mLDP.";
  }
  revision 2015-11-09 {
    description
      "IOS XR 6.0 revision.";
  }

  typedef Lsp {
    type enumeration {
      enum "invalid" {
        value 0;
        description
          "Invalid LSP Type";
      }
      enum "any" {
        value 1;
        description
          "Any LSP Type";
      }
      enum "p2mp" {
        value 2;
        description
          "P2MP LSP Type";
      }
      enum "mp2mp-upstream" {
        value 3;
        description
          "MP2MP Upstream LSP Type";
      }
      enum "mp2mp-downstream" {
        value 4;
        description
          "MP2MP Downstream LSP Type";
      }
      enum "mp2mp" {
        value 5;
        description
          "MP2MP LSP Type";
      }
    }
    description
      "Lsp";
  }

  typedef Opaque {
    type enumeration {
      enum "static-id" {
        value 0;
        description
          "Static ID Opaque Type";
      }
      enum "global-id" {
        value 1;
        description
          "Global ID Opaque Type";
      }
      enum "vpn-id" {
        value 2;
        description
          "VPN ID Opaque Type";
      }
      enum "ipv4" {
        value 3;
        description
          "IPv4 Opaque Type";
      }
      enum "ipv6" {
        value 4;
        description
          "IPv6 Opaque Type";
      }
      enum "ipv4-bidir" {
        value 5;
        description
          "IPv4 Bidir Opaque Type";
      }
      enum "ipv6-bidir" {
        value 6;
        description
          "IPv6 Bidir Opaque Type";
      }
      enum "recursive" {
        value 7;
        description
          "Recursive Opaque Type";
      }
      enum "recursive-route-distinguisher" {
        value 8;
        description
          "Recursive Route Distinguisher Opaque Type";
      }
      enum "vpnv4" {
        value 250;
        description
          "VPNv4 Opaque Type";
      }
      enum "vpnv6" {
        value 251;
        description
          "VPNv6 Opaque Type";
      }
    }
    description
      "Opaque";
  }

  grouping VRF-TABLE {
    description
      "Common node of active, standby";
    container vrfs {
      description
        "VRF specific operational data";
      list vrf {
        key "vrf-name";
        description
          "Operational data for given VRF";
        leaf vrf-name {
          type xr:Cisco-ios-xr-string {
            length "1..32";
          }
          description
            "VRF Name";
        }
        uses NEIGHBOR-ADDRESS-TABLE;
        uses DATABASE-TABLE;
        uses ROOT-ADDRESS-TABLE;
        uses CONTEXT;
        uses NEIGHBOR-TABLE;
      }
    }
  }

  grouping MFI-ENTRY-TABLE {
    description
      "Common node of active, standby";
    container mfi-entries {
      description
        "MLDP MFI Table";
      list mfi-entry {
        key "mpls-label";
        description
          "MLDP MFI Information";
        leaf mpls-label {
          type uint32;
          description
            "MPLS Label";
        }
        uses MLDP-MFI-RW-BAG;
      }
    }
  }

  grouping LSM-ID-TABLE {
    description
      "Common node of active, standby";
    container lsm-ids {
      description
        "MLDP LSM-ID";
      list lsm-id {
        key "lsm-id";
        description
          "MLDP LSMID Information";
        leaf lsm-id {
          type uint32;
          description
            "LSM ID";
        }
        uses MLDP-DATABASE-BAG;
      }
    }
  }

  grouping NEIGHBOR-ADDRESS-TABLE {
    description
      "Common node of vrf, default-context";
    container neighbor-addresses {
      description
        "MLDP Neighbors Addresses";
      list neighbor-address {
        key "address";
        description
          "Neighbor Address Information";
        leaf address {
          type inet:ipv4-address-no-zone;
          description
            "The Neighbor IP address";
        }
        uses MLDP-NEIGHBOR-ADDR-BAG;
      }
    }
  }

  grouping ROOT-ADDRESS-TABLE {
    description
      "Common node of vrf, default-context";
    container root-addresses {
      description
        "MLDP Root Table";
      list root-address {
        key "root-address";
        description
          "MLDP Root Information";
        leaf root-address {
          type inet:ipv4-address-no-zone;
          description
            "Root address";
        }
        uses MLDP-ROOT-BAG;
      }
    }
  }

  grouping FIB-REGDB-TABLE {
    description
      "Common node of active, standby";
    container labels {
      description
        "MLDP Regdb Table";
      list label {
        key "label";
        description
          "MLDP Label Information";
        leaf label {
          type uint32;
          description
            "LABEL ID";
        }
        uses MLDP-FIB-REGDB-BAG;
      }
    }
  }

  grouping STATUS {
    description
      "Common node of active, standby";
    container status {
      description
        "MLDP Status";
      uses MLDP-STATUS-BAG;
    }
  }

  grouping CONTEXT {
    description
      "Common node of vrf, default-context";
    container context {
      description
        "MLDP Context";
      uses MLDP-CONTEXT-BAG;
    }
  }

  grouping DATABASE-TABLE {
    description
      "Common node of vrf, default-context";
    container databases {
      description
        "MLDP Database";
      list database {
        key "lsp-type root-address opaque-type opaque-value-string";
        description
          "MLDP Database Information";
        leaf lsp-type {
          type Lsp;
          description
            "LSP Type";
        }
        leaf root-address {
          type inet:ipv4-address-no-zone;
          description
            "Root address";
        }
        leaf opaque-type {
          type Opaque;
          description
            "Opaque Type";
        }
        leaf opaque-value-string {
          type xr:Cisco-ios-xr-string {
            length "1..255";
          }
          description
            "OpaqueValue";
        }
        uses MLDP-DATABASE-BAG;
      }
    }
  }

  grouping LSP-BINDINGS-TABLE {
    description
      "Common node of active, standby";
    container lsp-bindings {
      description
        "MLDP LSP Bindings Table";
      list lsp-binding {
        key "lsm-id";
        description
          "MLDP LSP Binding Information";
        leaf lsm-id {
          type uint32;
          description
            "LSM ID";
        }
        uses MLDP-BINDING-LSP-BAG;
      }
    }
  }

  grouping DEFAULT-CONTEXT {
    description
      "Common node of active, standby";
    container default-context {
      description
        "Default context specific operational data";
      uses NEIGHBOR-ADDRESS-TABLE;
      uses DATABASE-TABLE;
      uses ROOT-ADDRESS-TABLE;
      uses CONTEXT;
      uses NEIGHBOR-TABLE;
    }
  }

  grouping NEIGHBOR-TABLE {
    description
      "Common node of vrf, default-context";
    container neighbors {
      description
        "MLDP Neighbors";
      list neighbor {
        key "address";
        description
          "Neighbor Information";
        leaf address {
          type inet:ipv4-address-no-zone;
          description
            "The Neighbor IP address";
        }
        uses MLDP-NEIGHBOR-BAG;
      }
    }
  }

  container mpls-mldp {
    config false;
    description
      "MPLS MLDP operational data";
    container active {
      description
        "Active MPLS MLDP operational data";
      uses STATUS;
      uses MFI-ENTRY-TABLE;
      uses LSP-BINDINGS-TABLE;
      uses LSM-ID-TABLE;
      uses VRF-TABLE;
      uses FIB-REGDB-TABLE;
      uses DEFAULT-CONTEXT;
    }
    container standby {
      description
        "Standby MPLS MLDP operational data";
      uses STATUS;
      uses MFI-ENTRY-TABLE;
      uses LSP-BINDINGS-TABLE;
      uses LSM-ID-TABLE;
      uses VRF-TABLE;
      uses FIB-REGDB-TABLE;
      uses DEFAULT-CONTEXT;
    }
  }
}
