module Cisco-IOS-XR-um-cont-optics-host-loopback-cfg {
  namespace "http://cisco.com/ns/yang/Cisco-IOS-XR-um-cont-optics-host-loopback-cfg";
  prefix um-cont-optics-host-loopback-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-optics-host-loopback package configuration.
     
     This YANG module augments the
     modules with configuration data.
     
     Copyright (c) 2023 by Cisco Systems, Inc.
     All rights reserved.";

  revision 2023-03-08 {
    description
      "Initial release";
    semver:module-version "1.0.0";
  }

  feature optics {
    description
      "optics";
  }

  grouping CONT-BODY {
    description
      "Grouping for controller";
    container host {
      when "../a1:controller-name[starts-with(text(),'Optics')]" {
        tailf:dependency "../a1:controller-name";
      }
      if-feature "optics";
      description
        "Configure loopback host mode ";
      leaf loopback {
        type enumeration {
          enum "internal" {
            value 1;
            description
              "Select internal loopback host mode";
          }
          enum "line" {
            value 2;
            description
              "Select line loopback host mode";
          }
        }
        description
          "loopback for host mode";
      }
    }
  }

  augment "/a1:interfaces/a1:controller" {
    description
      "This augment extends active nodes configuration";
    uses CONT-BODY;
  }
  augment "/a1:interfaces/a1:controller-preconfigure" {
    description
      "This augment extends preconfigured nodes
       configuration";
    uses CONT-BODY;
  }
}
