submodule Cisco-IOS-XR-controller-optics-oper-sub2 {
  belongs-to Cisco-IOS-XR-controller-optics-oper {
    prefix Cisco-IOS-XR-controller-optics-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-optics package operational data.
     
     Copyright (c) 2013-2023 by Cisco Systems, Inc.
     All rights reserved.";

  revision 2023-03-23 {
    description
      "Added support for optics observable data.
       2023-02-24
         Leaf loopback-host and loopback-media added for optics controller.
       2022-07-28
         enum added for new Optics Phy Type for 400G AEC
       2022-02-03
         Added power fields in mW unit in Grey lane data
       2022-01-27
         Added power fields for mW unit in optics transponder information
       2022-01-07
         enum added for new Optics Phy Type for 400G SR8 module
       2022-01-06
         New Enum OPTICS_PHY_TYPE_1G_LH are added in enum OpticsPhyType
       2021-12-03
         enumadded for new Optics Phy Type for 200G FR4 modules
       2021-11-22
         Added threshold fields for mW unit in optics transponder information
       2021-11-03
         Added Dac Rate field in optics_edm_info.";
    semver:module-version "5.1.0";
  }
  revision 2021-09-17 {
    description
      "enumadded for new Optics Phy Type for 200G Cu, 200G AOC, 2x200G CU and 2x200G AOC modules
       2021-07-30
          New Enum OPTICS_PHY_TYPE_100G_ERL are added in enum OpticsPhyType
       2021-07-06
          enum added for new Optics Phy Type for 4x100G LR module
       2021-06-22
          New OPTICS_PHY_TYPE_16G_FC,OPTICS_PHY_TYPE_32G_FC are added in enum OpticsPhyType
       2021-06-21
          New Enums added for FibreChannel 16G and 32G Optics Phy type
       2021-06-10
          New parameters added in bag
       2021-05-27
          DAC rate and Laser temperature and laser age Added for Optics Controller";
    semver:module-version "5.0.0";
  }
  revision 2021-04-14 {
    description
      "New Enums added for Multirate Optics Phy type
       2021-03-22
           New Enums added for Optics Phy type
       2021-02-23
           enum added for new Optics Phy Type for 400G LR4 module
       2021-02-19
           enum added for 1 new Optics Phy Type and new value added to enum EthernetPmdType
       2021-02-17
           New OPTICS_ETH_100GBASE_DR_S added to enum EthernetPmdType
       2021-01-18
           Added 2 enums for New FEC Type.
       2020-12-23
           New value added to enum EthernetPmdType
       2020-11-24
           Enum value in optics_modulation_type is changed from MODE_16QAM_32QAM to MOD_16QAM_32QAM
       2020-11-10
           enum added for 1 new Optics Phy Type for 100G DR-S optics module
       2020-09-10
           removed optics_edm_fastpoll_info and added new bag optics_edm_fastpoll_data
       2020-08-02
           New values added to enum FiberConnectorType
       2020-07-24
           New value added in optics yang for FastPollInfo
       2020-07-14
           New value added to enum EthernetPmdType";
    semver:module-version "4.0.0";
  }
  revision 2020-04-26 {
    description
      "New value added to enum EthernetPmdType
       2020-02-24
         enum added for OTN Application code.
       2020-02-19
         enum added for 1 new Optics Phy Type
       2020-01-31
         enum added for 1 new Optics Phy Type
       2020-01-27
         Added new parameters in optics bag to display parameters which are not configurable
       2019-12-05
         enum added for 2 new OTN Application codes.
       2019-11-30
         Back Reflection data field is added in bag.
       2019-09-30
         chan_num data field is added to support L-Band frequency range.";
    semver:module-version "3.0.0";
  }
  revision 2019-04-05 {
    description
      "Establish semantic version baseline.";
    semver:module-version "2.0.0";
  }
  revision 2017-09-07 {
    description
      "Fixed type translation error.";
  }
  revision 2017-05-01 {
    description
      "Fixing backward compatibility error in module.";
  }
  revision 2015-11-09 {
    description
      "IOS XR 6.0 revision.";
  }

  typedef Observable-lane-id {
    type enumeration {
      enum "lane0" {
        value 0;
        description
          "Lane0";
      }
      enum "lane1" {
        value 1;
        description
          "Lane1";
      }
      enum "lane2" {
        value 2;
        description
          "Lane2";
      }
      enum "lane3" {
        value 3;
        description
          "Lane3";
      }
      enum "lane4" {
        value 4;
        description
          "Lane4";
      }
      enum "lane5" {
        value 5;
        description
          "Lane5";
      }
      enum "lane6" {
        value 6;
        description
          "Lane6";
      }
      enum "lane7" {
        value 7;
        description
          "Lane7";
      }
      enum "lane8" {
        value 8;
        description
          "Lane8";
      }
      enum "lane9" {
        value 9;
        description
          "Lane9";
      }
      enum "lane10" {
        value 10;
        description
          "Lane10";
      }
      enum "lane11" {
        value 11;
        description
          "Lane11";
      }
      enum "lane12" {
        value 12;
        description
          "Lane12";
      }
      enum "module" {
        value 255;
        description
          "Module";
      }
    }
    description
      "Enumeration of lane/module identifiers";
  }

  grouping FERC-CURR-HOST-INPUT-INFO {
    description
      "FERC current host input information";
    leaf lane-id {
      type Observable-lane-id;
      description
        "Lane/module identifier";
    }
    leaf value {
      type uint64;
      description
        "Current value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-CURR-MEDIA-INPUT-INFO {
    description
      "FERC current media input information";
    leaf lane-id {
      type Observable-lane-id;
      description
        "Lane/module identifier";
    }
    leaf value {
      type uint64;
      description
        "Current value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-AVG-HOST-INPUT-INFO {
    description
      "FERC average host input information";
    leaf lane-id {
      type Observable-lane-id;
      description
        "Lane/module identifier";
    }
    leaf value {
      type uint64;
      description
        "Average value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-AVG-MEDIA-INPUT-INFO {
    description
      "FERC average media input information";
    leaf lane-id {
      type Observable-lane-id;
      description
        "Lane/module identifier";
    }
    leaf value {
      type uint64;
      description
        "Average value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-MAX-HOST-INPUT-INFO {
    description
      "FERC maximum host input information";
    leaf lane-id {
      type Observable-lane-id;
      description
        "Lane/module identifier";
    }
    leaf value {
      type uint64;
      description
        "Maximum value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-MAX-MEDIA-INPUT-INFO {
    description
      "FERC maximum media input information";
    leaf lane-id {
      type Observable-lane-id;
      description
        "Lane/module identifier";
    }
    leaf value {
      type uint64;
      description
        "Maximum value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-MIN-HOST-INPUT-INFO {
    description
      "FERC minimum host input information";
    leaf lane-id {
      type Observable-lane-id;
      description
        "Lane/module identifier";
    }
    leaf value {
      type uint64;
      description
        "Minimum value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping FERC-MIN-MEDIA-INPUT-INFO {
    description
      "FERC minimum media input information";
    leaf lane-id {
      type Observable-lane-id;
      description
        "Lane/module identifier";
    }
    leaf value {
      type uint64;
      description
        "Minimum value";
    }
    leaf low-warning-val {
      type uint64;
      description
        "Low warning threshold value";
    }
    leaf high-warning-val {
      type uint64;
      description
        "High warning threshold value";
    }
    leaf low-alarm-val {
      type uint64;
      description
        "Low alarm threshold value";
    }
    leaf high-alarm-val {
      type uint64;
      description
        "High alarm threshold value";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-CURR-HOST-INPUT-INFO {
    description
      "Pre-FEC BER current host input information";
    leaf lane-id {
      type Observable-lane-id;
      description
        "Lane/module identifier";
    }
    leaf value {
      type uint64;
      description
        "Current value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-CURR-MEDIA-INPUT-INFO {
    description
      "Pre-FEC BER current media input information";
    leaf lane-id {
      type Observable-lane-id;
      description
        "Lane/module identifier";
    }
    leaf value {
      type uint64;
      description
        "Current value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-AVG-HOST-INPUT-INFO {
    description
      "Pre-FEC BER average host input information";
    leaf lane-id {
      type Observable-lane-id;
      description
        "Lane/module identifier";
    }
    leaf value {
      type uint64;
      description
        "Average value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-AVG-MEDIA-INPUT-INFO {
    description
      "Pre-FEC BER average media input information";
    leaf lane-id {
      type Observable-lane-id;
      description
        "Lane/module identifier";
    }
    leaf value {
      type uint64;
      description
        "Average value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-MAX-HOST-INPUT-INFO {
    description
      "Pre-FEC BER maximum host input information";
    leaf lane-id {
      type Observable-lane-id;
      description
        "Lane/module identifier";
    }
    leaf value {
      type uint64;
      description
        "Maximum value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-MAX-MEDIA-INPUT-INFO {
    description
      "Pre-FEC BER maximum media input information";
    leaf lane-id {
      type Observable-lane-id;
      description
        "Lane/module identifier";
    }
    leaf value {
      type uint64;
      description
        "Maximum value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-MIN-HOST-INPUT-INFO {
    description
      "Pre-FEC BER minimum host input information";
    leaf lane-id {
      type Observable-lane-id;
      description
        "Lane/module identifier";
    }
    leaf value {
      type uint64;
      description
        "Minimum value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PRE-FEC-BER-MIN-MEDIA-INPUT-INFO {
    description
      "Pre-FEC BER minimum media input information";
    leaf lane-id {
      type Observable-lane-id;
      description
        "Lane/module identifier";
    }
    leaf value {
      type uint64;
      description
        "Minimum value scaled by 10^18";
    }
    leaf low-warning-val {
      type uint64;
      description
        "Low warning threshold value scaled by 10^18";
    }
    leaf high-warning-val {
      type uint64;
      description
        "High warning threshold value scaled by 10^18";
    }
    leaf low-alarm-val {
      type uint64;
      description
        "Low alarm threshold value scaled by 10^18";
    }
    leaf high-alarm-val {
      type uint64;
      description
        "High alarm threshold value scaled by 10^18";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PAM4-LVL-TRANSITION-PARAM-HOST-INPUT-INFO {
    description
      "PAM4 level transition parameter host input
       information";
    leaf lane-id {
      type Observable-lane-id;
      description
        "Lane/module identifier";
    }
    leaf value {
      type uint16;
      description
        "Current value in units of 1/256 dB";
    }
    leaf low-warning-val {
      type uint16;
      description
        "Low warning threshold value in units of 1/256 dB";
    }
    leaf high-warning-val {
      type uint16;
      description
        "High warning threshold value in units of 1/256
         dB";
    }
    leaf low-alarm-val {
      type uint16;
      description
        "Low alarm threshold value in units of 1/256 dB";
    }
    leaf high-alarm-val {
      type uint16;
      description
        "High alarm threshold value in units of 1/256 dB";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping PAM4-LVL-TRANSITION-PARAM-MEDIA-INPUT-INFO {
    description
      "PAM4 level transition parameter media input
       information";
    leaf lane-id {
      type Observable-lane-id;
      description
        "Lane/module identifier";
    }
    leaf value {
      type uint16;
      description
        "Current value in units of 1/256 dB";
    }
    leaf low-warning-val {
      type uint16;
      description
        "Low warning threshold value in units of 1/256 dB";
    }
    leaf high-warning-val {
      type uint16;
      description
        "High warning threshold value in units of 1/256
         dB";
    }
    leaf low-alarm-val {
      type uint16;
      description
        "Low alarm threshold value in units of 1/256 dB";
    }
    leaf high-alarm-val {
      type uint16;
      description
        "High alarm threshold value in units of 1/256 dB";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping ESNR-HOST-INPUT-INFO {
    description
      "ESNR host input information";
    leaf lane-id {
      type Observable-lane-id;
      description
        "Lane/module identifier";
    }
    leaf value {
      type uint16;
      description
        "Current value in units of 1/256 dB";
    }
    leaf low-warning-val {
      type uint16;
      description
        "Low warning threshold value in units of 1/256 dB";
    }
    leaf high-warning-val {
      type uint16;
      description
        "High warning threshold value in units of 1/256
         dB";
    }
    leaf low-alarm-val {
      type uint16;
      description
        "Low alarm threshold value in units of 1/256 dB";
    }
    leaf high-alarm-val {
      type uint16;
      description
        "High alarm threshold value in units of 1/256 dB";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping ESNR-MEDIA-INPUT-INFO {
    description
      "ESNR media input information";
    leaf lane-id {
      type Observable-lane-id;
      description
        "Lane/module identifier";
    }
    leaf value {
      type uint16;
      description
        "Current value in units of 1/256 dB";
    }
    leaf low-warning-val {
      type uint16;
      description
        "Low warning threshold value in units of 1/256 dB";
    }
    leaf high-warning-val {
      type uint16;
      description
        "High warning threshold value in units of 1/256
         dB";
    }
    leaf low-alarm-val {
      type uint16;
      description
        "Low alarm threshold value in units of 1/256 dB";
    }
    leaf high-alarm-val {
      type uint16;
      description
        "High alarm threshold value in units of 1/256 dB";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping LASER-TEMPERATURE-INFO {
    description
      "Laser temperature information";
    leaf lane-id {
      type Observable-lane-id;
      description
        "Lane/module identifier";
    }
    leaf value {
      type int16;
      description
        "Current value in units of 1/256 C";
    }
    leaf low-warning-val {
      type int16;
      description
        "Low warning threshold value in units of 1/256 C";
    }
    leaf high-warning-val {
      type int16;
      description
        "High warning threshold value in units of 1/256 C";
    }
    leaf low-alarm-val {
      type int16;
      description
        "Low alarm threshold value in units of 1/256 C";
    }
    leaf high-alarm-val {
      type int16;
      description
        "High alarm threshold value in units of 1/256 C";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping LASER-FREQUENCY-ERROR-INFO {
    description
      "Laser frequency error information";
    leaf lane-id {
      type Observable-lane-id;
      description
        "Lane/module identifier";
    }
    leaf value {
      type int16;
      description
        "Current value in units of 10 Mhz";
    }
    leaf low-warning-val {
      type int16;
      description
        "Low warning threshold value in units of 10 Mhz";
    }
    leaf high-warning-val {
      type int16;
      description
        "High warning threshold value in units of 10 Mhz";
    }
    leaf low-alarm-val {
      type int16;
      description
        "Low alarm threshold value in units of 10 Mhz";
    }
    leaf high-alarm-val {
      type int16;
      description
        "High alarm threshold value in units of 10 Mhz";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping TEC-CURRENT-INFO {
    description
      "TEC current information";
    leaf lane-id {
      type Observable-lane-id;
      description
        "Lane/module identifier";
    }
    leaf value {
      type int16;
      description
        "Current value in 100%/32767 increments";
    }
    leaf low-warning-val {
      type int16;
      description
        "Low warning threshold value in 100%/32767
         increments";
    }
    leaf high-warning-val {
      type int16;
      description
        "High warning threshold value in 100%/32767
         increments";
    }
    leaf low-alarm-val {
      type int16;
      description
        "Low alarm threshold value in 100%/32767
         increments";
    }
    leaf high-alarm-val {
      type int16;
      description
        "High alarm threshold value in 100%/32767
         increments";
    }
    leaf low-warning {
      type boolean;
      description
        "Low warning threshold crossing";
    }
    leaf high-warning {
      type boolean;
      description
        "High warning threshold crossing";
    }
    leaf low-alarm {
      type boolean;
      description
        "Low alarm threshold crossing";
    }
    leaf high-alarm {
      type boolean;
      description
        "High alarm threshold crossing";
    }
  }

  grouping LASER-AGE-INFO {
    description
      "Laser age information";
    leaf lane-id {
      type Observable-lane-id;
      description
        "Laser age lane/module identifier";
    }
    leaf value {
      type uint16;
      description
        "Laser age current value in %";
    }
    leaf low-warning-val {
      type uint16;
      description
        "Laser age low warning threshold value in %";
    }
    leaf high-warning-val {
      type uint16;
      description
        "Laser age high warning threshold value in %";
    }
    leaf low-alarm-val {
      type uint16;
      description
        "Laser age low alarm threshold value in %";
    }
    leaf high-alarm-val {
      type uint16;
      description
        "Laser age high alarm threshold value in %";
    }
    leaf low-warning {
      type boolean;
      description
        "Laser age low warning threshold crossing";
    }
    leaf high-warning {
      type boolean;
      description
        "Laser age high warning threshold crossing";
    }
    leaf low-alarm {
      type boolean;
      description
        "Laser age low alarm threshold crossing";
    }
    leaf high-alarm {
      type boolean;
      description
        "Laser age high alarm threshold crossing";
    }
  }

  grouping OPTICS-OBSERVABLE-LANE-INFO {
    description
      "Lane/module level information about observables";
    container laser-age {
      description
        "Information about laser age";
      uses LASER-AGE-INFO;
    }
    container tec-current {
      description
        "Information about TEC current";
      uses TEC-CURRENT-INFO;
    }
    container laser-frequency-error {
      description
        "Information about laser frequency error";
      uses LASER-FREQUENCY-ERROR-INFO;
    }
    container laser-temperature {
      description
        "Information about laser temperature";
      uses LASER-TEMPERATURE-INFO;
    }
    container esnr-media-input {
      description
        "Information about esnr media input";
      uses ESNR-MEDIA-INPUT-INFO;
    }
    container esnr-host-input {
      description
        "Information about esnr host input";
      uses ESNR-HOST-INPUT-INFO;
    }
    container pam4-lvl-trans-media-input {
      description
        "Information about PAM4 level transition
         parameter media input";
      uses PAM4-LVL-TRANSITION-PARAM-MEDIA-INPUT-INFO;
    }
    container pam4-lvl-trans-host-input {
      description
        "Information about PAM4 level transition
         parameter host input";
      uses PAM4-LVL-TRANSITION-PARAM-HOST-INPUT-INFO;
    }
    container pre-fec-ber-min-media-input {
      description
        "Information about pre-fec BER minimum media
         input";
      uses PRE-FEC-BER-MIN-MEDIA-INPUT-INFO;
    }
    container pre-fec-ber-min-host-input {
      description
        "Information about pre-fec BER minimum host input";
      uses PRE-FEC-BER-MIN-HOST-INPUT-INFO;
    }
    container pre-fec-ber-max-media-input {
      description
        "Information about pre-fec BER maximum media
         input";
      uses PRE-FEC-BER-MAX-MEDIA-INPUT-INFO;
    }
    container pre-fec-ber-max-host-input {
      description
        "Information about pre-fec BER maximum host input";
      uses PRE-FEC-BER-MAX-HOST-INPUT-INFO;
    }
    container pre-fec-ber-avg-media-input {
      description
        "Information about pre-fec BER average media
         input";
      uses PRE-FEC-BER-AVG-MEDIA-INPUT-INFO;
    }
    container pre-fec-ber-avg-host-input {
      description
        "Information about pre-fec BER average host input";
      uses PRE-FEC-BER-AVG-HOST-INPUT-INFO;
    }
    container pre-fec-ber-curr-media-input {
      description
        "Information about pre-fec BER current value
         media input";
      uses PRE-FEC-BER-CURR-MEDIA-INPUT-INFO;
    }
    container pre-fec-ber-curr-host-input {
      description
        "Information about pre-fec BER current value host
         input";
      uses PRE-FEC-BER-CURR-HOST-INPUT-INFO;
    }
    container ferc-min-media-input {
      description
        "Information about FERC minimum media input";
      uses FERC-MIN-MEDIA-INPUT-INFO;
    }
    container ferc-min-host-input {
      description
        "Information about FERC minimum Host Input";
      uses FERC-MIN-HOST-INPUT-INFO;
    }
    container ferc-max-media-input {
      description
        "Information about FERC maximum media input";
      uses FERC-MAX-MEDIA-INPUT-INFO;
    }
    container ferc-max-host-input {
      description
        "Information about FERC maximum host input";
      uses FERC-MAX-HOST-INPUT-INFO;
    }
    container ferc-avg-media-input {
      description
        "Information about FERC average media input";
      uses FERC-AVG-MEDIA-INPUT-INFO;
    }
    container ferc-avg-host-input {
      description
        "Information about FERC average host input";
      uses FERC-AVG-HOST-INPUT-INFO;
    }
    container ferc-curr-media-input {
      description
        "Information about FERC current value media input";
      uses FERC-CURR-MEDIA-INPUT-INFO;
    }
    container ferc-curr-host-input {
      description
        "Information about FERC current value host input";
      uses FERC-CURR-HOST-INPUT-INFO;
    }
  }
}
