submodule Cisco-IOS-XR-snmp-agent-oper-sub2 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2015 by Cisco Systems, Inc.
     All rights reserved.";

  revision "2015-01-07" {
    description
      "IOS XR 5.3.1 revision.";
  }

  typedef Dup-req-drop-status {
    type enumeration {
      enum disabled {
        description "Disabled";
      }
      enum enabled {
        description "Enabled";
      }
    }
    description "Dup req drop status";
  }

  grouping SNMP-STATISTICS {
    description "SNMP Statistics extension";
    leaf duplicate-request-status {
      xr:xr-xml-map "snmp:DuplicateRequestStatus";
      type Dup-req-drop-status;
      description "Duplicate requests drop feature status.";
    }
    leaf last-status-change-time {
      xr:xr-xml-map "snmp:LastStatusChangeTime";
      type string;
      description
        "Duplicate request drop feature last enable
        disable time (Day Mon Date HH:MM:SS)";
    }
    leaf duplicate-drop-configured-timeout {
      xr:xr-xml-map "snmp:DuplicateDropConfiguredTimeout";
      type uint32;
      description "Configured Duplicate Drop feature Timeout.";
    }
    leaf duplicate-dropped-requests {
      xr:xr-xml-map "snmp:DuplicateDroppedRequests";
      type uint32;
      description "Number of duplicate SNMP requests are dropped.";
    }
    leaf retry-processed-requests {
      xr:xr-xml-map "snmp:RetryProcessedRequests";
      type uint32;
      description "Number of Retry SNMP requests are Processed.";
    }
    leaf first-enable-time {
      xr:xr-xml-map "snmp:FirstEnableTime";
      type string;
      description
        "Duplicate request drop feature first  enable
        time (Day Mon Date HH:MM:SS)";
    }
    leaf latest-duplicate-dropped-requests {
      xr:xr-xml-map "snmp:LatestDuplicateDroppedRequests";
      type uint32;
      description
        "Number of duplicate SNMP requests dropped, from
        the last enable time.";
    }
    leaf latest-retry-processed-requests {
      xr:xr-xml-map "snmp:LatestRetryProcessedRequests";
      type uint32;
      description
        "Number of retry SNMP requests processed, from
        the last enable time.";
    }
    leaf duplicate-request-latest-enable-time {
      xr:xr-xml-map "snmp:DuplicateRequestLatestEnableTime";
      type string;
      description
        "Duplicate request drop feature last enable
        time(Day Mon Date HH:MM:SS)";
    }
    leaf duplicate-drop-enable-count {
      xr:xr-xml-map "snmp:DuplicateDropEnableCount";
      type uint32;
      description
        " Number of times duplicate request drop feature
        is enabled.";
    }
    leaf duplicate-drop-disable-count {
      xr:xr-xml-map "snmp:DuplicateDropDisableCount";
      type uint32;
      description
        " Number of times duplicate request drop feature
        is disabled.";
    }
  }

  grouping SNMP-MIB-INFO {
    description "SNMP MIB Information";
    leaf mib-name {
      xr:xr-xml-map "snmp:MIBName";
      type string;
      description "Name of the MIB module";
    }
    leaf dll-name {
      xr:xr-xml-map "snmp:DLLName";
      type string;
      description
        "MIB DLL filename, non-DLL MIBs will have no
        value";
    }
    leaf mib-config-filename {
      xr:xr-xml-map "snmp:MIBConfigFilename";
      type string;
      description
        "MIB config filename, non-DLL MIBs will have no
        value";
    }
    leaf is-mib-loaded {
      xr:xr-xml-map "snmp:IsMIBLoaded";
      type boolean;
      description
        "TRUE if MIB DLL is currently loaded, will always
        be TRUE for non-DLL MIBs";
    }
    leaf dll-capabilities {
      xr:xr-xml-map "snmp:DLLCapabilities";
      type uint32;
      description "DLL capabilities";
    }
    leaf trap-strings {
      xr:xr-xml-map "snmp:TrapStrings";
      type string;
      description "List of trapstring configured";
    }
    leaf timeout {
      xr:xr-xml-map "snmp:Timeout";
      type boolean;
      description "TRUE is mib is in phase 1 timeout";
    }
    leaf load-time {
      xr:xr-xml-map "snmp:LoadTime";
      type uint32;
      description "Load time";
    }
  }

  grouping SNMP-STATS {
    description "SNMP statistics";
    leaf packets-received {
      xr:xr-xml-map "snmp:PacketsReceived";
      type uint32;
      description "snmpInPkts";
    }
    leaf bad-versions-received {
      xr:xr-xml-map "snmp:BadVersionsReceived";
      type uint32;
      description "snmpInBadVersions";
    }
    leaf bad-community-names-received {
      xr:xr-xml-map "snmp:BadCommunityNamesReceived";
      type uint32;
      description "snmpInBadCommunityNames";
    }
    leaf bad-community-uses-received {
      xr:xr-xml-map "snmp:BadCommunityUsesReceived";
      type uint32;
      description "snmpInBadCommunityUses";
    }
    leaf asn-parse-errors-received {
      xr:xr-xml-map "snmp:ASNParseErrorsReceived";
      type uint32;
      description "snmpInASNParseErrs";
    }
    leaf silent-drop-count {
      xr:xr-xml-map "snmp:SilentDropCount";
      type uint32;
      description "snmpSilentDrops";
    }
    leaf proxy-drop-count {
      xr:xr-xml-map "snmp:ProxyDropCount";
      type uint32;
      description "snmpProxyDrops";
    }
    leaf too-big-packet-received {
      xr:xr-xml-map "snmp:TooBigPacketReceived";
      type uint32;
      description "snmpInTooBigs";
    }
    leaf max-packet-size {
      xr:xr-xml-map "snmp:MaxPacketSize";
      type uint32;
      description "snmp maximum packet size";
    }
    leaf no-such-names-received {
      xr:xr-xml-map "snmp:NoSuchNamesReceived";
      type uint32;
      description "snmpInNoSuchNames";
    }
    leaf bad-values-received {
      xr:xr-xml-map "snmp:BadValuesReceived";
      type uint32;
      description "snmpInBadValues";
    }
    leaf read-only-received {
      xr:xr-xml-map "snmp:ReadOnlyReceived";
      type uint32;
      description "snmpInReadOnlys";
    }
    leaf total-general-errors {
      xr:xr-xml-map "snmp:TotalGeneralErrors";
      type uint32;
      description "snmpInGenErrs";
    }
    leaf total-requested-variables {
      xr:xr-xml-map "snmp:TotalRequestedVariables";
      type uint32;
      description "snmpInTotalReqVars";
    }
    leaf total-set-variables-received {
      xr:xr-xml-map "snmp:TotalSetVariablesReceived";
      type uint32;
      description "snmpInTotalSetVars";
    }
    leaf get-requests-received {
      xr:xr-xml-map "snmp:GetRequestsReceived";
      type uint32;
      description "snmpInGetRequests";
    }
    leaf get-next-requests-received {
      xr:xr-xml-map "snmp:GetNextRequestsReceived";
      type uint32;
      description "snmpInGetNexts";
    }
    leaf set-requests-received {
      xr:xr-xml-map "snmp:SetRequestsReceived";
      type uint32;
      description "snmpInSetRequests";
    }
    leaf get-responses-received {
      xr:xr-xml-map "snmp:GetResponsesReceived";
      type uint32;
      description "snmpInGetResponses";
    }
    leaf traps-received {
      xr:xr-xml-map "snmp:TrapsReceived";
      type uint32;
      description "snmpInTraps";
    }
    leaf total-packets-sent {
      xr:xr-xml-map "snmp:TotalPacketsSent";
      type uint32;
      description "snmpOutPkts";
    }
    leaf too-big-packets-sent {
      xr:xr-xml-map "snmp:TooBigPacketsSent";
      type uint32;
      description "snmpOutTooBigs";
    }
    leaf no-such-names-sent {
      xr:xr-xml-map "snmp:NoSuchNamesSent";
      type uint32;
      description "snmpOutNoSuchNames";
    }
    leaf bad-values-sent {
      xr:xr-xml-map "snmp:BadValuesSent";
      type uint32;
      description "snmpOutBadValues";
    }
    leaf general-errors-sent {
      xr:xr-xml-map "snmp:GeneralErrorsSent";
      type uint32;
      description "snmpOutGenErrs";
    }
    leaf get-requests-sent {
      xr:xr-xml-map "snmp:GetRequestsSent";
      type uint32;
      description "snmpOutGetRequests";
    }
    leaf get-next-request-sent {
      xr:xr-xml-map "snmp:GetNextRequestSent";
      type uint32;
      description "snmpOutGetNexts";
    }
    leaf set-requests-sent {
      xr:xr-xml-map "snmp:SetRequestsSent";
      type uint32;
      description "snmpOutSetRequests";
    }
    leaf get-responses-sent {
      xr:xr-xml-map "snmp:GetResponsesSent";
      type uint32;
      description "snmpOutGetResponses";
    }
    leaf traps-sent {
      xr:xr-xml-map "snmp:TrapsSent";
      type uint32;
      description "snmpOutTraps";
    }
  }

  grouping SNMP-BULKSTATS-B {
    description "SNMP Bulkstats transfer Information";
    leaf transfer-name-xr {
      xr:xr-xml-map "snmp:transfer-name-xr";
      type string;
      description "Name of the bulkstats transfer session";
    }
    leaf url-primary {
      xr:xr-xml-map "snmp:URLPrimary";
      type string;
      description "Bulkstats transfer primary URL";
    }
    leaf url-secondary {
      xr:xr-xml-map "snmp:URLSecondary";
      type string;
      description "Bulkstats transfer secondary URL";
    }
    leaf retained-file {
      xr:xr-xml-map "snmp:RetainedFile";
      type string;
      description "Bulkstats transfer retained file name";
    }
    leaf time-left {
      xr:xr-xml-map "snmp:TimeLeft";
      type uint32;
      units "second";
      description "Bulkstats transfer retry time left in seconds";
    }
    leaf retry-left {
      xr:xr-xml-map "snmp:RetryLeft";
      type uint32;
      description "Bulkstats transfer retry attempt left";
    }
  }

  grouping SNMP-ENGINEID {
    description "SNMPv3 engineID Information";
    leaf engine-id {
      xr:xr-xml-map "snmp:EngineID";
      type string;
      description "SNMPv3 engineID";
    }
  }

  grouping SNMP-SYSUPTIME {
    description "SNMP sysUpTime in centi seconds";
    leaf system-up-time {
      xr:xr-xml-map "snmp:SystemUpTime";
      type uint32;
      description "sysUpTime";
    }
  }
}
