submodule Cisco-IOS-XR-shellutil-filesystem-oper-sub1 {

  belongs-to Cisco-IOS-XR-shellutil-filesystem-oper {
    prefix Cisco-IOS-XR-shellutil-filesystem-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR shellutil-filesystem package operational data.

     Copyright (c) 2013-2015 by Cisco Systems, Inc.
     All rights reserved.";

  revision "2015-11-09" {
    description
      "IOS XR 6.0 revision.";
  }


  grouping FILESYSTEM-UTIL {
    description "File System Description";
    leaf size {
      xr:xr-xml-map "shellutil_filesystem:Size";
      type string;
      units "byte";
      description "Size of the file system in bytes";
    }
    leaf free {
      xr:xr-xml-map "shellutil_filesystem:Free";
      type string;
      units "byte";
      description "Free space in the file system in bytes";
    }
    leaf type {
      xr:xr-xml-map "shellutil_filesystem:Type";
      type string;
      description "Type of file system";
    }
    leaf flags {
      xr:xr-xml-map "shellutil_filesystem:Flags";
      type string;
      description "Flags of file system";
    }
    leaf prefixes {
      xr:xr-xml-map "shellutil_filesystem:Prefixes";
      type string;
      description "Prefixes of file system";
    }
  }

  grouping FILESYSTEM {
    description "File Systems";

    list file-system {
      description "Available file systems";
      uses FILESYSTEM-UTIL;
    }
  }
}
