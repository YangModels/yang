module Cisco-IOS-XR-ipv4-bgp-cfg {

  /*** NAMESPACE / PREFIX DEFINITION ***/

  namespace "http://cisco.com/ns/yang/Cisco-IOS-XR-ipv4-bgp-cfg";


  prefix "ipv4-bgp-cfg";

  /*** LINKAGE (IMPORTS / INCLUDES) ***/

  import ietf-inet-types { prefix "inet"; }

  import Cisco-IOS-XR-types { prefix "xr"; }

  import Cisco-IOS-XR-ipv4-bgp-datatypes { prefix "dt1"; }

  import Cisco-IOS-XR-infra-rsi-cfg { prefix "a1"; }

  import Cisco-IOS-XR-snmp-agent-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-bgp package configuration.

     This module contains definitions
     for the following management objects:
       bgp: BGP configuration commands

     This YANG module augments the
       Cisco-IOS-XR-infra-rsi-cfg,
       Cisco-IOS-XR-snmp-agent-cfg
     modules with configuration data.

     Copyright (c) 2013-2015 by Cisco Systems, Inc.
     All rights reserved.";

  revision "2015-08-27" {
    description
      "IOS XR 5.3.2 revision.";
  }

  typedef Bgp-mvpn-sfs-select {
    type enumeration {
      enum all-paths {
        value 1;
        description "Select all paths as single forwarder PE";
      }
      enum highest-ip-address {
        value 2;
        description
          "Select PE with highest address as single
          forwarder PE";
      }
    }
    description "Bgp mvpn sfs select";
  }
  typedef Bgp-default-metric-range {
    type uint32 {
      range "0..4294967295";
    }
    description "Bgp default metric range";
  }
  typedef Bgp-signal {
    type enumeration {
      enum bgp-disable {
        value 1;
        description "Signalling BGP disable";
      }
      enum ldp-disable {
        value 2;
        description "Signalling LDP disable";
      }
    }
    description "Bgp signal";
  }
  typedef Bgp-vrf-route-target {
    type enumeration {
      enum as {
        value 0;
        description "AS format RT";
      }
      enum ipv4-address {
        value 1;
        description "IPv4 address format RT";
      }
      enum four-byte-as {
        value 2;
        description "4-byte AS format RT";
      }
    }
    description "Bgp vrf route target";
  }
  typedef Route-target-as-index {
    type uint32 {
      range "0..4294967295";
    }
    description "Route target as index";
  }
  typedef Bgp-send-mcast-attr-cfg {
    type enumeration {
      enum enable {
        value 1;
        description "Enable SendMcastAttr";
      }
      enum disable {
        value 2;
        description "Disable SendMcastAttr";
      }
    }
    description "Bgp send mcast attr cfg";
  }
  typedef Bgp-aigp-cfg-poi {
    type enumeration {
      enum pre-best-path {
        value 1;
        description "AIGP Pre-bestpath POI";
      }
      enum igp-cost {
        value 2;
        description "AIGP igp-cost POI";
      }
    }
    description "Bgp aigp cfg poi";
  }
  typedef Bgp-flowspec-validation-cfg {
    type enumeration {
      enum enable {
        value 1;
        description "Enable Flowspec validation";
      }
      enum disable {
        value 2;
        description "Disable Flowspec validation";
      }
      enum redirect-nexhop-disable {
        value 3;
        description "Disable Flowspec redirect nexthop validation";
      }
    }
    description "Bgp flowspec validation cfg";
  }
  typedef Route-target-addr-index {
    type uint32 {
      range "0..65535";
    }
    description "Route target addr index";
  }
  typedef Bgp-orf {
    type enumeration {
      enum none {
        value 0;
        description "No capability to send or receive";
      }
      enum receive {
        value 1;
        description "Receive ORF capability";
      }
      enum send {
        value 2;
        description "Send ORF capability";
      }
      enum both {
        value 3;
        description "Send and receive ORF capability";
      }
    }
    description "Bgp orf";
  }
  typedef Bgp-rpki-transport {
    type enumeration {
      enum tcp {
        value 0;
        description "TCP Transport";
      }
      enum ssh {
        value 1;
        description "SSH Transport";
      }
    }
    description "Bgp rpki transport";
  }
  typedef Bgp-reorg-opt {
    type enumeration {
      enum bgp-cfg-adv {
        value 1;
        description "Advertise translated routes";
      }
      enum bgp-cfg-adv-reorg {
        value 2;
        description "Advertise Reorig routes";
      }
      enum bgp-cfg-adv-disable {
        value 3;
        description "Disable adv of routes";
      }
      enum bgp-cfg-adv-local {
        value 4;
        description "Advertise local routes";
      }
    }
    description "Bgp reorg opt";
  }
  typedef Bgp-aigp-cfg {
    type enumeration {
      enum enable {
        value 1;
        description "Enable AIGP";
      }
      enum disable {
        value 2;
        description "Disable AIGP";
      }
    }
    description "Bgp aigp cfg";
  }
  typedef Bgp-route-distinguisher {
    type enumeration {
      enum auto {
        value 1;
        description "Automatically assigned";
      }
      enum as {
        value 2;
        description "AS format RD";
      }
      enum four-byte-as {
        value 3;
        description "4-byte AS format RD";
      }
      enum ipv4-address {
        value 4;
        description "IPv4 address format RD";
      }
    }
    description "Bgp route distinguisher";
  }
  typedef Bgp-tcp-mode {
    type enumeration {
      enum either {
        value 0;
        description "Either active or passive mode";
      }
      enum active-only {
        value 1;
        description "Active mode only";
      }
      enum passive-only {
        value 2;
        description "Passive mode only";
      }
    }
    description "Bgp tcp mode";
  }
  typedef Bgp-site-of-origin {
    type enumeration {
      enum as {
        value 0;
        description "AS format SoO";
      }
      enum ipv4-address {
        value 1;
        description "IPv4 address format SoO";
      }
      enum four-byte-as {
        value 2;
        description "4-byte AS format SoO";
      }
    }
    description "Bgp site of origin";
  }
  typedef Bgp-cluster-id {
    type enumeration {
      enum number {
        value 1;
        description "Number";
      }
      enum ipv4-address {
        value 2;
        description "IPv4 Address";
      }
    }
    description "Bgp cluster id";
  }

  grouping ADVERTISE-DISABLE {
    description
      "Common node of neighbor-group-af, neighbor-af,
      vrf-neighbor-af, af-group-af";

    container advertise-disable {
      xr:xr-xml-map "bgp_cfg:AdvertiseDisable";
      description "Disable Advertise Of Routes to the peer";
      leaf af-name {
        xr:xr-xml-map "bgp_cfg:AFName";
        type dt1:Bgp-address-family;
        description "Address family";
      }
      leaf reorg-option {
        xr:xr-xml-map "bgp_cfg:ReorgOption";
        type Bgp-reorg-opt;
        description "Reorigination option";
      }
    }
  }

  grouping TABLE-POLICY {
    description "Common node of global-af, vrf-global-af";
    leaf table-policy {
      xr:xr-xml-map "bgp_cfg:TablePolicy";
      type string;
      description "Table Policy name";
    }
  }

  grouping MAXIMUM-PREFIXES {
    description
      "Common node of neighbor-group-af, neighbor-af,
      vrf-neighbor-af, af-group-af";

    container maximum-prefixes {
      xr:xr-xml-map "bgp_cfg:MaximumPrefixes";
      presence "Indicates a maximum-prefixes node is configured.";
      description
        "Maximum number of prefixes to accept from this
        peer";
      leaf prefix-limit {
        xr:xr-xml-map "bgp_cfg:PrefixLimit";
        type uint32 {
          range "1..4294967295";
        }
        mandatory true;
        description "Maximum prefixes limit";
      }
      leaf warning-percentage {
        xr:xr-xml-map "bgp_cfg:WarningPercentage";
        type uint32 {
          range "1..100";
        }
        default "75";
        description
          "Threshold value (%) at which to generate a
          warning message.";
      }
      leaf warning-only {
        xr:xr-xml-map "bgp_cfg:WarningOnly";
        type boolean;
        default "false";
        description
          "TRUE to only give a warning message when limit
          is exceeded.  FALSE to accept max prefix limit
          only.";
      }
      leaf restart-time {
        xr:xr-xml-map "bgp_cfg:RestartTime";
        type uint32 {
          range "0..65535";
        }
        default "0";
        description "Restart interval";
      }
      leaf discard-extra-paths {
        xr:xr-xml-map "bgp_cfg:DiscardExtraPaths";
        type boolean;
        default "false";
        description "Discard extra paths when limit is exceeded";
      }
    }
  }

  grouping DISTANCE {
    description "Common node of global-af, vrf-global-af";

    container distance {
      xr:xr-xml-map "bgp_cfg:Distance";
      description "Define an administrative distance";
      leaf external-routes {
        xr:xr-xml-map "bgp_cfg:ExternalRoutes";
        type uint32 {
          range "1..255";
        }
        default "20";
        description "Distance for routes external to the AS";
      }
      leaf internal-routes {
        xr:xr-xml-map "bgp_cfg:InternalRoutes";
        type uint32 {
          range "1..255";
        }
        default "200";
        description "Distance for routes internal to the AS";
      }
      leaf local-routes {
        xr:xr-xml-map "bgp_cfg:LocalRoutes";
        type uint32 {
          range "1..255";
        }
        default "200";
        description "Distance for local routes";
      }
    }
  }

  grouping UPDATE-SOURCE-INTERFACE {
    description
      "Common node of neighbor-group, neighbor,
      vrf-neighbor, session-group";
    leaf update-source-interface {
      xr:xr-xml-map "bgp_cfg:UpdateSourceInterface";
      type xr:Interface-name;
      description "Select an interface to configure";
    }
  }

  grouping MULTI-PATH-AS-PATH-IGNORE-ONWARDS {
    description "Common node of global, vrf-global";
    leaf multi-path-as-path-ignore-onwards {
      xr:xr-xml-map "bgp_cfg:MultiPathASPathIgnoreOnwards";
      type empty;
      description
        "Change default multi-route selection criteria to
        ignore everything onwards as-path check";
    }
  }

  grouping PROPAGATE-DMZ-LINK-BANDWIDTH {
    description
      "Common node of neighbor-group, neighbor,
      vrf-neighbor, session-group";
    leaf propagate-dmz-link-bandwidth {
      xr:xr-xml-map "bgp_cfg:PropagateDMZLinkBandwidth";
      type boolean;
      description
        "TRUE to propagate DMZ link bandwidth.  FALSE to
        not propagate and to prevent inheritance from a
        parent";
    }
  }

  grouping DISABLE-AUTO-SOFT-RESET {
    description "Common node of global, vrf-global";
    leaf disable-auto-soft-reset {
      xr:xr-xml-map "bgp_cfg:DisableAutoSoftReset";
      type empty;
      description
        "Disable automatic soft peer reset on policy
        reconfiguration";
    }
  }

  grouping MSG-LOG-IN {
    description
      "Common node of neighbor-group, neighbor,
      vrf-neighbor, session-group";

    container msg-log-in {
      xr:xr-xml-map "bgp_cfg:MsgLogIn";
      description "Message log inbound";
      leaf msg-buf-count {
        xr:xr-xml-map "bgp_cfg:MsgBufCount";
        type uint32 {
          range "1..100";
        }
        description "Inbound message log buffer size";
      }
      leaf msg-log-disable {
        xr:xr-xml-map "bgp_cfg:MsgLogDisable";
        type boolean;
        description "Disable inbound message logging";
      }
      leaf msg-log-inherit-disable {
        xr:xr-xml-map "bgp_cfg:MsgLogInheritDisable";
        type boolean;
        description
          "TRUE, to prevent this entity from having a
          inbound message logging if parent has one";
      }
    }
  }

  grouping DISABLE-ENFORCE-FIRST-AS {
    description "Common node of global, vrf-global";
    leaf disable-enforce-first-as {
      xr:xr-xml-map "bgp_cfg:DisableEnforceFirstAS";
      type empty;
      description "Disable enforce the first AS for EBGP routes";
    }
  }

  grouping ROUTE-TARGET-TABLE {
    description
      "Common node of import-route-targets,
      export-route-targets";

    container route-targets {
      xr:xr-xml-map "bgp_vrf_cfg:RouteTargetTable";
      description "Route target table";

      list route-target {
        xr:xr-xml-map "bgp_vrf_cfg:RouteTarget";
        must "as-or-four-byte-as or ipv4-address" {
          description
            "AS-or-FourByteAS or IPV4Address must be
            present.";
        }
        key "stitching-rt type";
        description "Route target";
        leaf type {
          xr:xr-xml-map "bgp_vrf_cfg:Type";
          type Bgp-vrf-route-target;
          description "Type of RT";
        }
        leaf stitching-rt {
          xr:xr-xml-map "bgp_vrf_cfg:StitchingRt";
          type uint32 {
            range "0..1";
          }
          description "Stitching RT";
        }

        list as-or-four-byte-as {
          when "../type = 'as' or ../type = 'four-byte-as'" {
            description "../Type = AS or ../Type = FourByteAS";
          }
          key "as-xx as as-index";
          description "as or four byte as";
          leaf as-xx {
            xr:xr-xml-map "bgp_vrf_cfg:AS_XX";
            type uint32;
            description "AS number";
          }
          leaf as {
            xr:xr-xml-map "bgp_vrf_cfg:AS";
            type uint32 {
              range "1..4294967295";
            }
            description "AS number";
          }
          leaf as-index {
            xr:xr-xml-map "bgp_vrf_cfg:ASIndex";
            type Route-target-as-index;
            description "AS number Index";
          }
        }

        list ipv4-address {
          when "../type = 'ipv4-address'" {
            description "../Type = IPV4Address";
          }
          key "address address-index";
          description "ipv4 address";
          leaf address {
            xr:xr-xml-map "bgp_vrf_cfg:Address";
            type inet:ipv4-address-no-zone;
            description "IP address";
          }
          leaf address-index {
            xr:xr-xml-map "bgp_vrf_cfg:AddressIndex";
            type Route-target-addr-index;
            description "IP address Index";
          }
        }
      }
    }
  }

  grouping REMOTE-AS {
    description
      "Common node of neighbor-group, neighbor,
      vrf-neighbor, session-group";

    container remote-as {
      xr:xr-xml-map "bgp_cfg:RemoteAS";
      description "Set remote AS";
      leaf as-xx {
        xr:xr-xml-map "bgp_cfg:AS_XX";
        type dt1:Bgp-as-range;
        description "xx of AS number xx.yy";
      }
      leaf as-yy {
        xr:xr-xml-map "bgp_cfg:AS_YY";
        type dt1:Bgp-as-range;
        description "yy of AS number xx.yy";
      }
    }
  }

  grouping ADDITIONAL-PATHS-SEND {
    description "Common node of global-af, vrf-global-af";
    leaf additional-paths-send {
      xr:xr-xml-map "bgp_cfg:AdditionalPathsSend";
      type dt1:Bgpaf-additional-paths-cfg;
      description "Enable/disable Send capability";
    }
  }

  grouping UPDATE-IN-FILTERING {
    description
      "Common node of neighbor-group, neighbor,
      vrf-neighbor, session-group";

    container update-in-filtering {
      xr:xr-xml-map "bgp_cfg:UpdateInFiltering";
      description "Inbound update filtering";

      container update-in-filtering-message-buffers {
        xr:xr-xml-map "bgp_cfg:UpdateInFilteringMessageBuffers";
        presence "Indicates a update-in-filtering-message-buffers"+
          " node is configured.";
        description "Message buffers to store filtered updates";
        leaf number-of-buffers {
          xr:xr-xml-map "bgp_cfg:NumberOfBuffers";
          type uint32 {
            range "0..25";
          }
          mandatory true;
          description "Number of message buffers";
        }
        leaf non-circular-buffer {
          xr:xr-xml-map "bgp_cfg:NonCircularBuffer";
          type boolean;
          mandatory true;
          description "TRUE to configure non-circular buffer";
        }
      }
      leaf enable {
        xr:xr-xml-map "bgp_cfg:Enable";
        type empty;
        description "Configure inbound update filtering";
      }
      leaf update-in-filtering-attribute-filter-group {
        xr:xr-xml-map "bgp_cfg:UpdateInFilteringAttributeFilterGrou"+
          "p";
        type string;
        description "Attribute-filter group name";
      }
      leaf update-in-filtering-syslog-disable {
        xr:xr-xml-map "bgp_cfg:UpdateInFilteringSyslogDisable";
        type empty;
        description "Disable syslog messages";
      }
    }
  }

  grouping SHUTDOWN {
    description
      "Common node of neighbor-group, neighbor,
      vrf-neighbor, session-group";
    leaf shutdown {
      xr:xr-xml-map "bgp_cfg:Shutdown";
      type boolean;
      description
        "TRUE to shutdown this entity, FALSE to prevent
        this entity from being shutdown even if the
        parent is.";
    }
  }

  grouping BMP-ACTIVATE-TABLE {
    description
      "Common node of neighbor-group, neighbor,
      vrf-neighbor, session-group";

    container bmp-activates {
      xr:xr-xml-map "bgp_cfg:BMPActivateTable";
      description "Enable BMP logging for this neighbor";

      list bmp-activate {
        xr:xr-xml-map "bgp_cfg:BMPActivate";
        key "server-id";
        description "Enable BMP logging for this particular server";
        leaf server-id {
          xr:xr-xml-map "bgp_cfg:ServerID";
          type uint32 {
            range "1..8";
          }
          description "BMP Server ID";
        }
      }
    }
  }

  grouping SITE-OF-ORIGIN {
    description
      "Common node of neighbor-group-af, vrf-neighbor-af
      , af-group-af";

    container site-of-origin {
      xr:xr-xml-map "bgp_cfg:SiteOfOrigin";
      description
        "Site-of-Origin extended community associated
        with the neighbor";
      leaf type {
        xr:xr-xml-map "bgp_cfg:Type";
        type Bgp-site-of-origin;
        description "Type of Extended community";
      }
      leaf as-xx {
        xr:xr-xml-map "bgp_cfg:AS_XX";
        when "../type = 'as' or ../type = 'four-byte-as'" {
          description "../Type = AS or ../Type = FourByteAS";
        }
        type dt1:Bgp-as-range;
        description "AS number";
      }
      leaf as {
        xr:xr-xml-map "bgp_cfg:AS";
        when "../type = 'as' or ../type = 'four-byte-as'" {
          description "../Type = AS or ../Type = FourByteAS";
        }
        type dt1:Bgp-as-range;
        description "AS number";
      }
      leaf as-index {
        xr:xr-xml-map "bgp_cfg:ASIndex";
        when "../type = 'as' or ../type = 'four-byte-as'" {
          description "../Type = AS or ../Type = FourByteAS";
        }
        type dt1:Bgp-extcomm-asn-index;
        description "AS number Index";
      }
      leaf address {
        xr:xr-xml-map "bgp_cfg:Address";
        when "../type = 'ipv4-address'" {
          description "../Type = IPV4Address";
        }
        type inet:ipv4-address-no-zone;
        description "IP address";
      }
      leaf address-index {
        xr:xr-xml-map "bgp_cfg:AddressIndex";
        when "../type = 'ipv4-address'" {
          description "../Type = IPV4Address";
        }
        type dt1:Bgp-extcomm-v4-addr-index;
        description "IP address Index";
      }
    }
  }

  grouping ROUTE-POLICY-OUT {
    description
      "Common node of neighbor-group-af, neighbor-af,
      vrf-neighbor-af, af-group-af";
    leaf route-policy-out {
      xr:xr-xml-map "bgp_cfg:RoutePolicyOut";
      type string;
      description "Route policy name to apply to outbound routes";
    }
  }

  grouping ADVERTISE-V4 {
    description
      "Common node of neighbor-group-af, neighbor-af,
      vrf-neighbor-af, af-group-af";

    container advertise-v4 {
      xr:xr-xml-map "bgp_cfg:AdvertiseV4";
      description "Advertise Translated Routes to the peer";
      leaf af-name {
        xr:xr-xml-map "bgp_cfg:AFName";
        type dt1:Bgp-address-family;
        description "Address family";
      }
      leaf reorg-option {
        xr:xr-xml-map "bgp_cfg:ReorgOption";
        type Bgp-reorg-opt;
        description "Reorigination option";
      }
    }
  }

  grouping ADVERTISE-V6 {
    description
      "Common node of neighbor-group-af, neighbor-af,
      vrf-neighbor-af, af-group-af";

    container advertise-v6 {
      xr:xr-xml-map "bgp_cfg:AdvertiseV6";
      description "Advertise Translated Routes to the peer";
      leaf af-name {
        xr:xr-xml-map "bgp_cfg:AFName";
        type dt1:Bgp-address-family;
        description "Address family";
      }
      leaf reorg-option {
        xr:xr-xml-map "bgp_cfg:ReorgOption";
        type Bgp-reorg-opt;
        description "Reorigination option";
      }
    }
  }

  grouping DEFAULT-ORIGINATE {
    description
      "Common node of neighbor-group-af, neighbor-af,
      vrf-neighbor-af, af-group-af";

    container default-originate {
      xr:xr-xml-map "bgp_cfg:DefaultOriginate";
      description "Originate default route to this neighbor";
      leaf enable {
        xr:xr-xml-map "bgp_cfg:Enable";
        type boolean;
        default "false";
        description
          "FALSE to prevent default-originate from, being
          inherited from a parent. TRUE otherwise.";
      }
      leaf route-policy-name {
        xr:xr-xml-map "bgp_cfg:RoutePolicyName";
        type string;
        description
          "Route policy name to specify criteria to
          originate default.";
      }
    }
  }

  grouping TIMERS {
    description
      "Common node of neighbor-group, neighbor,
      vrf-neighbor, session-group";

    container timers {
      xr:xr-xml-map "bgp_cfg:Timers";
      description "BGP per neighbor timers.";
      leaf keepalive-interval {
        xr:xr-xml-map "bgp_cfg:KeepaliveInterval";
        type uint32 {
          range "0..65535";
        }
        default "60";
        description "Keepalive interval";
      }
      leaf hold-time {
        xr:xr-xml-map "bgp_cfg:HoldTime";
        type uint32 {
          range "0..65535";
        }
        default "180";
        description
          "Hold time.  Specify 0 to disable
          keepalives/hold time";
      }
      leaf min-accept-hold-time {
        xr:xr-xml-map "bgp_cfg:MinAcceptHoldTime";
        type uint32 {
          range "0..65535";
        }
        default "3";
        description
          "Minimum acceptable hold time.  Specify 0 to
          disable keepalives/hold time";
      }
    }
  }

  grouping DISABLE-FAST-EXTERNAL-FALLOVER {
    description "Common node of global, vrf-global";
    leaf disable-fast-external-fallover {
      xr:xr-xml-map "bgp_cfg:DisableFastExternalFallover";
      type empty;
      description
        "Disable immediate reset session if a link to a
        directly connected external peer goes down";
    }
  }

  grouping SEND-COMMUNITY-EBGP {
    description
      "Common node of neighbor-group-af, neighbor-af,
      vrf-neighbor-af, af-group-af";
    leaf send-community-ebgp {
      xr:xr-xml-map "bgp_cfg:SendCommunityEBGP";
      type boolean;
      description
        "TRUE to send communities to the external
        neighbor/neighbor-group/af-group.  FALSE not to
        send and to prevent inheritance from a parent";
    }
  }

  grouping ADDITIONAL-PATHS-RECEIVE-CAPABILITY {
    description
      "Common node of neighbor-group, neighbor,
      vrf-neighbor, session-group";
    leaf additional-paths-receive-capability {
      xr:xr-xml-map "bgp_cfg:AdditionalPathsReceiveCapability";
      type dt1:Bgp-nbr-cap-additional-paths-cfg;
      description "Enable/disable Receive capability";
    }
  }

  grouping SEND-EXT-COMMUNITY-EBGP {
    description
      "Common node of neighbor-group-af, neighbor-af,
      vrf-neighbor-af, af-group-af";
    leaf send-ext-community-ebgp {
      xr:xr-xml-map "bgp_cfg:SendExtCommunityEBGP";
      type boolean;
      description
        "TRUE to send extended communities to the
        external neighbor/neighbor-group/af-group. 
        FALSE not to send and to prevent inheritance
        from a parent";
    }
  }

  grouping AF-GROUP {
    description
      "Common node of neighbor-group-af, neighbor-af,
      vrf-neighbor-af";
    leaf af-group {
      xr:xr-xml-map "bgp_cfg:AFGroup";
      type string;
      description "AF group name";
    }
  }

  grouping ROUTE-POLICY-IN {
    description
      "Common node of neighbor-group-af, neighbor-af,
      vrf-neighbor-af, af-group-af";
    leaf route-policy-in {
      xr:xr-xml-map "bgp_cfg:RoutePolicyIn";
      type string;
      description "Route policy name to apply to inbound routes";
    }
  }

  grouping GRACEFUL-RESTART-TIME {
    description "Common node of global, vrf-global";
    leaf graceful-restart-time {
      xr:xr-xml-map "bgp_cfg:GracefulRestartTime";
      type uint32 {
        range "1..4095";
      }
      units "second";
      default "120";
      description "Max time (seconds)";
    }
  }

  grouping LABEL-MODE {
    description "Common node of global-af, vrf-global-af";

    container label-mode {
      xr:xr-xml-map "bgp_cfg:LabelMode";
      description "BGP 6PE/MPLS-VPN label allocation mode";
      leaf label-allocation-mode {
        xr:xr-xml-map "bgp_cfg:LabelAllocationMode";
        type string;
        description
          "Label allocation mode: per-ce  Set per CE label
          mode, per-vrf Set per VRF label mode,
          per-prefix Set per Prefix label mode (for
          MPLS-VPN only)";
      }
      leaf route-policy-name {
        xr:xr-xml-map "bgp_cfg:RoutePolicyName";
        type string;
        description "Label mode route policy name";
      }
    }
  }

  grouping DEFAULT-INFO-ORIGINATE {
    description "Common node of global, vrf-global";
    leaf default-info-originate {
      xr:xr-xml-map "bgp_cfg:DefaultInfoOriginate";
      type empty;
      description "Distribute a default route";
    }
  }

  grouping ENFORCE-FIRST-AS {
    description
      "Common node of neighbor-group, neighbor,
      vrf-neighbor, session-group";
    leaf enforce-first-as {
      xr:xr-xml-map "bgp_cfg:EnforceFirstAS";
      type boolean;
      description
        "TRUE to enforce first AS; FALSE to not enforce
        first AS.";
    }
  }

  grouping SOFT-RECONFIGURATION {
    description
      "Common node of neighbor-group-af, neighbor-af,
      vrf-neighbor-af, af-group-af";

    container soft-reconfiguration {
      xr:xr-xml-map "bgp_cfg:SoftReconfiguration";
      description
        "Enable/disable inbound soft reconfiguration for
        this neighbor/neighbor-group/af-group";
      leaf inbound-soft {
        xr:xr-xml-map "bgp_cfg:InboundSoft";
        type boolean;
        default "false";
        description
          "FALSE to prohibit inbound soft reconfiguration.
          TRUE otherwise.";
      }
      leaf soft-always {
        xr:xr-xml-map "bgp_cfg:SoftAlways";
        type boolean;
        default "false";
        description
          "TRUE to always use soft reconfig, even if route
          refresh is supported.  FALSE otherwise.";
      }
    }
  }

  grouping NEIGHBOR-GRACEFUL-RESTART {
    description
      "Common node of neighbor-group, neighbor,
      vrf-neighbor, session-group";
    leaf neighbor-graceful-restart {
      xr:xr-xml-map "bgp_cfg:NeighborGracefulRestart";
      type boolean;
      description
        "TRUE to Enable graceful restart support for
        neighbor.  FALSE to disable graceful restart
        support for neighbor.";
    }
  }

  grouping LOCAL-ADDRESS {
    description
      "Common node of neighbor-group, neighbor,
      vrf-neighbor, session-group";

    container local-address {
      xr:xr-xml-map "bgp_cfg:LocalAddress";
      description "Local ip address";
      leaf local-address-disable {
        xr:xr-xml-map "bgp_cfg:LocalAddressDisable";
        type boolean;
        description
          "TRUE to prevent this entity from having a local
          address if the parent has one.FALSE to specify
          local ip address";
      }
      leaf local-ip-address {
        xr:xr-xml-map "bgp_cfg:LocalIPAddress";
        when "../local-address-disable = 'false'" {
          description "../LocalAddressDisable = 0";
        }
        type inet:ip-address-no-zone;
        description "Local ip address for neighbor";
      }
    }
  }

  grouping AS-OVERRIDE {
    description
      "Common node of neighbor-group-af, neighbor-af,
      vrf-neighbor-af, af-group-af";
    leaf as-override {
      xr:xr-xml-map "bgp_cfg:ASOverride";
      type boolean;
      default "true";
      description
        "TRUE to override matching AS-number while
        sending update. FALSE to prevent as-override
        from being inherited from the parent";
    }
  }

  grouping IGNORE-CONNECTED-CHECK-EBGP {
    description
      "Common node of neighbor-group, neighbor,
      vrf-neighbor, session-group";
    leaf ignore-connected-check-ebgp {
      xr:xr-xml-map "bgp_cfg:IgnoreConnectedCheckEBGP";
      type boolean;
      description
        "TRUE to disable the connected nexthop check for
        this peer.FALSE to enable the connected nexthop
        check for this peer.";
    }
  }

  grouping SEND-MULTICAST-ATTR {
    description
      "Common node of neighbor-group-af, neighbor-af,
      vrf-neighbor-af, af-group-af";
    leaf send-multicast-attr {
      xr:xr-xml-map "bgp_cfg:SendMulticastAttr";
      type Bgp-send-mcast-attr-cfg;
      description
        "Config send multicast attribute for this
        neighbor";
    }
  }

  grouping IBGP {
    description "Common node of global-af, vrf-global-af";

    container ibgp {
      xr:xr-xml-map "bgp_cfg:IBGP";
      presence "Indicates a ibgp node is configured.";
      description "Use iBGP multipaths";
      leaf paths-value {
        xr:xr-xml-map "bgp_cfg:PathsValue";
        type uint32 {
          range "2..32";
        }
        mandatory true;
        description "Number of paths";
      }
      leaf unequal-cost {
        xr:xr-xml-map "bgp_cfg:UnequalCost";
        type boolean;
        default "false";
        description
          "Allow multipaths to have different IGP metrics";
      }
      leaf selective {
        xr:xr-xml-map "bgp_cfg:Selective";
        type boolean;
        default "false";
        description "Allow multipaths only from marked neighbors";
      }
      leaf order-by-igp-metric {
        xr:xr-xml-map "bgp_cfg:OrderByIGPMetric";
        type boolean;
        default "false";
        description "Order candidate multipaths by IGP metric";
      }
    }
  }

  grouping ADVERTISE-PERMANENT-NETWORK {
    description
      "Common node of neighbor-group-af, neighbor-af,
      vrf-neighbor-af, af-group-af";
    leaf advertise-permanent-network {
      xr:xr-xml-map "bgp_cfg:AdvertisePermanentNetwork";
      type empty;
      description "Advertise Permanent Networks";
    }
  }

  grouping BEST-PATH-COST-COMMUNITY {
    description "Common node of global, vrf-global";
    leaf best-path-cost-community {
      xr:xr-xml-map "bgp_cfg:BestPathCostCommunity";
      type empty;
      description
        "Change default route selection criteria to
        ignore cost community comparison";
    }
  }

  grouping RPKI-BESTPATH-ORIGIN-AS-ALLOW-INVALID {
    description
      "Common node of neighbor-group-af, neighbor-af,
      vrf-neighbor-af, af-group-af";
    leaf rpki-bestpath-origin-as-allow-invalid {
      xr:xr-xml-map "bgp_cfg:RPKIBestpathOriginASAllowInvalid";
      type empty;
      description "RPKI bestpath origin-AS allow invalid";
    }
  }

  grouping BGP-CFG-RPKI-BESTPATH-ORIGIN-AS-ALLOW-INVALID {
    description
      "Common node of neighbor-group, neighbor,
      vrf-neighbor, session-group";
    leaf rpki-bestpath-origin-as-allow-invalid {
      xr:xr-xml-map "bgp_cfg:RPKIBestpathOriginASAllowInvalid";
      type empty;
      description "RPKI bestpath origin-AS allow invalid";
    }
  }

  grouping NEIGHBOR-GRACEFUL-RESTART-TIME {
    description
      "Common node of neighbor-group, neighbor,
      vrf-neighbor, session-group";
    leaf neighbor-graceful-restart-time {
      xr:xr-xml-map "bgp_cfg:NeighborGracefulRestartTime";
      type uint32 {
        range "1..4095";
      }
      units "second";
      default "120";
      description "Max time (seconds)";
    }
  }

  grouping TOS {
    description
      "Common node of neighbor-group, neighbor,
      vrf-neighbor, session-group";

    container tos {
      xr:xr-xml-map "bgp_cfg:TOS";
      description "TOS (Type Of Service)";
      leaf type {
        xr:xr-xml-map "bgp_cfg:Type";
        type dt1:Bgp-tos;
        description "Set type of service";
      }
      leaf value {
        xr:xr-xml-map "bgp_cfg:Value";
        type dt1:Bgp-precedence-dscp;
        description "TOS value to set";
      }
    }
  }

  grouping NEIGHBOR-CLUSTER-ID {
    description
      "Common node of neighbor-group, neighbor,
      vrf-neighbor, session-group";

    container neighbor-cluster-id {
      xr:xr-xml-map "bgp_cfg:NeighborClusterID";
      description "Neighbor Cluster-id";
      leaf cluster-id-number {
        xr:xr-xml-map "bgp_cfg:ClusterIDNumber";
        type uint32 {
          range "1..4294967295";
        }
        description "Route-Reflector Cluster ID as 32 bit quantity";
      }
      leaf cluster-id-address {
        xr:xr-xml-map "bgp_cfg:ClusterIDAddress";
        type inet:ipv4-address-no-zone;
        description
          "Route-Reflector Cluster ID in IPV4 address
          format";
      }
    }
  }

  grouping ACTIVATE {
    description
      "Common node of neighbor-af, vrf-neighbor-af,
      neighbor-group-af";
    leaf activate {
      xr:xr-xml-map "bgp_cfg:Activate";
      type empty;
      description "Activate an address family for this neighbor";
    }
  }

  grouping NEXT-HOP-SELF {
    description
      "Common node of neighbor-group-af, neighbor-af,
      vrf-neighbor-af, af-group-af";
    leaf next-hop-self {
      xr:xr-xml-map "bgp_cfg:NextHopSelf";
      type boolean;
      description
        "TRUE to disable the next hop calculation.  FALSE
        to prevent next-hop-self from being inherited.";
    }
  }

  grouping ALLOW-AS-IN {
    description
      "Common node of neighbor-group-af, neighbor-af,
      vrf-neighbor-af, af-group-af";
    leaf allow-as-in {
      xr:xr-xml-map "bgp_cfg:AllowASIn";
      type uint32 {
        range "1..10";
      }
      default "3";
      description "Number of occurences of AS number";
    }
  }

  grouping ADVERTISE-LOCAL-V4 {
    description
      "Common node of neighbor-group-af, neighbor-af,
      vrf-neighbor-af, af-group-af";

    container advertise-local-v4 {
      xr:xr-xml-map "bgp_cfg:AdvertiseLocalV4";
      description
        "Advertise Of Local Routes to the peer with
        different RT";
      leaf af-name {
        xr:xr-xml-map "bgp_cfg:AFName";
        type dt1:Bgp-address-family;
        description "Address family";
      }
      leaf reorg-option {
        xr:xr-xml-map "bgp_cfg:ReorgOption";
        type Bgp-reorg-opt;
        description "Reorigination option";
      }
    }
  }

  grouping ADVERTISE-LOCAL-V6 {
    description
      "Common node of neighbor-group-af, neighbor-af,
      vrf-neighbor-af, af-group-af";

    container advertise-local-v6 {
      xr:xr-xml-map "bgp_cfg:AdvertiseLocalV6";
      description
        "Advertise Of Local Routes to the peer with
        different RT";
      leaf af-name {
        xr:xr-xml-map "bgp_cfg:AFName";
        type dt1:Bgp-address-family;
        description "Address family";
      }
      leaf reorg-option {
        xr:xr-xml-map "bgp_cfg:ReorgOption";
        type Bgp-reorg-opt;
        description "Reorigination option";
      }
    }
  }

  grouping BEST-EXTERNAL {
    description "Common node of global-af, vrf-global-af";
    leaf best-external {
      xr:xr-xml-map "bgp_cfg:BestExternal";
      type boolean;
      description
        "TRUE to enable BE FALSE to disable BE
        inheritance from a parent";
    }
  }

  grouping ATTRIBUTE-DOWNLOAD {
    description "Common node of global-af, vrf-global-af";
    leaf attribute-download {
      xr:xr-xml-map "bgp_cfg:AttributeDownload";
      type empty;
      description "Enable RIB Attribute download";
    }
  }

  grouping GRACEFUL-RESTART-STALEPATH-TIME {
    description "Common node of global, vrf-global";
    leaf graceful-restart-stalepath-time {
      xr:xr-xml-map "bgp_cfg:GracefulRestartStalepathTime";
      type uint32 {
        range "1..4095";
      }
      units "second";
      default "360";
      description "Max time (seconds)";
    }
  }

  grouping ADDITIONAL-PATHS-SELECTION {
    description "Common node of global-af, vrf-global-af";

    container additional-paths-selection {
      xr:xr-xml-map "bgp_cfg:AdditionalPathsSelection";
      description "Configure additional paths selection";
      leaf selection {
        xr:xr-xml-map "bgp_cfg:Selection";
        type dt1:Bgpaf-additional-paths-cfg;
        description "Enable/disable selection ";
      }
      leaf route-policy-name {
        xr:xr-xml-map "bgp_cfg:RoutePolicyName";
        type string;
        description "Route policy for selection";
      }
    }
  }

  grouping NEIGHBOR-AF-LONG-LIVED-GRACEFUL-RESTART-CAPABLE {
    description
      "Common node of neighbor-group-af, neighbor-af,
      vrf-neighbor-af, af-group-af";
    leaf neighbor-af-long-lived-graceful-restart-capable {
      xr:xr-xml-map "bgp_cfg:NeighborAFLongLivedGracefulRestartCapa"+
        "ble";
      type boolean;
      default "false";
      description
        "TRUE to treat neighbor as Long-lived
        Graceful-restart capable. FALSE to rely on
        capability negotiation.";
    }
  }

  grouping BEST-PATH-AS-MULTIPATH-RELAX {
    description "Common node of global, vrf-global";
    leaf best-path-as-multipath-relax {
      xr:xr-xml-map "bgp_cfg:BestPathASMultipathRelax";
      type empty;
      description
        "Change default multi-route selection criteria to
        relax as-path checking";
    }
  }

  grouping GLOBAL-TIMERS {
    description "Common node of global, vrf-global";

    container global-timers {
      xr:xr-xml-map "bgp_cfg:GlobalTimers";
      description "Adjust routing timers.";
      leaf keepalive {
        xr:xr-xml-map "bgp_cfg:Keepalive";
        type uint32 {
          range "0..65535";
        }
        units "second";
        default "60";
        description "Keepalive interval (seconds)";
      }
      leaf hold-time {
        xr:xr-xml-map "bgp_cfg:HoldTime";
        type uint32 {
          range "0..65535";
        }
        units "second";
        default "180";
        description
          "Hold time (seconds).  Specify 0 to disable
          keepalives/hold time";
      }
      leaf min-accept-hold-time {
        xr:xr-xml-map "bgp_cfg:MinAcceptHoldTime";
        type uint32 {
          range "0..65535";
        }
        units "second";
        default "3";
        description
          "Minimum acceptable hold time (seconds). Specify
          0 to disable keepalives/hold time";
      }
    }
  }

  grouping NEIGHBOR-GROUP-ADD-MEMBER {
    description "Common node of neighbor, vrf-neighbor";
    leaf neighbor-group-add-member {
      xr:xr-xml-map "bgp_cfg:NeighborGroupAddMember";
      type string;
      description "Neighbor-group name";
    }
  }

  grouping MOBILE-ROUTES {
    description "Common node of global-af, vrf-global-af";

    container mobile-routes {
      xr:xr-xml-map "bgp_cfg:MobileRoutes";
      presence "enable mobile-routes";
      description "Redistribute mobile routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
      leaf not-used {
        xr:xr-xml-map "bgp_cfg:NotUsed";
        type uint32 {
          range "0..127";
        }
        description "Not used";
      }
    }
  }

  grouping LOCAL-PREFERENCE {
    description "Common node of global, vrf-global";
    leaf local-preference {
      xr:xr-xml-map "bgp_cfg:LocalPreference";
      type uint32 {
        range "0..4294967295";
      }
      default "100";
      description "Higher = more preferred";
    }
  }

  grouping CREATE {
    description "Common node of neighbor-group, session-group";
    leaf create {
      xr:xr-xml-map "bgp_cfg:Create";
      type empty;
      description "Create this group";
    }
  }

  grouping GRACEFUL-RESTART-PURGE-TIME {
    description "Common node of global, vrf-global";
    leaf graceful-restart-purge-time {
      xr:xr-xml-map "bgp_cfg:GracefulRestartPurgeTime";
      type uint32 {
        range "1..6000";
      }
      units "second";
      default "600";
      description "Max time (seconds)";
    }
  }

  grouping SEND-SOCKET-BUFFER-SIZES {
    description "Common node of global, vrf-global";

    container send-socket-buffer-sizes {
      xr:xr-xml-map "bgp_cfg:SendSocketBufferSizes";
      description "set socket parameters";
      leaf socket-send-size {
        xr:xr-xml-map "bgp_cfg:SocketSendSize";
        type uint32 {
          range "4096..131072";
        }
        units "byte";
        default "24576";
        description "Send socket buffer size in bytes";
      }
      leaf bgp-send-size {
        xr:xr-xml-map "bgp_cfg:BGPSendSize";
        type uint32 {
          range "4096..131072";
        }
        units "byte";
        default "4096";
        description "BGP Write buffer size in bytes";
      }
    }
  }

  grouping RECEIVE-SOCKET-BUFFER-SIZES {
    description "Common node of global, vrf-global";

    container receive-socket-buffer-sizes {
      xr:xr-xml-map "bgp_cfg:ReceiveSocketBufferSizes";
      description "Set socket and BGP receive buffer sizes";
      leaf socket-receive-size {
        xr:xr-xml-map "bgp_cfg:SocketReceiveSize";
        type uint32 {
          range "512..131072";
        }
        units "byte";
        default "32768";
        description "Receive socket buffer size in bytes";
      }
      leaf bgp-receive-size {
        xr:xr-xml-map "bgp_cfg:BGPReceiveSize";
        type uint32 {
          range "512..131072";
        }
        units "byte";
        default "4096";
        description "BGP Read buffer size in bytes";
      }
    }
  }

  grouping RESET-WEIGHT-ON-IMPORT {
    description "Common node of global-af, vrf-global-af";
    leaf reset-weight-on-import {
      xr:xr-xml-map "bgp_cfg:ResetWeightOnImport";
      type boolean;
      description
        "TRUE to reset weight on import. FALSE to not
        reset and to prevent inheritance from a parent";
    }
  }

  grouping AGGREGATE-ADDRESS-TABLE {
    description "Common node of global-af, vrf-global-af";

    container aggregate-addresses {
      xr:xr-xml-map "bgp_cfg:AggregateAddressTable";
      description "Configure BGP aggregate entries";

      list aggregate-address {
        xr:xr-xml-map "bgp_cfg:AggregateAddress";
        key "aggregate-addr aggregate-prefix";
        description "Aggregate address configuration";
        leaf aggregate-addr {
          xr:xr-xml-map "bgp_cfg:Aggregate";
          type inet:ip-address;
          description
            "Aggregate in prefix/length format (address
            part)";
        }
        leaf aggregate-prefix {
          xr:xr-xml-map "bgp_cfg:Aggregate";
          type uint16 {
            range "0..128";
          }
          description
            "Aggregate in prefix/length format (prefix
            part)";
        }
        leaf generate-set-info {
          xr:xr-xml-map "bgp_cfg:GenerateSetInfo";
          type boolean;
          description
            "TRUE to generate AS set path information,
            FALSE otherwise";
        }
        leaf generate-confederation-set-info {
          xr:xr-xml-map "bgp_cfg:GenerateConfederationSetInfo";
          type boolean;
          description
            "TRUE to generate AS confederation set path
            information, FALSE otherwise";
        }
        leaf summary-only {
          xr:xr-xml-map "bgp_cfg:SummaryOnly";
          type boolean;
          description
            "TRUE to filter more specific routes from
            updates, FALSEotherwise";
        }
        leaf route-policy-name {
          xr:xr-xml-map "bgp_cfg:RoutePolicyName";
          type string;
          description
            "Route policy on which to condition
            advertisement, suppression, and attributes";
        }
      }
    }
  }

  grouping EBGP-MULTIHOP {
    description
      "Common node of neighbor-group, neighbor,
      vrf-neighbor, session-group";

    container ebgp-multihop {
      xr:xr-xml-map "bgp_cfg:EBGPMultihop";
      description
        "Allow EBGP neighbors not on directly connected
        networks";
      leaf max-hop-count {
        xr:xr-xml-map "bgp_cfg:MaxHopCount";
        type uint32 {
          range "1..255";
        }
        default "255";
        description "Maximum hop count";
      }
      leaf mpls-deactivation {
        xr:xr-xml-map "bgp_cfg:MPLSDeactivation";
        type boolean;
        default "false";
        description "TRUE to not enable MPLS and NULL rewrite.";
      }
    }
  }

  grouping GRACEFUL-RESET {
    description "Common node of global, vrf-global";
    leaf graceful-reset {
      xr:xr-xml-map "bgp_cfg:GracefulReset";
      type empty;
      description
        "Reset gracefully if configuration change forces
        a peer reset";
    }
  }

  grouping BFD-ENABLE {
    description
      "Common node of neighbor-group, neighbor,
      vrf-neighbor, session-group";
    leaf bfd-enable {
      xr:xr-xml-map "bgp_cfg:BFDEnable";
      type boolean;
      description
        "TRUE to enable BFD. FALSE to disable and to
        prevent inheritance from a parent";
    }
  }

  grouping NEIGHBOR-GRACEFUL-RESTART-STALEPATH-TIME {
    description
      "Common node of neighbor-group, neighbor,
      vrf-neighbor, session-group";
    leaf neighbor-graceful-restart-stalepath-time {
      xr:xr-xml-map "bgp_cfg:NeighborGracefulRestartStalepathTime";
      type uint32 {
        range "1..4095";
      }
      units "second";
      default "360";
      description "Max time (seconds)";
    }
  }

  grouping BEST-PATH-AIGP-IGNORE {
    description "Common node of global, vrf-global";
    leaf best-path-aigp-ignore {
      xr:xr-xml-map "bgp_cfg:BestPathAIGPIgnore";
      type empty;
      description
        "Change default route selection criteria to
        ignore AIGP unless both paths whichare compared
        have AIGP attribute";
    }
  }

  grouping SESSION-GROUP-ADD-MEMBER {
    description
      "Common node of neighbor-group, neighbor,
      vrf-neighbor";
    leaf session-group-add-member {
      xr:xr-xml-map "bgp_cfg:SessionGroupAddMember";
      type string;
      description "Session group name";
    }
  }

  grouping BFD-MULTIPLIER {
    description
      "Common node of neighbor-group, neighbor,
      vrf-neighbor, session-group";
    leaf bfd-multiplier {
      xr:xr-xml-map "bgp_cfg:BFDMultiplier";
      type uint32 {
        range "2..16";
      }
      description "BFD multiplier";
    }
  }

  grouping FLOWSPEC-VALIDATION {
    description
      "Common node of neighbor-group-af, neighbor-af,
      vrf-neighbor-af, af-group-af";
    leaf flowspec-validation {
      xr:xr-xml-map "bgp_cfg:FlowspecValidation";
      type Bgp-flowspec-validation-cfg;
      description "Config Flowspec validation for this neighbor";
    }
  }

  grouping TTL-SECURITY {
    description
      "Common node of neighbor-group, neighbor,
      vrf-neighbor, session-group";
    leaf ttl-security {
      xr:xr-xml-map "bgp_cfg:TTLSecurity";
      type boolean;
      description
        "TRUE to enable BGP TTL Security.  FALSE to not
        enable it and to prevent inheritance from a
        parent";
    }
  }

  grouping BEST-PATH-MED-ALWAYS {
    description "Common node of global, vrf-global";
    leaf best-path-med-always {
      xr:xr-xml-map "bgp_cfg:BestPathMEDAlways";
      type empty;
      description
        "Change default route selection criteria and
        allow comparing of MED from different neighbors";
    }
  }

  grouping SEND-COMMUNITY-EBGP-GRACEFUL-SHUTDOWN {
    description
      "Common node of neighbor-group-af, neighbor-af,
      vrf-neighbor-af, af-group-af";
    leaf send-community-ebgp-graceful-shutdown {
      xr:xr-xml-map "bgp_cfg:SendCommunityEBGPGracefulShutdown";
      type boolean;
      description
        "TRUE to send communities to the external
        neighbor/neighbor-group/af-group.  FALSE not to
        send and to prevent inheritance from a parent";
    }
  }

  grouping DISABLE-MSG-LOG {
    description "Common node of global, vrf-global";
    leaf disable-msg-log {
      xr:xr-xml-map "bgp_cfg:DisableMsgLog";
      type empty;
      description
        "Disable inbound and outbound messagelogging for
        all neighbors under the vrf";
    }
  }

  grouping LOCAL-AS {
    description
      "Common node of neighbor-group, neighbor,
      vrf-neighbor, session-group";

    container local-as {
      xr:xr-xml-map "bgp_cfg:LocalAS";
      description "Specify a local-as number";
      leaf as-xx {
        xr:xr-xml-map "bgp_cfg:AS_XX";
        type dt1:Bgp-as-range;
        description "xx of AS number xx.yy";
      }
      leaf as-yy {
        xr:xr-xml-map "bgp_cfg:AS_YY";
        type dt1:Bgp-as-range;
        description "yy of AS number xx.yy";
      }
      leaf no-prepend {
        xr:xr-xml-map "bgp_cfg:NoPrepend";
        type empty;
        description
          "Do not prepend Local AS to announcements from
          this neighbor";
      }
      leaf disable {
        xr:xr-xml-map "bgp_cfg:Disable";
        type empty;
        description
          "Disable Local AS and prevent it from being
          inherited from a parent";
      }
      leaf replace-as {
        xr:xr-xml-map "bgp_cfg:ReplaceAS";
        type empty;
        description
          "Prepend only Local AS to announcements from
          this neighbor";
      }
      leaf dual-as {
        xr:xr-xml-map "bgp_cfg:DualAS";
        type empty;
        description "Dual-AS mode";
      }
    }
  }

  grouping LISP-ROUTES {
    description "Common node of global-af, vrf-global-af";

    container lisp-routes {
      xr:xr-xml-map "bgp_cfg:LispRoutes";
      presence "enable lisp-routes";
      description "Redistribute lisp routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
    }
  }

  grouping ADDITIONAL-PATHS-SEND-CAPABILITY {
    description
      "Common node of neighbor-group, neighbor,
      vrf-neighbor, session-group";
    leaf additional-paths-send-capability {
      xr:xr-xml-map "bgp_cfg:AdditionalPathsSendCapability";
      type dt1:Bgp-nbr-cap-additional-paths-cfg;
      description "Enable/disable Send capability";
    }
  }

  grouping L2VPN-SIGNALLING {
    description
      "Common node of neighbor-group-af, neighbor-af,
      vrf-neighbor-af, af-group-af";
    leaf l2vpn-signalling {
      xr:xr-xml-map "bgp_cfg:L2VPNSignalling";
      type Bgp-signal;
      description "Disable signalling type";
    }
  }

  grouping DAMPENING {
    description "Common node of global-af, vrf-global-af";

    container dampening {
      xr:xr-xml-map "bgp_cfg:Dampening";
      presence "enable dampening";
      description "Enable route-flap dampening";
      leaf half-life {
        xr:xr-xml-map "bgp_cfg:HalfLife";
        type uint32 {
          range "1..45";
        }
        units "minute";
        description "Half-life time for the penalty (minutes).";
      }
      leaf reuse-threshold {
        xr:xr-xml-map "bgp_cfg:ReuseThreshold";
        type uint32 {
          range "1..20000";
        }
        description "Value to start reusing a route.";
      }
      leaf suppress-threshold {
        xr:xr-xml-map "bgp_cfg:SuppressThreshold";
        type uint32 {
          range "1..20000";
        }
        description "Value to start suppressing a route.";
      }
      leaf suppress-time {
        xr:xr-xml-map "bgp_cfg:SuppressTime";
        type uint32 {
          range "1..255";
        }
        units "second";
        description
          "Maximum duration to suppress a stable route
          (seconds).";
      }
      leaf route-policy-name {
        xr:xr-xml-map "bgp_cfg:RoutePolicyName";
        type string;
        description
          "Route policy to specify criteria for dampening.
          This cannot be specified if any other
          parameters are specified.";
      }
    }
  }

  grouping SUBSCRIBER-ROUTES {
    description "Common node of global-af, vrf-global-af";

    container subscriber-routes {
      xr:xr-xml-map "bgp_cfg:SubscriberRoutes";
      presence "enable subscriber-routes";
      description "Redistribute subscriber routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
      leaf not-used {
        xr:xr-xml-map "bgp_cfg:NotUsed";
        type uint32 {
          range "0..127";
        }
        description "Not used";
      }
    }
  }

  grouping INTERNAL-VPN-CLIENT-IBGPCE {
    description
      "Common node of neighbor-group, neighbor,
      vrf-neighbor, session-group";
    leaf internal-vpn-client-ibgpce {
      xr:xr-xml-map "bgp_cfg:InternalVPNClientIBGPCE";
      type boolean;
      description
        "TRUE to preserve the CE path attributes.FALSE to
        override CE path attributes.";
    }
  }

  grouping ACCEPT-ROUTE-LEGACY-RT {
    description
      "Common node of neighbor-group-af, neighbor-af,
      vrf-neighbor-af, af-group-af";
    leaf accept-route-legacy-rt {
      xr:xr-xml-map "bgp_cfg:AcceptRouteLegacyRT";
      type boolean;
      description
        "TRUE to configure as a accept-route-legacy-RT. 
        FALSE to prevent accept-route-legacy-RT from
        being inherited.";
    }
  }

  grouping PERMANENT-NETWORK {
    description "Common node of global-af, vrf-global-af";
    leaf permanent-network {
      xr:xr-xml-map "bgp_cfg:PermanentNetwork";
      type string;
      description "Route policy for permanent networks";
    }
  }

  grouping ENABLE {
    description "Common node of global-af, vrf-global-af";
    leaf enable {
      xr:xr-xml-map "bgp_cfg:Enable";
      type empty;
      description "Enable the address family";
    }
  }

  grouping ADVERTISEMENT-INTERVAL {
    description
      "Common node of neighbor-group, neighbor,
      vrf-neighbor, session-group";

    container advertisement-interval {
      xr:xr-xml-map "bgp_cfg:AdvertisementInterval";
      presence "Indicates a advertisement-interval node is"+
        " configured.";
      description
        "Minimum interval between sending BGP routing
        updates";
      leaf minimum-interval {
        xr:xr-xml-map "bgp_cfg:MinimumInterval";
        type uint32 {
          range "0..600";
        }
        units "second";
        mandatory true;
        description
          "Minimum advertisement interval time, secs part";
      }
      leaf minimum-interval-msecs {
        xr:xr-xml-map "bgp_cfg:MinimumIntervalMsecs";
        type uint32 {
          range "0..999";
        }
        units "millisecond";
        description
          "Minimum advertisement interval time, msecs part";
      }
    }
  }

  grouping EBGP {
    description "Common node of global-af, vrf-global-af";

    container ebgp {
      xr:xr-xml-map "bgp_cfg:EBGP";
      presence "Indicates a ebgp node is configured.";
      description "Use eBGP multipaths";
      leaf paths-value {
        xr:xr-xml-map "bgp_cfg:PathsValue";
        type uint32 {
          range "2..32";
        }
        mandatory true;
        description "Number of paths";
      }
      leaf unequal-cost {
        xr:xr-xml-map "bgp_cfg:UnequalCost";
        type boolean;
        default "false";
        description "UNUSED";
      }
      leaf selective {
        xr:xr-xml-map "bgp_cfg:Selective";
        type boolean;
        default "false";
        description "Allow multipaths only from marked neighbors";
      }
      leaf order-by-igp-metric {
        xr:xr-xml-map "bgp_cfg:OrderByIGPMetric";
        type boolean;
        default "false";
        description "Order candidate multipaths by IGP metric";
      }
    }
  }

  grouping IMPORT {
    description
      "Common node of neighbor-group-af, neighbor-af,
      vrf-neighbor-af, af-group-af";

    container import {
      xr:xr-xml-map "bgp_cfg:Import";
      description
        "Import Reorigination options for Routes from the
        peer";
      leaf import-stitching {
        xr:xr-xml-map "bgp_cfg:ImportStitching";
        type boolean;
        description
          "TRUE to Import with Stitching RTs, FALSE to
          Import with normal RTs";
      }
      leaf import-reoriginate {
        xr:xr-xml-map "bgp_cfg:ImportReoriginate";
        type boolean;
        description
          "TRUE to Reoriginate imported routes, FALSE to
          not Reoriginate imported routes - not supported";
      }
      leaf import-reoriginate-stitching {
        xr:xr-xml-map "bgp_cfg:ImportReoriginateStitching";
        type boolean;
        description
          "TRUE to Reoriginate imported routes with
          Stitching RTs, FALSE to Reoriginate imported
          routes with normal RTs";
      }
    }
  }

  grouping ACCEPT-OWN {
    description
      "Common node of neighbor-group-af, neighbor-af,
      vrf-neighbor-af, af-group-af";
    leaf accept-own {
      xr:xr-xml-map "bgp_cfg:AcceptOwn";
      type boolean;
      description
        "TRUE to enable. FALSE to disable and prevent
        inherit from parent.";
    }
  }

  grouping ADDITIONAL-PATHS-RECEIVE {
    description "Common node of global-af, vrf-global-af";
    leaf additional-paths-receive {
      xr:xr-xml-map "bgp_cfg:AdditionalPathsReceive";
      type dt1:Bgpaf-additional-paths-cfg;
      description "Enable/disable Receive capability";
    }
  }

  grouping MPLS-ACTIVATED-INTERFACE-TABLE {
    description "Common node of global, vrf-global";

    container mpls-activated-interfaces {
      xr:xr-xml-map "bgp_cfg:MPLSActivatedInterfaceTable";
      description "Configure list of MPLS activated interfaces";

      list mpls-activated-interface {
        xr:xr-xml-map "bgp_cfg:MPLSActivatedInterface";
        key "interface-name";
        description "Configure a MPLS activated interface";
        leaf interface-name {
          xr:xr-xml-map "bgp_cfg:InterfaceName";
          type xr:Interface-name;
          description "Interface Name";
        }
      }
    }
  }

  grouping MULTIPATH {
    description
      "Common node of neighbor-group-af, neighbor-af,
      vrf-neighbor-af, af-group-af";
    leaf multipath {
      xr:xr-xml-map "bgp_cfg:Multipath";
      type empty;
      description "Eligible for multipath";
    }
  }

  grouping EI-GRP-ROUTE-TABLE {
    description "Common node of global-af, vrf-global-af";

    container ei-grp-routes {
      xr:xr-xml-map "bgp_cfg:EIGRPRouteTable";
      description "Redistribute information for EIGRP routes.";

      list ei-grp-route {
        xr:xr-xml-map "bgp_cfg:EIGRPRoute";
        key "instance-name";
        description "Redistribute EIGRP routes";
        leaf instance-name {
          xr:xr-xml-map "bgp_cfg:InstanceName";
          type xr:Cisco-ios-xr-string;
          description "EIGRP router tag";
        }
        leaf default-metric {
          xr:xr-xml-map "bgp_cfg:DefaultMetric";
          type Bgp-default-metric-range;
          description "Default metric";
        }
        leaf route-policy-name {
          xr:xr-xml-map "bgp_cfg:RoutePolicyName";
          type string;
          description "Route policy name";
        }
        leaf redist-type {
          xr:xr-xml-map "bgp_cfg:RedistType";
          type xr:Hex-integer;
          description
            "Redistribution type: 0x01 for internal routes,
            0x02 for external routes, Logical combinations
            permitted.";
        }
      }
    }
  }

  grouping ROUTE-REFLECTOR-CLIENT {
    description
      "Common node of neighbor-group-af, neighbor-af,
      vrf-neighbor-af, af-group-af";
    leaf route-reflector-client {
      xr:xr-xml-map "bgp_cfg:RouteReflectorClient";
      type boolean;
      description
        "TRUE to configure as a route-reflector-client. 
        FALSE to prevent route-reflector-client from
        being inherited.";
    }
  }

  grouping SESSION-OPEN-MODE {
    description
      "Common node of neighbor-group, neighbor,
      vrf-neighbor, session-group";
    leaf session-open-mode {
      xr:xr-xml-map "bgp_cfg:SessionOpenMode";
      type Bgp-tcp-mode;
      default "either";
      description "The TCP mode to use";
    }
  }

  grouping STATIC-ROUTES {
    description "Common node of global-af, vrf-global-af";

    container static-routes {
      xr:xr-xml-map "bgp_cfg:StaticRoutes";
      presence "enable static-routes";
      description "Redistribute static routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
      leaf not-used {
        xr:xr-xml-map "bgp_cfg:NotUsed";
        type uint32 {
          range "0..127";
        }
        description "Not used";
      }
    }
  }

  grouping PASSWORD {
    description
      "Common node of neighbor-group, neighbor,
      vrf-neighbor, session-group";

    container password {
      xr:xr-xml-map "bgp_cfg:Password";
      description "Set or disable a password";
      leaf password-disable {
        xr:xr-xml-map "bgp_cfg:PasswordDisable";
        type boolean;
        description
          "TRUE to prevent this entity from having a
          password even if the parent has one.  FALSEto
          specify a password";
      }
      leaf password {
        xr:xr-xml-map "bgp_cfg:Password";
        when "../password-disable = 'false'" {
          description "../PasswordDisable = 0";
        }
        type xr:Proprietary-password;
        description
          "The neighbor password.  Leave unspecified when
          disabling the password.";
      }
    }
  }

  grouping NEXT-HOP-UNCHANGED-MULTIPATH {
    description
      "Common node of neighbor-group-af, neighbor-af,
      vrf-neighbor-af, af-group-af";
    leaf next-hop-unchanged-multipath {
      xr:xr-xml-map "bgp_cfg:NextHopUnchangedMultipath";
      type boolean;
      description
        "TRUE to disable overwriting of next hop for
        multipaths. FALSE to prevent next-hop-unchanged
        for multipaths.";
    }
  }

  grouping NEXT-HOP-RESOLUTION-PREFIX-LENGTH-MINIMUM {
    description "Common node of global-af, vrf-global-af";
    leaf next-hop-resolution-prefix-length-minimum {
      xr:xr-xml-map "bgp_cfg:NextHopResolutionPrefixLengthMinimum";
      type uint32 {
        range "0..128";
      }
      default "0";
      description "Minimum prefix-length";
    }
  }

  grouping BEST-PATH-AS-PATH-LENGTH {
    description "Common node of global, vrf-global";
    leaf best-path-as-path-length {
      xr:xr-xml-map "bgp_cfg:BestPathASPathLength";
      type empty;
      description
        "Change default route selection criteria to
        ignore AS path length";
    }
  }

  grouping MSG-LOG-OUT {
    description
      "Common node of neighbor-group, neighbor,
      vrf-neighbor, session-group";

    container msg-log-out {
      xr:xr-xml-map "bgp_cfg:MsgLogOut";
      description "Message log outbound";
      leaf msg-buf-count {
        xr:xr-xml-map "bgp_cfg:MsgBufCount";
        type uint32 {
          range "1..100";
        }
        description "Outbound message log buffer size";
      }
      leaf msg-log-disable {
        xr:xr-xml-map "bgp_cfg:MsgLogDisable";
        type boolean;
        description "Disable inbound message logging";
      }
      leaf msg-log-inherit-disable {
        xr:xr-xml-map "bgp_cfg:MsgLogInheritDisable";
        type boolean;
        description
          "TRUE, to prevent this entity from having a
          outbound message logging if parent has one";
      }
    }
  }

  grouping PREFIX-ORF-POLICY {
    description
      "Common node of neighbor-group-af, neighbor-af,
      vrf-neighbor-af, af-group-af";
    leaf prefix-orf-policy {
      xr:xr-xml-map "bgp_cfg:PrefixORFPolicy";
      type string;
      description "Prefix ORF policy name for incoming updates";
    }
  }

  grouping SOURCED-NETWORK-TABLE {
    description "Common node of global-af, vrf-global-af";

    container sourced-networks {
      xr:xr-xml-map "bgp_cfg:SourcedNetworkTable";
      description "Specify a network to announce via BGP";

      list sourced-network {
        xr:xr-xml-map "bgp_cfg:SourcedNetwork";
        key "network-addr network-prefix";
        description "Sourced network configuration";
        leaf network-addr {
          xr:xr-xml-map "bgp_cfg:Network";
          type inet:ip-address;
          description
            "Network in prefix/length format (address part)";
        }
        leaf network-prefix {
          xr:xr-xml-map "bgp_cfg:Network";
          type uint16 {
            range "0..128";
          }
          description
            "Network in prefix/length format (prefix part)";
        }
        leaf backdoor {
          xr:xr-xml-map "bgp_cfg:Backdoor";
          type boolean;
          description
            "Specify a BGP backdoor route, default is FALSE";
        }
        leaf route-policy-name {
          xr:xr-xml-map "bgp_cfg:RoutePolicyName";
          type string;
          description "Route policy name";
        }
      }
    }
  }

  grouping REMOVE-PRIVATE-AS-ENTIRE-AS-PATH {
    description
      "Common node of neighbor-group-af, neighbor-af,
      vrf-neighbor-af, af-group-af";

    container remove-private-as-entire-as-path {
      xr:xr-xml-map "bgp_cfg:RemovePrivateASEntireASpath";
      presence "Indicates a remove-private-as-entire-as-path node"+
        " is configured.";
      description "Remove private AS number from outbound updates";
      leaf enable {
        xr:xr-xml-map "bgp_cfg:Enable";
        type boolean;
        mandatory true;
        description
          "TRUE to remove private AS from outbound updates
          .  FALSE to prevent remove-private-AS from
          being inherited.";
      }
      leaf entire {
        xr:xr-xml-map "bgp_cfg:Entire";
        type boolean;
        description
          "TRUE to remove private AS from outbound updates
          if all ASes in aspath areprivate. FALSE to
          prevent remove-private-ASfrom being inherited.";
      }
    }
  }

  grouping GRACEFUL-MAINTENANCE {
    description
      "Common node of neighbor-group, neighbor,
      vrf-neighbor, session-group";

    container graceful-maintenance {
      xr:xr-xml-map "bgp_cfg:GracefulMaintenance";
      description "Graceful Maintenance mode";

      container graceful-maintenance-local-preference {
        xr:xr-xml-map "bgp_cfg:GracefulMaintenanceLocalPreference";
        description "Set Local Preference to advertise routes with";
        leaf gshut-loc-pref-disable {
          xr:xr-xml-map "bgp_cfg:GSHUTLocPrefDisable";
          type boolean;
          description
            "TRUE, to prevent inheritance of Local Pref
            value from its parents.FALSE, otherwise";
        }
        leaf local-preference {
          xr:xr-xml-map "bgp_cfg:LocalPreference";
          type uint32 {
            range "0..4294967295";
          }
          description "Local Preference Value";
        }
      }

      container graceful-maintenance-as-prepends {
        xr:xr-xml-map "bgp_cfg:GracefulMaintenanceASPrepends";
        description
          "Number of times to prepend local AS number to
          the AS path";
        leaf gshut-prepends-disable {
          xr:xr-xml-map "bgp_cfg:GSHUTPrependsDisable";
          type boolean;
          description
            "TRUE, to prevent inheritance of AS Prepends
            value from its parents.FALSE, otherwise";
        }
        leaf as-prepends {
          xr:xr-xml-map "bgp_cfg:ASPrepends";
          type uint32 {
            range "0..6";
          }
          description "number of times AS prepends";
        }
      }
      leaf enable {
        xr:xr-xml-map "bgp_cfg:Enable";
        type empty;
        description "Configure Graceful Maintenance parameters";
      }
      leaf graceful-maintenance-activate {
        xr:xr-xml-map "bgp_cfg:GracefulMaintenanceActivate";
        type boolean;
        description "Initiate graceful shutdown procedure";
      }
    }
  }

  grouping GRACEFUL-RESTART {
    description "Common node of global, vrf-global";
    leaf graceful-restart {
      xr:xr-xml-map "bgp_cfg:GracefulRestart";
      type empty;
      description "Enable graceful restart support";
    }
  }

  grouping NEIGHBOR-AF-LONG-LIVED-GRACEFUL-RESTART-STALE-TIME {
    description
      "Common node of neighbor-group-af, neighbor-af,
      vrf-neighbor-af, af-group-af";

    container neighbor-af-long-lived-graceful-restart-stale-time {
      xr:xr-xml-map "bgp_cfg:NeighborAFLongLivedGracefulRestartStal"+
        "eTime";
      description
        "Maximum time to wait before purging long lived
        routes";
      leaf stale-time-send {
        xr:xr-xml-map "bgp_cfg:StaleTimeSend";
        type uint32 {
          range "0..16777215";
        }
        units "second";
        default "0";
        description "Max time (seconds)";
      }
      leaf stale-time-accept {
        xr:xr-xml-map "bgp_cfg:StaleTimeAccept";
        type uint32 {
          range "0..16777215";
        }
        units "second";
        default "0";
        description "Max time (seconds)";
      }
    }
  }

  grouping BFD {
    description
      "Common node of neighbor-group, neighbor,
      vrf-neighbor, session-group";
    leaf bfd {
      xr:xr-xml-map "bgp_cfg:BFD";
      type boolean;
      description
        "TRUE to enable BFD. FALSE to disable and to
        prevent inheritance from a parent";
    }
  }

  grouping BGP-CFG-BFD {
    description "Common node of global, vrf-global";

    container bfd {
      xr:xr-xml-map "bgp_cfg:BFD";
      description "BFD configuration";
      leaf detection-multiplier {
        xr:xr-xml-map "bgp_cfg:DetectionMultiplier";
        type uint32 {
          range "2..16";
        }
        description "BFD multiplier";
      }
      leaf interval {
        xr:xr-xml-map "bgp_cfg:Interval";
        type uint32 {
          range "3..30000";
        }
        units "millisecond";
        description "BFD hello interval in milliseconds";
      }
    }
  }

  grouping ALLOCATE-LABEL {
    description "Common node of global-af, vrf-global-af";

    container allocate-label {
      xr:xr-xml-map "bgp_cfg:AllocateLabel";
      description "Label allocation policy";
      leaf all {
        xr:xr-xml-map "bgp_cfg:All";
        type boolean;
        description
          "Whether all nets should be labeled, default is
          FALSE";
      }
      leaf route-policy-name {
        xr:xr-xml-map "bgp_cfg:RoutePolicyName";
        type string;
        description "Route policy name";
      }
    }
  }

  grouping SEND-BUFFER-SIZE {
    description
      "Common node of neighbor-group, neighbor,
      vrf-neighbor, session-group";

    container send-buffer-size {
      xr:xr-xml-map "bgp_cfg:SendBufferSize";
      description
        "Set socket send buffer size and BGP write buffer
        size";
      leaf socket-send-size {
        xr:xr-xml-map "bgp_cfg:SocketSendSize";
        type uint32 {
          range "4096..131072";
        }
        units "byte";
        default "24576";
        description "Send socket buffer size in bytes";
      }
      leaf bgp-send-size {
        xr:xr-xml-map "bgp_cfg:BGPSendSize";
        type uint32 {
          range "4096..131072";
        }
        units "byte";
        default "4096";
        description "BGP write buffer size in bytes";
      }
    }
  }

  grouping BEST-PATH-MED-MISSING {
    description "Common node of global, vrf-global";
    leaf best-path-med-missing {
      xr:xr-xml-map "bgp_cfg:BestPathMEDMissing";
      type empty;
      description "Treat missing MED as the least preferred one";
    }
  }

  grouping DEFAULT-WEIGHT {
    description
      "Common node of neighbor-group-af, neighbor-af,
      vrf-neighbor-af, af-group-af";
    leaf default-weight {
      xr:xr-xml-map "bgp_cfg:DefaultWeight";
      type uint32 {
        range "0..65535";
      }
      description "Default weight";
    }
  }

  grouping SUPPRESS-FOUR-BYTE-AS-CAPABILITY {
    description
      "Common node of neighbor-group, neighbor,
      vrf-neighbor, session-group";
    leaf suppress-four-byte-as-capability {
      xr:xr-xml-map "bgp_cfg:SuppressFourByteASCapability";
      type boolean;
      description
        "TRUE to suppress BGP 4-byte-as capability. 
        FALSE to not suppress it and to prevent
        inheritance from a parent";
    }
  }

  grouping EGRESS-PEER-ENGINEERING {
    description
      "Common node of neighbor-group, neighbor,
      vrf-neighbor, session-group";
    leaf egress-peer-engineering {
      xr:xr-xml-map "bgp_cfg:EgressPeerEngineering";
      type boolean;
      description
        "TRUE to enable egress peer engineering FALSE to
        disable egress peer engineering and to prevent
        inheritance from a parent";
    }
  }

  grouping BEST-PATH-CONFEDERATION-PATHS {
    description "Common node of global, vrf-global";
    leaf best-path-confederation-paths {
      xr:xr-xml-map "bgp_cfg:BestPathConfederationPaths";
      type empty;
      description
        "Change default route selection criteria and
        allow the comparing of MED among confederation
        paths";
    }
  }

  grouping DYNAMIC-MED-INTERVAL {
    description "Common node of global-af, vrf-global-af";
    leaf dynamic-med-interval {
      xr:xr-xml-map "bgp_cfg:DynamicMEDInterval";
      type uint32 {
        range "0..10";
      }
      units "minute";
      default "10";
      description "Update generation delay after a MED change";
    }
  }

  grouping REMOVE-PRIVATE-AS-ENTIRE-AS-PATH-INBOUND {
    description
      "Common node of neighbor-group-af, neighbor-af,
      vrf-neighbor-af, af-group-af";

    container remove-private-as-entire-as-path-inbound {
      xr:xr-xml-map "bgp_cfg:RemovePrivateASEntireASpathInbound";
      presence "Indicates a"+
        " remove-private-as-entire-as-path-inbound node is"+
        " configured.";
      description "Remove private AS number from inbound updates";
      leaf enable {
        xr:xr-xml-map "bgp_cfg:Enable";
        type boolean;
        mandatory true;
        description
          "TRUE to remove private AS from inbound updates.
          FALSE to prevent remove-private-AS from being
          inherited.";
      }
      leaf entire {
        xr:xr-xml-map "bgp_cfg:Entire";
        type boolean;
        description
          "TRUE to remove private AS from inbound updates
          if all ASes in aspath areprivate. FALSE to
          prevent remove-private-ASfrom being inherited.";
      }
    }
  }

  grouping CONNECTED-ROUTES {
    description "Common node of global-af, vrf-global-af";

    container connected-routes {
      xr:xr-xml-map "bgp_cfg:ConnectedRoutes";
      presence "enable connected-routes";
      description "Redistribute connected routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
      leaf not-used {
        xr:xr-xml-map "bgp_cfg:NotUsed";
        type uint32 {
          range "0..127";
        }
        description "Not used";
      }
    }
  }

  grouping IGP-REDIST-INTERNAL {
    description "Common node of global, vrf-global";
    leaf igp-redist-internal {
      xr:xr-xml-map "bgp_cfg:IGPRedistInternal";
      type empty;
      description "Enable redistribution of iBGP into IGPs";
    }
  }

  grouping AIGP-SEND-MED {
    description
      "Common node of neighbor-group-af, neighbor-af,
      vrf-neighbor-af, af-group-af";
    leaf aigp-send-med {
      xr:xr-xml-map "bgp_cfg:AIGPSendMED";
      type Bgp-aigp-cfg;
      description "Enable/Disable sending AIGP in MED ";
    }
  }

  grouping AIGP {
    description
      "Common node of neighbor-group-af, neighbor-af,
      vrf-neighbor-af, af-group-af";
    leaf aigp {
      xr:xr-xml-map "bgp_cfg:AIGP";
      type Bgp-aigp-cfg;
      description "Enable/Disable disable AIGP ";
    }
  }

  grouping ADVERTISE-ORF {
    description
      "Common node of neighbor-group-af, neighbor-af,
      vrf-neighbor-af, af-group-af";
    leaf advertise-orf {
      xr:xr-xml-map "bgp_cfg:AdvertiseORF";
      type Bgp-orf;
      default "none";
      description "Receive, Send, Both or None.";
    }
  }

  grouping BFD-MINIMUM-INTERVAL {
    description
      "Common node of neighbor-group, neighbor,
      vrf-neighbor, session-group";
    leaf bfd-minimum-interval {
      xr:xr-xml-map "bgp_cfg:BFDMinimumInterval";
      type uint32 {
        range "3..30000";
      }
      units "millisecond";
      description "BFD hello interval in milliseconds";
    }
  }

  grouping AIGP-COST-COMMUNITY {
    description
      "Common node of neighbor-group-af, neighbor-af,
      vrf-neighbor-af, af-group-af";

    container aigp-cost-community {
      xr:xr-xml-map "bgp_cfg:AIGPCostCommunity";
      presence "Indicates a aigp-cost-community node is configured.";
      description "Send AIGP value in Cost Community. ";
      leaf enable {
        xr:xr-xml-map "bgp_cfg:Enable";
        type boolean;
        mandatory true;
        description
          "TRUE to enable sending cost community, FALSE
          otherwise ";
      }
      leaf cost-community-id {
        xr:xr-xml-map "bgp_cfg:CostCommunityID";
        type uint32 {
          range "0..255";
        }
        mandatory true;
        description "Cost Community ID";
      }
      leaf transitive {
        xr:xr-xml-map "bgp_cfg:Transitive";
        type boolean;
        description
          "True to send transitive cost community FALSE
          otherwise";
      }
      leaf cost-community-poi-type {
        xr:xr-xml-map "bgp_cfg:CostCommunityPOIType";
        type Bgp-aigp-cfg-poi;
        mandatory true;
        description "Cost Community POI";
      }
    }
  }

  grouping DISABLE-AS-PATH-LOOP-CHECK {
    description "Common node of global-af, vrf-global-af";
    leaf disable-as-path-loop-check {
      xr:xr-xml-map "bgp_cfg:DisableASPathLoopCheck";
      type empty;
      description "Disable outbound AS Path loopcheck";
    }
  }

  grouping BEST-PATH-ROUTER-ID {
    description "Common node of global, vrf-global";
    leaf best-path-router-id {
      xr:xr-xml-map "bgp_cfg:BestPathRouterID";
      type empty;
      description
        "Change default route selection criteria and
        compare router-id for identical EBGP paths";
    }
  }

  grouping RIP-ROUTES {
    description "Common node of global-af, vrf-global-af";

    container rip-routes {
      xr:xr-xml-map "bgp_cfg:RIPRoutes";
      presence "enable rip-routes";
      description "Redistribute RIP routes";
      leaf default-metric {
        xr:xr-xml-map "bgp_cfg:DefaultMetric";
        type Bgp-default-metric-range;
        description "Default metric";
      }
      leaf route-policy-name {
        xr:xr-xml-map "bgp_cfg:RoutePolicyName";
        type string;
        description "Route policy name";
      }
      leaf not-used {
        xr:xr-xml-map "bgp_cfg:NotUsed";
        type uint32 {
          range "0..127";
        }
        description "Not used";
      }
    }
  }

  grouping DESCRIPTION {
    description
      "Common node of neighbor-group, neighbor,
      vrf-neighbor, session-group";
    leaf description {
      xr:xr-xml-map "bgp_cfg:Description";
      type string;
      description "Up to 80 characters describing this neighbor";
    }
  }

  grouping KEYCHAIN {
    description
      "Common node of neighbor-group, neighbor,
      vrf-neighbor, session-group";

    container keychain {
      xr:xr-xml-map "bgp_cfg:Keychain";
      description "Set or disable keychain based authentication";
      leaf keychain-disable {
        xr:xr-xml-map "bgp_cfg:KeychainDisable";
        type boolean;
        description
          "TRUE to prevent this entity from having a
          keychain based authentication even if the
          parent has one.FALSE to specify a keychain name";
      }
      leaf keychain-name {
        xr:xr-xml-map "bgp_cfg:KeychainName";
        when "../keychain-disable = 'false'" {
          description "../KeychainDisable = 0";
        }
        type string;
        description "Name of the keychain associated with neighbor";
      }
    }
  }

  grouping RECEIVE-BUFFER-SIZE {
    description
      "Common node of neighbor-group, neighbor,
      vrf-neighbor, session-group";

    container receive-buffer-size {
      xr:xr-xml-map "bgp_cfg:ReceiveBufferSize";
      description
        "Set socket receive buffer size and BGP read
        buffer size";
      leaf socket-receive-size {
        xr:xr-xml-map "bgp_cfg:SocketReceiveSize";
        type uint32 {
          range "512..131072";
        }
        units "byte";
        default "32768";
        description "Receive socket buffer size in bytes";
      }
      leaf bgp-receive-size {
        xr:xr-xml-map "bgp_cfg:BGPReceiveSize";
        type uint32 {
          range "512..131072";
        }
        units "byte";
        default "4096";
        description "BGP read buffer size in bytes";
      }
    }
  }

  grouping NEXT-HOP-UNCHANGED {
    description
      "Common node of neighbor-group-af, neighbor-af,
      vrf-neighbor-af, af-group-af";
    leaf next-hop-unchanged {
      xr:xr-xml-map "bgp_cfg:NextHopUnchanged";
      type boolean;
      description
        "TRUE to disable overwriting of next hop before
        advertising to eBGP peers. FALSE to prevent
        next-hop-unchanged from being inherited.";
    }
  }

  grouping OSPF-ROUTE-TABLE {
    description "Common node of global-af, vrf-global-af";

    container ospf-routes {
      xr:xr-xml-map "bgp_cfg:OSPFRouteTable";
      description "Redistribute information for OSPF routes.";

      list ospf-route {
        xr:xr-xml-map "bgp_cfg:OSPFRoute";
        key "instance-name";
        description "Redistribute OSPF routes";
        leaf instance-name {
          xr:xr-xml-map "bgp_cfg:InstanceName";
          type xr:Cisco-ios-xr-string;
          description "OSPF router tag";
        }
        leaf default-metric {
          xr:xr-xml-map "bgp_cfg:DefaultMetric";
          type Bgp-default-metric-range;
          description "Default metric";
        }
        leaf route-policy-name {
          xr:xr-xml-map "bgp_cfg:RoutePolicyName";
          type string;
          description "Route policy name";
        }
        leaf redist-type {
          xr:xr-xml-map "bgp_cfg:RedistType";
          type xr:Hex-integer;
          description
            "Redistribution type: 0x01 for internal routes,
            0x02 for external routes of type 1, 0x04 for
            external routes of type 2, 0x08 for NSSA
            external routes of type 1, 0x10 for NSSA
            external routes of type 2, 0x20 for external
            routes, 0x40 for NSSA external routes. 
            Logical combinations permitted.";
        }
      }
    }
  }

  grouping EIBGP {
    description "Common node of global-af, vrf-global-af";

    container eibgp {
      xr:xr-xml-map "bgp_cfg:EIBGP";
      presence "Indicates a eibgp node is configured.";
      description "Use eiBGP multipaths";
      leaf paths-value {
        xr:xr-xml-map "bgp_cfg:PathsValue";
        type uint32 {
          range "2..32";
        }
        mandatory true;
        description "Number of paths";
      }
      leaf unequal-cost {
        xr:xr-xml-map "bgp_cfg:UnequalCost";
        type boolean;
        default "false";
        description "UNUSED";
      }
      leaf selective {
        xr:xr-xml-map "bgp_cfg:Selective";
        type boolean;
        default "false";
        description "Allow multipaths only from marked neighbors";
      }
      leaf order-by-igp-metric {
        xr:xr-xml-map "bgp_cfg:OrderByIGPMetric";
        type boolean;
        default "false";
        description "Order candidate multipaths by IGP metric";
      }
    }
  }

  grouping ROUTER-ID {
    description "Common node of global, vrf-global";
    leaf router-id {
      xr:xr-xml-map "bgp_cfg:RouterID";
      type inet:ipv4-address-no-zone;
      default "0.0.0.0";
      description "IPV4 address";
    }
  }

  grouping DEFAULT-METRIC {
    description "Common node of global, vrf-global";
    leaf default-metric {
      xr:xr-xml-map "bgp_cfg:DefaultMetric";
      type uint32 {
        range "1..4294967295";
      }
      description "Default metric";
    }
  }

  grouping RPKI-ORIGIN-AS-VALIDATION-DISABLE {
    description
      "Common node of neighbor-group-af, neighbor-af,
      vrf-neighbor-af, af-group-af";
    leaf rpki-origin-as-validation-disable {
      xr:xr-xml-map "bgp_cfg:RPKIOriginASValidationDisable";
      type empty;
      description "RPKI origin-AS validation disable";
    }
  }

  grouping BGP-CFG-RPKI-ORIGIN-AS-VALIDATION-DISABLE {
    description
      "Common node of neighbor-group, neighbor,
      vrf-neighbor, session-group";
    leaf rpki-origin-as-validation-disable {
      xr:xr-xml-map "bgp_cfg:RPKIOriginASValidationDisable";
      type empty;
      description "RPKI origin-AS validation disable";
    }
  }

  grouping DISABLE-NEIGHBOR-LOGGING {
    description "Common node of global, vrf-global";
    leaf disable-neighbor-logging {
      xr:xr-xml-map "bgp_cfg:DisableNeighborLogging";
      type empty;
      description "Disable neighbor change logging";
    }
  }

  grouping TCPMSS {
    description
      "Common node of neighbor-group, neighbor,
      vrf-neighbor, session-group";

    container tcpmss {
      xr:xr-xml-map "bgp_cfg:TCPMSS";
      description "TCP Maximum segment size";
      leaf tcpmss-disable {
        xr:xr-xml-map "bgp_cfg:TCPMSSDisable";
        type boolean;
        description
          "TRUE, to prevent inheritance ofTCP MSS
          valuefrom its parents.FALSE, otherwise";
      }
      leaf mss {
        xr:xr-xml-map "bgp_cfg:MSS";
        type uint32 {
          range "68..10000";
        }
        description "Maximum Segment Size";
      }
    }
  }

  container bgp {
    xr:xr-xml-map "bgp_cfg:BGP";
    description "BGP configuration commands";

    list instance {
      xr:xr-xml-map "bgp_cfg:Instance";
      key "instance-name";
      description "BGP instance configuration commands";
      leaf instance-name {
        xr:xr-xml-map "bgp_cfg:InstanceName";
        type xr:Cisco-ios-xr-string;
        description "Instance Name";
      }

      list instance-as {
        xr:xr-xml-map "bgp_cfg:InstanceAS";
        key "as";
        description "Autonomous system";
        leaf as {
          xr:xr-xml-map "bgp_cfg:AS";
          type dt1:Bgp-as-range;
          description
            "Higher 16 bits of 4-byte Autonomous system
            number";
        }

        list four-byte-as {
          xr:xr-xml-map "bgp_cfg:FourByteAS";
          key "as";
          description "4-byte Autonomous system";

          container vrfs {
            xr:xr-xml-map "bgp_cfg:VRFTable";
            description "VRF config";

            list vrf {
              xr:xr-xml-map "bgp_cfg:VRF";
              key "vrf-name";
              description "VRF config";

              container vrf-global {
                xr:xr-xml-map "bgp_cfg:VRFGlobal";
                description "VRF attribute config";

                container route-distinguisher {
                  xr:xr-xml-map "bgp_cfg:RouteDistinguisher";
                  description "Route distinguisher";
                  leaf type {
                    xr:xr-xml-map "bgp_cfg:Type";
                    type Bgp-route-distinguisher;
                    description "Type of RD";
                  }
                  leaf as-xx {
                    xr:xr-xml-map "bgp_cfg:AS_XX";
                    when "../type = 'as' or ../type ="+
                      " 'four-byte-as'" {
                        description
                          "../Type = AS or ../Type = FourByteAS";
                    }
                    type dt1:Bgp-as-range;
                    description "AS number";
                  }
                  leaf as {
                    xr:xr-xml-map "bgp_cfg:AS";
                    when "../type = 'as' or ../type ="+
                      " 'four-byte-as'" {
                        description
                          "../Type = AS or ../Type = FourByteAS";
                    }
                    type dt1:Bgp-as-range;
                    description "AS number";
                  }
                  leaf as-index {
                    xr:xr-xml-map "bgp_cfg:ASIndex";
                    when "../type = 'as' or ../type ="+
                      " 'four-byte-as'" {
                        description
                          "../Type = AS or ../Type = FourByteAS";
                    }
                    type dt1:Bgp-extcomm-asn-index;
                    description "ASN Index";
                  }
                  leaf address {
                    xr:xr-xml-map "bgp_cfg:Address";
                    when "../type = 'ipv4-address'" {
                      description "../Type = IPV4Address";
                    }
                    type inet:ipv4-address-no-zone;
                    description "IP address";
                  }
                  leaf address-index {
                    xr:xr-xml-map "bgp_cfg:AddressIndex";
                    when "../type = 'ipv4-address'" {
                      description "../Type = IPV4Address";
                    }
                    type dt1:Bgp-extcomm-v4-addr-index;
                    description "IP address index";
                  }
                }

                container label-mode {
                  xr:xr-xml-map "bgp_cfg:LabelMode";
                  description "MPLS/VPN label allocation mode";
                  leaf label-allocation-mode {
                    xr:xr-xml-map "bgp_cfg:LabelAllocationMode";
                    type string;
                    description
                      "Label allocation mode: per-ce  Set per CE
                      label mode, per-vrf Set per VRF label
                      mode";
                  }
                  leaf route-policy-name {
                    xr:xr-xml-map "bgp_cfg:RoutePolicyName";
                    type string;
                    description "Label mode route policy name";
                  }
                }

                container vrf-global-afs {
                  xr:xr-xml-map "bgp_cfg:VRFGlobalAFTable";
                  description "Global VRF-specific configuration";

                  list vrf-global-af {
                    xr:xr-xml-map "bgp_cfg:VRFGlobalAF";
                    key "af-name";
                    description
                      "Global VRF AF-specific configuration";

                    container mvpn {
                      xr:xr-xml-map "bgp_cfg:MVPN";
                      description "MVPN configurations";
                      leaf single-forwarder-selection {
                        xr:xr-xml-map "bgp_cfg:SingleForwarderSelec"+
                          "tion";
                        type Bgp-mvpn-sfs-select;
                        description
                          "Select MVPN single forwarder selection";
                      }
                    }
                    leaf rt-download {
                      xr:xr-xml-map "bgp_cfg:RTDownload";
                      type empty;
                      description "Enable RT Extcomm download";
                    }
                    leaf allow-vpn-default-originate {
                      xr:xr-xml-map "bgp_cfg:AllowVpnDefaultOrigina"+
                        "te";
                      type boolean;
                      description
                        "TRUE to send default orig route to VPN
                        neighborFALSE to not send default
                        originate route ";
                    }
                    leaf af-name {
                      xr:xr-xml-map "bgp_cfg:AFName";
                      type dt1:Bgp-address-family;
                      description "Address family";
                    }
                    uses AGGREGATE-ADDRESS-TABLE;
                    uses DYNAMIC-MED-INTERVAL;
                    uses DAMPENING;
                    uses ENABLE;
                    uses RIP-ROUTES;
                    uses LISP-ROUTES;
                    uses STATIC-ROUTES;
                    uses DISTANCE;
                    uses TABLE-POLICY;
                    uses ATTRIBUTE-DOWNLOAD;
                    uses LABEL-MODE;
                    uses EI-GRP-ROUTE-TABLE;
                    uses BEST-EXTERNAL;
                    uses SOURCED-NETWORK-TABLE;
                    uses CONNECTED-ROUTES;
                    uses ADDITIONAL-PATHS-RECEIVE;
                    uses PERMANENT-NETWORK;
                    uses ALLOCATE-LABEL;
                    uses ADDITIONAL-PATHS-SELECTION;
                    uses NEXT-HOP-RESOLUTION-PREFIX-LENGTH-MINIMUM;
                    uses RESET-WEIGHT-ON-IMPORT;
                    uses EBGP;
                    uses EIBGP;
                    uses OSPF-ROUTE-TABLE;
                    uses IBGP;
                    uses ADDITIONAL-PATHS-SEND;
                    uses MOBILE-ROUTES;
                    uses DISABLE-AS-PATH-LOOP-CHECK;
                    uses SUBSCRIBER-ROUTES;
                  }
                }
                leaf exists {
                  xr:xr-xml-map "bgp_cfg:Exists";
                  type empty;
                  description "Create this VRF";
                }
                uses GRACEFUL-RESTART;
                uses ROUTER-ID;
                uses DISABLE-ENFORCE-FIRST-AS;
                uses BEST-PATH-COST-COMMUNITY;
                uses BEST-PATH-AIGP-IGNORE;
                uses BEST-PATH-AS-PATH-LENGTH;
                uses IGP-REDIST-INTERNAL;
                uses MULTI-PATH-AS-PATH-IGNORE-ONWARDS;
                uses DISABLE-FAST-EXTERNAL-FALLOVER;
                uses DEFAULT-METRIC;
                uses DEFAULT-INFO-ORIGINATE;
                uses BEST-PATH-CONFEDERATION-PATHS;
                uses BEST-PATH-AS-MULTIPATH-RELAX;
                uses MPLS-ACTIVATED-INTERFACE-TABLE;
                uses DISABLE-AUTO-SOFT-RESET;
                uses DISABLE-MSG-LOG;
                uses GRACEFUL-RESTART-PURGE-TIME;
                uses GLOBAL-TIMERS;
                uses GRACEFUL-RESTART-TIME;
                uses BGP-CFG-BFD;
                uses DISABLE-NEIGHBOR-LOGGING;
                uses GRACEFUL-RESTART-STALEPATH-TIME;
                uses SEND-SOCKET-BUFFER-SIZES;
                uses BEST-PATH-MED-ALWAYS;
                uses RECEIVE-SOCKET-BUFFER-SIZES;
                uses BEST-PATH-ROUTER-ID;
                uses GRACEFUL-RESET;
                uses BEST-PATH-MED-MISSING;
                uses LOCAL-PREFERENCE;
              }

              container vrf-neighbors {
                xr:xr-xml-map "bgp_cfg:VRFNeighborTable";
                description "BGP VRF peer";

                list vrf-neighbor {
                  xr:xr-xml-map "bgp_cfg:VRFNeighbor";
                  key "neighbor-address";
                  description "A particular VRF peer";

                  container vrf-neighbor-afs {
                    xr:xr-xml-map "bgp_cfg:VRFNeighborAFTable";
                    description
                      "Address family type of a VRF neighbor";

                    list vrf-neighbor-af {
                      xr:xr-xml-map "bgp_cfg:VRFNeighborAF";
                      key "af-name";
                      description
                        "Address family type of a VRF neighbor";
                      leaf af-name {
                        xr:xr-xml-map "bgp_cfg:AFName";
                        type dt1:Bgp-address-family;
                        description "BGP neighbor address family";
                      }
                      uses "NEIGHBOR-AF-LONG-LIVED"+
                        "-GRACEFUL-RESTART-CAPABLE";
                      uses L2VPN-SIGNALLING;
                      uses SEND-EXT-COMMUNITY-EBGP;
                      uses ACCEPT-ROUTE-LEGACY-RT;
                      uses AIGP-COST-COMMUNITY;
                      uses SEND-COMMUNITY-EBGP;
                      uses ADVERTISE-DISABLE;
                      uses SEND-MULTICAST-ATTR;
                      uses MAXIMUM-PREFIXES;
                      uses REMOVE-PRIVATE-AS-ENTIRE-AS-PATH-INBOUND;
                      uses NEXT-HOP-UNCHANGED;
                      uses RPKI-ORIGIN-AS-VALIDATION-DISABLE;
                      uses FLOWSPEC-VALIDATION;
                      uses RPKI-BESTPATH-ORIGIN-AS-ALLOW-INVALID;
                      uses AS-OVERRIDE;
                      uses MULTIPATH;
                      uses SEND-COMMUNITY-EBGP-GRACEFUL-SHUTDOWN;
                      uses ACTIVATE;
                      uses PREFIX-ORF-POLICY;
                      uses "NEIGHBOR-AF-LONG-LIVED"+
                        "-GRACEFUL-RESTART-STALE-TIME";
                      uses SITE-OF-ORIGIN;
                      uses AIGP;
                      uses AIGP-SEND-MED;
                      uses ADVERTISE-V6;
                      uses ALLOW-AS-IN;
                      uses ADVERTISE-ORF;
                      uses ROUTE-REFLECTOR-CLIENT;
                      uses NEXT-HOP-SELF;
                      uses ADVERTISE-LOCAL-V6;
                      uses ROUTE-POLICY-IN;
                      uses IMPORT;
                      uses DEFAULT-ORIGINATE;
                      uses SOFT-RECONFIGURATION;
                      uses DEFAULT-WEIGHT;
                      uses AF-GROUP;
                      uses ADVERTISE-V4;
                      uses NEXT-HOP-UNCHANGED-MULTIPATH;
                      uses ACCEPT-OWN;
                      uses ROUTE-POLICY-OUT;
                      uses ADVERTISE-LOCAL-V4;
                      uses ADVERTISE-PERMANENT-NETWORK;
                      uses REMOVE-PRIVATE-AS-ENTIRE-AS-PATH;
                    }
                  }
                  leaf neighbor-address {
                    xr:xr-xml-map "bgp_cfg:NeighborAddress";
                    type inet:ip-address-no-zone;
                    description "Neighbor address";
                  }
                  uses INTERNAL-VPN-CLIENT-IBGPCE;
                  uses LOCAL-ADDRESS;
                  uses BMP-ACTIVATE-TABLE;
                  uses BFD-ENABLE;
                  uses EBGP-MULTIHOP;
                  uses SESSION-GROUP-ADD-MEMBER;
                  uses EGRESS-PEER-ENGINEERING;
                  uses REMOTE-AS;
                  uses LOCAL-AS;
                  uses NEIGHBOR-GRACEFUL-RESTART-STALEPATH-TIME;
                  uses SHUTDOWN;
                  uses DESCRIPTION;
                  uses BFD;
                  uses NEIGHBOR-GROUP-ADD-MEMBER;
                  uses PASSWORD;
                  uses ADVERTISEMENT-INTERVAL;
                  uses NEIGHBOR-CLUSTER-ID;
                  uses NEIGHBOR-GRACEFUL-RESTART;
                  uses ENFORCE-FIRST-AS;
                  uses TCPMSS;
                  uses SESSION-OPEN-MODE;
                  uses BGP-CFG-RPKI-ORIGIN-AS-VALIDATION-DISABLE;
                  uses TOS;
                  uses UPDATE-IN-FILTERING;
                  uses MSG-LOG-OUT;
                  uses BGP-CFG-RPKI-BESTPATH-ORIGIN-AS-ALLOW-INVALID;
                  uses RECEIVE-BUFFER-SIZE;
                  uses MSG-LOG-IN;
                  uses ADDITIONAL-PATHS-SEND-CAPABILITY;
                  uses PROPAGATE-DMZ-LINK-BANDWIDTH;
                  uses SEND-BUFFER-SIZE;
                  uses TTL-SECURITY;
                  uses NEIGHBOR-GRACEFUL-RESTART-TIME;
                  uses TIMERS;
                  uses BFD-MULTIPLIER;
                  uses BFD-MINIMUM-INTERVAL;
                  uses ADDITIONAL-PATHS-RECEIVE-CAPABILITY;
                  uses KEYCHAIN;
                  uses IGNORE-CONNECTED-CHECK-EBGP;
                  uses SUPPRESS-FOUR-BYTE-AS-CAPABILITY;
                  uses UPDATE-SOURCE-INTERFACE;
                  uses GRACEFUL-MAINTENANCE;
                }
              }
              leaf vrf-name {
                xr:xr-xml-map "bgp_cfg:VRFName";
                type xr:Cisco-ios-xr-string;
                description "VRF name";
              }
            }
          }

          container default-vrf {
            xr:xr-xml-map "bgp_cfg:DefaultVRF";
            description "Global default config";

            container bgp-entity {
              xr:xr-xml-map "bgp_cfg:BGPEntity";
              description
                "Neighbor, neighbor-group, af-group and
                session-group configuration";

              container neighbors {
                xr:xr-xml-map "bgp_cfg:NeighborTable";
                description "Neighbor configuration";

                list neighbor {
                  xr:xr-xml-map "bgp_cfg:Neighbor";
                  key "neighbor-address";
                  description "A particular BGP peer";

                  container neighbor-afs {
                    xr:xr-xml-map "bgp_cfg:NeighborAFTable";
                    description
                      "BGP neighbor AF configuration table";

                    list neighbor-af {
                      xr:xr-xml-map "bgp_cfg:NeighborAF";
                      key "af-name";
                      description "Address family type of neighbor";
                      leaf af-name {
                        xr:xr-xml-map "bgp_cfg:AFName";
                        type dt1:Bgp-address-family;
                        description "BGP neighbor address family";
                      }
                      uses "NEIGHBOR-AF-LONG-LIVED"+
                        "-GRACEFUL-RESTART-CAPABLE";
                      uses L2VPN-SIGNALLING;
                      uses SEND-EXT-COMMUNITY-EBGP;
                      uses ACCEPT-ROUTE-LEGACY-RT;
                      uses AIGP-COST-COMMUNITY;
                      uses SEND-COMMUNITY-EBGP;
                      uses ADVERTISE-DISABLE;
                      uses SEND-MULTICAST-ATTR;
                      uses MAXIMUM-PREFIXES;
                      uses REMOVE-PRIVATE-AS-ENTIRE-AS-PATH-INBOUND;
                      uses NEXT-HOP-UNCHANGED;
                      uses RPKI-ORIGIN-AS-VALIDATION-DISABLE;
                      uses FLOWSPEC-VALIDATION;
                      uses RPKI-BESTPATH-ORIGIN-AS-ALLOW-INVALID;
                      uses AS-OVERRIDE;
                      uses MULTIPATH;
                      uses SEND-COMMUNITY-EBGP-GRACEFUL-SHUTDOWN;
                      uses ACTIVATE;
                      uses PREFIX-ORF-POLICY;
                      uses "NEIGHBOR-AF-LONG-LIVED"+
                        "-GRACEFUL-RESTART-STALE-TIME";
                      uses AIGP;
                      uses AIGP-SEND-MED;
                      uses ADVERTISE-V6;
                      uses ALLOW-AS-IN;
                      uses ADVERTISE-ORF;
                      uses ROUTE-REFLECTOR-CLIENT;
                      uses NEXT-HOP-SELF;
                      uses ADVERTISE-LOCAL-V6;
                      uses ROUTE-POLICY-IN;
                      uses IMPORT;
                      uses DEFAULT-ORIGINATE;
                      uses SOFT-RECONFIGURATION;
                      uses DEFAULT-WEIGHT;
                      uses AF-GROUP;
                      uses ADVERTISE-V4;
                      uses NEXT-HOP-UNCHANGED-MULTIPATH;
                      uses ACCEPT-OWN;
                      uses ROUTE-POLICY-OUT;
                      uses ADVERTISE-LOCAL-V4;
                      uses ADVERTISE-PERMANENT-NETWORK;
                      uses REMOVE-PRIVATE-AS-ENTIRE-AS-PATH;
                    }
                  }
                  leaf neighbor-address {
                    xr:xr-xml-map "bgp_cfg:NeighborAddress";
                    type inet:ip-address-no-zone;
                    description "Neighbor address";
                  }
                  uses INTERNAL-VPN-CLIENT-IBGPCE;
                  uses LOCAL-ADDRESS;
                  uses BMP-ACTIVATE-TABLE;
                  uses BFD-ENABLE;
                  uses EBGP-MULTIHOP;
                  uses SESSION-GROUP-ADD-MEMBER;
                  uses EGRESS-PEER-ENGINEERING;
                  uses REMOTE-AS;
                  uses LOCAL-AS;
                  uses NEIGHBOR-GRACEFUL-RESTART-STALEPATH-TIME;
                  uses SHUTDOWN;
                  uses DESCRIPTION;
                  uses BFD;
                  uses NEIGHBOR-GROUP-ADD-MEMBER;
                  uses PASSWORD;
                  uses ADVERTISEMENT-INTERVAL;
                  uses NEIGHBOR-CLUSTER-ID;
                  uses NEIGHBOR-GRACEFUL-RESTART;
                  uses ENFORCE-FIRST-AS;
                  uses TCPMSS;
                  uses SESSION-OPEN-MODE;
                  uses BGP-CFG-RPKI-ORIGIN-AS-VALIDATION-DISABLE;
                  uses TOS;
                  uses UPDATE-IN-FILTERING;
                  uses MSG-LOG-OUT;
                  uses BGP-CFG-RPKI-BESTPATH-ORIGIN-AS-ALLOW-INVALID;
                  uses RECEIVE-BUFFER-SIZE;
                  uses MSG-LOG-IN;
                  uses ADDITIONAL-PATHS-SEND-CAPABILITY;
                  uses PROPAGATE-DMZ-LINK-BANDWIDTH;
                  uses SEND-BUFFER-SIZE;
                  uses TTL-SECURITY;
                  uses NEIGHBOR-GRACEFUL-RESTART-TIME;
                  uses TIMERS;
                  uses BFD-MULTIPLIER;
                  uses BFD-MINIMUM-INTERVAL;
                  uses ADDITIONAL-PATHS-RECEIVE-CAPABILITY;
                  uses KEYCHAIN;
                  uses IGNORE-CONNECTED-CHECK-EBGP;
                  uses SUPPRESS-FOUR-BYTE-AS-CAPABILITY;
                  uses UPDATE-SOURCE-INTERFACE;
                  uses GRACEFUL-MAINTENANCE;
                }
              }

              container neighbor-groups {
                xr:xr-xml-map "bgp_cfg:NeighborGroupTable";
                description "Neighbor-group configuration";

                list neighbor-group {
                  xr:xr-xml-map "bgp_cfg:NeighborGroup";
                  key "neighbor-group-name";
                  description "A particular BGP neighbor group";

                  container neighbor-group-afs {
                    xr:xr-xml-map "bgp_cfg:NeighborGroupAFTable";
                    description
                      "BGP neighbor-group AF configuration table";

                    list neighbor-group-af {
                      xr:xr-xml-map "bgp_cfg:NeighborGroupAF";
                      key "af-name";
                      description
                        "Address family type of neighbor group";
                      leaf af-name {
                        xr:xr-xml-map "bgp_cfg:AFName";
                        type dt1:Bgp-address-family;
                        description
                          "BGP neighbor group address family";
                      }
                      uses "NEIGHBOR-AF-LONG-LIVED"+
                        "-GRACEFUL-RESTART-CAPABLE";
                      uses L2VPN-SIGNALLING;
                      uses SEND-EXT-COMMUNITY-EBGP;
                      uses ACCEPT-ROUTE-LEGACY-RT;
                      uses AIGP-COST-COMMUNITY;
                      uses SEND-COMMUNITY-EBGP;
                      uses ADVERTISE-DISABLE;
                      uses SEND-MULTICAST-ATTR;
                      uses MAXIMUM-PREFIXES;
                      uses REMOVE-PRIVATE-AS-ENTIRE-AS-PATH-INBOUND;
                      uses NEXT-HOP-UNCHANGED;
                      uses RPKI-ORIGIN-AS-VALIDATION-DISABLE;
                      uses FLOWSPEC-VALIDATION;
                      uses RPKI-BESTPATH-ORIGIN-AS-ALLOW-INVALID;
                      uses AS-OVERRIDE;
                      uses MULTIPATH;
                      uses SEND-COMMUNITY-EBGP-GRACEFUL-SHUTDOWN;
                      uses ACTIVATE;
                      uses PREFIX-ORF-POLICY;
                      uses "NEIGHBOR-AF-LONG-LIVED"+
                        "-GRACEFUL-RESTART-STALE-TIME";
                      uses SITE-OF-ORIGIN;
                      uses AIGP;
                      uses AIGP-SEND-MED;
                      uses ADVERTISE-V6;
                      uses ALLOW-AS-IN;
                      uses ADVERTISE-ORF;
                      uses ROUTE-REFLECTOR-CLIENT;
                      uses NEXT-HOP-SELF;
                      uses ADVERTISE-LOCAL-V6;
                      uses ROUTE-POLICY-IN;
                      uses IMPORT;
                      uses DEFAULT-ORIGINATE;
                      uses SOFT-RECONFIGURATION;
                      uses DEFAULT-WEIGHT;
                      uses AF-GROUP;
                      uses ADVERTISE-V4;
                      uses NEXT-HOP-UNCHANGED-MULTIPATH;
                      uses ACCEPT-OWN;
                      uses ROUTE-POLICY-OUT;
                      uses ADVERTISE-LOCAL-V4;
                      uses ADVERTISE-PERMANENT-NETWORK;
                      uses REMOVE-PRIVATE-AS-ENTIRE-AS-PATH;
                    }
                  }
                  leaf neighbor-group-add-member {
                    xr:xr-xml-map "bgp_cfg:NeighborGroupAddMember";
                    type string;
                    description "Neighbor-group name";
                  }
                  leaf neighbor-group-name {
                    xr:xr-xml-map "bgp_cfg:NeighborGroupName";
                    type xr:Cisco-ios-xr-string;
                    description "BGP neighbor group name";
                  }
                  uses INTERNAL-VPN-CLIENT-IBGPCE;
                  uses LOCAL-ADDRESS;
                  uses BMP-ACTIVATE-TABLE;
                  uses BFD-ENABLE;
                  uses EBGP-MULTIHOP;
                  uses SESSION-GROUP-ADD-MEMBER;
                  uses EGRESS-PEER-ENGINEERING;
                  uses REMOTE-AS;
                  uses LOCAL-AS;
                  uses NEIGHBOR-GRACEFUL-RESTART-STALEPATH-TIME;
                  uses SHUTDOWN;
                  uses DESCRIPTION;
                  uses BFD;
                  uses PASSWORD;
                  uses ADVERTISEMENT-INTERVAL;
                  uses NEIGHBOR-CLUSTER-ID;
                  uses NEIGHBOR-GRACEFUL-RESTART;
                  uses ENFORCE-FIRST-AS;
                  uses TCPMSS;
                  uses SESSION-OPEN-MODE;
                  uses BGP-CFG-RPKI-ORIGIN-AS-VALIDATION-DISABLE;
                  uses TOS;
                  uses UPDATE-IN-FILTERING;
                  uses MSG-LOG-OUT;
                  uses BGP-CFG-RPKI-BESTPATH-ORIGIN-AS-ALLOW-INVALID;
                  uses RECEIVE-BUFFER-SIZE;
                  uses MSG-LOG-IN;
                  uses ADDITIONAL-PATHS-SEND-CAPABILITY;
                  uses PROPAGATE-DMZ-LINK-BANDWIDTH;
                  uses SEND-BUFFER-SIZE;
                  uses TTL-SECURITY;
                  uses NEIGHBOR-GRACEFUL-RESTART-TIME;
                  uses TIMERS;
                  uses BFD-MULTIPLIER;
                  uses BFD-MINIMUM-INTERVAL;
                  uses ADDITIONAL-PATHS-RECEIVE-CAPABILITY;
                  uses KEYCHAIN;
                  uses IGNORE-CONNECTED-CHECK-EBGP;
                  uses SUPPRESS-FOUR-BYTE-AS-CAPABILITY;
                  uses UPDATE-SOURCE-INTERFACE;
                  uses CREATE;
                  uses GRACEFUL-MAINTENANCE;
                }
              }

              container af-groups {
                xr:xr-xml-map "bgp_cfg:AFGroupTable";
                description "AF-group configuration";

                list af-group {
                  xr:xr-xml-map "bgp_cfg:AFGroup";
                  key "af-group-name";
                  description "A particular BGP AF group";

                  container af-group-afs {
                    xr:xr-xml-map "bgp_cfg:AFGroupAFTable";
                    description "AF group configuration table";

                    list af-group-af {
                      xr:xr-xml-map "bgp_cfg:AFGroupAF";
                      key "af-name";
                      description
                        "Address family type of an AF group";
                      leaf af-group {
                        xr:xr-xml-map "bgp_cfg:AFGroup";
                        type string;
                        description "AF group name";
                      }
                      leaf create {
                        xr:xr-xml-map "bgp_cfg:Create";
                        type empty;
                        description
                          "Create this address family group";
                      }
                      leaf af-name {
                        xr:xr-xml-map "bgp_cfg:AFName";
                        type dt1:Bgp-address-family;
                        description "BGP AF group address family";
                      }
                      uses "NEIGHBOR-AF-LONG-LIVED"+
                        "-GRACEFUL-RESTART-CAPABLE";
                      uses L2VPN-SIGNALLING;
                      uses SEND-EXT-COMMUNITY-EBGP;
                      uses ACCEPT-ROUTE-LEGACY-RT;
                      uses AIGP-COST-COMMUNITY;
                      uses SEND-COMMUNITY-EBGP;
                      uses ADVERTISE-DISABLE;
                      uses SEND-MULTICAST-ATTR;
                      uses MAXIMUM-PREFIXES;
                      uses REMOVE-PRIVATE-AS-ENTIRE-AS-PATH-INBOUND;
                      uses NEXT-HOP-UNCHANGED;
                      uses RPKI-ORIGIN-AS-VALIDATION-DISABLE;
                      uses FLOWSPEC-VALIDATION;
                      uses RPKI-BESTPATH-ORIGIN-AS-ALLOW-INVALID;
                      uses AS-OVERRIDE;
                      uses MULTIPATH;
                      uses SEND-COMMUNITY-EBGP-GRACEFUL-SHUTDOWN;
                      uses PREFIX-ORF-POLICY;
                      uses "NEIGHBOR-AF-LONG-LIVED"+
                        "-GRACEFUL-RESTART-STALE-TIME";
                      uses SITE-OF-ORIGIN;
                      uses AIGP;
                      uses AIGP-SEND-MED;
                      uses ADVERTISE-V6;
                      uses ALLOW-AS-IN;
                      uses ADVERTISE-ORF;
                      uses ROUTE-REFLECTOR-CLIENT;
                      uses NEXT-HOP-SELF;
                      uses ADVERTISE-LOCAL-V6;
                      uses ROUTE-POLICY-IN;
                      uses IMPORT;
                      uses DEFAULT-ORIGINATE;
                      uses SOFT-RECONFIGURATION;
                      uses DEFAULT-WEIGHT;
                      uses ADVERTISE-V4;
                      uses NEXT-HOP-UNCHANGED-MULTIPATH;
                      uses ACCEPT-OWN;
                      uses ROUTE-POLICY-OUT;
                      uses ADVERTISE-LOCAL-V4;
                      uses ADVERTISE-PERMANENT-NETWORK;
                      uses REMOVE-PRIVATE-AS-ENTIRE-AS-PATH;
                    }
                  }
                  leaf af-group-name {
                    xr:xr-xml-map "bgp_cfg:AFGroupName";
                    type xr:Cisco-ios-xr-string;
                    description "BGP AF group name";
                  }
                }
              }

              container session-groups {
                xr:xr-xml-map "bgp_cfg:SessionGroupTable";
                description "Session group configuration";

                list session-group {
                  xr:xr-xml-map "bgp_cfg:SessionGroup";
                  key "session-group-name";
                  description "A particular BGP session group";
                  leaf session-group-add-member {
                    xr:xr-xml-map "bgp_cfg:SessionGroupAddMember";
                    type string;
                    description "Session group name";
                  }
                  leaf session-group-name {
                    xr:xr-xml-map "bgp_cfg:SessionGroupName";
                    type xr:Cisco-ios-xr-string;
                    description "BGP session group name";
                  }
                  uses INTERNAL-VPN-CLIENT-IBGPCE;
                  uses LOCAL-ADDRESS;
                  uses BMP-ACTIVATE-TABLE;
                  uses BFD-ENABLE;
                  uses EBGP-MULTIHOP;
                  uses EGRESS-PEER-ENGINEERING;
                  uses REMOTE-AS;
                  uses LOCAL-AS;
                  uses NEIGHBOR-GRACEFUL-RESTART-STALEPATH-TIME;
                  uses SHUTDOWN;
                  uses DESCRIPTION;
                  uses BFD;
                  uses PASSWORD;
                  uses ADVERTISEMENT-INTERVAL;
                  uses NEIGHBOR-CLUSTER-ID;
                  uses NEIGHBOR-GRACEFUL-RESTART;
                  uses ENFORCE-FIRST-AS;
                  uses TCPMSS;
                  uses SESSION-OPEN-MODE;
                  uses BGP-CFG-RPKI-ORIGIN-AS-VALIDATION-DISABLE;
                  uses TOS;
                  uses UPDATE-IN-FILTERING;
                  uses MSG-LOG-OUT;
                  uses BGP-CFG-RPKI-BESTPATH-ORIGIN-AS-ALLOW-INVALID;
                  uses RECEIVE-BUFFER-SIZE;
                  uses MSG-LOG-IN;
                  uses ADDITIONAL-PATHS-SEND-CAPABILITY;
                  uses PROPAGATE-DMZ-LINK-BANDWIDTH;
                  uses SEND-BUFFER-SIZE;
                  uses TTL-SECURITY;
                  uses NEIGHBOR-GRACEFUL-RESTART-TIME;
                  uses TIMERS;
                  uses BFD-MULTIPLIER;
                  uses BFD-MINIMUM-INTERVAL;
                  uses ADDITIONAL-PATHS-RECEIVE-CAPABILITY;
                  uses KEYCHAIN;
                  uses IGNORE-CONNECTED-CHECK-EBGP;
                  uses SUPPRESS-FOUR-BYTE-AS-CAPABILITY;
                  uses UPDATE-SOURCE-INTERFACE;
                  uses CREATE;
                  uses GRACEFUL-MAINTENANCE;
                }
              }
            }

            container global {
              xr:xr-xml-map "bgp_cfg:Global";
              description "Global default config";

              container cluster-id {
                xr:xr-xml-map "bgp_cfg:ClusterID";
                description "Configure Route-Reflector Cluster-id";
                leaf cluster-id-number {
                  xr:xr-xml-map "bgp_cfg:ClusterIDNumber";
                  type uint32 {
                    range "1..4294967295";
                  }
                  description
                    "Route-Reflector Cluster ID as 32 bit
                    quantity";
                }
                leaf cluster-id-address {
                  xr:xr-xml-map "bgp_cfg:ClusterIDAddress";
                  type inet:ipv4-address-no-zone;
                  description
                    "Route-Reflector Cluster ID in IPV4 address
                    format";
                }
              }

              container write-limit {
                xr:xr-xml-map "bgp_cfg:WriteLimit";
                description
                  "Set write-queue limit for each update group";
                leaf formatted-messages {
                  xr:xr-xml-map "bgp_cfg:FormattedMessages";
                  type uint32 {
                    range "500..100000000";
                  }
                  default "50000";
                  description
                    "Number of messages to be formatted per
                    update group";
                }
                leaf enqueued-messages {
                  xr:xr-xml-map "bgp_cfg:EnqueuedMessages";
                  type uint32 {
                    range "500..100000000";
                  }
                  default "250000";
                  description
                    "Number of messages that can be enqueued in
                    total";
                }
                leaf desynchronize {
                  xr:xr-xml-map "bgp_cfg:Desynchronize";
                  type boolean;
                  default "false";
                  description
                    "TRUE to enable desynchronization, FALSE
                    otherwise.";
                }
              }

              container update-delay {
                xr:xr-xml-map "bgp_cfg:UpdateDelay";
                description
                  "Set the max initial delay for sending
                  updates";
                leaf delay {
                  xr:xr-xml-map "bgp_cfg:Delay";
                  type uint32 {
                    range "0..3600";
                  }
                  units "second";
                  default "120";
                  description "Delay value (seconds)";
                }
                leaf always {
                  xr:xr-xml-map "bgp_cfg:Always";
                  type boolean;
                  default "false";
                  description
                    "Set to TRUE to disable keepalive trigger
                    bestpath and delay is enforced.";
                }
              }

              container as-league {
                xr:xr-xml-map "bgp_cfg:ASLeague";
                description "AS League";

                container peers {
                  xr:xr-xml-map "bgp_cfg:PeerTable";
                  description "AS League Peers";

                  list peer {
                    xr:xr-xml-map "bgp_cfg:Peer";
                    key "as-xx as-yy";
                    description "AS League Peer AS";
                    leaf as-xx {
                      xr:xr-xml-map "bgp_cfg:AS_XX";
                      type dt1:Bgp-as-range;
                      description "xx of peer AS xx.yy";
                    }
                    leaf as-yy {
                      xr:xr-xml-map "bgp_cfg:AS_YY";
                      type dt1:Bgp-as-range;
                      description "yy of peer AS xx.yy";
                    }
                  }
                }
                leaf enable {
                  xr:xr-xml-map "bgp_cfg:Enable";
                  type empty;
                  description "Create AS League";
                }
              }

              container rpki-servers {
                xr:xr-xml-map "bgp_cfg:RPKIServerTable";
                description "RPKI server configuration";

                list rpki-server {
                  xr:xr-xml-map "bgp_cfg:RPKIServer";
                  key "server";
                  description "RPKI server configuration";

                  container transport {
                    xr:xr-xml-map "bgp_cfg:Transport";
                    description "RPKI server transport";
                    leaf transport {
                      xr:xr-xml-map "bgp_cfg:Transport";
                      type Bgp-rpki-transport;
                      default "ssh";
                      description "RPKI server transport";
                    }
                    leaf port {
                      xr:xr-xml-map "bgp_cfg:Port";
                      type xr:Cisco-ios-xr-port-number;
                      default "22";
                      description "port";
                    }
                  }
                  leaf enable {
                    xr:xr-xml-map "bgp_cfg:Enable";
                    type empty;
                    description "RPKI server configuration";
                  }
                  leaf shutdown {
                    xr:xr-xml-map "bgp_cfg:Shutdown";
                    type empty;
                    description "RPKI server shutdown";
                  }
                  leaf password {
                    xr:xr-xml-map "bgp_cfg:Password";
                    type string;
                    description "RPKI server password";
                  }
                  leaf response-time {
                    xr:xr-xml-map "bgp_cfg:ResponseTime";
                    type int32;
                    units "second";
                    description
                      "RPKI server response-time (seconds)";
                  }
                  leaf username {
                    xr:xr-xml-map "bgp_cfg:Username";
                    type string;
                    description "RPKI server username";
                  }
                  leaf refresh-time {
                    xr:xr-xml-map "bgp_cfg:RefreshTime";
                    type int32;
                    units "second";
                    description
                      "RPKI server refresh-time (seconds)";
                  }
                  leaf purge-time {
                    xr:xr-xml-map "bgp_cfg:PurgeTime";
                    type int32;
                    units "second";
                    description "RPKI server purge-time (seconds)";
                  }
                  leaf server {
                    xr:xr-xml-map "bgp_cfg:Server";
                    type string;
                    description "Server address (opaque string)";
                  }
                }
              }

              container limits {
                xr:xr-xml-map "bgp_cfg:Limits";
                description "Maximum number that can be configured";
                leaf maximum-neighbors {
                  xr:xr-xml-map "bgp_cfg:MaximumNeighbors";
                  type uint32 {
                    range "1..15000";
                  }
                  default "10000";
                  description "Maximum number of neighbors";
                }
              }

              container confederation-domain {
                xr:xr-xml-map "bgp_cfg:ConfederationDomain";
                description "Set routing domain confederation AS";
                leaf as-xx {
                  xr:xr-xml-map "bgp_cfg:AS_XX";
                  type dt1:Bgp-as-range;
                  description "xx of AS number xx.yy";
                }
                leaf as-yy {
                  xr:xr-xml-map "bgp_cfg:AS_YY";
                  type dt1:Bgp-as-range;
                  description "yy of AS number xx.yy";
                }
              }

              container confederation-peer-ases {
                xr:xr-xml-map "bgp_cfg:ConfederationPeerASTable";
                description "Define peer ASes in BGP confederation";

                list confederation-peer-as {
                  xr:xr-xml-map "bgp_cfg:ConfederationPeerAS";
                  key "as-xx as-yy";
                  description "Confederation peer AS";
                  leaf as-xx {
                    xr:xr-xml-map "bgp_cfg:AS_XX";
                    type dt1:Bgp-as-range;
                    description "xx of AS number/confed peer xx.yy";
                  }
                  leaf as-yy {
                    xr:xr-xml-map "bgp_cfg:AS_YY";
                    type dt1:Bgp-as-range;
                    description "yy of AS number/confed peer xx.yy";
                  }
                }
              }

              container attribute-filter-groups {
                xr:xr-xml-map "bgp_cfg:AttributeFilterGroupTable";
                description "Attribute-filter groups list";

                list attribute-filter-group {
                  xr:xr-xml-map "bgp_cfg:AttributeFilterGroup";
                  key "attribute-filter-group-name";
                  description "Attribute-filter group";

                  container attribute-filters {
                    xr:xr-xml-map "bgp_cfg:AttributeFilterTable";
                    description
                      "Attribute-filter group attributes list";

                    list attribute-filter {
                      xr:xr-xml-map "bgp_cfg:AttributeFilter";
                      key "attribute-start attribute-end";
                      description
                        "Attribute-filter group attribute";
                      leaf attribute-start {
                        xr:xr-xml-map "bgp_cfg:AttributeStart";
                        type dt1:Bgp-attribute-range;
                        description "Start of attribute range";
                      }
                      leaf attribute-end {
                        xr:xr-xml-map "bgp_cfg:AttributeEnd";
                        type dt1:Bgp-attribute-range;
                        description "End of attribute range";
                      }
                      leaf filter-action {
                        xr:xr-xml-map "bgp_cfg:FilterAction";
                        type dt1:Bgp-update-filter-action;
                        mandatory true;
                        description "Filtering action";
                      }
                    }
                  }
                  leaf enable {
                    xr:xr-xml-map "bgp_cfg:Enable";
                    type empty;
                    description "Create Attribute-filter group";
                  }
                  leaf attribute-filter-group-name {
                    xr:xr-xml-map "bgp_cfg:AttributeFilterGroupName";
                    type xr:Cisco-ios-xr-string;
                    description "Group name";
                  }
                }
              }

              container global-graceful-maintenance-activate {
                xr:xr-xml-map "bgp_cfg:GlobalGracefulMaintenanceAct"+
                  "ivate";
                description
                  "Activate Graceful Maintenance Mode for all
                  neighbors with graceful maintenance config";
                leaf all-neighbors {
                  xr:xr-xml-map "bgp_cfg:AllNeighbors";
                  type boolean;
                  description
                    "Also for neighbors without graceful
                    maintenance config";
                }
                leaf retain-routes {
                  xr:xr-xml-map "bgp_cfg:RetainRoutes";
                  type boolean;
                  description "Keep routes in RIB once BGP stops";
                }
              }

              container global-afs {
                xr:xr-xml-map "bgp_cfg:GlobalAFTable";
                description "Global AF-specific configuration";

                list global-af {
                  xr:xr-xml-map "bgp_cfg:GlobalAF";
                  key "af-name";
                  description "Global AF-specific configuration";

                  container isis-routes {
                    xr:xr-xml-map "bgp_cfg:ISISRouteTable";
                    description
                      "Redistribute information for IS-IS routes
                      .";

                    list isis-route {
                      xr:xr-xml-map "bgp_cfg:ISISRoute";
                      key "instance-name";
                      description "Redistribute IS-IS routes";
                      leaf instance-name {
                        xr:xr-xml-map "bgp_cfg:InstanceName";
                        type xr:Cisco-ios-xr-string;
                        description "IS-IS instance name";
                      }
                      leaf default-metric {
                        xr:xr-xml-map "bgp_cfg:DefaultMetric";
                        type Bgp-default-metric-range;
                        description "Default metric";
                      }
                      leaf route-policy-name {
                        xr:xr-xml-map "bgp_cfg:RoutePolicyName";
                        type string;
                        description "Route policy name";
                      }
                      leaf redist-type {
                        xr:xr-xml-map "bgp_cfg:RedistType";
                        type xr:Hex-integer;
                        description
                          "Redistribution type: 0x01 for level 1
                          routes, 0x02 for level 2 routes, 0x04
                          for level 1 inter-area routes. Logical
                          combinations permitted.";
                      }
                    }
                  }

                  container domain-distinguisher {
                    xr:xr-xml-map "bgp_cfg:DomainDistinguisher";
                    presence "Indicates a domain-distinguisher node"+
                      " is configured.";
                    description
                      "<ASN, router-id> tuple to use to identify
                      the link-state domain";
                    leaf as {
                      xr:xr-xml-map "bgp_cfg:AS";
                      type dt1:Bgp-as-range;
                      mandatory true;
                      description "AS Number";
                    }
                    leaf router-id {
                      xr:xr-xml-map "bgp_cfg:RouterID";
                      type inet:ipv4-address-no-zone;
                      mandatory true;
                      description "Router ID";
                    }
                  }

                  container vrf-all {
                    xr:xr-xml-map "bgp_cfg:VRFAll";
                    description
                      "Configurations to be inherited to all
                      vrfs";

                    container label-mode {
                      xr:xr-xml-map "bgp_cfg:LabelMode";
                      description "MPLS-VPN label allocation mode";
                      leaf label-allocation-mode {
                        xr:xr-xml-map "bgp_cfg:LabelAllocationMode";
                        type string;
                        description
                          "Label allocation mode: per-ce  Set per
                          CE label mode, per-vrf Set per VRF
                          label mode";
                      }
                      leaf route-policy-name {
                        xr:xr-xml-map "bgp_cfg:RoutePolicyName";
                        type string;
                        description "Label mode route policy name";
                      }
                    }
                    leaf enable {
                      xr:xr-xml-map "bgp_cfg:Enable";
                      type empty;
                      description
                        "Enable vrf all configuration submode";
                    }
                    leaf source-rt-import-policy {
                      xr:xr-xml-map "bgp_cfg:SourceRTImportPolicy";
                      type empty;
                      description
                        "Enable sourcing of import route-targets 
                        from import-policy";
                    }
                  }

                  container application-routes {
                    xr:xr-xml-map "bgp_cfg:AppRouteTable";
                    description
                      "Redistribute information for Application
                      routes.";

                    list application-route {
                      xr:xr-xml-map "bgp_cfg:ApplicationRoutes";
                      key "instance-name";
                      description "Redistribute application routes";
                      leaf instance-name {
                        xr:xr-xml-map "bgp_cfg:InstanceName";
                        type xr:Cisco-ios-xr-string;
                        description "OnePK application name";
                      }
                      leaf default-metric {
                        xr:xr-xml-map "bgp_cfg:DefaultMetric";
                        type Bgp-default-metric-range;
                        description "Default metric";
                      }
                      leaf route-policy-name {
                        xr:xr-xml-map "bgp_cfg:RoutePolicyName";
                        type string;
                        description "Route policy name";
                      }
                      leaf not-used {
                        xr:xr-xml-map "bgp_cfg:NotUsed";
                        type uint32 {
                          range "0..127";
                        }
                        description "Not used";
                      }
                    }
                  }

                  container disable-cluster-client-to-client-rrs {
                    xr:xr-xml-map "bgp_cfg:DisableClusterClientToCl"+
                      "ientRRTable";
                    description
                      "Disable client-to-client reflection for a
                      cluster";

                    list disable-cluster-client-to-client-rr {
                      xr:xr-xml-map "bgp_cfg:DisableClusterClientTo"+
                        "ClientRR";
                      key "cluster-type cluster-id-number"+
                        " cluster-id-address";
                      description
                        "Cluster ID for which reflection is to be
                        disbled";
                      leaf cluster-type {
                        xr:xr-xml-map "bgp_cfg:ClusterType";
                        type Bgp-cluster-id;
                        description "Type of cluster-id";
                      }
                      leaf cluster-id-number {
                        xr:xr-xml-map "bgp_cfg:ClusterIDNumber";
                        type uint32 {
                          range "0..4294967295";
                        }
                        description
                          "Cluster ID: if configured as a number";
                      }
                      leaf cluster-id-address {
                        xr:xr-xml-map "bgp_cfg:ClusterIDAddress";
                        type inet:ip-address-no-zone;
                        description
                          "Cluster ID: if configured as an IP
                          Address";
                      }
                    }
                  }

                  container label-delay {
                    xr:xr-xml-map "bgp_cfg:LabelDelay";
                    presence "Indicates a label-delay node is"+
                      " configured.";
                    description
                      "Delay timer to batch label processing.";
                    leaf seconds {
                      xr:xr-xml-map "bgp_cfg:Seconds";
                      type uint32 {
                        range "0..10";
                      }
                      units "second";
                      mandatory true;
                      description "Delay, seconds part";
                    }
                    leaf milliseconds {
                      xr:xr-xml-map "bgp_cfg:Milliseconds";
                      type uint32 {
                        range "0..999";
                      }
                      units "millisecond";
                      mandatory true;
                      description "Delay, milliseconds part";
                    }
                  }

                  container retain-rt {
                    xr:xr-xml-map "bgp_cfg:RetainRT";
                    description
                      "Accept received updates with the
                      specified attributes";
                    leaf all {
                      xr:xr-xml-map "bgp_cfg:All";
                      type boolean;
                      description
                        "Whether all RTs are to be retained,
                        default is FALSE";
                    }
                    leaf route-policy-name {
                      xr:xr-xml-map "bgp_cfg:RoutePolicyName";
                      type string;
                      description "Route policy name";
                    }
                  }

                  container import-delay {
                    xr:xr-xml-map "bgp_cfg:ImportDelay";
                    presence "Indicates a import-delay node is"+
                      " configured.";
                    description
                      "Delay timer to batch import processing.";
                    leaf seconds {
                      xr:xr-xml-map "bgp_cfg:Seconds";
                      type uint32 {
                        range "0..10";
                      }
                      units "second";
                      mandatory true;
                      description "Delay, seconds part";
                    }
                    leaf milliseconds {
                      xr:xr-xml-map "bgp_cfg:Milliseconds";
                      type uint32 {
                        range "0..999";
                      }
                      units "millisecond";
                      mandatory true;
                      description "Delay, milliseconds part";
                    }
                  }
                  leaf inter-as-install {
                    xr:xr-xml-map "bgp_cfg:InterASInstall";
                    type empty;
                    description
                      "Enable install remote MVPN routes to PIM
                      in default VRF";
                  }
                  leaf segmented-mcast {
                    xr:xr-xml-map "bgp_cfg:SegmentedMcast";
                    type empty;
                    description "Enable segmented multicast";
                  }
                  leaf disable-default-martian-check {
                    xr:xr-xml-map "bgp_cfg:DisableDefaultMartianChe"+
                      "ck";
                    type empty;
                    description "Disable default Martian Check";
                  }
                  leaf next-hop-critical-trigger-delay {
                    xr:xr-xml-map "bgp_cfg:NextHopCriticalTriggerDe"+
                      "lay";
                    type uint32 {
                      range "0..4294967295";
                    }
                    units "millisecond";
                    default "3000";
                    description "Delay in milliseconds";
                  }
                  leaf next-hop-non-critical-trigger-delay {
                    xr:xr-xml-map "bgp_cfg:NextHopNonCriticalTrigge"+
                      "rDelay";
                    type uint32 {
                      range "0..4294967295";
                    }
                    units "millisecond";
                    default "10000";
                    description "Delay in milliseconds";
                  }
                  leaf label-security-rpf {
                    xr:xr-xml-map "bgp_cfg:LabelSecurityRPF";
                    type empty;
                    description
                      "Calculate/Install label-rpf information";
                  }
                  leaf label-retain {
                    xr:xr-xml-map "bgp_cfg:LabelRetain";
                    type uint32 {
                      range "3..60";
                    }
                    units "minute";
                    description "Label retention time in minutes";
                  }
                  leaf scan-time {
                    xr:xr-xml-map "bgp_cfg:ScanTime";
                    type uint32 {
                      range "5..3600";
                    }
                    units "second";
                    default "60";
                    description "Scanner interval (seconds)";
                  }
                  leaf rpki-origin-as-validation-disable {
                    xr:xr-xml-map "bgp_cfg:RPKIOriginASValidationDi"+
                      "sable";
                    type empty;
                    description "RPKI origin-AS validation disable";
                  }
                  leaf rpki-origin-as-validity-signal-ibgp {
                    xr:xr-xml-map "bgp_cfg:RPKIOriginASValiditySign"+
                      "alIBGP";
                    type empty;
                    description
                      "RPKI origin-AS validity signal ibgp";
                  }
                  leaf update-limit-sub-group-ebgp {
                    xr:xr-xml-map "bgp_cfg:UpdateLimitSubGroupEBGP";
                    type uint32 {
                      range "1..512";
                    }
                    units "megabyte";
                    default "32";
                    description "Update limit in MegaBytes(MB)";
                  }
                  leaf update-limit-address-family {
                    xr:xr-xml-map "bgp_cfg:UpdateLimitAddressFamily";
                    type uint32 {
                      range "4..2048";
                    }
                    units "megabyte";
                    default "256";
                    description "Update limit in MegaBytes(MB)";
                  }
                  leaf rpki-bestpath-use-origin-as-validity {
                    xr:xr-xml-map "bgp_cfg:RPKIBestpathUseOriginASV"+
                      "alidity";
                    type empty;
                    description
                      "RPKI bestpath use origin-AS validity";
                  }
                  leaf update-limit-sub-group-ibgp {
                    xr:xr-xml-map "bgp_cfg:UpdateLimitSubGroupIBGP";
                    type uint32 {
                      range "1..512";
                    }
                    units "megabyte";
                    default "32";
                    description "Update limit in MegaBytes(MB)";
                  }
                  leaf rpki-bestpath-origin-as-allow-invalid {
                    xr:xr-xml-map "bgp_cfg:RPKIBestpathOriginASAllo"+
                      "wInvalid";
                    type empty;
                    description
                      "RPKI bestpath origin-AS allow invalid";
                  }
                  leaf disable-client-to-client-rr {
                    xr:xr-xml-map "bgp_cfg:DisableClientToClientRR";
                    type empty;
                    description
                      "Disable client-to-client reflection";
                  }
                  leaf next-hop-route-policy {
                    xr:xr-xml-map "bgp_cfg:NextHopRoutePolicy";
                    type string;
                    description "Next hop route policy name";
                  }
                  leaf global-table-mcast {
                    xr:xr-xml-map "bgp_cfg:GlobalTableMcast";
                    type empty;
                    description "Enable global table multicast";
                  }
                  leaf wait-rib-install {
                    xr:xr-xml-map "bgp_cfg:WaitRIBInstall";
                    type empty;
                    description
                      "Wait for route install before updates";
                  }
                  leaf af-name {
                    xr:xr-xml-map "bgp_cfg:AFName";
                    type dt1:Bgp-address-family;
                    description "Address family";
                  }
                  uses AGGREGATE-ADDRESS-TABLE;
                  uses DYNAMIC-MED-INTERVAL;
                  uses DAMPENING;
                  uses ENABLE;
                  uses RIP-ROUTES;
                  uses LISP-ROUTES;
                  uses STATIC-ROUTES;
                  uses DISTANCE;
                  uses TABLE-POLICY;
                  uses ATTRIBUTE-DOWNLOAD;
                  uses LABEL-MODE;
                  uses EI-GRP-ROUTE-TABLE;
                  uses BEST-EXTERNAL;
                  uses SOURCED-NETWORK-TABLE;
                  uses CONNECTED-ROUTES;
                  uses ADDITIONAL-PATHS-RECEIVE;
                  uses PERMANENT-NETWORK;
                  uses ALLOCATE-LABEL;
                  uses ADDITIONAL-PATHS-SELECTION;
                  uses NEXT-HOP-RESOLUTION-PREFIX-LENGTH-MINIMUM;
                  uses RESET-WEIGHT-ON-IMPORT;
                  uses EBGP;
                  uses EIBGP;
                  uses OSPF-ROUTE-TABLE;
                  uses IBGP;
                  uses ADDITIONAL-PATHS-SEND;
                  uses MOBILE-ROUTES;
                  uses DISABLE-AS-PATH-LOOP-CHECK;
                  uses SUBSCRIBER-ROUTES;
                }
              }

              container rpki-static-routes {
                xr:xr-xml-map "bgp_cfg:RPKIStaticRouteTable";
                description "RPKI static route configuration";

                list rpki-static-route {
                  xr:xr-xml-map "bgp_cfg:RPKIStaticRoute";
                  key "addrress minimum maximum as";
                  description "RPKI static route";
                  leaf addrress {
                    xr:xr-xml-map "bgp_cfg:Addrress";
                    type inet:ip-address-no-zone;
                    description "Address";
                  }
                  leaf minimum {
                    xr:xr-xml-map "bgp_cfg:Minimum";
                    type int32;
                    description "Minimum Prefix Length";
                  }
                  leaf maximum {
                    xr:xr-xml-map "bgp_cfg:Maximum";
                    type int32;
                    description "Maximum Prefix Length";
                  }
                  leaf as {
                    xr:xr-xml-map "bgp_cfg:AS";
                    type int32;
                    description "AS Number";
                  }
                }
              }
              leaf update-out-logging {
                xr:xr-xml-map "bgp_cfg:UpdateOutLogging";
                type empty;
                description
                  "Enables logging of update generation events";
              }
              leaf install-diversion {
                xr:xr-xml-map "bgp_cfg:InstallDiversion";
                type empty;
                description "Enable bgp install diversion";
              }
              leaf next-hop-trigger-delay {
                xr:xr-xml-map "bgp_cfg:NextHopTriggerDelay";
                type uint32 {
                  range "0..300";
                }
                units "second";
                default "5";
                description "Delay value (seconds)";
              }
              leaf nsr {
                xr:xr-xml-map "bgp_cfg:NSR";
                type empty;
                description "Enable non-stop routing support";
              }
              leaf neighbor-logging-detail {
                xr:xr-xml-map "bgp_cfg:NeighborLoggingDetail";
                type empty;
                description
                  "Include extra detail in neighbor change
                  messages";
              }
              leaf mvpn {
                xr:xr-xml-map "bgp_cfg:MVPN";
                type empty;
                description "Connect to PIM/PIM6";
              }
              leaf rpki-origin-as-validation-disable {
                xr:xr-xml-map "bgp_cfg:RPKIOriginASValidationDisabl"+
                  "e";
                type empty;
                description "RPKI origin-AS validation disable";
              }
              leaf rpki-origin-as-validity-signal-ibgp {
                xr:xr-xml-map "bgp_cfg:RPKIOriginASValiditySignalIB"+
                  "GP";
                type empty;
                description "RPKI origin-AS validity signal ibgp";
              }
              leaf global-scan-time {
                xr:xr-xml-map "bgp_cfg:GlobalScanTime";
                type uint32 {
                  range "5..3600";
                }
                units "second";
                default "60";
                description "Scanner interval (seconds)";
              }
              leaf rpki-bestpath-use-origin-as-validity {
                xr:xr-xml-map "bgp_cfg:RPKIBestpathUseOriginASValid"+
                  "ity";
                type empty;
                description "RPKI bestpath use origin-AS validity";
              }
              leaf rpki-origin-as-validation-time {
                xr:xr-xml-map "bgp_cfg:RPKIOriginASValidationTime";
                type uint32 {
                  range "0..60";
                }
                units "second";
                description
                  "Prefix validation time (in seconds). Range 
                  : 5 - 60. Specify 0 to disable the timer";
              }
              leaf rpki-bestpath-origin-as-allow-invalid {
                xr:xr-xml-map "bgp_cfg:RPKIBestpathOriginASAllowInv"+
                  "alid";
                type empty;
                description "RPKI bestpath origin-AS allow invalid";
              }
              leaf enforce-ibgp-out-policy {
                xr:xr-xml-map "bgp_cfg:EnforceIBGPOutPolicy";
                type empty;
                description
                  "Allow all attributes to be modified by
                  outbound policy for iBGP peers";
              }
              leaf update-limit-process {
                xr:xr-xml-map "bgp_cfg:UpdateLimitProcess";
                type uint32 {
                  range "16..2048";
                }
                units "megabyte";
                default "512";
                description "Update limit in MegaBytes(MB)";
              }
              leaf update-error-handling-basic-ibgp-disable {
                xr:xr-xml-map "bgp_cfg:UpdateErrorHandlingBasicIBGP"+
                  "Disable";
                type empty;
                description "Disable basic error-handling";
              }
              leaf read-only {
                xr:xr-xml-map "bgp_cfg:ReadOnly";
                type empty;
                description "Enable bgp read-only";
              }
              leaf update-error-handling-extended-ebgp {
                xr:xr-xml-map "bgp_cfg:UpdateErrorHandlingExtendedE"+
                  "BGP";
                type empty;
                description "Enable extended error-handling";
              }
              leaf update-error-handling-basic-ebgp-disable {
                xr:xr-xml-map "bgp_cfg:UpdateErrorHandlingBasicEBGP"+
                  "Disable";
                type empty;
                description "Disable basic error-handling";
              }
              leaf igp-loop-check {
                xr:xr-xml-map "bgp_cfg:IGPLoopCheck";
                type empty;
                description
                  "Enable AS-path loop checking for iBGP peers";
              }
              leaf update-error-handling-extended-ibgp {
                xr:xr-xml-map "bgp_cfg:UpdateErrorHandlingExtendedI"+
                  "BGP";
                type empty;
                description "Enable extended error-handling";
              }
              uses GRACEFUL-RESTART;
              uses ROUTER-ID;
              uses DISABLE-ENFORCE-FIRST-AS;
              uses BEST-PATH-COST-COMMUNITY;
              uses BEST-PATH-AIGP-IGNORE;
              uses BEST-PATH-AS-PATH-LENGTH;
              uses IGP-REDIST-INTERNAL;
              uses MULTI-PATH-AS-PATH-IGNORE-ONWARDS;
              uses DISABLE-FAST-EXTERNAL-FALLOVER;
              uses DEFAULT-METRIC;
              uses DEFAULT-INFO-ORIGINATE;
              uses BEST-PATH-CONFEDERATION-PATHS;
              uses BEST-PATH-AS-MULTIPATH-RELAX;
              uses MPLS-ACTIVATED-INTERFACE-TABLE;
              uses DISABLE-AUTO-SOFT-RESET;
              uses DISABLE-MSG-LOG;
              uses GRACEFUL-RESTART-PURGE-TIME;
              uses GLOBAL-TIMERS;
              uses GRACEFUL-RESTART-TIME;
              uses BGP-CFG-BFD;
              uses DISABLE-NEIGHBOR-LOGGING;
              uses GRACEFUL-RESTART-STALEPATH-TIME;
              uses SEND-SOCKET-BUFFER-SIZES;
              uses BEST-PATH-MED-ALWAYS;
              uses RECEIVE-SOCKET-BUFFER-SIZES;
              uses BEST-PATH-ROUTER-ID;
              uses GRACEFUL-RESET;
              uses BEST-PATH-MED-MISSING;
              uses LOCAL-PREFERENCE;
            }
          }
          leaf bgp-running {
            xr:xr-xml-map "bgp_cfg:BGPRunning";
            type empty;
            description "BGP is running";
          }
          leaf as {
            xr:xr-xml-map "bgp_cfg:AS";
            type dt1:Bgp-as-range;
            description "2-byte or 4-byte Autonomous system number";
          }
        }
      }
    }
  }

  augment "/a2:snmp/a2:notification" {

    container bgp {
      xr:xr-xml-map "bgpmib_cfg:BGP";
      description
        "BGP4-MIB and CISCO-BGP4-MIB notification
        configuration";

      container bgp4mib {
        xr:xr-xml-map "bgpmib_cfg:BGP4MIB";
        description
          "Enable BGP4-MIB and CISCO-BGP4-MIB IPv4-only
          notifications: bgpEstablishedNotification,
          bgpBackwardTransNotification,
          cbgpFsmStateChange, cbgpBackwardTransition,
          cbgpPrefixThresholdExceeded,
          cbgpPrefixThresholdClear.";
        leaf enable {
          xr:xr-xml-map "bgpmib_cfg:Enable";
          type empty;
          description
            "Enable BGP4-MIB and CISCO-BGP4-MIB IPv4-only
            notifications";
        }
        leaf up-down {
          xr:xr-xml-map "bgpmib_cfg:UpDown";
          type empty;
          description
            "Enable BGP4-MIB and CISCO-BGP4-MIB IPv4-only
            up/down notifications";
        }
      }

      container cisco-bgp4mib {
        xr:xr-xml-map "bgpmib_cfg:CiscoBGP4MIB";
        description
          "Enable CISCO-BGP4-MIB v2 notifications:
          cbgpPeer2EstablishedNotification,
          cbgpPeer2BackwardTransNotification,
          cbgpPeer2FsmStateChange,
          cbgpPeer2BackwardTransition,
          cbgpPeer2PrefixThresholdExceeded,
          cbgpPeer2PrefixThresholdClear.";
        leaf enable {
          xr:xr-xml-map "bgpmib_cfg:Enable";
          type empty;
          description "Enable CISCO-BGP4-MIB v2 notifications";
        }
        leaf up-down {
          xr:xr-xml-map "bgpmib_cfg:UpDown";
          type empty;
          description
            "Enable CISCO-BGP4-MIB v2 up/down notifications";
        }
      }
    }
    description
      "This augment extends the configuration data of
      'Cisco-IOS-XR-snmp-agent-cfg'";
  }

  augment "/a1:vrfs/a1:vrf/a1:afs/a1:af" {

    container bgp {
      xr:xr-xml-map "bgp_vrf_cfg:BGP";
      description "BGP AF VRF config";

      container import-route-targets {
        xr:xr-xml-map "bgp_vrf_cfg:ImportRouteTargets";
        description "Import Route targets";
        uses ROUTE-TARGET-TABLE;
      }

      container export-route-targets {
        xr:xr-xml-map "bgp_vrf_cfg:ExportRouteTargets";
        description "Export Route targets";
        uses ROUTE-TARGET-TABLE;
      }

      container global-to-vrf-import-route-policy {
        xr:xr-xml-map "bgp_vrf_cfg:GlobalToVRFImportRoutePolicy";
        presence "Indicates a global-to-vrf-import-route-policy"+
          " node is configured.";
        description
          "Route policy for global to vrf import filtering";
        leaf route-policy-name {
          xr:xr-xml-map "bgp_vrf_cfg:RoutePolicyName";
          type string;
          mandatory true;
          description "Global to vrf import route policy";
        }
        leaf advertise-as-vpn {
          xr:xr-xml-map "bgp_vrf_cfg:AdvertiseAsVPN";
          type empty;
          description "Enable advertising imported paths to PEs";
        }
      }
      leaf export-route-policy {
        xr:xr-xml-map "bgp_vrf_cfg:ExportRoutePolicy";
        type string;
        description "Export route policy";
      }
      leaf import-route-policy {
        xr:xr-xml-map "bgp_vrf_cfg:ImportRoutePolicy";
        type string;
        description "Import route policy";
      }
      leaf vrf-to-global-export-route-policy {
        xr:xr-xml-map "bgp_vrf_cfg:VRFToGlobalExportRoutePolicy";
        type string;
        description "Vrf to global export route policy";
      }
    }
    description
      "This augment extends the configuration data of
      'Cisco-IOS-XR-infra-rsi-cfg'";
  }
}
