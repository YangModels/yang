submodule Cisco-IOS-XR-l2vpn-oper-sub2 {
  belongs-to Cisco-IOS-XR-l2vpn-oper {
    prefix Cisco-IOS-XR-l2vpn-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR l2vpn package operational data.
     
     Copyright (c) 2013-2023 by Cisco Systems, Inc.
     All rights reserved.";

  revision 2023-06-16 {
    description
      "- Added to stale-xid-modified to l2fib-mroute-summary.
       2023-02-10
         - Add more states to l2fib-evpn-ip4mac and l2fib-evpn-ip6mac.";
    semver:module-version "6.1.0";
  }
  revision 2022-03-14 {
    description
      "- Added new members to main-interface-info protect-type
       2022-03-09
          - l2fib-mroute-port: Added hardware-information leaf.
       2022-02-24
          - l2fib-mroute-port: Added pin-down-interface-name leaf.
       2022-02-09
          - Added l2fib-l3-sync-interfaces - Update keys of l2fib-mroute-port - Add l2fib-evpn-etree-remote - Update keys of l2fib-evpn-incl-mcast-ole - Add l2fib-mroute-ipv6-summary - Only expose valid keys and members of l2fib-mac-learning-mac, l2fib-mac-learning-mac-ipv4, and l2fib-mac-learning-mac-ipv6";
    semver:module-version "6.0.0";
  }
  revision 2021-09-07 {
    description
      "- Added SRv6 nhop
       2021-08-24
           Updated l2vpn forwarding adjacencies to expose both interface and address information.
       2021-08-13
           - Changed flag-extension to 32bit
       2021-07-20
           - Added support for MAC is-cfm flag";
    semver:module-version "5.0.0";
  }
  revision 2020-05-05 {
    description
      "changes related to treat SRv6 and SID as well-known when parsing XML for yang";
    semver:module-version "4.0.0";
  }
  revision 2020-04-28 {
    description
      "- AC Backup related changes
       2020-01-22
       - PWGROUP related changes
       2019-12-20
       - EVPN-VPWS related changes - SR-TE policy related changes";
    semver:module-version "3.0.0";
  }
  revision 2019-04-05 {
    description
      "Establish semantic version baseline.";
    semver:module-version "2.0.0";
  }
  revision 2019-03-30 {
    description
      "- Rename l2fib-mac-learning-mac* interface-handle to interface-name - Rename l2fib-pw-group tunnel-if-handle to tunnel-interface-name - Convert several array from leaf-list to list syntax. - Implement range datatypes for all L2FIB integers.";
  }
  revision 2018-08-01 {
    description
      "Removed empty groupings.";
  }
  revision 2017-09-07 {
    description
      "Fixed type translation error.";
  }
  revision 2017-06-26 {
    description
      "Change identifiers to be more readable.";
  }
  revision 2017-05-01 {
    description
      "Fixing backward compatibility error in module.";
  }
  revision 2015-11-09 {
    description
      "IOS XR 6.0 revision.";
  }

  grouping PWHE-EA-SUM {
    description
      "PWHE EA SUM";
    leaf eaidb-count {
      type uint32;
      description
        "EA IDB count";
    }
    leaf ea-intf-count {
      type uint32;
      description
        "EA Interface count";
    }
  }

  grouping PWHE-EA-IDB {
    description
      "PWHE EA Interface DB Bag";
    leaf interface-handle {
      type xr:Interface-name;
      description
        "Interface Handle";
    }
    leaf interface-type {
      type string;
      description
        "Interface Type";
    }
    leaf interface-up {
      type boolean;
      description
        "Interface Up (true/false)";
    }
    leaf l2-overhead {
      type uint32;
      units "byte";
      description
        "L2 overhead size in bytes (1-64)";
    }
    leaf bandwidth {
      type uint32;
      units "kbit/s";
      description
        "Bandwidth in kbps";
    }
    leaf mtu {
      type uint32;
      description
        "Maximum Transmission Unit";
    }
  }
}
