module Cisco-IOS-XR-um-ipv6-nd-cfg {
  namespace "http://cisco.com/ns/yang/Cisco-IOS-XR-um-ipv6-nd-cfg";
  prefix um-ipv6-nd-cfg;

  import Cisco-IOS-XR-types {
    prefix xr;
  }
  import ietf-inet-types {
    prefix inet;
  }
  import ietf-yang-types {
    prefix yang;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-nd package configuration.
     
     This YANG module augments the
     modules with configuration data.
     
     Copyright (c) 2021-2022 by Cisco Systems, Inc.
     All rights reserved.";

  revision 2022-03-11 {
    description
      "Added proxy-nd container under ipv6 nd";
    semver:module-version "1.1.0";
  }
  revision 2021-06-03 {
    description
      "Initial release";
    semver:module-version "1.0.0";
  }

  feature ipv6_nd_ra_dns_server_support_check {
    description
      "ipv6 nd ra dns server support check";
  }

  feature ipv6_nd_ra_specific_route_support_check {
    description
      "ipv6 nd ra specific route support check";
  }

  feature ipv6_nd_default_router_preference_support_check {
    description
      "ipv6 nd default router preference support check";
  }

  feature ipv6_nd_cos_supported {
    description
      "Cos value for all outgoing ND control packets";
  }

  grouping IF-IPV6-BODY {
    container nd {
      description
        "IPv6 interface Neighbor Discovery subcommands";
      leaf reachable-time {
        type uint32 {
          range "0..3600000" {
            description
              "Reachability time in milliseconds";
          }
        }
        description
          "Set advertised reachability time";
      }
      leaf cache-limit {
        type uint32 {
          range "0..128000" {
            description
              "Cache Limit";
          }
        }
        description
          "Set Cache Limit for neighbor entry";
      }
      container dad {
        description
          "Duplicate Address Detection";
        leaf attempts {
          type uint32 {
            range "0..600" {
              description
                "Number of attempts";
            }
          }
          description
            "Set IPv6 Duplicate Address Detection Transmits";
        }
      }
      container unicast-ra {
        presence "Indicates a unicast-ra node is configured.";
        description
          "Send Unicast Solicited IPv6 Router Advertisements";
      }
      container suppress-ra {
        presence "Indicates a suppress-ra node is configured.";
        description
          "Suppress IPv6 Router Advertisements";
      }
      container managed-config-flag {
        presence "Indicates a managed-config-flag node is configured.";
        description
          "Hosts should use stateful protocol for address config";
      }
      container other-config-flag {
        presence "Indicates a other-config-flag node is configured.";
        description
          "Hosts should use stateful protocol for non-address config";
      }
      leaf ns-interval {
        type uint32 {
          range "1000..4294967295" {
            description
              "Retransmission interval in milliseconds";
          }
        }
        description
          "Set advertised NS retransmission interval";
      }
      container ra-interval {
        presence "Indicates a ra-interval node is configured.";
        description
          "Set IPv6 Router Advertisement Interval";
        leaf maximum-ra-interval {
          type uint32 {
            range "4..1800" {
              description
                "Maximum RA Interval (sec)";
            }
          }
          mandatory true;
          description
            "Set IPv6 Router Advertisement Interval";
        }
        leaf minimum-ra-interval {
          type uint32 {
            range "3..1800" {
              description
                "Minimum RA Interval (sec). Must be less than 0.75 * maximum interval";
            }
          }
          description
            "Minimum RA Interval (sec). Must be less than 0.75 * maximum interval";
        }
      }
      leaf ra-lifetime {
        type uint32 {
          range "0..9000" {
            description
              "RA Lifetime (seconds)";
          }
        }
        description
          "Set IPv6 Router Advertisement Lifetime";
      }
      container redirects {
        presence "Indicates a redirects node is configured.";
        description
          "Enable sending of ICMP Redirect messages";
      }
      container nud-conform {
        presence "Indicates a nud-conform node is configured.";
        description
          "Enable NUD conformance logic";
      }
      container prefix {
        description
          "Configure IPv6 Routing Prefix Advertisement";
        container default {
          must "infinite or valid-lifetime or at or no-adv or off-link or no-autoconfig";
          presence "Indicates a default node is configured.";
          description
            "Specify prefix default parameters";
          container infinite {
            must "not(../valid-lifetime or ../at or ../no-adv) and (infinite or preferred-lifetime)";
            presence "Indicates a infinite node is configured.";
            description
              "Infinite Valid Lifetime";
            container infinite {
              must "not(../preferred-lifetime)";
              presence "Indicates a infinite node is configured.";
              description
                "Infinite Preferred Lifetime";
            }
            leaf preferred-lifetime {
              type uint32 {
                range "0..4294967294" {
                  description
                    "Preferred Lifetime (secs) must be <= Valid Lifetime";
                }
              }
              must "not(../infinite)";
              description
                "Preferred Lifetime (secs) must be <= Valid Lifetime";
            }
          }
          leaf valid-lifetime {
            type uint32 {
              range "0..4294967294" {
                description
                  "Valid Lifetime (secs)";
              }
            }
            must "not(../infinite or ../at or ../no-adv) and ../preferred-lifetime";
            description
              "Valid Lifetime (secs)";
          }
          leaf preferred-lifetime {
            type uint32 {
              range "0..4294967294" {
                description
                  "Preferred Lifetime (secs) must be <= Valid Lifetime";
              }
            }
            must "../valid-lifetime";
            description
              "Preferred Lifetime (secs) must be <= Valid Lifetime";
          }
          container at {
            must "not(../valid-lifetime or ../infinite or ../no-adv)";
            presence "Indicates a at node is configured.";
            description
              "Expire prefix at a specific time/date";
            container expire-valid-lifetime {
              description
                "Expire prefix at a specific time/date";
              leaf month {
                type enumeration {
                  enum "January" {
                    value 0;
                    description
                      "January";
                  }
                  enum "February" {
                    value 1;
                    description
                      "February";
                  }
                  enum "March" {
                    value 2;
                    description
                      "March";
                  }
                  enum "April" {
                    value 3;
                    description
                      "April";
                  }
                  enum "May" {
                    value 4;
                    description
                      "May";
                  }
                  enum "June" {
                    value 5;
                    description
                      "June";
                  }
                  enum "July" {
                    value 6;
                    description
                      "July";
                  }
                  enum "August" {
                    value 7;
                    description
                      "August";
                  }
                  enum "September" {
                    value 8;
                    description
                      "September";
                  }
                  enum "October" {
                    value 9;
                    description
                      "October";
                  }
                  enum "November" {
                    value 10;
                    description
                      "November";
                  }
                  enum "December" {
                    value 11;
                    description
                      "December";
                  }
                }
                mandatory true;
                description
                  "Month to expire Valid Lifetime";
              }
              leaf date {
                type uint32 {
                  range "1..31" {
                    description
                      "Date to expire Valid Lifetime";
                  }
                }
                mandatory true;
                description
                  "Date to expire Valid Lifetime";
              }
              leaf year {
                type uint32 {
                  range "2003..2035" {
                    description
                      "Year to expire Valid Lifetime";
                  }
                }
                mandatory true;
                description
                  "Year to expire Valid Lifetime";
              }
              leaf time-hour {
                type uint32 {
                  range "0..23" {
                    description
                      "Time to expire Valid Lifetime (hh:mm)";
                  }
                }
                mandatory true;
                description
                  "Time to expire Valid Lifetime (hh:mm)";
              }
              leaf time-minute {
                type uint32 {
                  range "0..59" {
                    description
                      "Time to Valid (hh:mm)";
                  }
                }
                mandatory true;
                description
                  "Time to Valid (hh:mm)";
              }
            }
            container expire-preferred-lifetime {
              description
                "Expire prefix at a specific time/date";
              leaf month {
                type enumeration {
                  enum "January" {
                    value 0;
                    description
                      "January";
                  }
                  enum "February" {
                    value 1;
                    description
                      "February";
                  }
                  enum "March" {
                    value 2;
                    description
                      "March";
                  }
                  enum "April" {
                    value 3;
                    description
                      "April";
                  }
                  enum "May" {
                    value 4;
                    description
                      "May";
                  }
                  enum "June" {
                    value 5;
                    description
                      "June";
                  }
                  enum "July" {
                    value 6;
                    description
                      "July";
                  }
                  enum "August" {
                    value 7;
                    description
                      "August";
                  }
                  enum "September" {
                    value 8;
                    description
                      "September";
                  }
                  enum "October" {
                    value 9;
                    description
                      "October";
                  }
                  enum "November" {
                    value 10;
                    description
                      "November";
                  }
                  enum "December" {
                    value 11;
                    description
                      "December";
                  }
                }
                mandatory true;
                description
                  "Month to expire Preferred Lifetime";
              }
              leaf date {
                type uint32 {
                  range "1..31" {
                    description
                      "Date to expire Preferred Lifetime";
                  }
                }
                mandatory true;
                description
                  "Date to expire Preferred Lifetime";
              }
              leaf year {
                type uint32 {
                  range "2003..2035" {
                    description
                      "Year to expire Preferred Lifetime";
                  }
                }
                mandatory true;
                description
                  "Year to expire Preferred Lifetime";
              }
              leaf time-hour {
                type uint32 {
                  range "0..23" {
                    description
                      "Time to expire Preferred Lifetime (hh:mm)";
                  }
                }
                mandatory true;
                description
                  "Time to expire Preferred Lifetime (hh:mm)";
              }
              leaf time-minute {
                type uint32 {
                  range "0..59" {
                    description
                      "Time to Preferred (hh:mm)";
                  }
                }
                mandatory true;
                description
                  "Time to Preferred (hh:mm)";
              }
            }
          }
          container off-link {
            presence "Indicates a off-link node is configured.";
            description
              "Do not use prefix for onlink determination";
          }
          container no-autoconfig {
            presence "Indicates a no-autoconfig node is configured.";
            description
              "Do not use prefix for autoconfiguration";
          }
          container no-adv {
            must "not(../valid-lifetime or ../at or ../infinite)";
            presence "Indicates a no-adv node is configured.";
            description
              "Do not advertise prefix";
          }
        }
        container ipv6-addresses {
          list ipv6-address {
            must "infinite or valid-lifetime or at or no-adv or off-link or no-autoconfig";
            key "address";
            description
              "IPv6 prefix x:x::y/<z>";
            leaf address {
              type inet:ipv6-address-no-zone;
              description
                "IPv6 prefix x:x::y/<z>";
            }
            leaf prefix-length {
              type xr:Ipv6-prefix-length;
              mandatory true;
              description
                "IPv6 prefix x:x::y/<z>";
            }
            leaf zone {
              type union {
                type string {
                  pattern "0" {
                    description
                      "Default zone id";
                  }
                }
                type string;
              }
              mandatory true;
              description
                "IPv6 address zone";
            }
            container infinite {
              must "not(../valid-lifetime or ../at or ../no-adv) and (infinite or preferred-lifetime)";
              presence "Indicates a infinite node is configured.";
              description
                "Infinite Valid Lifetime";
              container infinite {
                must "not(../preferred-lifetime)";
                presence "Indicates a infinite node is configured.";
                description
                  "Infinite Preferred Lifetime";
              }
              leaf preferred-lifetime {
                type uint32 {
                  range "0..4294967294" {
                    description
                      "Preferred Lifetime (secs) must be <= Valid Lifetime";
                  }
                }
                must "not(../infinite)";
                description
                  "Preferred Lifetime (secs) must be <= Valid Lifetime";
              }
            }
            leaf valid-lifetime {
              type uint32 {
                range "0..4294967294" {
                  description
                    "Valid Lifetime (secs)";
                }
              }
              must "not(../infinite or ../at or ../no-adv) and ../preferred-lifetime";
              description
                "Valid Lifetime (secs)";
            }
            leaf preferred-lifetime {
              type uint32 {
                range "0..4294967294" {
                  description
                    "Preferred Lifetime (secs) must be <= Valid Lifetime";
                }
              }
              must "../valid-lifetime";
              description
                "Preferred Lifetime (secs) must be <= Valid Lifetime";
            }
            container at {
              must "not(../valid-lifetime or ../infinite or ../no-adv)";
              presence "Indicates a at node is configured.";
              description
                "Expire prefix at a specific time/date";
              container expire-valid-lifetime {
                description
                  "Expire prefix at a specific time/date";
                leaf month {
                  type enumeration {
                    enum "January" {
                      value 0;
                      description
                        "January";
                    }
                    enum "February" {
                      value 1;
                      description
                        "February";
                    }
                    enum "March" {
                      value 2;
                      description
                        "March";
                    }
                    enum "April" {
                      value 3;
                      description
                        "April";
                    }
                    enum "May" {
                      value 4;
                      description
                        "May";
                    }
                    enum "June" {
                      value 5;
                      description
                        "June";
                    }
                    enum "July" {
                      value 6;
                      description
                        "July";
                    }
                    enum "August" {
                      value 7;
                      description
                        "August";
                    }
                    enum "September" {
                      value 8;
                      description
                        "September";
                    }
                    enum "October" {
                      value 9;
                      description
                        "October";
                    }
                    enum "November" {
                      value 10;
                      description
                        "November";
                    }
                    enum "December" {
                      value 11;
                      description
                        "December";
                    }
                  }
                  mandatory true;
                  description
                    "Month to expire Valid Lifetime";
                }
                leaf date {
                  type uint32 {
                    range "1..31" {
                      description
                        "Date to expire Valid Lifetime";
                    }
                  }
                  mandatory true;
                  description
                    "Date to expire Valid Lifetime";
                }
                leaf year {
                  type uint32 {
                    range "2003..2035" {
                      description
                        "Year to expire Valid Lifetime";
                    }
                  }
                  mandatory true;
                  description
                    "Year to expire Valid Lifetime";
                }
                leaf time-hour {
                  type uint32 {
                    range "0..23" {
                      description
                        "Time to expire Valid Lifetime (hh:mm)";
                    }
                  }
                  mandatory true;
                  description
                    "Time to expire Valid Lifetime (hh:mm)";
                }
                leaf time-minute {
                  type uint32 {
                    range "0..59" {
                      description
                        "Time to Valid (hh:mm)";
                    }
                  }
                  mandatory true;
                  description
                    "Time to Valid (hh:mm)";
                }
              }
              container expire-preferred-lifetime {
                description
                  "Expire prefix at a specific time/date";
                leaf month {
                  type enumeration {
                    enum "January" {
                      value 0;
                      description
                        "January";
                    }
                    enum "February" {
                      value 1;
                      description
                        "February";
                    }
                    enum "March" {
                      value 2;
                      description
                        "March";
                    }
                    enum "April" {
                      value 3;
                      description
                        "April";
                    }
                    enum "May" {
                      value 4;
                      description
                        "May";
                    }
                    enum "June" {
                      value 5;
                      description
                        "June";
                    }
                    enum "July" {
                      value 6;
                      description
                        "July";
                    }
                    enum "August" {
                      value 7;
                      description
                        "August";
                    }
                    enum "September" {
                      value 8;
                      description
                        "September";
                    }
                    enum "October" {
                      value 9;
                      description
                        "October";
                    }
                    enum "November" {
                      value 10;
                      description
                        "November";
                    }
                    enum "December" {
                      value 11;
                      description
                        "December";
                    }
                  }
                  mandatory true;
                  description
                    "Month to expire Preferred Lifetime";
                }
                leaf date {
                  type uint32 {
                    range "1..31" {
                      description
                        "Date to expire Preferred Lifetime";
                    }
                  }
                  mandatory true;
                  description
                    "Date to expire Preferred Lifetime";
                }
                leaf year {
                  type uint32 {
                    range "2003..2035" {
                      description
                        "Year to expire Preferred Lifetime";
                    }
                  }
                  mandatory true;
                  description
                    "Year to expire Preferred Lifetime";
                }
                leaf time-hour {
                  type uint32 {
                    range "0..23" {
                      description
                        "Time to expire Preferred Lifetime (hh:mm)";
                    }
                  }
                  mandatory true;
                  description
                    "Time to expire Preferred Lifetime (hh:mm)";
                }
                leaf time-minute {
                  type uint32 {
                    range "0..59" {
                      description
                        "Time to Preferred (hh:mm)";
                    }
                  }
                  mandatory true;
                  description
                    "Time to Preferred (hh:mm)";
                }
              }
            }
            container off-link {
              presence "Indicates a off-link node is configured.";
              description
                "Do not use prefix for onlink determination";
            }
            container no-autoconfig {
              presence "Indicates a no-autoconfig node is configured.";
              description
                "Do not use prefix for autoconfiguration";
            }
            container no-adv {
              must "not(../valid-lifetime or ../at or ../infinite)";
              presence "Indicates a no-adv node is configured.";
              description
                "Do not advertise prefix";
            }
          }
        }
      }
      leaf srp-encap {
        type enumeration {
          enum "SRP-A" {
            value 5;
            description
              "Encapsulation type SRP, prefer side A";
          }
          enum "SRP-B" {
            value 6;
            description
              "Encapsulation type SRP, prefer side B";
          }
        }
        description
          "Set SRP Unicast prefer encapsulation";
      }
      leaf srp-mcast-encap {
        type enumeration {
          enum "SRP-A" {
            value 5;
            description
              "Encapsulation type SRP, prefer side A";
          }
          enum "SRP-B" {
            value 6;
            description
              "Encapsulation type SRP, prefer side B";
          }
        }
        description
          "Set SRP Mcast prefer encapsulation";
      }
      container ra {
        description
          "IPv6 interface ND RA subcommands";
        container hoplimit {
          description
            "IPv6 ND RA hoplimit";
          container unspecified {
            presence "Indicates a unspecified node is configured.";
            description
              "Unspecified IPv6 ND RA hop-limit value";
          }
        }
        container mtu {
          description
            "IPv6 ND RA mtu option configuration";
          container suppress {
            presence "Indicates a suppress node is configured.";
            description
              "Suppress mtu option in IPv6 ND RA header";
          }
        }
        container dns {
          description
            "IPv6 ND RA DNS";
          container servers {
            description
              "IPv6 ND RA DNS Server";
            list server {
              must "server-lifetime or infinite-lifetime or zero-lifetime";
              key "address";
              description
                "IPv6 ND RA DNS Server";
              leaf address {
                type inet:ipv6-address-no-zone;
                description
                  "RA DNS Server IPv6 Address x:x::y";
              }
              leaf server-lifetime {
                type uint32 {
                  range "12..4294967295" {
                    description
                      "IPv6 RA DNS Server Lifetime Interval in Seconds,range should be between(3*(max ra lifetime)) <= dns lifetime <= 4294967295";
                  }
                }
                must "not(../infinite-lifetime or ../zero-lifetime)";
                description
                  "IPv6 RA DNS Server Lifetime Interval in Seconds,range should be between(3*(max ra lifetime)) <= dns lifetime <= 4294967295";
              }
              container infinite-lifetime {
                must "not(../server-lifetime or ../zero-lifetime)";
                presence "Indicates a infinite-lifetime node is configured.";
                description
                  "Infinite IPv6 RA DNS Server Lifetime";
              }
              container zero-lifetime {
                must "not(../server-lifetime or ../infinite-lifetime)";
                presence "Indicates a zero-lifetime node is configured.";
                description
                  "Zero IPv6 RA DNS Server Lifetime";
              }
            }
          }
          container search {
            description
              "IPv6 ND RA DNS Search";
            container lists {
              description
                "IPv6 ND RA DNS Search List";
              list list {
                key "list-name";
                description
                  "IPv6 ND RA DNS Search List";
                leaf list-name {
                  type xr:Cisco-ios-xr-string {
                    length "1..255" {
                      description
                        "RA DNS Search List Name String";
                    }
                  }
                  description
                    "IPv6 ND RA DNS Search List";
                }
                leaf lifetime-interval {
                  type uint32 {
                    range "12..4294967295" {
                      description
                        "IPv6 RA DNS Search List Lifetime Interval in Seconds,range should be between (3*(max ra lifetime)) <= dns lifetime <= 4294967295";
                    }
                  }
                  must "not(../infinite-lifetime or ../zero-lifetime)";
                  description
                    "IPv6 RA DNS Search List Lifetime Interval in Seconds,range should be between (3*(max ra lifetime)) <= dns lifetime <= 4294967295";
                }
                container infinite-lifetime {
                  must "not(../lifetime-interval or ../zero-lifetime)";
                  presence "Indicates a infinite-lifetime node is configured.";
                  description
                    "Infinite IPv6 RA DNS Search List Lifetime";
                }
                container zero-lifetime {
                  must "not(../lifetime-interval or ../infinite-lifetime)";
                  presence "Indicates a zero-lifetime node is configured.";
                  description
                    "Zero IPv6 RA DNS Search List Lifetime";
                }
              }
            }
          }
        }
        container specific {
          description
            "IPv6 ND RA Specific";
          container routes {
            description
              "IPv6 ND RA Specific Route";
            list route {
              must "lifetime";
              key "prefix-address";
              description
                "IPv6 ND RA Specific Route";
              leaf prefix-address {
                type inet:ipv6-address-no-zone;
                description
                  "RA Specific Route IPv6 prefix x:x::y/<z>";
              }
              leaf prefix-length {
                type xr:Ipv6-prefix-length;
                mandatory true;
                description
                  "RA Specific Route IPv6 prefix x:x::y/<z>";
              }
              container lifetime {
                must "lifetime-interval or infinite-lifetime or zero-lifetime";
                presence "Indicates a lifetime node is configured.";
                description
                  "IPv6 RA Specific Route Lifetime";
                leaf lifetime-interval {
                  type uint32 {
                    range "0..4294967295" {
                      description
                        "IPv6 RA Specific Route Lifetime Interval in Seconds";
                    }
                  }
                  must "not(../infinite-lifetime or ../zero-lifetime)";
                  description
                    "IPv6 RA Specific Route Lifetime Interval in Seconds";
                }
                container infinite-lifetime {
                  must "not(../lifetime-interval or ../zero-lifetime)";
                  presence "Indicates a infinite-lifetime node is configured.";
                  description
                    "Infinite IPv6 RA Specific Route Lifetime";
                }
                container zero-lifetime {
                  must "not(../lifetime-interval or ../infinite-lifetime)";
                  presence "Indicates a zero-lifetime node is configured.";
                  description
                    "Zero IPv6 RA Specific Route Lifetime";
                }
                container preference {
                  description
                    "IPv6 RA Specific Route preference";
                  container high {
                    must "not(../medium or ../low)";
                    presence "Indicates a high node is configured.";
                    description
                      "High RA Specific Route preference";
                  }
                  container medium {
                    must "not(../high or ../low)";
                    presence "Indicates a medium node is configured.";
                    description
                      "Medium RA Specific Route preference";
                  }
                  container low {
                    must "not(../high or ../medium)";
                    presence "Indicates a low node is configured.";
                    description
                      "Low RA Specific Route router preference";
                  }
                }
              }
            }
          }
        }
      }
      container proxy-nd {
        presence "Indicates a proxy-nd node is configured.";
        description
          "Enable IPv6 ND proxy";
      }
      container router-preference {
        description
          "IPv6 ND router-preference";
        container high {
          must "not(../medium or ../low)";
          presence "Indicates a high node is configured.";
          description
            "High default router preference";
        }
        container medium {
          must "not(../high or ../low)";
          presence "Indicates a medium node is configured.";
          description
            "Medium default router preference";
        }
        container low {
          must "not(../high or ../medium)";
          presence "Indicates a low node is configured.";
          description
            "Low default router preference";
        }
      }
    }
  }

  augment "/a1:interfaces/a1:interface/a1:ipv6" {
    uses IF-IPV6-BODY;
  }
  augment "/a1:interfaces/a1:interface-preconfigure/a1:ipv6" {
    uses IF-IPV6-BODY;
  }
  container ipv6 {
    description
      "Global IPv6 configuration commands";
    container nd {
      description
        "IPv6 Neighbor Discovery subcommands";
      leaf cos {
        if-feature "ipv6_nd_cos_supported";
        type uint32 {
          range "0..7" {
            description
              "cos value";
          }
        }
        description
          "Set cos value to outer vlan and inner vlan (if present) in all outgoing ND control packets";
      }
      leaf scavenge-timeout {
        type uint32 {
          range "1..43200" {
            description
              "RA Lifetime (seconds)";
          }
        }
        description
          "Set Lifetime for STALE neighbor entry";
      }
    }
    container neighbors {
      description
        "Neighbor";
      list neighbor {
        key "address interface-name";
        description
          "Neighbor";
        leaf address {
          type inet:ipv6-address-no-zone;
          description
            "Neighbor";
        }
        leaf interface-name {
          type xr:Interface-name;
          description
            "Enter interface";
        }
        leaf zone {
          type union {
            type string {
              pattern "0" {
                description
                  "Default zone id";
              }
            }
            type string;
          }
          mandatory true;
          description
            "IPv6 address zone";
        }
        leaf hardware-address {
          type yang:mac-address;
          mandatory true;
          description
            "48-bit hardware address";
        }
      }
    }
  }
}
