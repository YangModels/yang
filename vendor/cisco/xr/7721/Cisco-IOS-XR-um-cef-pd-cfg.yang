module Cisco-IOS-XR-um-cef-pd-cfg {
  namespace "http://cisco.com/ns/yang/Cisco-IOS-XR-um-cef-pd-cfg";
  prefix um-cef-pd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cef-pd package configuration.
     
     This YANG module augments the
     modules with configuration data.
     
     Copyright (c) 2020 by Cisco Systems, Inc.
     All rights reserved.";

  revision 2020-12-10 {
    description
      "Initial release";
    semver:module-version "1.0.0";
  }

  container cef-pd {
    description
      "cef platform specific options";
    container one-hop-imp-null-te-tunnel {
      description
        "single hop implicit-null mpls-te tunnel";
      container stats {
        description
          "statistics";
        container disable {
          presence "Indicates a disable node is configured.";
          description
            "turn off";
        }
      }
    }
  }
}
