module Cisco-IOS-XR-ofa-npu-pfc-oper {
  namespace "http://cisco.com/ns/yang/Cisco-IOS-XR-ofa-npu-pfc-oper";
  prefix ofa-npu-pfc-oper;

  import Cisco-IOS-XR-types {
    prefix xr;
  }
  import cisco-semver {
    prefix semver;
  }
  include Cisco-IOS-XR-ofa-npu-pfc-oper-sub1 {
    revision-date 2021-08-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-npu-pfc package operational data.
     
     This module contains definitions
     for the following management objects:
       ofapfc: Stats Data
     
     Copyright (c) 2013-2021 by Cisco Systems, Inc.
     All rights reserved.";

  revision 2021-08-19 {
    description
      "Create the initial priority-flow-control oper yang model.";
    semver:module-version "1.0.0";
  }
  revision 2019-04-05 {
    description
      "Establish semantic version baseline.";
  }
  revision 2015-11-09 {
    description
      "IOS XR 6.0 revision.";
  }

  container ofapfc {
    config false;
    description
      "Stats Data";
    container pfc {
      description
        "PFC data";
      container nodes {
        description
          "PFC data for available nodes";
        list node {
          key "node-name";
          description
            "PFC operational data for a particular node";
          container display {
            description
              "pfc data";
            uses OFA-PFC-CFG;
          }
          leaf node-name {
            type xr:Node-id;
            description
              "Node ID";
          }
        }
      }
    }
  }
}
