module Cisco-IOS-XR-NCS-BDplatforms-npu-resources-oper {
  namespace "http://cisco.com/ns/yang/Cisco-IOS-XR-NCS-BDplatforms-npu-resources-oper";
  prefix ncs-bdplatforms-npu-resources-oper;

  import cisco-semver {
    prefix semver;
  }
  import Cisco-IOS-XR-platforms-ofa-oper {
    prefix a1;
  }
  include Cisco-IOS-XR-NCS-BDplatforms-npu-resources-oper-sub1 {
    revision-date 2022-07-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR NCS-BDplatforms-npu-resources package operational data.
     
     This YANG module augments the
       Cisco-IOS-XR-platforms-ofa-oper
     module with state data.
     
     Copyright (c) 2013-2022 by Cisco Systems, Inc.
     All rights reserved.";

  revision 2022-07-22 {
    description
      "Updated task id in root oper";
    semver:module-version "2.1.0";
  }
  revision 2022-04-01 {
    description
      "rif and inlif tracking added";
    semver:module-version "2.1.0";
  }
  revision 2020-10-09 {
    description
      "Updated task id in root oper";
    semver:module-version "2.0.0";
  }
  revision 2019-12-14 {
    description
      "Updated date for npu resources model";
    semver:module-version "1.2.0";
  }
  revision 2019-04-05 {
    description
      "Establish semantic version baseline.";
    semver:module-version "1.0.0";
  }
  revision 2015-11-09 {
    description
      "IOS XR 6.0 revision.";
  }

  typedef Resource {
    type enumeration {
      enum "lem" {
        value 0;
        description
          "lem";
      }
      enum "lpm" {
        value 1;
        description
          "lpm";
      }
      enum "encap" {
        value 2;
        description
          "encap";
      }
      enum "ext-tcam-ipv4" {
        value 3;
        description
          "ext tcam ipv4";
      }
      enum "ext-tcam-ipv6-short" {
        value 4;
        description
          "ext tcam ipv6 short";
      }
      enum "ext-tcam-ipv6-long" {
        value 5;
        description
          "ext tcam ipv6 long";
      }
      enum "fec" {
        value 6;
        description
          "fec";
      }
      enum "ecmp-fec" {
        value 7;
        description
          "ecmp fec";
      }
      enum "ext-tcam-ipv6" {
        value 8;
        description
          "ext tcam ipv6";
      }
      enum "rif" {
        value 9;
        description
          "rif";
      }
      enum "inlif" {
        value 10;
        description
          "inlif";
      }
      enum "inlif1" {
        value 11;
        description
          "inlif1";
      }
      enum "inlif2" {
        value 12;
        description
          "inlif2";
      }
    }
    description
      "Resource";
  }

  augment "/a1:ofa/a1:stats/a1:nodes/a1:node" {
    description
      "This augment extends the operational data of
       'Cisco-IOS-XR-platforms-ofa-oper'";
    container hw-resources-datas {
      description
        "OFA hw resources stats ";
      list hw-resources-data {
        key "resource";
        description
          "Hardware resources table";
        leaf resource {
          type Resource;
          description
            "Resource type";
        }
        uses OFA-SYSDB-HW-RESOURCE;
      }
    }
  }
}
