module Cisco-IOS-XR-healthcheck-oper {
  namespace "http://cisco.com/ns/yang/Cisco-IOS-XR-healthcheck-oper";
  prefix healthcheck-oper;

  import Cisco-IOS-XR-types {
    prefix xr;
  }
  import cisco-semver {
    prefix semver;
  }
  include Cisco-IOS-XR-healthcheck-oper-sub2 {
    revision-date 2021-10-19;
  }
  include Cisco-IOS-XR-healthcheck-oper-sub1 {
    revision-date 2021-10-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package operational data.
     
     This module contains definitions
     for the following management objects:
       health-check: Health check operational data space
     
     Copyright (c) 2013-2021 by Cisco Systems, Inc.
     All rights reserved.";

  revision 2021-10-19 {
    description
      "Updated Custom Metric";
    semver:module-version "1.1.0";
  }
  revision 2020-09-18 {
    description
      "Fabric health metric updated.";
    semver:module-version "1.0.0";
  }
  revision 2019-04-05 {
    description
      "Establish semantic version baseline.";
  }
  revision 2015-11-09 {
    description
      "IOS XR 6.0 revision.";
  }

  grouping SUMMARY {
    description
      "Common node of asic-reset, packet-drop";
    container summary {
      description
        "ASIC reset and packet drop summary";
      uses HCMGR-USE-CASE-SUMMARY-DATA;
    }
  }

  grouping NODE-TABLE {
    description
      "Common node of asic-reset, packet-drop";
    container node-entries {
      description
        "Node";
      list node-entry {
        key "node-name";
        description
          "Node name";
        container npus {
          description
            "NPU ID";
          list npu {
            key "npu-id";
            description
              "NPU ID";
            leaf npu-id {
              type uint32;
              description
                "NPU ID";
            }
            uses HCMGR-USE-CASE-DETAIL-DATA;
          }
        }
        leaf node-name {
          type xr:Node-id;
          description
            "Node name";
        }
      }
    }
  }

  container health-check {
    config false;
    description
      "Health check operational data space";
    container metric-info {
      description
        "Metric";
      container fpd {
        description
          "FPD metric";
        uses HCMGR-FPD-METRIC-DATA;
      }
      container redundancy {
        description
          "Redundancy metric";
        uses HCMGR-REDUNDANCY-METRIC-DATA;
      }
      container fabric-health {
        description
          "Fabric health metric";
        uses HCMGR-FABRIC-HEALTH-METRIC-DATA;
      }
      container platform {
        description
          "Platform metric";
        uses HCMGR-PLATFORM-METRIC-DATA;
      }
      container interface-counters {
        description
          "Interface counter metric";
        container interface-counters-details {
          description
            "Interface name";
          list interface-counters-detail {
            key "intf-name";
            description
              "Interface name";
            container interface-counters-detail-data {
              description
                "Interface counters metric detail";
              uses HCMGR-INTF-COUNTERS-METRIC-DETAIL-DATA;
            }
            leaf intf-name {
              type xr:Interface-name;
              description
                "Interface name";
            }
          }
        }
        container interface-counters-info {
          description
            "Interface counter metric";
          uses HCMGR-INTF-COUNTERS-METRIC-DATA;
        }
      }
      container asic-errors {
        description
          "ASIC errors metric";
        container asic-errors-details {
          description
            "Node name";
          list asic-errors-detail {
            key "node-name";
            description
              "Node name";
            container asic-errors-detail-data {
              description
                "ASIC errors metric detail";
              uses HCMGR-ASIC-ERRORS-METRIC-DETAIL-DATA;
            }
            leaf node-name {
              type xr:Cisco-ios-xr-string;
              description
                "Node name";
            }
          }
        }
        container asic-errors-info {
          description
            "ASIC errors metric";
          uses HCMGR-ASIC-ERRORS-METRIC-DATA;
        }
      }
      container free-memory {
        description
          "Free memory metric";
        uses HCMGR-FREE-MEM-METRIC-DATA;
      }
      container custom-metric {
        description
          "Custom metric oper data";
        container custom-metric-infos {
          description
            "Name";
          list custom-metric-info {
            key "metric-name";
            description
              "Metric name";
            container custom-metric-info-data {
              description
                "Custom metric oper data";
              uses HCMGR-CUSTOM-METRIC-DATA;
            }
            leaf metric-name {
              type xr:Cisco-ios-xr-string;
              description
                "Metric name";
            }
          }
        }
        container infos {
          description
            "A list of custom metrics and user defined
             information";
          list info {
            key "metric-name";
            description
              "Custom metric user defined information";
            leaf metric-name {
              type xr:Cisco-ios-xr-string;
              description
                "Metric name";
            }
            uses HCMGR-CUSTOM-METRIC-DATA;
          }
        }
      }
      container fabric-stats {
        description
          "ASIC errors metric";
        container fabric-stats-info {
          description
            "Fabric statistics metric";
          uses HCMGR-FABRIC-STATS-METRIC-DATA;
        }
        container fabric-stats-details {
          description
            "Plane ID";
          list fabric-stats-detail {
            key "plane-id";
            description
              "Plane ID";
            container fabric-stats-detail-data {
              description
                "Fabric statistics metric detail";
              uses HCMGR-FABRIC-STATS-METRIC-DETAIL-DATA;
            }
            leaf plane-id {
              type uint32;
              description
                "Plane ID";
            }
          }
        }
      }
      container filesystem {
        description
          "Filesystem metric";
        uses HCMGR-FILESYSTEM-METRIC-DATA;
      }
      container shared-memory {
        description
          "Shared memory metric";
        uses HCMGR-SHARED-MEM-METRIC-DATA;
      }
      container cpu {
        description
          "CPU metric";
        uses HCMGR-CPU-METRIC-DATA;
      }
    }
    container report-info {
      description
        "Report data";
      uses HCMGR-REPORT-DATA;
    }
    container use-case {
      description
        "Use case";
      container asic-reset {
        description
          "ASIC reset use case";
        uses NODE-TABLE;
        uses SUMMARY;
      }
      container packet-drop {
        description
          "Packet drop use case";
        uses NODE-TABLE;
        uses SUMMARY;
      }
    }
    container status {
      description
        "Health check status data";
      container metric {
        description
          "Holds specific metric information from list of
           different metrics";
        uses HCMGR-METRIC-DATA;
      }
      container status-use-cases {
        description
          "Enabled use cases information";
        list status-use-case {
          key "use-case";
          description
            "Specific use case information from list of
             different use cases";
          leaf use-case {
            type xr:Cisco-ios-xr-string;
            description
              "Use case";
          }
          uses HCMGR-STATUS-USECASE-DATA;
        }
      }
    }
    container status-info {
      description
        "Status";
      uses HCMGR-STATUS-DATA;
    }
    container report {
      description
        "Report data";
      container metrics {
        description
          "Holds information associated with different
           metrics";
        list metric {
          key "metric";
          description
            "Holds specific metric information from list of
             different metrics";
          leaf metric {
            type xr:Cisco-ios-xr-string;
            description
              "Metric name";
          }
          uses HCMGR-METRIC-DATA-REPORT;
        }
      }
      container use-cases {
        description
          "Enabled use cases information";
        list use-case {
          key "use-case";
          description
            "Specific use case information from list of
             different use cases";
          leaf use-case {
            type xr:Cisco-ios-xr-string;
            description
              "Use case";
          }
          uses HCMGR-USE-CASE-REPORT-DATA;
        }
      }
    }
  }
}
