module Cisco-IOS-XR-um-pce-cfg {
  namespace "http://cisco.com/ns/yang/Cisco-IOS-XR-um-pce-cfg";
  prefix um-pce-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pce package configuration.
     
     This YANG module augments the
     modules with configuration data.
     
     Copyright (c) 2021-2022 by Cisco Systems, Inc.
     All rights reserved.";

  revision 2022-03-25 {
    description
      "Model Deprecated";
    semver:module-version "2.1.0";
  }
  revision 2021-07-12 {
    description
      "Added must statement under the list index
       2021-07-01
           Added leaf ip-address under all the containers pcc";
    semver:module-version "2.0.0";
  }
  revision 2021-05-10 {
    description
      "Initial release";
    semver:module-version "1.0.0";
  }

  container pce {
    presence "Indicates a pce node is configured.";
    status deprecated;
    description
      "Path Computation Server configurations";
    container constraints {
      description
        "Assign constraints for the computed paths";
      container bounds {
        description
          "Assign bounds for the path";
        container cumulative {
          description
            "Cumulative metric bound";
          container type {
            description
              "The metric type for the bound";
            leaf latency {
              type uint32 {
                range "1..4294967295" {
                  description
                    "Bound metric value in microseconds";
                }
              }
              description
                "Bound metric type latency";
            }
          }
        }
      }
    }
    container address {
      description
        "Address of PCE server";
      leaf ipv4 {
        type inet:ipv4-address-no-zone;
        description
          "IPv4 address";
      }
      leaf ipv6 {
        type inet:ipv6-address-no-zone;
        description
          "IPv6 address";
      }
    }
    container state-sync {
      description
        "Forward received reports to other PCE";
      container ipv4s {
        description
          "IPv4 address";
        list ipv4 {
          key "address";
          description
            "IPv4 address";
          leaf address {
            type inet:ipv4-address-no-zone;
            description
              "IPv4 address";
          }
        }
      }
      container ipv6s {
        description
          "IPv6 address";
        list ipv6 {
          key "address";
          description
            "IPv6 address";
          leaf address {
            type inet:ipv6-address-no-zone;
            description
              "IPv6 address";
          }
        }
      }
    }
    container tcp-buffer {
      description
        "TCP buffer configuration";
      leaf size {
        type uint32 {
          range "204800..1024000" {
            description
              "Maximum size of event-buffer, default is 256000";
          }
        }
        description
          "Size of buffer in bytes";
      }
    }
    container password {
      description
        "Configure global password for MD5 authentication";
      leaf encrypted {
        type xr:Cisco-ios-xr-string {
          length "1..1024" {
            description
              "Encrypted password string";
          }
        }
        description
          "Specify unencrypted password";
      }
    }
    container tcp-ao {
      presence "Indicates a tcp-ao node is configured.";
      description
        "Configure global AO keychain based authentication";
      leaf key-chain-name {
        type xr:Cisco-ios-xr-string {
          length "1..32" {
            description
              "Name of the key chain - maximum 32 characters";
          }
        }
        mandatory true;
        description
          "Configure global AO keychain based authentication";
      }
      container include-tcp-options {
        presence "Indicates a include-tcp-options node is configured.";
        description
          "Include other TCP options in the header";
      }
      container accept-ao-mismatch-connection {
        presence "Indicates a accept-ao-mismatch-connection node is configured.";
        description
          "Accept new connection even if Authentication Option mismatched";
      }
    }
    container trace {
      description
        "Configure PCE trace options";
      container buffer {
        description
          "PCE Trace buffers";
        container all {
          description
            "All buffers control";
          leaf trace-count {
            type uint32 {
              range "0..1000000" {
                description
                  "count";
              }
            }
            description
              "Trace count";
          }
        }
        container common {
          description
            "Common buffer control";
          container gen-error {
            description
              "Common generic error buffer";
            leaf trace-count {
              type uint32 {
                range "0..1000000" {
                  description
                    "count";
                }
              }
              description
                "Trace count";
            }
          }
          container lslib {
            description
              "lslib trace buffer";
            leaf trace-count {
              type uint32 {
                range "0..1000000" {
                  description
                    "count";
                }
              }
              description
                "Trace count";
            }
          }
          container cspf {
            description
              "cspf trace buffer";
            leaf trace-count {
              type uint32 {
                range "0..1000000" {
                  description
                    "count";
                }
              }
              description
                "Trace count";
            }
          }
          container topo {
            description
              "topo trace buffer";
            leaf trace-count {
              type uint32 {
                range "0..1000000" {
                  description
                    "count";
                }
              }
              description
                "Trace count";
            }
          }
          container mempool {
            description
              "mempool trace buffer";
            leaf trace-count {
              type uint32 {
                range "0..1000000" {
                  description
                    "count";
                }
              }
              description
                "Trace count";
            }
          }
          container pcep {
            description
              "pcep trace buffer";
            leaf trace-count {
              type uint32 {
                range "0..1000000" {
                  description
                    "count";
                }
              }
              description
                "Trace count";
            }
          }
          container timing {
            description
              "timing trace buffer";
            leaf trace-count {
              type uint32 {
                range "0..1000000" {
                  description
                    "count";
                }
              }
              description
                "Trace count";
            }
          }
        }
        container error {
          description
            "Error buffer control";
          leaf trace-count {
            type uint32 {
              range "0..1000000" {
                description
                  "count";
              }
            }
            description
              "Trace count";
          }
        }
        container gen-error {
          description
            "Generic error buffer control";
          leaf trace-count {
            type uint32 {
              range "0..1000000" {
                description
                  "count";
              }
            }
            description
              "Trace count";
          }
        }
        container cfg {
          description
            "Configuration buffer control";
          leaf trace-count {
            type uint32 {
              range "0..1000000" {
                description
                  "count";
              }
            }
            description
              "Trace count";
          }
        }
        container rest {
          description
            "Rest buffer control";
          leaf trace-count {
            type uint32 {
              range "0..1000000" {
                description
                  "count";
              }
            }
            description
              "Trace count";
          }
        }
        container treesid {
          description
            "Treesid buffer control";
          leaf trace-count {
            type uint32 {
              range "0..1000000" {
                description
                  "count";
              }
            }
            description
              "Trace count";
          }
        }
        container pcep-lsp {
          description
            "PCEP lsp buffer control";
          leaf trace-count {
            type uint32 {
              range "0..1000000" {
                description
                  "count";
              }
            }
            description
              "Trace count";
          }
        }
        container pcep-peer {
          description
            "PCEP peer buffer control";
          leaf trace-count {
            type uint32 {
              range "0..1000000" {
                description
                  "count";
              }
            }
            description
              "Trace count";
          }
        }
        container policy {
          description
            "Policy buffer control";
          leaf trace-count {
            type uint32 {
              range "0..1000000" {
                description
                  "count";
              }
            }
            description
              "Trace count";
          }
        }
        container cmn-codeflow {
          description
            "code flow buffer control";
          leaf trace-count {
            type uint32 {
              range "0..1000000" {
                description
                  "count";
              }
            }
            description
              "Trace count";
          }
        }
      }
    }
    container disjoint-path {
      presence "Indicates a disjoint-path node is configured.";
      description
        "Disjoint Path Configuration";
      container group-ids {
        description
          "Group ID";
        list group-id {
          key "group-id";
          description
            "Group ID";
          leaf group-id {
            type uint32 {
              range "1..65535" {
                description
                  "Group ID";
              }
            }
            description
              "Group ID";
          }
          container type {
            description
              "Disjointness type";
            container link {
              description
                "Link Disjointness";
              container enable {
                presence "Indicates an enable node is configured.";
                description
                  "Enable Link Disjointness";
              }
              container sub-ids {
                description
                  "Sub ID";
                list sub-id {
                  key "sub-id";
                  description
                    "Sub ID";
                  leaf sub-id {
                    type uint32 {
                      range "1..65535" {
                        description
                          "Sub ID";
                      }
                    }
                    description
                      "Sub ID";
                  }
                  container lsp {
                    description
                      "Configure lsps in the association";
                    container one {
                      description
                        "Configure first lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                    container two {
                      description
                        "Configure second lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                  }
                  container strict {
                    presence "Indicates a strict node is configured.";
                    description
                      "Disable Fallback";
                  }
                }
              }
              container lsp {
                description
                  "Configure lsps in the association";
                container one {
                  description
                    "Configure first lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
                container two {
                  description
                    "Configure second lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
              }
              container strict {
                presence "Indicates a strict node is configured.";
                description
                  "Disable Fallback";
              }
            }
            container node {
              description
                "Node Disjointness";
              container enable {
                presence "Indicates an enable node is configured.";
                description
                  "Enable Node Disjointness";
              }
              container sub-ids {
                description
                  "Sub ID";
                list sub-id {
                  key "sub-id";
                  description
                    "Sub ID";
                  leaf sub-id {
                    type uint32 {
                      range "1..65535" {
                        description
                          "Sub ID";
                      }
                    }
                    description
                      "Sub ID";
                  }
                  container lsp {
                    description
                      "Configure lsps in the association";
                    container one {
                      description
                        "Configure first lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                    container two {
                      description
                        "Configure second lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                  }
                  container strict {
                    presence "Indicates a strict node is configured.";
                    description
                      "Disable Fallback";
                  }
                }
              }
              container lsp {
                description
                  "Configure lsps in the association";
                container one {
                  description
                    "Configure first lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
                container two {
                  description
                    "Configure second lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
              }
              container strict {
                presence "Indicates a strict node is configured.";
                description
                  "Disable Fallback";
              }
            }
            container srlg {
              description
                "SRLG Disjointness";
              container enable {
                presence "Indicates an enable node is configured.";
                description
                  "Enable SRLG Disjointness";
              }
              container sub-ids {
                description
                  "Sub ID";
                list sub-id {
                  key "sub-id";
                  description
                    "Sub ID";
                  leaf sub-id {
                    type uint32 {
                      range "1..65535" {
                        description
                          "Sub ID";
                      }
                    }
                    description
                      "Sub ID";
                  }
                  container lsp {
                    description
                      "Configure lsps in the association";
                    container one {
                      description
                        "Configure first lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                    container two {
                      description
                        "Configure second lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                  }
                  container strict {
                    presence "Indicates a strict node is configured.";
                    description
                      "Disable Fallback";
                  }
                }
              }
              container lsp {
                description
                  "Configure lsps in the association";
                container one {
                  description
                    "Configure first lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
                container two {
                  description
                    "Configure second lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
              }
              container strict {
                presence "Indicates a strict node is configured.";
                description
                  "Disable Fallback";
              }
            }
            container srlg-node {
              description
                "SRLG Node Disjointness";
              container enable {
                presence "Indicates an enable node is configured.";
                description
                  "Enable SRLG Node Disjointness";
              }
              container sub-ids {
                description
                  "Sub ID";
                list sub-id {
                  key "sub-id";
                  description
                    "Sub ID";
                  leaf sub-id {
                    type uint32 {
                      range "1..65535" {
                        description
                          "Sub ID";
                      }
                    }
                    description
                      "Sub ID";
                  }
                  container lsp {
                    description
                      "Configure lsps in the association";
                    container one {
                      description
                        "Configure first lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                    container two {
                      description
                        "Configure second lsp in the association";
                      container pcc {
                        presence "Indicates a pcc node is configured.";
                        description
                          "PCC address";
                        leaf address-type {
                          type enumeration {
                            enum "ipv4" {
                              value 1;
                              description
                                "IPV4 address";
                            }
                            enum "ipv6" {
                              value 2;
                              description
                                "IPV6 address";
                            }
                          }
                          mandatory true;
                          description
                            "Address type";
                        }
                        leaf ip-address {
                          type inet:ip-address-no-zone;
                          mandatory true;
                          description
                            "IP address of PCC";
                        }
                        leaf lsp-name {
                          type xr:Cisco-ios-xr-string {
                            length "1..800" {
                              description
                                "Identifying name for LSP";
                            }
                          }
                          mandatory true;
                          description
                            "Name of label switched path";
                        }
                        container shortest-path {
                          presence "Indicates a shortest-path node is configured.";
                          description
                            "Set LSP to follow shortest-path";
                        }
                        leaf exclude-srlg {
                          type uint32 {
                            range "1..4294967295" {
                              description
                                "SRLG value to be excluded from LSP";
                            }
                          }
                          description
                            "Exclude SRLG";
                        }
                      }
                    }
                  }
                  container strict {
                    presence "Indicates a strict node is configured.";
                    description
                      "Disable Fallback";
                  }
                }
              }
              container lsp {
                description
                  "Configure lsps in the association";
                container one {
                  description
                    "Configure first lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
                container two {
                  description
                    "Configure second lsp in the association";
                  container pcc {
                    presence "Indicates a pcc node is configured.";
                    description
                      "PCC address";
                    leaf address-type {
                      type enumeration {
                        enum "ipv4" {
                          value 1;
                          description
                            "IPV4 address";
                        }
                        enum "ipv6" {
                          value 2;
                          description
                            "IPV6 address";
                        }
                      }
                      mandatory true;
                      description
                        "Address type";
                    }
                    leaf ip-address {
                      type inet:ip-address-no-zone;
                      mandatory true;
                      description
                        "IP address of PCC";
                    }
                    leaf lsp-name {
                      type xr:Cisco-ios-xr-string {
                        length "1..800" {
                          description
                            "Identifying name for LSP";
                        }
                      }
                      mandatory true;
                      description
                        "Name of label switched path";
                    }
                    container shortest-path {
                      presence "Indicates a shortest-path node is configured.";
                      description
                        "Set LSP to follow shortest-path";
                    }
                    leaf exclude-srlg {
                      type uint32 {
                        range "1..4294967295" {
                          description
                            "SRLG value to be excluded from LSP";
                        }
                      }
                      description
                        "Exclude SRLG";
                    }
                  }
                }
              }
              container strict {
                presence "Indicates a strict node is configured.";
                description
                  "Disable Fallback";
              }
            }
          }
        }
      }
      leaf maximum-attempts {
        type uint32 {
          range "1..100000" {
            description
              "Maximum number of attempts";
          }
        }
        description
          "Maximum number of attempts during disjoint path computation (default: 1000)";
      }
    }
    container peer {
      description
        "Peer Configuration";
      container ipv4s {
        description
          "IPv4 address family";
        list ipv4 {
          key "address";
          description
            "IPv4 address family";
          leaf address {
            type inet:ipv4-address-no-zone;
            description
              "IPv4 address family";
          }
          container password {
            description
              "Configure peer password for MD5 authentication";
            leaf encrypted {
              type xr:Cisco-ios-xr-string {
                length "1..1024" {
                  description
                    "Encrypted password string";
                }
              }
              description
                "Specify unencrypted password";
            }
          }
          container tcp-ao {
            presence "Indicates a tcp-ao node is configured.";
            description
              "Configure AO keychain based authentication";
            leaf key-chain-name {
              type xr:Cisco-ios-xr-string {
                length "1..32" {
                  description
                    "Name of the key chain - maximum 32 characters";
                }
              }
              mandatory true;
              description
                "Configure AO keychain based authentication";
            }
            container include-tcp-options {
              presence "Indicates a include-tcp-options node is configured.";
              description
                "Include other TCP options in the header";
            }
            container accept-ao-mismatch-connection {
              presence "Indicates a accept-ao-mismatch-connection node is configured.";
              description
                "Accept new connection even if Authentication Option mismatched";
            }
          }
        }
      }
      container ipv6s {
        description
          "IPv6 address family";
        list ipv6 {
          key "address";
          description
            "IPv6 address family";
          leaf address {
            type inet:ipv6-address-no-zone;
            description
              "IPv6 address family";
          }
          container password {
            description
              "Configure peer password for MD5 authentication";
            leaf encrypted {
              type xr:Cisco-ios-xr-string {
                length "1..1024" {
                  description
                    "Encrypted password string";
                }
              }
              description
                "Specify unencrypted password";
            }
          }
          container tcp-ao {
            presence "Indicates a tcp-ao node is configured.";
            description
              "Configure AO keychain based authentication";
            leaf key-chain-name {
              type xr:Cisco-ios-xr-string {
                length "1..32" {
                  description
                    "Name of the key chain - maximum 32 characters";
                }
              }
              mandatory true;
              description
                "Configure AO keychain based authentication";
            }
            container include-tcp-options {
              presence "Indicates a include-tcp-options node is configured.";
              description
                "Include other TCP options in the header";
            }
            container accept-ao-mismatch-connection {
              presence "Indicates a accept-ao-mismatch-connection node is configured.";
              description
                "Accept new connection even if Authentication Option mismatched";
            }
          }
        }
      }
    }
    container netconf {
      presence "Indicates a netconf node is configured.";
      description
        "NETCONF Configuration";
      container ssh {
        description
          "SSH configuration used by Netconf";
        leaf user {
          type string {
            length "1..800" {
              description
                "SSH username";
            }
          }
          description
            "Specify SSH username that will be used to log on to routers";
        }
        container password {
          description
            "Configure password for Netconf SSH";
          leaf encrypted {
            type xr:Cisco-ios-xr-string {
              length "1..1024" {
                description
                  "Encrypted password string";
              }
            }
            description
              "Specify unencrypted password";
          }
        }
      }
    }
    container api {
      presence "Indicates a api node is configured.";
      description
        "Northbound API Configuration";
      container authentication {
        description
          "Configure desired REST authentication";
        container digest {
          presence "Indicates a digest node is configured.";
          description
            "Use HTTP Digest authentication (MD5)";
        }
      }
      container sibling {
        description
          "Sibling PCE";
        leaf ipv4 {
          type inet:ipv4-address-no-zone;
          description
            "IPv4 address of the PCE sibling";
        }
      }
      leaf vrf {
        type xr:Cisco-ios-xr-string {
          length "1..33" {
            description
              "VRF name";
          }
        }
        description
          "VRF for northbound API and PCE sibling connections.";
      }
      container users {
        description
          "Northbound API username";
        list user {
          key "user-name";
          description
            "Northbound API username";
          leaf user-name {
            type string {
              length "1..800" {
                description
                  "Username for the northbound API";
              }
            }
            description
              "Northbound API username";
          }
          container password {
            description
              "Configure password for API username";
            leaf encrypted {
              type xr:Cisco-ios-xr-string {
                length "1..1024" {
                  description
                    "Encrypted password string";
                }
              }
              description
                "Specify unencrypted password";
            }
          }
        }
      }
      container ipv4 {
        description
          "IPv4 specific configuration";
        leaf address {
          type inet:ipv4-address-no-zone;
          description
            "NB-API server IPv4 address";
        }
      }
      container ipv6 {
        description
          "IPv6 specific configuration";
        leaf address {
          type inet:ipv6-address-no-zone;
          description
            "NB-API server IPv6 address";
        }
      }
    }
    container timers {
      description
        "PCE timers configuration";
      leaf reoptimization {
        type uint32 {
          range "600..86400" {
            description
              "Timer value in seconds; default is 1800";
          }
        }
        description
          "Topology reoptimization interval";
      }
      leaf keepalive {
        type uint32 {
          range "0..255" {
            description
              "Time value in seconds. Use zero to disable; default is 30";
          }
        }
        description
          "Keepalive interval";
      }
      leaf minimum-peer-keepalive {
        type uint32 {
          range "0..255" {
            description
              "Time value in seconds. Use zero to disable; default is 20";
          }
        }
        description
          "Minimum acceptable peer proposed keepalive interval";
      }
      leaf peer-zombie {
        type uint32 {
          range "0..3600" {
            description
              "Timer value in seconds 0-3600. Use 0 to disable. Default is 60.";
          }
        }
        description
          "Keep LSP peer in zombie state after disconnect";
      }
      leaf init-verify-restart {
        type uint32 {
          range "10..10000" {
            description
              "Time value in seconds. Default is 40";
          }
        }
        description
          "Timer to wait for topology convergence after topology starts populating for restart case";
      }
      leaf init-verify-switchover {
        type uint32 {
          range "10..10000" {
            description
              "Time value in seconds. Default is 60";
          }
        }
        description
          "Timer to wait for topology convergence after topology starts populating for switchover case";
      }
      leaf init-verify-startup {
        type uint32 {
          range "10..10000" {
            description
              "Time value in seconds. Default is 120";
          }
        }
        description
          "Timer to wait for topology convergence after topology starts populating for startup case";
      }
    }
    container backoff {
      description
        "PCE backoff configuration";
      leaf ratio {
        type uint32 {
          range "0..255" {
            description
              "Backoff common ratio; default is 2";
          }
        }
        description
          "Backoff common ratio";
      }
      leaf difference {
        type uint32 {
          range "0..255" {
            description
              "Backoff common difference; default is 2";
          }
        }
        description
          "Backoff common difference";
      }
      leaf threshold {
        type uint32 {
          range "0..3600" {
            description
              "Threshold value in seconds. Use zero to disable; default is 0";
          }
        }
        description
          "Backoff threshold";
      }
    }
    container logging {
      description
        "PCE logging configuration";
      container no-path {
        presence "Indicates a no-path node is configured.";
        description
          "logging no-path messages";
      }
      container fallback {
        presence "Indicates a fallback node is configured.";
        description
          "logging fallback messages";
      }
      container pcep {
        description
          "Path Computation Element Protocol (PCEP) logging";
        container pcerr-received {
          presence "Indicates a pcerr-received node is configured.";
          description
            "logging of received PCErr messages";
        }
        container api {
          description
            "API logging configuration";
          container send-queue-congestion {
            description
              "logging of peer send queue related messages";
            container disable {
              presence "Indicates a disable node is configured.";
              description
                "disable messages";
            }
          }
        }
        container disjointness-status {
          presence "Indicates a disjointness-status node is configured.";
          description
            "logging of disjointness status related messages";
        }
      }
    }
    container segment-routing {
      description
        "PCE segment-routing configuration";
      container strict-sid-only {
        presence "Indicates a strict-sid-only node is configured.";
        description
          "Use strict sids only";
      }
      container traffic-eng {
        presence "Indicates a traffic-eng node is configured.";
        description
          "Segment Routing Traffic Engineering";
        container affinity {
          description
            "Affinity configuration";
          container bit-map {
            description
              "Affinity attribute value to color mapping";
            container affinity-colors {
              description
                "Affinity color name";
              list affinity-color {
                key "affinity-color-name";
                description
                  "Affinity color name";
                leaf affinity-color-name {
                  type string {
                    length "1..32" {
                      description
                        "Affinity color name";
                    }
                  }
                  description
                    "Affinity color name";
                }
                leaf affinity-attribute-bit {
                  type uint32 {
                    range "0..255" {
                      description
                        "Affinity attribute bit position";
                    }
                  }
                  mandatory true;
                  description
                    "Affinity attribute bit position";
                }
              }
            }
          }
        }
        container segment-lists {
          description
            "Segment-list configuration";
          list segment-list {
            key "segment-list-name";
            description
              "Segment-list name";
            leaf segment-list-name {
              type xr:Cisco-ios-xr-string {
                length "1..128" {
                  description
                    "Identifying name for segment-list with max 128 characters";
                }
              }
              description
                "Segment-list name";
            }
            container indexes {
              description
                "Next entry index";
              list index {
                must "mpls/label or mpls/adjacency";
                key "index-number";
                description
                  "Next entry index";
                leaf index-number {
                  type uint32 {
                    range "1..65535" {
                      description
                        "Index number";
                    }
                  }
                  description
                    "Next entry index";
                }
                container mpls {
                  description
                    "MPLS configuration";
                  leaf label {
                    type uint32 {
                      range "0..1048575" {
                        description
                          "MPLS label value";
                      }
                    }
                    must "not(../adjacency)";
                    description
                      "MPLS label configuration";
                  }
                  leaf adjacency {
                    type inet:ip-address-no-zone;
                    must "not(../label)";
                    description
                      "Specify hop address";
                  }
                }
              }
            }
          }
        }
        container peer {
          description
            "PCEP peer to configure";
          container ipv4s {
            description
              "IPv4 address of the PCEP peer";
            list ipv4 {
              key "address";
              description
                "IPv4 address of the PCEP peer";
              leaf address {
                type inet:ipv4-address-no-zone;
                description
                  "IPv4 address of the PCEP peer";
              }
              container policies {
                description
                  "Name of SR-TE Policy";
                list policy {
                  key "policy-name";
                  description
                    "Name of SR-TE Policy";
                  leaf policy-name {
                    type xr:Cisco-ios-xr-string {
                      length "1..128" {
                        description
                          "Identifying name for policy with max 128 characters";
                      }
                    }
                    description
                      "Name of SR-TE Policy";
                  }
                  container candidate-paths {
                    presence "Indicates a candidate-paths node is configured.";
                    description
                      "Candidate-paths configuration";
                    container append-sid {
                      description
                        "Append specified SID to the currently used path";
                      leaf mpls {
                        type uint32 {
                          range "1..1048575" {
                            description
                              "MPLS label";
                          }
                        }
                        description
                          "MPLS label";
                      }
                    }
                    container preferences {
                      description
                        "Policy path-option preference entry";
                      list preference {
                        key "preference-id";
                        description
                          "Policy path-option preference entry";
                        leaf preference-id {
                          type uint32 {
                            range "1..65535" {
                              description
                                "Path-option preference";
                            }
                          }
                          description
                            "Policy path-option preference entry";
                        }
                        container dynamic {
                          description
                            "Dynamically allocated path";
                          container mpls {
                            presence "Indicates a mpls node is configured.";
                            description
                              "MPLS path type";
                            container metric {
                              presence "Indicates a metric node is configured.";
                              description
                                "Path metric configuration";
                              container type {
                                description
                                  "Metric type configuration";
                                container te {
                                  must
                                    "not(../igp or ../hopcount
                                     or ../latency)";
                                  presence "Indicates a te node is configured.";
                                  description
                                    "TE metric type";
                                }
                                container igp {
                                  must
                                    "not(../te or ../hopcount
                                     or ../latency)";
                                  presence "Indicates a igp node is configured.";
                                  description
                                    "IGP metric type";
                                }
                                container hopcount {
                                  must
                                    "not(../te or ../igp
                                     or ../latency)";
                                  presence "Indicates a hopcount node is configured.";
                                  description
                                    "Hopcount metric type";
                                }
                                container latency {
                                  must
                                    "not(../te or ../igp
                                     or ../hopcount)";
                                  presence "Indicates a latency node is configured.";
                                  description
                                    "Latency metric type";
                                }
                              }
                              leaf sid-limit {
                                type uint32 {
                                  range "1..255" {
                                    description
                                      "SID limit value";
                                  }
                                }
                                description
                                  "SID limit";
                              }
                            }
                          }
                        }
                        container explicit {
                          description
                            "Preconfigured path";
                          container segment-list {
                            description
                              "Specify Segment-list";
                          }
                          container segment-list-names {
                            description
                              "Identifying name for Segment-list";
                            list segment-list-name {
                              key "segment-list-name";
                              description
                                "Identifying name for Segment-list";
                              leaf segment-list-name {
                                type string {
                                  length "1..128" {
                                    description
                                      "Identifying name for Segment-list";
                                  }
                                }
                                description
                                  "Identifying name for Segment-list";
                              }
                              container metric {
                                presence "Indicates a metric node is configured.";
                                description
                                  "Path metric configuration";
                                container type {
                                  description
                                    "Metric type configuration";
                                  container te {
                                    must
                                      "not(../igp or ../hopcount
                                       or ../latency)";
                                    presence "Indicates a te node is configured.";
                                    description
                                      "TE metric type";
                                  }
                                  container igp {
                                    must
                                      "not(../te or ../hopcount
                                       or ../latency)";
                                    presence "Indicates a igp node is configured.";
                                    description
                                      "IGP metric type";
                                  }
                                  container hopcount {
                                    must
                                      "not(../te or ../igp
                                       or ../latency)";
                                    presence "Indicates a hopcount node is configured.";
                                    description
                                      "Hopcount metric type";
                                  }
                                  container latency {
                                    must
                                      "not(../te or ../igp
                                       or ../hopcount)";
                                    presence "Indicates a latency node is configured.";
                                    description
                                      "Latency metric type";
                                  }
                                }
                                leaf sid-limit {
                                  type uint32 {
                                    range "1..255" {
                                      description
                                        "SID limit value";
                                    }
                                  }
                                  description
                                    "SID limit";
                                }
                              }
                            }
                          }
                        }
                        container constraints {
                          description
                            "Candidate path constraints";
                          container segments {
                            description
                              "Path segments constraints";
                            leaf sid-algorithm {
                              type uint32 {
                                range "128..255" {
                                  description
                                    "Prefix-SID algorithm";
                                }
                              }
                              description
                                "Prefix-SID algorithm";
                            }
                            container protection {
                              description
                                "Protection type";
                              container protected-preferred {
                                must
                                  "not(../protected-only or ../unprotected-only
                                   or ../unprotected-preferred)";
                                presence "Indicates a protected-preferred node is configured.";
                                description
                                  "Protected adj-SID preferred (default)";
                              }
                              container protected-only {
                                must
                                  "not(../protected-preferred or ../unprotected-only
                                   or ../unprotected-preferred)";
                                presence "Indicates a protected-only node is configured.";
                                description
                                  "Protected adj-SID only";
                              }
                              container unprotected-only {
                                must
                                  "not(../protected-preferred or ../protected-only
                                   or ../unprotected-preferred)";
                                presence "Indicates a unprotected-only node is configured.";
                                description
                                  "Unprotected adj-SID only";
                              }
                              container unprotected-preferred {
                                must
                                  "not(../protected-preferred or ../protected-only
                                   or ../unprotected-only)";
                                presence "Indicates a unprotected-preferred node is configured.";
                                description
                                  "Unprotected adj-SID preferred";
                              }
                            }
                          }
                        }
                      }
                    }
                    container affinity {
                      description
                        "Assign affinities to path";
                      container include-any {
                        description
                          "Affinity attributes - at least one must be included";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                      container include-all {
                        description
                          "Affinity attributes - all must be included";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                      container exclude {
                        description
                          "Affinity attributes to exclude";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                    }
                  }
                  leaf color {
                    type uint32 {
                      range "1..4294967295" {
                        description
                          "Color value";
                      }
                    }
                    description
                      "Specify color for policy";
                  }
                  container end-point {
                    description
                      "Policy endpoint";
                    leaf ipv4 {
                      type inet:ipv4-address-no-zone;
                      description
                        "IPv4 address";
                    }
                  }
                  container binding-sid {
                    description
                      "Bnding Segment Identifier";
                    leaf mpls {
                      type uint32 {
                        range "16..1048575" {
                          description
                            "MPLS label";
                        }
                      }
                      description
                        "MPLS label";
                    }
                  }
                  container shutdown {
                    presence "Indicates a shutdown node is configured.";
                    description
                      "Policy admin-shutdown";
                  }
                  leaf profile-id {
                    type uint32 {
                      range "1..65535" {
                        description
                          "Numeric profile identifer that the PCC will use";
                      }
                    }
                    description
                      "Policy configuration profile that the PCC should apply to this policy";
                  }
                  container path-selection {
                    description
                      "Options for path-selection";
                    container protected {
                      must "not(../unprotected)";
                      presence "Indicates a protected node is configured.";
                      description
                        "Use local protected if possible";
                    }
                    container unprotected {
                      must "not(../protected)";
                      presence "Indicates a unprotected node is configured.";
                      description
                        "Force use of unprotected adjacency SIDs";
                    }
                  }
                }
              }
            }
          }
        }
        container cspf {
          description
            "Path computation configuration";
          container anycast-sid-inclusion {
            presence "Indicates a anycast-sid-inclusion node is configured.";
            description
              "Enable Anycast SID Inclusion for all policies";
          }
          container sr-native {
            presence "Indicates a sr-native node is configured.";
            description
              "Enable SR native algorithm";
            container force {
              presence "Indicates a force node is configured.";
              description
                "Must use this algorithm for all path computations";
            }
          }
        }
        container p2mp {
          description
            "P2MP configuration";
          container endpoint-sets {
            description
              "Endpoint-set configuration";
            list endpoint-set {
              key "endpoint-set-name";
              description
                "Endpoint-set configuration";
              leaf endpoint-set-name {
                type xr:Cisco-ios-xr-string {
                  length "1..128" {
                    description
                      "Identifying name for endpoint-set with max 128 characters";
                  }
                }
                description
                  "Endpoint-set configuration";
              }
              container ipv4s {
                description
                  "Specify the address AFI";
                list ipv4 {
                  key "address";
                  description
                    "Specify the address AFI";
                  leaf address {
                    type inet:ipv4-address-no-zone;
                    description
                      "Specify the address AFI";
                  }
                }
              }
            }
          }
          container policies {
            description
              "Policy configuration";
            list policy {
              key "policy-name";
              description
                "Policy configuration";
              leaf policy-name {
                type xr:Cisco-ios-xr-string {
                  length "1..128" {
                    description
                      "Identifying name for policy with max 128 characters";
                  }
                }
                description
                  "Policy configuration";
              }
              container candidate-paths {
                description
                  "Candidate-paths configuration";
                container constraints {
                  description
                    "Candidate path constraints";
                  container affinity {
                    description
                      "Assign affinities to path";
                    container include-any {
                      description
                        "Affinity attributes - at least one must be included";
                      container affinity-colors {
                        description
                          "Affinity color name";
                        list affinity-color {
                          key "affinity-color-name";
                          description
                            "Affinity color name";
                          leaf affinity-color-name {
                            type string {
                              length "1..32" {
                                description
                                  "Affinity color name";
                              }
                            }
                            description
                              "Affinity color name";
                          }
                        }
                      }
                    }
                    container include-all {
                      description
                        "Affinity attributes - all must be included";
                      container affinity-colors {
                        description
                          "Affinity color name";
                        list affinity-color {
                          key "affinity-color-name";
                          description
                            "Affinity color name";
                          leaf affinity-color-name {
                            type string {
                              length "1..32" {
                                description
                                  "Affinity color name";
                              }
                            }
                            description
                              "Affinity color name";
                          }
                        }
                      }
                    }
                    container exclude {
                      description
                        "Affinity attributes to exclude";
                      container affinity-colors {
                        description
                          "Affinity color name";
                        list affinity-color {
                          key "affinity-color-name";
                          description
                            "Affinity color name";
                          leaf affinity-color-name {
                            type string {
                              length "1..32" {
                                description
                                  "Affinity color name";
                              }
                            }
                            description
                              "Affinity color name";
                          }
                        }
                      }
                    }
                  }
                }
                container preferences {
                  description
                    "Policy path preference entry";
                  list preference {
                    key "preference-id";
                    description
                      "Policy path preference entry";
                    leaf preference-id {
                      type uint32 {
                        range "100" {
                          description
                            "Path preference";
                        }
                      }
                      description
                        "Policy path preference entry";
                    }
                    container dynamic {
                      presence "Indicates a dynamic node is configured.";
                      description
                        "Dynamically computed path";
                      container metric {
                        description
                          "Path metric configuration";
                        container type {
                          description
                            "Metric type configuration";
                          container te {
                            must
                              "not(../igp or ../latency
                               or ../hopcount)";
                            presence "Indicates a te node is configured.";
                            description
                              "TE metric type";
                          }
                          container igp {
                            must
                              "not(../te or ../latency
                               or ../hopcount)";
                            presence "Indicates a igp node is configured.";
                            description
                              "IGP metric type";
                          }
                          container latency {
                            must
                              "not(../te or ../igp
                               or ../hopcount)";
                            presence "Indicates a latency node is configured.";
                            description
                              "Latency metric type";
                          }
                          container hopcount {
                            must
                              "not(../te or ../igp
                               or ../latency)";
                            presence "Indicates a hopcount node is configured.";
                            description
                              "Use the least number of hops for path computation";
                          }
                        }
                      }
                    }
                  }
                }
              }
              leaf color {
                type uint32 {
                  range "1..4294967295" {
                    description
                      "Color value";
                  }
                }
                description
                  "Specify color for policy";
              }
              leaf endpoint-set {
                type xr:Cisco-ios-xr-string {
                  length "1..128" {
                    description
                      "Identifying name of the endpoint-set with max 128 characters";
                  }
                }
                description
                  "Policy endpoint-set";
              }
              container source {
                description
                  "Specify source IP address";
                leaf ipv4 {
                  type inet:ipv4-address-no-zone;
                  description
                    "IPv4 address";
                }
              }
              container shutdown {
                presence "Indicates a shutdown node is configured.";
                description
                  "Policy admin-shutdown";
              }
              container fast-reroute {
                description
                  "Enable Fast Re-route protection for this tree";
                container lfa {
                  presence "Indicates a lfa node is configured.";
                  description
                    "LFA Fast Re-route";
                }
              }
              container treesid {
                description
                  "Specify the TreeSID";
                leaf mpls {
                  type uint32 {
                    range "16..1048575" {
                      description
                        "Label value";
                    }
                  }
                  description
                    "MPLS label";
                }
              }
            }
          }
          container timers {
            description
              "Timers configuration";
            leaf reoptimization {
              type uint32 {
                range "60..3600" {
                  description
                    "Timer value in seconds; default is 600";
                }
              }
              description
                "How often to reoptimize all P2MP paths.";
            }
            leaf cleanup {
              type uint32 {
                range "1..86400" {
                  description
                    "Timer value in seconds; default is 60";
                }
              }
              description
                "Delay before node is excluded from P2MP path computation after PCEP connection with it goes away";
            }
          }
          container label-range {
            description
              "Label range for dynamic p2mp SR policies";
            leaf min {
              type uint32 {
                range "16..1048575" {
                  description
                    "Lower bound of the label range";
                }
              }
              must "../max";
              description
                "Minimum value of label range";
            }
            leaf max {
              type uint32 {
                range "16..1048575" {
                  description
                    "Upper bound of the label range";
                }
              }
              must "../min";
              description
                "Maximum value of label range";
            }
          }
          container multipath-disable {
            presence "Indicates a multipath-disable node is configured.";
            description
              "Disable load balancing of SR P2MP across ECMP paths";
          }
          container fast-reroute {
            description
              "Enable Fast Re-route protection for all trees";
            container lfa {
              presence "Indicates a lfa node is configured.";
              description
                "LFA Fast Re-route";
            }
          }
          container frr-node-set {
            description
              "Node set needing Fast Re-route Protection";
            container from {
              presence "Indicates a from node is configured.";
              description
                "Nodes from which adjacencies are to be protected";
              container ipv4s {
                description
                  "Specify the address AFI";
                list ipv4 {
                  key "address";
                  description
                    "Specify the address AFI";
                  leaf address {
                    type inet:ipv4-address-no-zone;
                    description
                      "Specify the address AFI";
                  }
                }
              }
            }
            container to {
              presence "Indicates a to node is configured.";
              description
                "Nodes to which adjacencies are to be protected";
              container ipv4s {
                description
                  "Specify the address AFI";
                list ipv4 {
                  key "address";
                  description
                    "Specify the address AFI";
                  leaf address {
                    type inet:ipv4-address-no-zone;
                    description
                      "Specify the address AFI";
                  }
                }
              }
            }
          }
        }
      }
    }
    container peer-filter {
      description
        "Configure PCE peer filtering";
      container ipv4 {
        description
          "IPv4 peer filtering";
        leaf access-list {
          type xr:Cisco-ios-xr-string {
            length "1..800" {
              description
                "Access-list name";
            }
          }
          description
            "Access-list for IPv4 peer filtering";
        }
      }
    }
    container hierarchical {
      presence "Indicates a hierarchical node is configured.";
      description
        "Configure hierarchical policy computation";
      container underlay {
        presence "Indicates a underlay node is configured.";
        description
          "Configure underlay tunnels";
        container enable-all {
          presence "Indicates a enable-all node is configured.";
          description
            "Use all available tunnels as underlay";
        }
      }
    }
  }
}
