module Cisco-IOS-XR-crypto-cepki-new-oper {
  namespace "http://cisco.com/ns/yang/Cisco-IOS-XR-crypto-cepki-new-oper";
  prefix crypto-cepki-new-oper;

  import Cisco-IOS-XR-types {
    prefix xr;
  }
  import cisco-semver {
    prefix semver;
  }
  include Cisco-IOS-XR-crypto-cepki-new-oper-sub1 {
    revision-date 2022-05-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-cepki-new package operational data.
     
     This module contains definitions
     for the following management objects:
       crypto-cepki: Public Key Infrastructure Related Information
     
     Copyright (c) 2013-2022 by Cisco Systems, Inc.
     All rights reserved.";

  revision 2022-05-04 {
    description
      "oper support added for mypub key DSA and RSA.";
    semver:module-version "1.0.0";
  }
  revision 2019-04-05 {
    description
      "Establish semantic version baseline.";
  }
  revision 2015-11-09 {
    description
      "IOS XR 6.0 revision.";
  }

  container crypto-cepki {
    config false;
    description
      "Public Key Infrastructure Related Information";
    container mypubkey {
      description
        "Public Key Infrastructure Related Information";
      container rsa-keys {
        description
          "RSA Keys";
        list rsa-key {
          key "rsa-key-name";
          description
            "RSA Key Related Information";
          leaf rsa-key-name {
            type xr:Cisco-ios-xr-string;
            description
              "RSA key name";
          }
          uses CEPKI-MYPUBKEY-RSA;
        }
      }
      container dsa-keys {
        description
          "DSA Keys";
        list dsa-key {
          key "dsa-key-name";
          description
            "DSA Key Related Information";
          leaf dsa-key-name {
            type xr:Cisco-ios-xr-string;
            description
              "DSA key name";
          }
          uses CEPKI-MYPUBKEY-DSA;
        }
      }
    }
  }
}
