module Cisco-IOS-XR-ha-eem-cfg {
  namespace "http://cisco.com/ns/yang/Cisco-IOS-XR-ha-eem-cfg";
  prefix ha-eem-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ha-eem package configuration.
     
     This module contains definitions
     for the following management objects:
       event-manager: Event manager configuration
     
     Copyright (c) 2013-2019 by Cisco Systems, Inc.
     All rights reserved.";

  revision 2019-04-05 {
    description
      "Establish semantic version baseline.";
    semver:module-version "1.0.0";
  }
  revision 2015-07-30 {
    description
      "Descriptions updated.";
  }
  revision 2015-01-07 {
    description
      "IOS XR 5.3.1 revision.";
  }

  typedef Event-manager-persist-time {
    type uint32 {
      range "0..4294967295";
    }
    description
      "Event manager persist time";
  }

  typedef Event-manager-checksum {
    type enumeration {
      enum "sha-1" {
        value 1;
        description
          "Use SHA-1 checksum";
      }
      enum "md5" {
        value 2;
        description
          "Use MD5 checksum";
      }
    }
    description
      "Event manager checksum";
  }

  typedef Event-manager-policy-sec {
    type enumeration {
      enum "rsa-2048" {
        value 2;
        description
          "Cisco Signature";
      }
      enum "trust" {
        value 3;
        description
          "Trust Signature";
      }
    }
    description
      "Event manager policy sec";
  }

  typedef Event-manager-policy-mode {
    type enumeration {
      enum "cisco" {
        value 1;
        description
          "Cisco Signature";
      }
      enum "trust" {
        value 2;
        description
          "Trust Signature";
      }
    }
    description
      "Event manager policy mode";
  }

  typedef Event-manager-policy {
    type enumeration {
      enum "system" {
        value 0;
        description
          "Event manager system policy";
      }
      enum "user" {
        value 1;
        description
          "Event manager user policy";
      }
    }
    description
      "Event manager policy";
  }

  container event-manager {
    description
      "Event manager configuration";
    container policies {
      description
        "Register an event manager policy";
      list policy {
        key "policy-name";
        description
          "Name of the policy file";
        leaf policy-name {
          type xr:Cisco-ios-xr-string;
          description
            "Name of the policy file";
        }
        leaf username {
          type string;
          mandatory true;
          description
            "A configured username";
        }
        leaf persist-time {
          type Event-manager-persist-time;
          units "second";
          mandatory true;
          description
            "Time of validity (in seconds) for cached AAA
             taskmap of username (default is 3600)";
        }
        leaf policy-type {
          type Event-manager-policy;
          description
            "Event manager type of this policy";
        }
        leaf checksum-type {
          type Event-manager-checksum;
          description
            "Specify Embedded Event Manager policy checksum";
        }
        leaf check-sum-value {
          type string;
          description
            "CheckSum Value";
        }
        leaf policy-security-mode {
          type Event-manager-policy-mode;
          description
            "Specify Embedded Event Manager policy security
             mode";
        }
        leaf policy-security-level {
          type Event-manager-policy-sec;
          description
            "Event Manager policy security Level";
        }
      }
    }
    container scheduler-script {
      description
        "scheduler classs type";
      container thread-classes {
        description
          "scheduler thread classs ";
        list thread-class {
          key "thread-class-name";
          description
            "scheduler classs type argument";
          leaf thread-class-name {
            type xr:Cisco-ios-xr-string;
            description
              "Name of the global variable";
          }
          leaf num-threads {
            type uint32 {
              range "1..5";
            }
            mandatory true;
            description
              "number of scheduler threads";
          }
        }
      }
    }
    container environments {
      description
        "Set an event manager global variable for event
         manager policies";
      list environment {
        key "environment-name";
        description
          "Name of the global variable";
        leaf environment-name {
          type xr:Cisco-ios-xr-string;
          description
            "Name of the global variable";
        }
        leaf environment-value {
          type string;
          mandatory true;
          description
            "Value of the global variable";
        }
      }
    }
    leaf refresh-time {
      type uint32 {
        range "10..4294967295";
      }
      units "second";
      default "1800";
      description
        "Set refresh time (in seconds) for policy
         username's AAA taskmap";
    }
    leaf schedule-suspend {
      type boolean;
      description
        "Enable suspend policy scheduling";
    }
    leaf directory-user-policy {
      type string;
      description
        "Set event manager user policy directory";
    }
    leaf directory-user-library {
      type string;
      description
        "Path of the user policy library directory";
    }
  }
}
