module Cisco-IOS-XR-segment-routing-srv6-datatypes {
  namespace "http://cisco.com/ns/yang/Cisco-IOS-XR-segment-routing-srv6-datatypes";
  prefix segment-routing-srv6-datatypes;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2022 by Cisco Systems, Inc.
     All rights reserved.";

  revision 2022-08-02 {
    description
      "Extended SRv6EncapsulationHopLimitOption to include Propagate-disable";
    semver:module-version "1.4.0";
  }
  revision 2022-03-08 {
    description
      "Static endpoint related changes";
    semver:module-version "1.3.0";
  }
  revision 2019-11-19 {
    description
      "Support config knob to specify locator behavior.";
    semver:module-version "1.2.0";
  }
  revision 2019-04-05 {
    description
      "Establish semantic version baseline.";
    semver:module-version "1.0.1";
  }
  revision 2015-11-09 {
    description
      "IOS XR 6.0 revision.";
  }

  typedef Srv6-differentiator {
    type string {
      length "1..46";
    }
    description
      "Srv6 differentiator";
  }

  typedef Srv6-locator-name {
    type xr:Cisco-ios-xr-string {
      length "1..58";
    }
    description
      "Srv6 locator name";
  }

  typedef Srv6sid-holdtime {
    type uint32 {
      range "0..60";
    }
    description
      "Srv6sid holdtime";
  }

  typedef Srv6-locator-len {
    type uint32 {
      range "32..112";
    }
    description
      "Srv6 locator len";
  }

  typedef Srv6-encapsulation-hop-limit-value {
    type uint32 {
      range "0..255";
    }
    description
      "Srv6 encapsulation hop limit value";
  }

  typedef Srv6-static-sid-behavior {
    type enumeration {
      enum "end-x-psp" {
        value 6;
        description
          "end x psp";
      }
      enum "end-x-psp-usd" {
        value 33;
        description
          "end x psp usd";
      }
      enum "ua-psp" {
        value 53;
        description
          "ua psp";
      }
      enum "ua-psp-usd" {
        value 57;
        description
          "ua psp usd";
      }
    }
    description
      "Srv6 static sid behavior";
  }

  typedef Srv6-encapsulation-tc-value {
    type uint32 {
      range "0..255";
    }
    description
      "Srv6 encapsulation tc value";
  }

  typedef Srv6-encapsulation-tc-option {
    type enumeration {
      enum "value" {
        value 1;
        description
          "Set Value";
      }
      enum "propagate" {
        value 2;
        description
          "Set value by propagation";
      }
      enum "propagate-disable" {
        value 3;
        description
          "Disable set value by propagation";
      }
    }
    description
      "Srv6 encapsulation tc option";
  }

  typedef Srv6-encapsulation-hop-limit-option {
    type enumeration {
      enum "count" {
        value 1;
        description
          "Set Value";
      }
      enum "propagate" {
        value 2;
        description
          "Propagate IP TLL";
      }
      enum "propagate-disable" {
        value 3;
        description
          "Disable Propagate IP TLL";
      }
    }
    description
      "Srv6 encapsulation hop limit option";
  }

  typedef Srv6u-behavior {
    type enumeration {
      enum "unode-shift-only" {
        value 42;
        description
          "uNode (shift keyword: unode-only)";
      }
      enum "unode-psp-usd" {
        value 48;
        description
          "uNode (PSP/USD variant)";
      }
    }
    description
      "Srv6u behavior";
  }

  typedef Srv6-algo-value {
    type uint32 {
      range "128..255";
    }
    description
      "Srv6 algo value";
  }
}
