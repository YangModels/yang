module Cisco-IOS-XR-um-cont-optics-fec-threshold-cfg {
  namespace "http://cisco.com/ns/yang/Cisco-IOS-XR-um-cont-optics-fec-threshold-cfg";
  prefix um-cont-optics-fec-threshold-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-optics-fec-threshold package configuration.
     
     This YANG module augments the
     modules with configuration data.
     
     Copyright (c) 2023-2025 by Cisco Systems, Inc., and/or its affiliates.
     All rights reserved.";

  revision 2024-05-11 {
    description
      "Added support for media, link-down, prefec-degrade";
    semver:module-version "1.0.0";
  }
  revision 2023-05-03 {
    description
      "Initial release";
  }

  feature optics {
    description
      "optics";
  }

  grouping CONT-BODY {
    description
      "Grouping for controller";
    container host {
      when "../a1:controller-name[starts-with(text(),'Optics')]" {
        tailf:dependency "../a1:controller-name";
      }
      if-feature "optics";
      description
        "Configure host side parameters";
      container fec-threshold {
        description
          "Configure FEC thresholds";
        container excess-degrade {
          description
            "Configure FEC excess degrade thresholds";
          leaf raise {
            type uint64 {
              range "1..18446744073709551615" {
                description
                  "Select threshold value relative to 1E-18";
              }
            }
            description
              "Configure raise threshold";
          }
          leaf clear {
            type uint64 {
              range "1..18446744073709551615" {
                description
                  "Select threshold value relative to 1E-18";
              }
            }
            description
              "Configure clear threshold";
          }
        }
        container detected-degrade {
          description
            "Configure FEC detected degrade thresholds";
          leaf raise {
            type uint64 {
              range "1..18446744073709551615" {
                description
                  "Select threshold value relative to 1E-18";
              }
            }
            description
              "Configure raise threshold";
          }
          leaf clear {
            type uint64 {
              range "1..18446744073709551615" {
                description
                  "Select threshold value relative to 1E-18";
              }
            }
            description
              "Configure clear threshold";
          }
        }
      }
    }
    container media {
      when "../a1:controller-name[starts-with(text(),'Optics')]" {
        tailf:dependency "../a1:controller-name";
      }
      if-feature "optics";
      description
        "Configure media side parameters";
      container fec-threshold {
        description
          "Configure FEC thresholds";
        container excess-degrade {
          description
            "Configure FEC excess degrade thresholds";
          leaf raise {
            type uint64 {
              range "1..18446744073709551615" {
                description
                  "Select threshold value relative to 1E-18";
              }
            }
            description
              "Configure raise threshold";
          }
          leaf clear {
            type uint64 {
              range "1..18446744073709551615" {
                description
                  "Select threshold value relative to 1E-18";
              }
            }
            description
              "Configure clear threshold";
          }
        }
        container detected-degrade {
          description
            "Configure FEC detected degrade thresholds";
          leaf raise {
            type uint64 {
              range "1..18446744073709551615" {
                description
                  "Select threshold value relative to 1E-18";
              }
            }
            description
              "Configure raise threshold";
          }
          leaf clear {
            type uint64 {
              range "1..18446744073709551615" {
                description
                  "Select threshold value relative to 1E-18";
              }
            }
            description
              "Configure clear threshold";
          }
        }
      }
      container link-down {
        description
          "Configure media linkdown related parameters";
        container prefec-degrade {
          presence "Indicates a prefec-degrade node is configured.";
          description
            "Enable media linkdown prefec degrade";
        }
      }
    }
  }

  augment "/a1:controllers/a1:controller" {
    description
      "This augment extends active nodes configuration";
    uses CONT-BODY;
  }
  augment "/a1:controllers/a1:controller-preconfigure" {
    description
      "This augment extends preconfigured nodes configuration";
    uses CONT-BODY;
  }
}
