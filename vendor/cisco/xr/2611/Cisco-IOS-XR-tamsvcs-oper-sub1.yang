submodule Cisco-IOS-XR-tamsvcs-oper-sub1 {
  belongs-to Cisco-IOS-XR-tamsvcs-oper {
    prefix Cisco-IOS-XR-tamsvcs-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tamsvcs package operational data.
     
     Copyright (c) 2013-2025 by Cisco Systems, Inc.
     All rights reserved.";

  revision 2025-10-25 {
    description
      "Added new ECC256 SUDI/AIK certificate type
       2024-12-19
         Firmware status support in device info
       2024-05-27
         Show storage info for tam
       2022-08-30
         Show ha-sudi certs support for tam";
    semver:module-version "1.3.0";
  }
  revision 2021-06-25 {
    description
      "3rd Party Key Package support in XR";
    semver:module-version "1.2.0";
  }
  revision 2020-11-15 {
    description
      "Show device info and sudi certs support for tam";
    semver:module-version "1.1.0";
  }
  revision 2019-04-05 {
    description
      "Establish semantic version baseline.";
    semver:module-version "1.0.1";
  }
  revision 2015-11-09 {
    description
      "IOS XR 6.0 revision.";
  }

  typedef String1 {
    type string;
    description
      "String1";
  }

  grouping TAMSVCS-SUDI-CERTS {
    description
      "Tam/Tpm Sudi certs bag";
    leaf sudi-root-cert {
      type string;
      description
        "Sudi Root Certificate";
    }
    leaf sudi-subca-cert {
      type string;
      description
        "Sudi SubCA Certificate";
    }
    leaf sudi-cert {
      type string;
      description
        "Sudi Certificate of Tam/Tpm Device";
    }
  }

  grouping TAMSVCS-DEVICE-INFO {
    description
      "Tam/Tpm device info bag";
    container firmware-status {
      description
        "Tam firmware status";
      uses TAMSVCS-FIRMWARE-STATUS;
    }
    leaf device-type {
      type string;
      description
        "Type of Tam/Tpm Device";
    }
    leaf device-pid {
      type string;
      description
        "Pid of Tam/Tpm Device";
    }
    leaf device-serial {
      type string;
      description
        "Serial Number of Tam/Tpm Device";
    }
    leaf device-firware-version {
      type string;
      description
        "Firmware version of the device";
    }
    leaf server-version {
      type string;
      description
        "Tam/Tpm Server Version";
    }
    leaf server-package-version {
      type string;
      description
        "Tam/Tpm Services Server Package Version";
    }
    leaf client-package-version {
      type string;
      description
        "Tam/Tpm Services Client Package Version";
    }
  }

  grouping TAMSVCS-PUBKEYS-REVOKED {
    description
      "Tam Revoked Public Key List ";
    list revoked {
      description
        "Revoked list of Public Key";
      uses TAMSVCS-PUBKEYS;
    }
  }

  grouping TAMSVCS-STORAGE {
    description
      "Tam/Tpm Storage bag";
    leaf is-hwnvram {
      type boolean;
      description
        "Flag to indicate if this platform supports
         Tam/Tpm hardware storage";
    }
    leaf hw-nvram-available {
      type uint32;
      units "byte";
      description
        "Available space in HW NVRAM, in Bytes";
    }
    leaf hw-nvram-total {
      type uint32;
      units "byte";
      description
        "Total Space in HW NVRAM, in Bytes";
    }
    leaf-list app-name-arr {
      type String1;
      description
        "List containing names of Tam/Tpm apps";
    }
    leaf-list nvram-available {
      type uint32;
      units "byte";
      description
        "Available space in NVRAM, in Bytes";
    }
    leaf-list nvram-used {
      type uint32;
      units "byte";
      description
        "Used space in NVRAM, in Bytes";
    }
    leaf-list nvram-total {
      type uint32;
      units "byte";
      description
        "Total Space in NVRAM, in Bytes";
    }
    leaf-list hw-nvram-used {
      type uint32;
      units "byte";
      description
        "Used space in HW NVRAM, in Bytes";
    }
  }

  grouping TAMSVCS-FIRMWARE-STATUS {
    description
      "Tam firmware status";
    leaf crc-supported {
      type boolean;
      description
        "Firmware CRC supported";
    }
    leaf crc {
      type uint32;
      description
        "Firmware CRC";
    }
    leaf restore-status-supported {
      type boolean;
      description
        "Firmware restore status supported";
    }
    leaf restore-status {
      type uint32;
      description
        "Firmware restore status";
    }
  }

  grouping TAMSVCS-INFO-ALL {
    description
      "Tam All info bag";
    container firmware-status {
      description
        "Tam firmware status";
      uses TAMSVCS-FIRMWARE-STATUS;
    }
    leaf device-type {
      type string;
      description
        "Type of Tam/Tpm Device";
    }
    leaf device-pid {
      type string;
      description
        "Pid of Tam/Tpm Device";
    }
    leaf device-serial {
      type string;
      description
        "Serial Number of Tam/Tpm Device";
    }
    leaf device-firware-version {
      type string;
      description
        "Firmware version of the device";
    }
    leaf server-version {
      type string;
      description
        "Tam/Tpm Server Version";
    }
    leaf server-package-version {
      type string;
      description
        "Tam/Tpm Services Server Package Version";
    }
    leaf client-package-version {
      type string;
      description
        "Tam/Tpm Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
    leaf ha-sudi-root-cert {
      type string;
      description
        "HA Sudi Root Certificate";
    }
    leaf ha-sudi-subca-cert {
      type string;
      description
        "HA Sudi SubCA Certificate";
    }
    leaf ha-sudi-cert {
      type string;
      description
        "HA Sudi Leaf Certificate";
    }
  }

  grouping TAMSVCS-PUBKEYS {
    description
      "Tam Public Key ";
    leaf so-name {
      type string;
      description
        "Name of Public Key";
    }
    leaf so-data {
      type string;
      description
        "Content of SO Public Key";
    }
  }

  grouping TAMSVCS-PUBKEYS-ALLOWED {
    description
      "Tam Allowed Public Key List ";
    list allowed {
      description
        "Allowed list of Public Key";
      uses TAMSVCS-PUBKEYS;
    }
  }

  grouping TAMSVCS-HA-SUDI-CERTS {
    description
      "Tam/Tpm Ha Sudi certs bag";
    leaf ha-sudi-root-cert {
      type string;
      description
        "HA Sudi Root Certificate";
    }
    leaf ha-sudi-subca-cert {
      type string;
      description
        "HA Sudi SubCA Certificate";
    }
    leaf ha-sudi-cert {
      type string;
      description
        "HA Sudi Certificate of Tam/Tpm Device";
    }
  }
}
