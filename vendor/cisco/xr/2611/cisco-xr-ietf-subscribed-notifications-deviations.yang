module cisco-xr-ietf-subscribed-notifications-deviations {
  namespace "http://cisco.com/ns/yang/cisco-xr-ietf-subscribed-notifications-deviations";
  prefix xr-sn-d;

  import ietf-subscribed-notifications {
    prefix sn;
  }

  import Cisco-IOS-XR-types {
    prefix xr;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations of:

        ietf-subscribed-notifications@2019-09-09

     on Cisco IOS-XR devices.

     Copyright (c) 2025 by Cisco Systems, Inc., and/or its affiliates.
     All rights reserved.";


  revision 2025-01-20 {
    description
      "Initial version.";
  }

  /*
   * If in the future this deviations file only contains RPC or notification
   * nodes, it will stop appearing in Yang Library or capabilities/hello
   * output.
   * See CSCwn84289 for more details. This comment can be removed once the
   * issue is resolved.
   */

  // DATA MODEL DEVIATIONS

  // "Not-supported" deviations.

  // Remove streams and subtree filters.
  deviation /sn:streams {
    deviate not-supported;
  }

  // For the initial release we don't support any filters, but plan on adding
  // support for datastore filters in a future release.
  deviation /sn:filters {
    deviate not-supported;
  }

  deviation /sn:subscriptions/sn:subscription/sn:target/sn:stream {
    deviate not-supported;
  }

  deviation /sn:subscriptions/sn:subscription/sn:notification-message-origin/sn:address-originated {
    deviate not-supported;
  }

  // Simplify the subscription model.
  deviation /sn:subscriptions/sn:subscription/sn:stop-time {
    deviate not-supported;
  }

  deviation /sn:subscriptions/sn:subscription/sn:weighting {
    deviate not-supported;
  }

  deviation /sn:subscriptions/sn:subscription/sn:dependency {
    deviate not-supported;
  }

  deviation /sn:subscriptions/sn:subscription/sn:configured-subscription-state {
    deviate not-supported;
  }

  deviation /sn:subscriptions/sn:subscription/sn:receivers/sn:receiver/sn:excluded-event-records {
    deviate not-supported;
  }

  deviation /sn:subscriptions/sn:subscription/sn:receivers/sn:receiver/sn:reset {
    deviate not-supported;
  }

  deviation /sn:subscriptions/sn:subscription/sn:receivers/sn:receiver/sn:sent-event-records {
    deviate not-supported;
  }

  deviation /sn:subscriptions/sn:subscription/sn:receivers/sn:receiver/sn:state {
    deviate not-supported;
  }

  // RPC DEVIATIONS

  deviation /sn:establish-subscription {
    deviate not-supported;
  }

  deviation /sn:modify-subscription {
    deviate not-supported;
  }

  deviation /sn:delete-subscription {
    deviate not-supported;
  }

  deviation /sn:kill-subscription {
    deviate not-supported;
  }


  // NOTIFICATION DEVIATIONS

  deviation /sn:replay-completed {
    deviate not-supported;
  }

  deviation /sn:subscription-suspended {
    deviate not-supported;
  }

  deviation /sn:subscription-resumed {
    deviate not-supported;
  }

  deviation /sn:subscription-modified {
    deviate not-supported;
  }

  deviation /sn:subscription-completed {
    deviate not-supported;
  }

  // Remove the bits of the subscription started notification we don't support.
  deviation /sn:subscription-started/sn:target/sn:stream {
    deviate not-supported;
  }

  deviation /sn:subscription-started/sn:stop-time {
    deviate not-supported;
  }

  deviation /sn:subscription-started/sn:weighting {
    deviate not-supported;
  }

  deviation /sn:subscription-started/sn:dependency {
    deviate not-supported;
  }

  // Type deviations.

  deviation /sn:subscriptions/sn:subscription/sn:notification-message-origin/sn:interface-originated/sn:source-interface {
    deviate replace {
        type "xr:Interface-name";
    }
  }

}
