submodule Cisco-IOS-XR-install-augmented-oper-sub2 {
  belongs-to Cisco-IOS-XR-install-augmented-oper {
    prefix Cisco-IOS-XR-install-augmented-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR install-augmented package operational data.
     
     Copyright (c) 2013-2025 by Cisco Systems, Inc.
     All rights reserved.";

  revision 2025-09-24 {
    description
      "Move schema items from InstallAgent to InstallLocal
       2025-09-03
         Add new RPM rejection reason for owner packages with files with setuid or setgid bit set.
       2025-08-15
         Add new RPM rejection reason for owner packages with special files.
       2025-07-29
         Add new activity enum values to report post reimage flows.
       2025-05-06
         Add enum values for several previously unreported node activities and message types.
       2025-05-01
         Add new activity enum values to report early FPD upgrade flows.
       2025-04-25
         Add new fields in not installed package reason bag for owner packages with invalid signatures.
       2025-04-16
         Add new enum value to activation type for apply by reimage reporting.
       2024-09-19
         Add new fields in package op bag for added and removed supported PIDs.
       2024-05-23
         Add new bagtypes for list of PIDs and node inventory.
       2024-05-03
         Add new constraint for owner packages with cisco key id.
       2024-02-22
         Add origin filtering to available package queries.
       2023-12-12
         Add summary to available package queries.
       2023-11-16
         Add origin information for owner RPMs.
       2023-07-11
         Add packages which were not installed at boot time.
       2023-02-10
         Add awaited unsolicited messages to internal data.
       2022-12-20
         Add username information.
       2022-11-17
         Add latest reimage bags.
       2022-05-05
         Add warning to inst_request_verbose_bag.
       2022-02-18
         Add detailed intervention event information.
       2021-10-27
         Add new bag for platform-specific disabled packages.
       2021-10-25
         Add source to package operation reporting.
       2021-10-01
         Add details in history for package verification failure reporting.";
    semver:module-version "2.3.0";
  }
  revision 2021-08-25 {
    description
      "7.5.1 release features.";
    semver:module-version "2.2.0";
  }
  revision 2021-03-22 {
    description
      "7.4.1 release features.
       2020-09-30
           7.3.1 release features.";
    semver:module-version "2.1.0";
  }
  revision 2020-05-12 {
    description
      "Removal of compound from enum naming conventions to avoid confusion.
       2019-12-11
         Obsoleted the nodes list for history items.
       2019-10-14
         Combined platform updates including updates to show install rollback list-ids";
    semver:module-version "2.0.0";
  }
  revision 2019-10-13 {
    description
      "NCS540L 7.1.1 release
       2019-10-12
       8000 series 7.0.11 release";
    semver:module-version "1.1.0";
  }
  revision 2019-04-05 {
    description
      "Establish semantic version baseline.";
    semver:module-version "1.0.0";
  }
  revision 2015-11-09 {
    description
      "IOS XR 6.0 revision.";
  }

  typedef Inst-activation {
    type enumeration {
      enum "restart" {
        value 0;
        description
          "Process restart";
      }
      enum "reload" {
        value 1;
        description
          "Reload";
      }
      enum "least-impactful" {
        value 2;
        description
          "Least impactful";
      }
      enum "reimage" {
        value 3;
        description
          "Automatic reimage";
      }
    }
    description
      "Activation type";
  }

  typedef Inst-package-abort {
    type enumeration {
      enum "latest" {
        value 0;
        description
          "Latest packaging operation";
      }
      enum "all-since-apply" {
        value 1;
        description
          "All packaging operations since the last apply";
      }
    }
    description
      "Package abort type";
  }

  typedef String1 {
    type string;
    description
      "String1";
  }

  grouping STRING-LIST-TYPE {
    description
      "STRING LIST TYPE";
    leaf-list string-list-type {
      type String1;
      description
        "string list type";
    }
  }
}
