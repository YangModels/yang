submodule Cisco-IOS-XR-spp-oper-sub1 {
  belongs-to Cisco-IOS-XR-spp-oper {
    prefix Cisco-IOS-XR-spp-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR spp package operational data.
     
     Copyright (c) 2013-2025 by Cisco Systems, Inc.
     All rights reserved.";

  revision 2025-05-10 {
    description
      "Introduced yang support for spp";
    semver:module-version "1.0.0";
  }
  revision 2019-04-05 {
    description
      "Establish semantic version baseline.";
  }
  revision 2015-11-09 {
    description
      "IOS XR 6.0 revision.";
  }

  grouping SPP-NODE-DROP-COUNTERS-INFO {
    description
      "SPP Node Counters Drop information";
    leaf aggr-drop-counters {
      type uint64;
      description
        "Aggregated Drop counters";
    }
  }
}
