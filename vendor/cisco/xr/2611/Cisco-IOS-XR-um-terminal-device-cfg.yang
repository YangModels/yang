module Cisco-IOS-XR-um-terminal-device-cfg {
  namespace "http://cisco.com/ns/yang/Cisco-IOS-XR-um-terminal-device-cfg";
  prefix um-terminal-device-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR terminal-device package configuration.
     
     This YANG module augments the
     modules with configuration data.
     
     Copyright (c) 2022-2025 by Cisco Systems, Inc., and/or its affiliates.
     All rights reserved.";

  revision 2025-06-23 {
    description
      "rate-class enum changed from 1.5G to 2.5G";
    semver:module-version "1.0.0";
  }
  revision 2022-09-07 {
    description
      "Initial release";
  }

  container terminal-device {
    description
      "Terminal Device";
    container logical-channel {
      description
        "Logical Channel";
      container logical-channel-numbers {
        description
          "Logical channel number (1-100000)";
        list logical-channel-number {
          key "logical-channel-number-id";
          description
            "Logical channel number (1-100000)";
          leaf logical-channel-number-id {
            type uint32 {
              range "1..100000" {
                description
                  "Logical channel number (1-100000)";
              }
            }
            description
              "Logical channel number (1-100000)";
          }
          container assignment-ids {
            description
              "Logical channel assignment id for logical channel";
            list assignment-id {
              key "assignment-id";
              description
                "Logical channel assignment id for logical channel";
              leaf assignment-id {
                type uint32 {
                  range "1..100000" {
                    description
                      "Assignment number (1 to 100000)";
                  }
                }
                description
                  "Logical channel assignment id for logical channel";
              }
              leaf assigned-logical-channel {
                type uint32 {
                  range "1..100000" {
                    description
                      "Logical channel number (1-100000)";
                  }
                }
                description
                  "Logical channel assigned to this assigment id";
              }
              leaf assigned-optical-channel {
                type xr:Cisco-ios-xr-string {
                  length "1..800" {
                    description
                      "Optical channel name";
                  }
                }
                description
                  "Optical channel assigned to this assigment id";
              }
              leaf assignment-type {
                type enumeration {
                  enum "logical" {
                    value 1;
                    description
                      "assignment type logical";
                  }
                  enum "optical" {
                    value 2;
                    description
                      "assignment type optical";
                  }
                }
                description
                  "Assignment type (logical or optical)";
              }
              leaf allocation {
                type uint32 {
                  range "0..4294967295" {
                    description
                      "Allocation (10, 40 or 100G)";
                  }
                }
                description
                  "Allocation";
              }
              leaf description {
                type string {
                  length "1..800" {
                    description
                      "Description";
                  }
                }
                description
                  "Description";
              }
            }
          }
          leaf description {
            type string {
              length "1..800" {
                description
                  "Description";
              }
            }
            description
              "Description";
          }
          leaf admin-state {
            type enumeration {
              enum "enable" {
                value 1;
                description
                  "enable";
              }
              enum "disable" {
                value 2;
                description
                  "shutdown";
              }
              enum "maintenance" {
                value 3;
                description
                  "Maintenance";
              }
            }
            description
              "Administrative state";
          }
          leaf loopback-mode {
            type enumeration {
              enum "none" {
                value 0;
                description
                  "none";
              }
              enum "facility" {
                value 1;
                description
                  "facility";
              }
              enum "terminal" {
                value 2;
                description
                  "terminal";
              }
            }
            description
              "Loopback mode";
          }
          leaf rate-class {
            type enumeration {
              enum "1G" {
                value 1;
                description
                  "1G tributary signal rate";
              }
              enum "2.5G" {
                value 2;
                description
                  "2.5G tributary signal rate";
              }
              enum "10G" {
                value 3;
                description
                  "10G tributary signal rate";
              }
              enum "40G" {
                value 4;
                description
                  "40G tributary signal rate";
              }
              enum "100G" {
                value 5;
                description
                  "100G tributary signal rate";
              }
              enum "150G" {
                value 6;
                description
                  "150G tributary signal rate";
              }
              enum "200G" {
                value 7;
                description
                  "200G tributary signal rate";
              }
              enum "250G" {
                value 8;
                description
                  "250G tributary signal rate";
              }
              enum "300G" {
                value 9;
                description
                  "300G tributary signal rate";
              }
              enum "400G" {
                value 10;
                description
                  "400G tributary signal rate";
              }
              enum "500G" {
                value 11;
                description
                  "500G tributary signal rate";
              }
              enum "600G" {
                value 12;
                description
                  "600G tributary signal rate";
              }
              enum "700G" {
                value 13;
                description
                  "700G tributary signal rate";
              }
              enum "800G" {
                value 14;
                description
                  "800G tributary signal rate";
              }
              enum "900G" {
                value 15;
                description
                  "900G tributary signal rate";
              }
              enum "1000G" {
                value 16;
                description
                  "1000G tributary signal rate";
              }
              enum "1100G" {
                value 17;
                description
                  "1100G tributary signal rate";
              }
            }
            description
              "Rate Class";
          }
          leaf trib-protocol {
            type enumeration {
              enum "1GE" {
                value 1;
                description
                  "1G Ethernet protocol";
              }
              enum "OC48" {
                value 2;
                description
                  "OC48 protocol";
              }
              enum "STM16" {
                value 3;
                description
                  "STM 16 protocol";
              }
              enum "10GE-LAN" {
                value 4;
                description
                  "10G Ethernet LAN protocol";
              }
              enum "10GE-WAN" {
                value 5;
                description
                  "10G Ethernet WAN protocol";
              }
              enum "OC192" {
                value 6;
                description
                  "OC 192 (9.6GB) port protocol";
              }
              enum "STM64" {
                value 7;
                description
                  "STM 64 protocol";
              }
              enum "OTU2" {
                value 8;
                description
                  "OTU 2 protocol";
              }
              enum "OTU2e" {
                value 9;
                description
                  "OTU 2e protocol";
              }
              enum "OTU1e" {
                value 10;
                description
                  "OTU 1e protocol";
              }
              enum "ODU2" {
                value 11;
                description
                  "ODU 2 protocol";
              }
              enum "ODU2e" {
                value 12;
                description
                  "ODU 2e protocol";
              }
              enum "40GE" {
                value 13;
                description
                  "40G Ethernet port protocol";
              }
              enum "OC768" {
                value 14;
                description
                  "OC 768 protocol";
              }
              enum "STM256" {
                value 15;
                description
                  "STM 256 protocol";
              }
              enum "OTU3" {
                value 16;
                description
                  "OTU 3 protocol";
              }
              enum "ODU3" {
                value 17;
                description
                  "ODU 3 protocol";
              }
              enum "100GE" {
                value 18;
                description
                  "100G Ethernet protocol";
              }
              enum "100G-MLG" {
                value 19;
                description
                  "100G MLG protocol";
              }
              enum "OTU4" {
                value 20;
                description
                  "OTU4 signal protocol (112G) for transporting 100GE signal";
              }
              enum "OTUCn" {
                value 21;
                description
                  "OTU Cn protocol";
              }
              enum "ODU4" {
                value 22;
                description
                  "ODU 4 protocol";
              }
              enum "ODUCn" {
                value 23;
                description
                  "ODU Cn protocol";
              }
              enum "ODUFlex-CBR" {
                value 24;
                description
                  "ODU FLEX CBR protocol";
              }
              enum "ODUFlex-GFP" {
                value 25;
                description
                  "ODU FLEX GFP protocol";
              }
              enum "400GE" {
                value 26;
                description
                  "400G Ethernet Protocol";
              }
            }
            description
              "Optical channel assigned to this assigment id";
          }
          leaf logical-channel-type {
            type enumeration {
              enum "Ethernet" {
                value 1;
                description
                  "Ethernet protocol framing";
              }
              enum "Otn" {
                value 2;
                description
                  "OTN protocol framing";
              }
            }
            description
              "Assignment type (logical or optical)";
          }
          leaf otn-tti-msg-transmit {
            type string {
              length "1..800" {
                description
                  "tti message transmit";
              }
            }
            description
              "tti message transmit";
          }
          leaf otn-tti-msg-expected {
            type string {
              length "1..800" {
                description
                  "tti message expected";
              }
            }
            description
              "tti message expected";
          }
          leaf otn-tti-msg-auto {
            type enumeration {
              enum "0" {
                value 0;
                description
                  "false";
              }
              enum "1" {
                value 1;
                description
                  "true";
              }
            }
            description
              "tti message auto";
          }
          leaf ethernet-client-als {
            type enumeration {
              enum "ethernet" {
                value 1;
                description
                  "ethernet";
              }
              enum "laser-shutdown" {
                value 2;
                description
                  "laser_shutdown";
              }
            }
            description
              "Configure the client-als";
          }
          leaf ethernet-als-delay {
            type uint32 {
              range "0..3000" {
                description
                  "als-delay in ms";
              }
            }
            description
              "Configure the als-delay";
          }
          leaf ingress-client-port {
            type xr:Interface-name {
              pattern "Optics.*";
            }
            description
              "Ingress client port of the logical channel";
          }
          leaf ingress-physical-channel {
            type uint32 {
              range "1..4" {
                description
                  "Physical channel id";
              }
            }
            description
              "Physical channel id for logical channel";
          }
        }
      }
    }
    container optical-channel {
      description
        "Optical Channel";
      container optical-channels {
        description
          "Optical Channel name";
        list optical-channel {
          key "optical-channel-name";
          description
            "Optical Channel name";
          leaf optical-channel-name {
            type xr:Cisco-ios-xr-string {
              length "1..800" {
                description
                  "Optical Channel name";
              }
            }
            description
              "Optical Channel name";
          }
          leaf line-port {
            type xr:Interface-name {
              pattern "Optics.*";
            }
            description
              "Line-Port";
          }
          leaf frequency {
            type uint32 {
              range "186100000..196137500" {
                description
                  "Freq in Mhz";
              }
            }
            description
              "Frequency (in MHz)";
          }
          leaf power {
            type int32 {
              range "-1900..500" {
                description
                  "Select power level (in units of 0.01dBm)";
              }
            }
            description
              "Configure transponder power";
          }
          leaf operational-mode {
            type uint32 {
              range "1..65536" {
                description
                  "Enter operational mode";
              }
            }
            description
              "Operational Mode";
          }
          leaf cpr-ext-win-mode {
            type uint32 {
              range "1..9" {
                description
                  "Enter carrier phase extended window mode";
              }
            }
            description
              "Carrier Phase Recovery Extended Window Mode";
          }
          leaf cross-pol-gain-mode {
            type uint32 {
              range "1..15" {
                description
                  "Select carrier phase recovery cross polarization gain mode";
              }
            }
            description
              "Carrier Phase Recovery Cross Polarization Gain Mode";
          }
          leaf cross-pol-weight-mode {
            type uint32 {
              range "1..7" {
                description
                  "Select carrier phase recovery cross polarization weight mode";
              }
            }
            description
              "Carrier Phase Recovery Cross Polarization Weight Mode";
          }
          leaf enh-colorless-mode {
            type uint32 {
              range "1..3" {
                description
                  "Select enhanced colorless mode";
              }
            }
            description
              "Enhanced Colorless Mode";
          }
          leaf enh-sop-tol-mode {
            type uint32 {
              range "1..3" {
                description
                  "Select enhanced SOP tolerance mode";
              }
            }
            description
              "Enhanced SOP Tolerance Mode";
          }
          leaf filter-roll-off-factor {
            type xr:Cisco-ios-xr-string {
              length "5" {
                description
                  "RRC Filter Roll-Off factor in increments of 0.001";
              }
            }
            description
              "RRC Filter Roll-Off factor";
          }
          leaf cpr-win-mode {
            type uint32 {
              range "1..4" {
                description
                  "Select carrier phase recovery window mode";
              }
            }
            description
              "Carrier Phase Recovery Window Mode";
          }
          leaf nleq-comp-mode {
            type uint32 {
              range "1..5" {
                description
                  "Select non-linear effect compensation";
              }
            }
            description
              "Non-Linear Effect Compensation";
          }
          leaf cd-max {
            type int32 {
              range "-350000..350000" {
                description
                  "Enter max chromatic dispersion";
              }
            }
            description
              "Max Chromatic Dispersion";
          }
          leaf cd-min {
            type int32 {
              range "-350000..350000" {
                description
                  "Enter min chromatic dispersion";
              }
            }
            description
              "Min Chromatic Dispersion";
          }
          leaf cd-high-threshold {
            type int32 {
              range "-350000..350000" {
                description
                  "Enter chromatic dispersion high threshold";
              }
            }
            description
              "Chromatic Dispersion High Threshold";
          }
          leaf cd-low-threshold {
            type int32 {
              range "-350000..350000" {
                description
                  "Enter chromatic dispersion low threshold";
              }
            }
            description
              "Chromatic Dispersion Low Threshold";
          }
          leaf rx-voa-target-power {
            type int32 {
              range "-190..30" {
                description
                  "Receive Target Power in 0.1 dbm.";
              }
            }
            description
              "Rx-voa target power configuration";
          }
          leaf rx-voa-fixed-ratio {
            type int32 {
              range "100..1700" {
                description
                  "Receive Ratio of Optical Attenuation in 0.01 db";
              }
            }
            description
              "Rx-voa fixed ratio configuration";
          }
        }
      }
    }
    container transceiver {
      description
        "Transceiver";
      container transceivers {
        description
          "Transceiver name";
        list transceiver {
          key "transceiver-name";
          description
            "Transceiver name";
          leaf transceiver-name {
            type xr:Cisco-ios-xr-string {
              length "1..800" {
                description
                  "Transceiver name";
              }
            }
            description
              "Transceiver name";
          }
          leaf ethernet-fec-mode {
            type enumeration {
              enum "fec-disabled" {
                value 0;
                description
                  "fec_disabled";
              }
              enum "fec-enabled" {
                value 1;
                description
                  "fec_enabled";
              }
            }
            description
              "Configure the fec-mode";
          }
        }
      }
    }
  }
}
