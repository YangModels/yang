module Cisco-IOS-XR-um-router-isis-cfg {
  yang-version 1.1;
  namespace "http://cisco.com/ns/yang/Cisco-IOS-XR-um-router-isis-cfg";
  prefix um-router-isis-cfg;

  import Cisco-IOS-XR-um-snmp-server-cfg {
    prefix snmp-server-cfg;
  }
  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco router isis package configuration.
     
     Copyright (c) 2024-2025 by Cisco Systems, Inc., and/or its affiliates.
     All rights reserved.";

  revision 2025-09-15 {
    description
      "Added support for srv6 encapsulate configuration
       2025-09-01
         Added support for conditional static neighbor advertisement
       2025-07-01
         Change auto-cost reference-bandwidth to 64-bit number
       2025-05-30
         Added support for auto-cost reference-bandwidth
       2024-11-22
         Fix for address-family distance allowing both ipv4 and ipv6
       2024-11-08
         Fix for instance-id and udpated naming for pre-link to per-link
       2024-10-23
         Fix for per-prefix srlg-protection
       2024-10-09
         Added support generic-metric for fallback anomaly and static-neighbor
       2024-07-19
         Added support for protocol shutdown
       2024-07-15
         Added support level 1 level 2 and level 12 for mpl
       2024-05-30
         Added support for flex-algo bandwidth metric
       2024-04-23
         Add new trace buffers flood-speed and flood-speed-detail
       2024-04-04
         Updated UM2 for if remote-psnp-delay support
       2024-03-27
         Design change for enums for UM2
       2024-02-28
         Updating model for um2 changes
       2024-02-05
         Correct container distribute-list metadata
       2024-02-01
         Add ip-only support
       2024-01-05
         Add Log Size
       2023-11-21
         Add Generic-metric
       2023-11-09
         Add lsp-fast-flooding submode, psnp-interval and if remote-psnp-delay
       2023-11-09
         Add oor-set-overload-bit
       2023-08-22
         Add nsr-restart-time
       2023-07-12
         Add flex-algo UCMP
       2023-06-28
         Change the must clause from ../../srv6-locator-xxx to srv6-locator-xxx
       2023-04-09
         Add maximum paths per route-policy for standard and flex algo
       2023-04-03
         Add flex-algo MinimumBandwidth and MaximumDelay constraints
       2023-03-13
         Add Uloop filtering suport
       2023-02-10
         Modify must statement for SPF interval per-level
       2022-11-18
         Add distribute link-state prefix filtering
       2022-10-14
         Added new nodes for partition-detect
       2022-10-04
         Added support for ISIS Prefix-SID UHP
       2022-10-02
         Added hello-padding under router-isis
       2022-10-01
         Add support for flex-algo reverse link affinities.
       2022-07-25
         Added new node anycast-prefer-igp-cost to traffic-eng tunnel
       2022-07-18
         Added new node php-disable to the existing connected-prefix-sid-map, strict-spf and flex-algo.
       2022-07-11
         Added missing description statement to nodes
       2022-05-12
         Added new node adv-unreachable with sub-node unreachable-component-tag and tag value to an existing ISIS address-family sub-mode summary-prefix command.Added new node prefix-unreachable under ISIS address-family sub-mode.
       2022-05-05
         Added new node anomaly to the existing ISIS affinity flex-algo
       2022-04-22
         Added support for maximum-paths under flex-algo,
       Added container algorithm
       2022-04-05
         Added support for te and delay
       2022-03-03
         Added container metric & tag under segment-routing/srv6/locators,
       Added container format,
       Added container lsp-fast-flood
       2022-01-19
         Added ietf support for spf-interval
       2022-01-04
         Added support for unhidden CLI commands
       2021-12-14
         Added authentication-check feature";
    semver:module-version "5.0.0";
  }
  revision 2021-09-23 {
    description
      "Merged container levels under disable|interval/periodic/address-family-topology,
        Merged container levels under disable|interval/periodic/address-family,
        Merged disable & interval-time into one leaf interval
       2021-07-27
          Re-ordered maximum-wait, initial-wait and secondary-wait nodes under
        level container/spf-interval
       2021-06-15
          Added when statement to container prefix-attributes";
    semver:module-version "4.0.0";
  }
  revision 2021-05-18 {
    description
      "Added features, 1. flex-algo srlg exclude
       2. advertise application flex-algo link-attributes srlg
       2021-04-22
           Added te-metric flex-algo feature
       2021-03-02
           Re-ordered maximum-wait, initial-wait and secondary-wait nodes under
         level container
       2021-02-11
           Re-ordered per-link, per-prefix nodes under interface fast-reroute container
       2021-01-28
           Added cisco-support task yang nodes
       2021-01-27
           Re-ordered nodes under lsp-gen-interval, min-lsp-arrivaltime container
       2021-01-20
           Moved presence containers as leafs under snmp-server traps
       2021-01-18
           Added presence statement and re-ordered few nodes under container max-metric
       2021-01-11
           Add support to metric and preferred container under tunnel
       2021-01-07
           Updated range value in leaf multiplier under fallback container
       2021-01-06
           Added presence statement under link-state container
       2020-12-09
           Removed cisco-support yang nodes
       2020-12-01
           Added container anomaly under metric/fallback
       2020-11-20
           Added metric type te
       2020-11-19
           Fixed a must statement under absolute, added presence statement to text
       2020-11-13
           Added container receive and attestation under list process.
       2020-11-02
           Moved levels container under lsp-password out of it and renamed as
         lsp-password-levels.
       2020-08-20
           Added level option under srv6/locator
       2020-08-13
           Remove presence container and constraints on the match container
       2020-08-10
           Updated the fallback topology
       2020-07-21
           Slight changes to prefix-priority nodes
       2020-07-17
           Added must statements and moved rib-update-delay up one node
       2020-07-15
           Added down-flag-clear node under redistribute isis
       2020-07-14
           Added mandatory node to bit-position under affinity-map";
    semver:module-version "3.0.0";
  }
  revision 2020-05-19 {
    description
      "Added nodes for new ISIS features
       2020-05-07
         Added a container anycast and its child nodes
       2020-04-14
         Updated the constraints in the nodes under stagger to be less strict
       2020-03-09
         Updated lsp-password and summary-prefix trees with proper constaraint
         statements";
    semver:module-version "2.0.0";
  }
  revision 2019-06-10 {
    description
      "Establish semantic version baseline.";
    semver:module-version "1.0.0";
  }
  revision 2019-03-30 {
    description
      "Initial draft";
  }

  feature isis_is_csi_config_supported {
    description
      "isisconfigurability";
  }

  feature isis_srmpls_is_platform_supported {
    description
      "isisconfigurability";
  }

  feature isis_ucmp_is_platform_supported {
    description
      "isisconfigurability";
  }

  feature isis_srv6_is_srv6_cap_config_supported {
    description
      "isisconfigurability";
  }

  grouping GROUP-SNMP-SERVER-CFG-SNMP-SERVER-TRAPS-BODY {
    description
      "Enable SNMP isis traps";
    container isis {
      presence "Enable SNMP isis traps";
      description
        "Enable SNMP isis traps";
      choice ISIS {
        mandatory true;
        description
          "Enable SNMP isis traps";
        case ALL {
          leaf all {
            type empty;
            description
              "Enable all IS-IS traps";
          }
        }
        case ISIS-TRAPS {
          leaf database-overload {
            type empty;
            description
              "isisDatabaseOverload";
          }
          leaf manual-address-drops {
            type empty;
            description
              "isisManualAddressDrops";
          }
          leaf corrupted-lsp-detected {
            type empty;
            description
              "isisCorruptedLSPDetected";
          }
          leaf attempt-to-exceed-max-sequence {
            type empty;
            description
              "isisAttemptToExceedMaxSequence";
          }
          leaf id-len-mismatch {
            type empty;
            description
              "isisIDLenMismatch";
          }
          leaf max-area-addresses-mismatch {
            type empty;
            description
              "isisMaxAreaAddressesMismatch";
          }
          leaf own-lsp-purge {
            type empty;
            description
              "isisOwnLSPPurge";
          }
          leaf sequence-number-skip {
            type empty;
            description
              "isisSequenceNumberSkip";
          }
          leaf authentication-type-failure {
            type empty;
            description
              "isisAuthenticationTypeFailure";
          }
          leaf authentication-failure {
            type empty;
            description
              "isisAuthenticationFailure";
          }
          leaf version-skew {
            type empty;
            description
              "isisVersionSkew";
          }
          leaf area-mismatch {
            type empty;
            description
              "isisAreaMismatch";
          }
          leaf rejected-adjacency {
            type empty;
            description
              "isisRejectedAdjacency";
          }
          leaf lsp-too-large-to-propagate {
            type empty;
            description
              "isisLSPTooLargeToPropagate";
          }
          leaf orig-lsp-buff-size-mismatch {
            type empty;
            description
              "isisOrigLSPBuffSizeMismatch";
          }
          leaf protocols-supported-mismatch {
            type empty;
            description
              "isisProtocolsSupportedMismatch";
          }
          leaf adjacency-change {
            type empty;
            description
              "isisAdjacencyChange";
          }
          leaf lsp-error-detected {
            type empty;
            description
              "isisLSPErrorDetected";
          }
        }
      }
    }
  }

  augment "/snmp-server-cfg:snmp-server/snmp-server-cfg:traps" {
    description
      "This augment extends the configuration data of Cisco-IOS-XR-um-snmp-server-cfg";
    uses GROUP-SNMP-SERVER-CFG-SNMP-SERVER-TRAPS-BODY;
  }
  container router {
    description
      "ISO IS-IS";
    container isis {
      description
        "ISO IS-IS";
      container processes {
        description
          "ISO IS-IS";
        list process {
          key "process-id";
          description
            "ISO IS-IS";

          grouping ADVERTISE {
            description
              "If overload-bit set advertise the following types of IP prefixes";
            container advertise {
              description
                "If overload-bit set advertise the following types of IP prefixes";
              leaf external {
                type empty;
                description
                  "If overload-bit set advertise IP prefixes learned from other protocols";
              }
              leaf interlevel {
                type empty;
                description
                  "If overload-bit set advertise IP prefixes learned from another ISIS level";
              }
            }
          }

          grouping PASSWORD-OPTIONS {
            description
              "password options";
            container password-options {
              description
                "password options";
              leaf encrypted {
                type xr:Proprietary-password;
                mandatory true;
                description
                  "Specifies a password will follow";
              }
              uses SNP;
            }
          }

          grouping SNP {
            description
              "specify SNP packets authentication mode";
            leaf send-only {
              type empty;
              description
                "specify SNP packets authentication mode";
            }
            container snp {
              description
                "Specify SNP packets authentication mode";
              leaf send-only {
                type empty;
                description
                  "Authenticate outgoing SNPs, no check on incoming SNPs";
              }
            }
            leaf enable-poi {
              type empty;
              description
                "Enable purge originator identification";
            }
          }

          grouping MAX-METRIC {
            description
              "max metric";
            leaf external {
              type empty;
              description
                "Override metric of prefixes learned from another protocol with maximum metric";
            }
            leaf interlevel {
              type empty;
              description
                "Override metric of prefixes learned from another ISIS level with maximum metric";
            }
            leaf default-route {
              type empty;
              description
                "Override default route metric with maximum metric";
            }
            leaf srv6-locator {
              type empty;
              description
                "Override segment routing ipv6 locator metric with maximum metric";
            }
            leaf te {
              type empty;
              description
                "Apply max-metric to TE metric";
            }
            leaf delay {
              type empty;
              description
                "Apply max-metric to delay metric";
            }
          }
          leaf process-id {
            type xr:Cisco-ios-xr-string {
              length "1..36" {
                description
                  "Process ID";
              }
            }
            description
              "Process ID";
          }
          container segment-routing {
            description
              "IS-IS segment-routing configuration";
            container global-block {
              description
                "Prefix-SID Global label Block (SRGB)";
              leaf lower-bound-of-srgb {
                type uint32 {
                  range "16000..1048575" {
                    description
                      "The lower bound of the SRGB";
                  }
                }
                must "../upper-bound-of-srgb";
                description
                  "The lower bound of the SRGB";
              }
              leaf upper-bound-of-srgb {
                type uint32 {
                  range "16001..1048575" {
                    description
                      "The upper bound SRGB";
                  }
                }
                must "../lower-bound-of-srgb";
                description
                  "The upper bound SRGB";
              }
            }
          }
          container receive {
            description
              "Control if ASLA takes precedence over Legacy";
            container application {
              description
                "Select Application";
              container flex-algo {
                description
                  "Flex-Algo Applciation";
                container delay {
                  description
                    "Unidirectionial Min Delay metric";
                  leaf app-only {
                    type empty;
                    description
                      "ASLA to take precedence";
                  }
                }
              }
            }
          }
          leaf lsp-refresh-interval {
            type uint32 {
              range "1..65535" {
                description
                  "LSP refresh time in seconds";
              }
            }
            description
              "Set LSP refresh interval";
          }
          container lsp-refresh-interval-levels {
            description
              "Set LSP refresh interval for one level only";
            list lsp-refresh-interval-level {
              key "level-number";
              description
                "Set LSP refresh interval for one level only";
              leaf level-number {
                type uint32 {
                  range "1..2" {
                    description
                      "Level";
                  }
                }
                description
                  "Level";
              }
              leaf lsp-refresh-interval {
                type uint32 {
                  range "1..65535" {
                    description
                      "LSP refresh time in seconds";
                  }
                }
                mandatory true;
                description
                  "Set LSP refresh interval";
              }
            }
          }
          container oor-set-overload-bit {
            description
              "Overload-bit setting when Out-Of-Resource (OOR)";
            leaf disable {
              type empty;
              description
                "Disable setting of overload-bit when OOR. ISIS will continue to participate in forwarding but its decision will be based on an incomplete link-state database. It may lead to routing loops and other forwarding failures. NOT recommended.";
            }
          }
          container set-overload-bit {
            presence "Signal other routers not to use us in SPF";
            description
              "Signal other routers not to use us in SPF";
            container on-startup {
              description
                "Set overload-bit temporarily after reboot";
              choice ON-STARTUP {
                description
                  "Set overload-bit temporarily after reboot";
                case TIME-TO-ADVERTISE {
                  container time-to-advertise {
                    presence "Time in seconds to advertise ourself as overloaded after reboot";
                    description
                      "Time in seconds to advertise ourself as overloaded after reboot";
                    leaf time-to-advertise-number {
                      type uint32 {
                        range "5..86400" {
                          description
                            "Time in seconds to advertise ourself as overloaded after reboot";
                        }
                      }
                      mandatory true;
                      description
                        "Time in seconds to advertise ourself as overloaded after reboot";
                    }
                  }
                }
                case WAIT-FOR-BGP {
                  container wait-for-bgp {
                    presence "Set overload bit on startup until BGP signals convergence, or timeout";
                    description
                      "Set overload bit on startup until BGP signals convergence, or timeout";
                  }
                }
              }
            }
            uses ADVERTISE;
          }
          container set-overload-bit-levels {
            description
              "Set overload-bit for one level only";
            list set-overload-bit-level {
              key "level-number";
              description
                "Set overload-bit for one level only";
              leaf level-number {
                type uint32 {
                  range "1..2" {
                    description
                      "Level";
                  }
                }
                description
                  "Level";
              }
              container on-startup {
                description
                  "Set overload-bit temporarily after reboot";
                choice ON-STARTUP {
                  description
                    "Set overload-bit temporarily after reboot";
                  case TIME-TO-ADVERTISE {
                    container time-to-advertise {
                      presence "Time in seconds to advertise ourself as overloaded after reboot";
                      description
                        "Time in seconds to advertise ourself as overloaded after reboot";
                      leaf time-to-advertise-number {
                        type uint32 {
                          range "5..86400" {
                            description
                              "Time in seconds to advertise ourself as overloaded after reboot";
                          }
                        }
                        mandatory true;
                        description
                          "Time in seconds to advertise ourself as overloaded after reboot";
                      }
                    }
                  }
                  case WAIT-FOR-BGP {
                    container wait-for-bgp {
                      presence "Set overload bit on startup until BGP signals convergence, or timeout";
                      description
                        "Set overload bit on startup until BGP signals convergence, or timeout";
                    }
                  }
                }
              }
              uses ADVERTISE;
            }
          }
          leaf lsp-mtu {
            type uint32 {
              range "128..8979" {
                description
                  "Max LSP size in bytes";
              }
            }
            description
              "Set maximum LSP size";
          }
          container lsp-mtu-levels {
            description
              "Set LSP size for one level only";
            list lsp-mtu-level {
              key "level-number";
              description
                "Set LSP size for one level only";
              leaf level-number {
                type uint32 {
                  range "1..2" {
                    description
                      "Level";
                  }
                }
                description
                  "Level";
              }
              leaf lsp-mtu {
                type uint32 {
                  range "128..8979" {
                    description
                      "Max LSP size in bytes";
                  }
                }
                mandatory true;
                description
                  "Set maximum LSP size";
              }
            }
          }
          leaf extended-admin-group {
            type enumeration {
              enum "both" {
                value 2;
                description
                  "Use both the Cisco pre-standard and IETF EAG subTLV code-points";
              }
              enum "cisco" {
                value 0;
                description
                  "Use the Cisco pre-standard EAG subTLV code-point (252)";
              }
              enum "ietf" {
                value 1;
                description
                  "Use the IETF standard EAG subTLV code-point (14)";
              }
            }
            description
              "Code-point for Extended Administrative Group subTLV";
          }
          container nsf {
            description
              "Allow non-stop forwarding (NSF) on next restart";
            leaf interface-expires {
              type uint32 {
                range "1..10" {
                  description
                    "expiry count";
                }
              }
              description
                "# of times T1 can expire waiting for the restart ACK";
            }
            leaf interface-timer {
              type uint32 {
                range "1..20" {
                  description
                    "seconds";
                }
              }
              description
                "Timer used to wait for a restart ACK (seconds)";
            }
            leaf lifetime {
              type uint32 {
                range "5..300" {
                  description
                    "seconds";
                }
              }
              description
                "Maximum route lifetime following restart (seconds)";
            }
            choice NSF {
              description
                "Allow non-stop forwarding (NSF) on next restart";
              case IETF {
                leaf ietf {
                  type empty;
                  description
                    "IETF NSF restart";
                }
              }
              case CISCO {
                leaf cisco {
                  type empty;
                  description
                    "Checkpoint NSF restart";
                }
              }
            }
          }
          leaf lsp-check-interval {
            type uint32 {
              range "10..65535" {
                description
                  "LSP checksum check interval time in seconds";
              }
            }
            description
              "Set LSP checksum check interval";
          }
          container lsp-check-interval-levels {
            description
              "Set LSP check interval for one level only";
            list lsp-check-interval-level {
              key "level-number";
              description
                "Set LSP check interval for one level only";
              leaf level-number {
                type uint32 {
                  range "1..2" {
                    description
                      "Level";
                  }
                }
                description
                  "Level";
              }
              leaf lsp-check-interval {
                type uint32 {
                  range "10..65535" {
                    description
                      "LSP checksum check interval time in seconds";
                  }
                }
                mandatory true;
                description
                  "LSP checksum check interval time in seconds";
              }
            }
          }
          container lsp-gen-interval {
            description
              "System and Pseudonode LSP generation scheduling parameters";
            leaf initial-wait {
              type uint32 {
                range "0..120000" {
                  description
                    "Delay in milliseconds";
                }
              }
              description
                "Initial delay before generating an LSP [50]";
            }
            leaf secondary-wait {
              type uint32 {
                range "0..120000" {
                  description
                    "Delay in milliseconds";
                }
              }
              description
                "Secondary delay before generating an LSP [200]";
            }
            leaf maximum-wait {
              type uint32 {
                range "0..120000" {
                  description
                    "Delay in milliseconds";
                }
              }
              description
                "Maximum delay before generating an LSP [5000]";
            }
          }
          container lsp-gen-interval-levels {
            description
              "Set LSP generation interval for one level only";
            list lsp-gen-interval-level {
              must "initial-wait or secondary-wait or maximum-wait";
              key "level-number";
              description
                "Set LSP generation interval for one level only";
              leaf level-number {
                type uint32 {
                  range "1..2" {
                    description
                      "Level";
                  }
                }
                description
                  "Level";
              }
              leaf initial-wait {
                type uint32 {
                  range "0..120000" {
                    description
                      "Delay in milliseconds";
                  }
                }
                description
                  "Initial delay before generating an LSP [50]";
              }
              leaf secondary-wait {
                type uint32 {
                  range "0..120000" {
                    description
                      "Delay in milliseconds";
                  }
                }
                description
                  "Secondary delay before generating an LSP [200]";
              }
              leaf maximum-wait {
                type uint32 {
                  range "0..120000" {
                    description
                      "Delay in milliseconds";
                  }
                }
                description
                  "Maximum delay before generating an LSP [5000]";
              }
            }
          }
          container adjacency {
            description
              "ISIS adjacency bring up";
            container stagger {
              presence "Stagger ISIS adjacency bring up";
              description
                "Stagger ISIS adjacency bring up";
              leaf initial-neighbors {
                type uint32 {
                  range "2..65000" {
                    description
                      "Initial number of neighbors to bring up (default 2)";
                  }
                }
                must "../max-neighbors";
                description
                  "Initial number of neighbors to bring up (default 2)";
              }
              leaf max-neighbors {
                type uint32 {
                  range "2..65000" {
                    description
                      "Maximum simultaneous neighbors to bring up (default 64)";
                  }
                }
                must "../initial-neighbors";
                description
                  "Maximum simultaneous neighbors to bring up (default 64)";
              }
            }
          }
          container hostname {
            description
              "Dynamic hostname resolution for show/debug output";
            container dynamic {
              description
                "Dynamic hostname resolution";
              leaf disable {
                type empty;
                description
                  "Disable dynamic hostname resolution";
              }
            }
          }
          container trace {
            description
              "Set trace buffer parameters";
            container trace-option {
              must "detailed or standard or severe or hello or startup or config-number or lspgen or adj or spf or sr or rib or te or update or flood-speed or flood-speed-detail or pkt";
              presence "Set trace buffer parameters";
              description
                "Set trace buffer parameters";
              leaf detailed {
                type uint32 {
                  range "1..1000000" {
                    description
                      "Maximum number of trace entries";
                  }
                }
                description
                  "Buffer size for detailed traces";
              }
              leaf standard {
                type uint32 {
                  range "1..1000000" {
                    description
                      "Maximum number of trace entries";
                  }
                }
                description
                  "Buffer size for standard traces";
              }
              leaf severe {
                type uint32 {
                  range "1..1000000" {
                    description
                      "Maximum number of trace entries";
                  }
                }
                description
                  "Buffer size for severe traces";
              }
              leaf hello {
                type uint32 {
                  range "1..1000000" {
                    description
                      "Maximum number of trace entries";
                  }
                }
                description
                  "Buffer size for hello traces";
              }
              leaf startup {
                type uint32 {
                  range "1..1000000" {
                    description
                      "Maximum number of trace entries";
                  }
                }
                description
                  "Buffer size for startup traces";
              }
              leaf config-number {
                type uint32 {
                  range "1..1000000" {
                    description
                      "Maximum number of trace entries";
                  }
                }
                description
                  "Buffer size for config traces";
              }
              leaf lspgen {
                type uint32 {
                  range "1..1000000" {
                    description
                      "Maximum number of trace entries";
                  }
                }
                description
                  "Buffer size for lspgen traces";
              }
              leaf adj {
                type uint32 {
                  range "1..1000000" {
                    description
                      "Maximum number of trace entries";
                  }
                }
                description
                  "Buffer size for adj traces";
              }
              leaf spf {
                type uint32 {
                  range "1..1000000" {
                    description
                      "Maximum number of trace entries";
                  }
                }
                description
                  "Buffer size for spf traces";
              }
              leaf sr {
                type uint32 {
                  range "1..1000000" {
                    description
                      "Maximum number of trace entries";
                  }
                }
                description
                  "Buffer size for sr traces";
              }
              leaf rib {
                type uint32 {
                  range "1..1000000" {
                    description
                      "Maximum number of trace entries";
                  }
                }
                description
                  "Buffer size for rib traces";
              }
              leaf te {
                type uint32 {
                  range "1..1000000" {
                    description
                      "Maximum number of trace entries";
                  }
                }
                description
                  "Buffer size for te traces";
              }
              leaf update {
                type uint32 {
                  range "1..1000000" {
                    description
                      "Maximum number of trace entries";
                  }
                }
                description
                  "Buffer size for update traces";
              }
              leaf flood-speed {
                type uint32 {
                  range "1..1000000" {
                    description
                      "Maximum number of trace entries";
                  }
                }
                description
                  "Buffer size for flood-speed traces";
              }
              leaf flood-speed-detail {
                type uint32 {
                  range "1..1000000" {
                    description
                      "Maximum number of trace entries";
                  }
                }
                description
                  "Buffer size for flood-speed-detail traces";
              }
              leaf pkt {
                type uint32 {
                  range "1..1000000" {
                    description
                      "Maximum number of trace entries";
                  }
                }
                description
                  "Buffer size for pkt traces";
              }
            }
            leaf mode {
              type enumeration {
                enum "off" {
                  value 0;
                  description
                    "No tracing";
                }
                enum "basic" {
                  value 1;
                  description
                    "Basic tracing (less overhead)";
                }
                enum "enhanced" {
                  value 2;
                  description
                    "Enhanced tracing (more overhead)";
                }
              }
              description
                "Set tracing type";
            }
          }
          leaf is-type {
            type enumeration {
              enum "level-1" {
                value 1;
                description
                  "Act as a station router only";
              }
              enum "level-2-only" {
                value 2;
                description
                  "Act as an area router only";
              }
              enum "level-1-2" {
                value 3;
                description
                  "Act as both a station router and an area router";
              }
            }
            description
              "Area type (level)";
          }
          container multi-part-tlv {
            description
              "Multi-part TLV configuration";
            container disable {
              presence "Disable advertising multi-part TLVs";
              description
                "Disable advertising multi-part TLVs";
              leaf neighbor {
                type empty;
                description
                  "Disable advertisement of multi-part neighbor TLVs";
              }
              leaf prefix-tlvs {
                type empty;
                description
                  "Disable advertisement of multi-part prefix TLVs";
              }
              leaf router-capability {
                type empty;
                description
                  "Disable advertisement of multi-part router capability TLVs";
              }
            }
            container disable-levels {
              description
                "Disable advertising multi-part TLVs for one level only";
              list disable-level {
                key "level-number";
                description
                  "Disable advertising multi-part TLVs for one level only";
                leaf level-number {
                  type uint32 {
                    range "1..2" {
                      description
                        "Level";
                    }
                  }
                  description
                    "Level";
                }
                leaf neighbor {
                  type empty;
                  description
                    "Disable advertisement of multi-part neighbor TLVs";
                }
                leaf prefix-tlvs {
                  type empty;
                  description
                    "Disable advertisement of multi-part prefix TLVs";
                }
                leaf router-capability {
                  type empty;
                  description
                    "Disable advertisement of multi-part router capability TLVs";
                }
              }
            }
          }
          container log {
            description
              "Enable logging";
            container adjacency {
              description
                "Enable logging of adjacency state";
              leaf changes {
                type empty;
                description
                  "Enable logging adjacency state changes";
              }
            }
            container pdu {
              description
                "Enable PDU logging";
              leaf drops {
                type empty;
                description
                  "Enable logging PDU drops";
              }
            }
            container format {
              description
                "Select log message format";
              leaf brief {
                type empty;
                description
                  "Don't add additional information to ISIS log messages";
              }
            }
            container sizes {
              description
                "Set size of the log buffer";
              list size {
                key "log-type";
                description
                  "Set size of the log buffer";
                leaf log-type {
                  type enumeration {
                    enum "adjacency" {
                      value 0;
                      description
                        "Adjacency log";
                    }
                    enum "database" {
                      value 1;
                      description
                        "Database log";
                    }
                    enum "error" {
                      value 2;
                      description
                        "Error log";
                    }
                    enum "lsp" {
                      value 3;
                      description
                        "LSP log";
                    }
                    enum "microloop-avoidance" {
                      value 4;
                      description
                        "Microloop-avoidance log";
                    }
                    enum "route" {
                      value 5;
                      description
                        "Route log";
                    }
                    enum "spf" {
                      value 6;
                      description
                        "SPF log";
                    }
                  }
                  description
                    "Log type";
                }
                leaf size-number {
                  type uint32 {
                    range "20..50000" {
                      description
                        "Maximum number of log entries";
                    }
                  }
                  mandatory true;
                  description
                    "Maximum number of log entries";
                }
              }
            }
          }
          container lsp-password {
            description
              "Configure the area password";
            container accept {
              description
                "Use password for incoming authentication only";
              leaf encrypted {
                type xr:Proprietary-password;
                description
                  "Specifies a password will follow";
              }
            }
            container accept-levels {
              description
                "Set lsp-password for one level only";
              list accept-level {
                key "level-number";
                description
                  "Set lsp-password for one level only";
                leaf level-number {
                  type uint32 {
                    range "1..2" {
                      description
                        "Set lsp-password for LSPs/SNPs at this level only";
                    }
                  }
                  description
                    "Set lsp-password for LSPs/SNPs at this level only";
                }
                leaf encrypted {
                  type xr:Proprietary-password;
                  mandatory true;
                  description
                    "Specifies a password will follow";
                }
              }
            }
            container lsp-password-option {
              description
                "lsp-password-option";
              choice LSP-PASSWORD-OPTION {
                description
                  "lsp-password-option";
                case TEXT {
                  container text {
                    presence "Use cleartext password authentication";
                    description
                      "Use cleartext password authentication";
                    uses PASSWORD-OPTIONS;
                  }
                }
                case HMAC-MD5 {
                  container hmac-md5 {
                    presence "Use HMAC-MD5 authentication";
                    description
                      "Use HMAC-MD5 authentication";
                    uses PASSWORD-OPTIONS;
                  }
                }
                case KEYCHAIN {
                  container keychain {
                    presence "Specifies a Key Chain name will follow";
                    description
                      "Specifies a Key Chain name will follow";
                    leaf keychain-name {
                      type string {
                        length "1..1024" {
                          description
                            "The Key Chain name";
                        }
                      }
                      mandatory true;
                      description
                        "Specifies a Key Chain name will follow";
                    }
                    uses SNP;
                  }
                }
              }
            }
          }
          container lsp-password-levels {
            description
              "Configure the area password";
            list lsp-password-level {
              must "text or hmac-md5 or keychain";
              key "level-number";
              description
                "Configure the area password";
              leaf level-number {
                type uint32 {
                  range "1..2" {
                    description
                      "Level";
                  }
                }
                description
                  "Level";
              }
              choice LSP-PASSWORD-LEVEL {
                description
                  "lsp password level";
                case TEXT {
                  container text {
                    presence "Use cleartext password authentication";
                    description
                      "Use cleartext password authentication";
                    uses PASSWORD-OPTIONS;
                  }
                }
                case HMAC-MD5 {
                  container hmac-md5 {
                    presence "Use HMAC-MD5 authentication";
                    description
                      "Use HMAC-MD5 authentication";
                    uses PASSWORD-OPTIONS;
                  }
                }
                case KEYCHAIN {
                  container keychain {
                    presence "Specifies a Key Chain name will follow";
                    description
                      "Specifies a Key Chain name will follow";
                    leaf keychain-name {
                      type string {
                        length "1..1024" {
                          description
                            "The Key Chain name";
                        }
                      }
                      mandatory true;
                      description
                        "Specifies a Key Chain name will follow";
                    }
                    uses SNP;
                  }
                }
              }
            }
          }
          container authentication-check {
            description
              "Check authentication type and key of isis PDUs";
            leaf disable {
              type empty;
              description
                "Disable authentication check";
            }
          }
          container iid {
            description
              "ISIS instance-id";
            leaf disable {
              type empty;
              description
                "Disable instance-id";
            }
          }
          container mpls {
            description
              "Configure MPLS routing protocol parameters";
            container ldp {
              description
                "Configure LDP parameters";
              container sync {
                presence "Configure LDP ISIS synchronization";
                description
                  "Configure LDP ISIS synchronization";
                leaf level {
                  type uint32 {
                    range "1..2" {
                      description
                        "Set LDP synchronization at this level only";
                    }
                  }
                  description
                    "Set LDP synchronization for one level only";
                }
              }
            }
          }
          leaf vrf-context {
            type string {
              length "1..32" {
                description
                  "VRF name";
              }
            }
            description
              "VRF context for this ISIS process";
          }
          container protocol {
            description
              "Protocol";
            leaf shutdown {
              type empty;
              description
                "Protocol Shutdown. ISIS will set overload-bit and isolate itself by not forming adjacencies.";
            }
          }
          container min-lsp-arrivaltime {
            description
              "Set minimum arrival time of incoming LSPs";
            leaf initial-wait {
              type uint32 {
                range "0..120000" {
                  description
                    "Delay in milliseconds";
                }
              }
              description
                "Initial delay expected to take since last LSP [50]";
            }
            leaf secondary-wait {
              type uint32 {
                range "0..120000" {
                  description
                    "Delay in milliseconds";
                }
              }
              description
                "Secondary delay expected to take since last LSP [200]";
            }
            leaf maximum-wait {
              type uint32 {
                range "0..120000" {
                  description
                    "Delay in milliseconds";
                }
              }
              description
                "Maximum delay expected to take since last LSP [5000]";
            }
          }
          container min-lsp-arrivaltime-levels {
            description
              "Set LSP arrival time for one level only";
            list min-lsp-arrivaltime-level {
              must "initial-wait or secondary-wait or maximum-wait";
              key "level-number";
              description
                "Set LSP arrival time for one level only";
              leaf level-number {
                type uint32 {
                  range "1..2" {
                    description
                      "Level";
                  }
                }
                description
                  "Level";
              }
              leaf initial-wait {
                type uint32 {
                  range "0..120000" {
                    description
                      "Delay in milliseconds";
                  }
                }
                description
                  "Initial delay expected to take since last LSP [50]";
              }
              leaf secondary-wait {
                type uint32 {
                  range "0..120000" {
                    description
                      "Delay in milliseconds";
                  }
                }
                description
                  "Secondary delay expected to take since last LSP [200]";
              }
              leaf maximum-wait {
                type uint32 {
                  range "0..120000" {
                    description
                      "Delay in milliseconds";
                  }
                }
                description
                  "Maximum delay expected to take since last LSP [5000]";
              }
            }
          }
          container max-metric {
            presence "Signal other routers to use us as transit option of last resort";
            description
              "Signal other routers to use us as transit option of last resort";
            container on-startup {
              description
                "Set maximum metric temporarily after reboot";
              choice ON-STARTUP {
                description
                  "Set maximum metric temporarily after reboot";
                case ADVERTISE {
                  container advertise {
                    presence "Set maximum metric temporarily after reboot";
                    description
                      "Set maximum metric temporarily after reboot";
                    leaf advertise-number {
                      type uint32 {
                        range "5..86400" {
                          description
                            "Time in seconds to advertise maximum metric after reboot";
                        }
                      }
                      mandatory true;
                      description
                        "Time in seconds to advertise maximum metric after reboot";
                    }
                  }
                }
                case WAIT-FOR-BGP {
                  container wait-for-bgp {
                    presence "Set maximum metric on startup until BGP signals convergence, or timeout";
                    description
                      "Set maximum metric on startup until BGP signals convergence, or timeout";
                  }
                }
              }
            }
            uses MAX-METRIC;
          }
          container max-metric-levels {
            description
              "Set maximum metric for one level only";
            list max-metric-level {
              key "level-number";
              description
                "Set maximum metric for one level only";
              leaf level-number {
                type uint32 {
                  range "1..2" {
                    description
                      "Level";
                  }
                }
                description
                  "Level";
              }
              container on-startup {
                description
                  "Set maximum metric temporarily after reboot";
                choice ON-STARTUP {
                  description
                    "Set maximum metric temporarily after reboot";
                  case ADVERTISE {
                    container advertise {
                      presence "Set maximum metric temporarily after reboot";
                      description
                        "Set maximum metric temporarily after reboot";
                      leaf advertise-number {
                        type uint32 {
                          range "5..86400" {
                            description
                              "Time in seconds to advertise maximum metric after reboot";
                          }
                        }
                        mandatory true;
                        description
                          "Time in seconds to advertise maximum metric after reboot";
                      }
                    }
                  }
                  case WAIT-FOR-BGP {
                    container wait-for-bgp {
                      presence "Set maximum metric on startup until BGP signals convergence, or timeout";
                      description
                        "Set maximum metric on startup until BGP signals convergence, or timeout";
                    }
                  }
                }
              }
              uses MAX-METRIC;
            }
          }
          container distribute {
            description
              "Distribute routing information to external services";

            grouping DISTRIBUTE {
              description
                "distribute";
              leaf level {
                type uint32 {
                  range "1..2" {
                    description
                      "Level";
                  }
                }
                description
                  "Set distribution for one level only";
              }
              leaf instance-id {
                type uint32 {
                  range "32..4294967295" {
                    description
                      "Instance ID";
                  }
                }
                description
                  "Set distribution process instance identifier";
              }
              leaf throttle {
                type uint32 {
                  range "1..20" {
                    description
                      "Seconds";
                  }
                }
                description
                  "Set throttle update in seconds";
              }
              leaf exclude-interarea {
                type empty;
                description
                  "Don't distribute ISIS inter-area prefixes";
              }
              leaf exclude-external {
                type empty;
                description
                  "Don't distribute ISIS external prefixes";
              }
              leaf route-policy {
                type xr:Route-policy-name;
                description
                  "Distribute prefixes based on a route policy";
              }
            }
            container link-state {
              presence "Distribute the link-state database to external services";
              description
                "Distribute the link-state database to external services";
              uses DISTRIBUTE;
            }
          }
          leaf max-lsp-lifetime {
            type uint32 {
              range "1..65535" {
                description
                  "Maximum LSP lifetime in seconds";
              }
            }
            description
              "Set maximum LSP lifetime";
          }
          container max-lsp-lifetime-levels {
            description
              "Set LSP regeneration interval for one level only";
            list max-lsp-lifetime-level {
              key "level-number";
              description
                "Set LSP regeneration interval for one level only";
              leaf level-number {
                type uint32 {
                  range "1..2" {
                    description
                      "Level";
                  }
                }
                description
                  "Level";
              }
              leaf max-lsp-lifetime {
                type uint32 {
                  range "1..65535" {
                    description
                      "Maximum LSP lifetime in seconds";
                  }
                }
                mandatory true;
                description
                  "Set maximum LSP lifetime";
              }
            }
          }
          leaf instance-id {
            type uint32 {
              range "1..65535" {
                description
                  "Instance id";
              }
            }
            description
              "ISIS-MI instance id";
          }
          leaf hello-padding {
            type enumeration {
              enum "disable" {
                value 0;
                description
                  "Disable hello-padding";
              }
              enum "sometimes" {
                value 1;
                description
                  "Enable hello-padding during adjacency formation only";
              }
              enum "adaptive" {
                value 3;
                description
                  "Enable hello-padding till neighbor confirms adjacecency up";
              }
            }
            description
              "Add padding to IS-IS hello packets";
          }
          leaf extended-sequence-numbers {
            type enumeration {
              enum "send" {
                value 1;
                description
                  "Send extended sequence numbers when cryptographic authentication is enabled";
              }
              enum "always-send" {
                value 2;
                description
                  "Send extended sequence numbers in all packets";
              }
              enum "verify" {
                value 3;
                description
                  "Send and verify extended sequence numbers when cryptographic authentication is enabled";
              }
            }
            description
              "RFC 7602 Extended Sequence Numbers";
          }
          leaf triggers {
            type string {
              length "1..1024" {
                description
                  "<adj>/<LSP>/<routes>";
              }
            }
            description
              "Set logging triggers for performance testing";
          }
          container lsp-fast-flooding {
            presence "Enable and enter LSP fast flooding submode";
            description
              "Enable and enter LSP fast flooding submode";
            leaf max-lsp-tx {
              type uint32 {
                range "33..5000" {
                  description
                    "Maximum LSP transmit rate (LSP per second), default is 1000";
                }
              }
              description
                "Set maximum LSP transmit rate";
            }
            leaf remote-psnp-delay {
              type uint32 {
                range "1..5000" {
                  description
                    "remote PSNP delay (milliseconds), default is 500";
                }
              }
              description
                "Set remote PSNP delay";
            }
          }
          leaf psnp-interval {
            type uint32 {
              range "1..5000" {
                description
                  "Longest wait to send PSNP (milliseconds), default is 50";
              }
            }
            description
              "Longest wait to send PSNP";
          }
          container nets {
            description
              "A Network Entity Title (NET) for this process";
            list net {
              key "net-id";
              description
                "A Network Entity Title (NET) for this process";
              leaf net-id {
                type string {
                  length "1..1024" {
                    description
                      "NET (XX.XXXX. ... .XXXX.XX)";
                  }
                }
                description
                  "NET (XX.XXXX. ... .XXXX.XX)";
              }
            }
          }
          container affinity-maps {
            description
              "Affinity map configuration";
            list affinity-map {
              key "affinity-attribute-name";
              description
                "Affinity map configuration";
              leaf affinity-attribute-name {
                type xr:Cisco-ios-xr-string {
                  length "1..32" {
                    description
                      "Affinity attribute name";
                  }
                }
                description
                  "Affinity attribute name";
              }
              leaf bit-position {
                type uint32 {
                  range "0..255" {
                    description
                      "Bit position";
                  }
                }
                mandatory true;
                description
                  "Bit position for affinity attribute value";
              }
            }
          }
          leaf nsr {
            type empty;
            description
              "Enable NSR";
          }
          leaf nsr-restart-time {
            type uint32 {
              range "60..300" {
                description
                  "Maximum time allowed to resync following NSR, default is 60";
              }
            }
            description
              "Maximum time allowed to resync following NSR";
          }
          container ignore-lsp-errors {
            description
              "Ignore LSPs with bad checksums instead of purging the LSP";
            leaf disable {
              type empty;
              description
                "Purge LSPs with failed checksums";
            }
          }
          container purge-transmit {
            description
              "Control TLVs permitted in purge LSP";
            container strict {
              presence "Only authentication TLV is allowed";
              description
                "Only authentication TLV is allowed";
              leaf strict-value {
                type enumeration {
                  enum "level-1" {
                    value 1;
                    description
                      "Apply for Level-1 only";
                  }
                  enum "level-2" {
                    value 2;
                    description
                      "Apply for Level-2 only";
                  }
                }
                description
                  "Only authentication TLV is allowed";
              }
            }
          }
          container algorithm {
            description
              "Standard algorithm definition";
            container zero {
              presence "Algorithm number";
              description
                "Algorithm number";

              grouping MAXIMUM-PATHS {
                description
                  "Maximum number of active parallel paths per route";
                container maximum-paths {
                  description
                    "Maximum number of active parallel paths per route";
                  choice MAXIMUM-PATHS {
                    description
                      "Maximum number of active parallel paths per route";
                    case NUMBER-OF-PATHS {
                      leaf number-of-paths {
                        type uint32 {
                          range "1..64" {
                            description
                              "Number of paths";
                          }
                        }
                        description
                          "Number of paths";
                      }
                    }
                    case ROUTE-POLICY {
                      leaf route-policy {
                        type xr:Route-policy-name;
                        description
                          "Filter routes based on a route policy";
                      }
                    }
                  }
                }
              }
              container address-families {
                description
                  "Enter the IS-IS Flex-Algo address-family configuration submode";
                list address-family {
                  key "af-name saf-name";
                  description
                    "Enter the IS-IS Flex-Algo address-family configuration submode";
                  leaf af-name {
                    type enumeration {
                      enum "ipv4" {
                        value 0;
                        description
                          "IPv4 address family";
                      }
                      enum "ipv6" {
                        value 1;
                        description
                          "IPv6 address family";
                      }
                    }
                    description
                      "af-name";
                  }
                  leaf saf-name {
                    type enumeration {
                      enum "unicast" {
                        value 0;
                        description
                          "unicast topology";
                      }
                      enum "multicast" {
                        value 1;
                        description
                          "multicast topology";
                      }
                    }
                    description
                      "saf-name";
                  }
                  uses MAXIMUM-PATHS;
                }
              }
            }
          }
          container srlg {
            presence "ISIS SRLG submode";
            description
              "ISIS SRLG submode";
            leaf admin-weight {
              type uint32 {
                range "0..16777215" {
                  description
                    "Value added to link admin-weight during SRLG-aware path computation";
                }
              }
              description
                "Administrative weight for all SRLGs, default is 1000";
            }
            container names {
              description
                "SRLG Name";
              list name {
                key "srlg-name";
                description
                  "SRLG Name";
                leaf srlg-name {
                  type xr:Cisco-ios-xr-string {
                    length "1..64" {
                      description
                        "SRLG Name";
                    }
                  }
                  description
                    "SRLG Name";
                }
                leaf admin-weight {
                  type uint32 {
                    range "0..16777215" {
                      description
                        "Value added to link admin-weight during SRLG-aware path computation";
                    }
                  }
                  description
                    "Administrative weight: default inherited from the global admin-weight";
                }
                container static {
                  description
                    "Configure static SRLG under name";
                  container ipv4 {
                    description
                      "IPv4 address";
                    container addresses {
                      description
                        "IPv4 address";
                      list addresss {
                        key "local-end-point remote-end-point";
                        description
                          "IPv4 address";
                        leaf local-end-point {
                          type inet:ipv4-address-no-zone;
                          description
                            "IPv4 address of local end-point of the link";
                        }
                        leaf remote-end-point {
                          type inet:ipv4-address-no-zone;
                          description
                            "IPv4 address of remote end-point of the link";
                        }
                      }
                    }
                  }
                }
              }
            }
          }
          container attestation {
            presence "ISIS Attestation submode";
            description
              "ISIS Attestation submode";
            container application {
              description
                "Application";
              container flex-algo {
                presence "Flexible Algorithm application";
                description
                  "Flexible Algorithm application";
                container trust-vector {
                  presence "Trust Vector Configuration";
                  description
                    "Trust Vector Configuration";
                  container boot-integrity-passed {
                    description
                      "Boot Integrity Passed";
                    leaf affinity {
                      type string {
                        length "1..32" {
                          description
                            "Affinity name";
                        }
                      }
                      description
                        "Affinity configuration";
                    }
                  }
                  container boot-integrity-failed {
                    description
                      "Boot Integrity Failed";
                    leaf affinity {
                      type string {
                        length "1..32" {
                          description
                            "Affinity name";
                        }
                      }
                      description
                        "Affinity configuration";
                    }
                  }
                  container failures-found {
                    description
                      "Failures Found";
                    leaf affinity {
                      type string {
                        length "1..32" {
                          description
                            "Affinity name";
                        }
                      }
                      description
                        "Affinity configuration";
                    }
                  }
                }
              }
              container traffic-engineering {
                presence "Traffic-engineering application";
                description
                  "Traffic-engineering application";
                container trust-vector {
                  presence "Trust Vector Configuration";
                  description
                    "Trust Vector Configuration";
                  container boot-integrity-passed {
                    description
                      "Boot Integrity Passed";
                    leaf affinity {
                      type string {
                        length "1..32" {
                          description
                            "Affinity name";
                        }
                      }
                      description
                        "Affinity configuration";
                    }
                  }
                  container boot-integrity-failed {
                    description
                      "Boot Integrity Failed";
                    leaf affinity {
                      type string {
                        length "1..32" {
                          description
                            "Affinity name";
                        }
                      }
                      description
                        "Affinity configuration";
                    }
                  }
                  container failures-found {
                    description
                      "Failures Found";
                    leaf affinity {
                      type string {
                        length "1..32" {
                          description
                            "Affinity name";
                        }
                      }
                      description
                        "Affinity configuration";
                    }
                  }
                }
              }
            }
          }
          container interfaces {
            description
              "Enter the IS-IS interface configuration submode";
            list interface {
              key "interface-name";
              description
                "Enter the IS-IS interface configuration submode";

              grouping HELLO-PASSWORD-OPTIONS {
                description
                  "HELLO-PASSWORD-OPTIONS";
                container hello-password-options {
                  description
                    "hello-password-options";
                  leaf encrypted {
                    type xr:Proprietary-password;
                    mandatory true;
                    description
                      "Specifies a password will follow";
                  }
                  uses IIH;
                }
              }

              grouping IIH {
                description
                  "Do not require authentication of incoming IIHs";
                leaf send-only {
                  type empty;
                  description
                    "Do not require authentication of incoming IIHs";
                }
              }
              leaf interface-name {
                type xr:Interface-name;
                description
                  "Interface to configure";
              }
              container static-neighbor {
                presence "Configre static neighbor";
                description
                  "Configre static neighbor";
                leaf system-id {
                  type xr:Cisco-ios-xr-string {
                    length "1..1024" {
                      description
                        "System ID (XXXX.XXXX.XXXX)";
                    }
                  }
                  description
                    "ISIS System-id of the static neighbor";
                }
                container remote {
                  description
                    "Remote address";
                  container ipv4 {
                    description
                      "IPv4 address";
                    leaf address {
                      type inet:ipv4-address-no-zone;
                      description
                        "Remote IPv4 addres";
                    }
                  }
                  container ipv6 {
                    description
                      "IPv6 address";
                    leaf address {
                      type inet:ipv6-address-no-zone;
                      description
                        "Remote IPv6 address";
                    }
                  }
                }
                leaf affinity {
                  type xr:Cisco-ios-xr-string {
                    length "1..32" {
                      description
                        "Affinity name";
                    }
                  }
                  description
                    "Affinity to advertise";
                }
                leaf log-advertisement-changes {
                  type empty;
                  description
                    "Enable logging static neighbor advertisement changes";
                }
                container advertise {
                  description
                    "Configure conditional static neighbor advertisement";
                  leaf route-policy {
                    type xr:Route-policy-name;
                    description
                      "Advertise static neighbor based on a route policy";
                  }
                }
              }
              container mesh-group {
                description
                  "Set IS-IS mesh group";
                choice MESH-GROUP {
                  description
                    "Set IS-IS mesh group";
                  case MESH-GROUP-NUMBER {
                    leaf mesh-group-number {
                      type uint32 {
                        range "1..4294967295" {
                          description
                            "Mesh group number";
                        }
                      }
                      description
                        "Mesh group number";
                    }
                  }
                  case BLOCKED {
                    leaf blocked {
                      type empty;
                      description
                        "Block LSPs on this interface";
                    }
                  }
                }
              }
              leaf state {
                type enumeration {
                  enum "passive" {
                    value 2;
                    description
                      "Do not establish adjacencies over this interface";
                  }
                  enum "suppressed" {
                    value 1;
                    description
                      "Do not advertise connected prefixes of this interface";
                  }
                  enum "shutdown" {
                    value 0;
                    description
                      "Shutdown IS-IS on this interface";
                  }
                }
                description
                  "Do not establish adjacencies over this interface";
              }
              leaf circuit-type {
                type enumeration {
                  enum "level-1" {
                    value 1;
                    description
                      "Form level-1 adjacencies only";
                  }
                  enum "level-2-only" {
                    value 2;
                    description
                      "Form level-2 adjacencies only";
                  }
                  enum "level-1-2" {
                    value 3;
                    description
                      "Form level-1 and level-2 adjacencies";
                  }
                }
                description
                  "Configure circuit type for interface";
              }
              leaf csnp-interval {
                type uint32 {
                  range "0..65535" {
                    description
                      "CSNP interval value (seconds)";
                  }
                }
                description
                  "Set CSNP interval";
              }
              container csnp-interval-levels {
                description
                  "Set the CSNP interval only at the supplied level";
                list csnp-interval-level {
                  key "level-number";
                  description
                    "Set the CSNP interval only at the supplied level";
                  leaf level-number {
                    type uint32 {
                      range "1..2" {
                        description
                          "Set the CSNP interval only at this level";
                      }
                    }
                    description
                      "Set the CSNP interval only at this level";
                  }
                  leaf csnp-interval {
                    type uint32 {
                      range "0..65535" {
                        description
                          "CSNP interval value (seconds)";
                      }
                    }
                    mandatory true;
                    description
                      "Set CSNP interval";
                  }
                }
              }
              leaf hello-padding {
                type enumeration {
                  enum "always" {
                    value 2;
                    description
                      "Always enable hello-padding";
                  }
                  enum "disable" {
                    value 0;
                    description
                      "Disable hello-padding";
                  }
                  enum "sometimes" {
                    value 1;
                    description
                      "Enable hello-padding during adjacency formation only";
                  }
                  enum "adaptive" {
                    value 3;
                    description
                      "Enable hello-padding till neighbor confirms adjacency up";
                  }
                }
                description
                  "Add padding to IS-IS hello packets";
              }
              container hello-padding-levels {
                description
                  "Set hello-padding for one level only";
                list hello-padding-level {
                  key "level-number";
                  description
                    "Set hello-padding for one level only";
                  leaf level-number {
                    type uint32 {
                      range "1..2" {
                        description
                          "Set hello-padding for IIHs at this level only";
                      }
                    }
                    description
                      "Set hello-padding for IIHs at this level only";
                  }
                  leaf hello-padding {
                    type enumeration {
                      enum "always" {
                        value 2;
                        description
                          "Always enable hello-padding";
                      }
                      enum "disable" {
                        value 0;
                        description
                          "Disable hello-padding";
                      }
                      enum "sometimes" {
                        value 1;
                        description
                          "Enable hello-padding during adjacency formation only";
                      }
                      enum "adaptive" {
                        value 3;
                        description
                          "Enable hello-padding till neighbor confirms adjacency up";
                      }
                    }
                    mandatory true;
                    description
                      "hello-padding";
                  }
                }
              }
              leaf hello-interval {
                type uint32 {
                  range "1..65535" {
                    description
                      "Hello interval value";
                  }
                }
                description
                  "Set Hello interval in seconds";
              }
              container hello-interval-levels {
                description
                  "Set hello-interval for one level only";
                list hello-interval-level {
                  key "level-number";
                  description
                    "Set hello-interval for IIHs at this level only";
                  leaf level-number {
                    type uint32 {
                      range "1..2" {
                        description
                          "Set hello-interval for IIHs at this level only";
                      }
                    }
                    description
                      "Set hello-interval for IIHs at this level only";
                  }
                  leaf hello-interval {
                    type uint32 {
                      range "1..65535" {
                        description
                          "Hello interval value";
                      }
                    }
                    mandatory true;
                    description
                      "Set Hello interval in seconds";
                  }
                }
              }
              leaf hello-multiplier {
                type uint32 {
                  range "3..1000" {
                    description
                      "Hello multiplier value";
                  }
                }
                description
                  "Set multiplier for Hello holding time";
              }
              container hello-multiplier-levels {
                description
                  "Set hello-multiplier for one level only";
                list hello-multiplier-level {
                  key "level-number";
                  description
                    "Set hello-multiplier for one level only";
                  leaf level-number {
                    type uint32 {
                      range "1..2" {
                        description
                          "Set hello-multiplier for IIHs at this level only";
                      }
                    }
                    description
                      "Set hello-multiplier for IIHs at this level only";
                  }
                  leaf hello-multiplier {
                    type uint32 {
                      range "3..1000" {
                        description
                          "Hello multiplier value";
                      }
                    }
                    mandatory true;
                    description
                      "Set multiplier for Hello holding time";
                  }
                }
              }
              leaf lsp-interval {
                type uint32 {
                  range "1..4294967295" {
                    description
                      "LSP transmission interval (milliseconds)";
                  }
                }
                description
                  "Set LSP transmission interval";
              }
              container lsp-interval-levels {
                description
                  "Set LSP transmission interval one level only";
                list lsp-interval-level {
                  key "level-number";
                  description
                    "Set LSP transmission interval one level only";
                  leaf level-number {
                    type uint32 {
                      range "1..2" {
                        description
                          "Set LSP transmission interval at this level only";
                      }
                    }
                    description
                      "Set LSP transmission interval at this level only";
                  }
                  leaf lsp-interval {
                    type uint32 {
                      range "1..4294967295" {
                        description
                          "LSP transmission interval (milliseconds)";
                      }
                    }
                    mandatory true;
                    description
                      "Set LSP transmission interval";
                  }
                }
              }
              container hello-password {
                description
                  "Configure the IIH password";
                container accepts {
                  description
                    "Use password for incoming authentication only";
                  leaf encrypted {
                    type xr:Proprietary-password;
                    description
                      "Specifies a password will follow";
                  }
                }
                container accepts-levels {
                  description
                    "Set hello-password for one level only";
                  list accepts-level {
                    key "level-number";
                    description
                      "Set hello-password for one level only";
                    leaf level-number {
                      type uint32 {
                        range "1..2" {
                          description
                            "Set hello-password for IIHs at this level only";
                        }
                      }
                      description
                        "Set hello-password for IIHs at this level only";
                    }
                    leaf encrypted {
                      type xr:Proprietary-password;
                      mandatory true;
                      description
                        "Specifies a password will follow";
                    }
                  }
                }
                container hello-password-options {
                  description
                    "hello-password-options";
                  choice HELLO-PASSWORD-OPTIONS {
                    description
                      "HELLO-PASSWORD-OPTIONS";
                    case TEXT {
                      container text {
                        presence "Use cleartext password authentication";
                        description
                          "Use cleartext password authentication";
                        uses HELLO-PASSWORD-OPTIONS;
                      }
                    }
                    case HMAC-MD5 {
                      container hmac-md5 {
                        presence "Use HMAC-MD5 authentication";
                        description
                          "Use HMAC-MD5 authentication";
                        uses HELLO-PASSWORD-OPTIONS;
                      }
                    }
                    case KEYCHAIN {
                      container keychain {
                        presence "Specifies a Key Chain name will follow";
                        description
                          "Specifies a Key Chain name will follow";
                        leaf keychain-name {
                          type string {
                            length "1..1024" {
                              description
                                "The Key Chain name";
                            }
                          }
                          mandatory true;
                          description
                            "Specifies a Key Chain name will follow";
                        }
                        uses IIH;
                      }
                    }
                  }
                }
              }
              container hello-password-levels {
                description
                  "Set hello-password for one level only";
                list hello-password-level {
                  must "text or hmac-md5 or keychain";
                  key "level-number";
                  description
                    "Set hello-password for one level only";
                  leaf level-number {
                    type uint32 {
                      range "1..2" {
                        description
                          "Set hello-password for IIHs at this level only";
                      }
                    }
                    description
                      "Set hello-password for one level only";
                  }
                  choice HELLO-PASSWORD-LEVEL {
                    description
                      "hello-password-level";
                    case TEXT {
                      container text {
                        presence "Use cleartext password authentication";
                        description
                          "Use cleartext password authentication";
                        uses HELLO-PASSWORD-OPTIONS;
                      }
                    }
                    case HMAC-MD5 {
                      container hmac-md5 {
                        presence "Use HMAC-MD5 authentication";
                        description
                          "Use HMAC-MD5 authentication";
                        uses HELLO-PASSWORD-OPTIONS;
                      }
                    }
                    case KEYCHAIN {
                      container keychain {
                        presence "Specifies a Key Chain name will follow";
                        description
                          "Specifies a Key Chain name will follow";
                        leaf keychain-name {
                          type string {
                            length "1..1024" {
                              description
                                "The Key Chain name";
                            }
                          }
                          mandatory true;
                          description
                            "Specifies a Key Chain name will follow";
                        }
                        uses IIH;
                      }
                    }
                  }
                }
              }
              container lsp {
                description
                  "LSP configuration";
                container fast-flood {
                  description
                    "LSP fast flood configuration";
                  leaf threshold {
                    type uint32 {
                      range "1..4294967295" {
                        description
                          "Number of LSPs to send back to back";
                      }
                    }
                    description
                      "Set LSP transmission fast flood threshold";
                  }
                  container threshold-levels {
                    description
                      "Set lsp fast-flood threshold for this level";
                    list threshold-level {
                      key "level-number";
                      description
                        "Set lsp fast-flood threshold for this level";
                      leaf level-number {
                        type uint32 {
                          range "1..2" {
                            description
                              "Set lsp fast-flood threshold at this level only";
                          }
                        }
                        description
                          "Set lsp fast-flood threshold at this level only";
                      }
                      leaf threshold {
                        type uint32 {
                          range "1..4294967295" {
                            description
                              "Number of LSPs to send back to back";
                          }
                        }
                        mandatory true;
                        description
                          "Set LSP transmission fast flood threshold";
                      }
                    }
                  }
                }
              }
              leaf remote-psnp-delay {
                type uint32 {
                  range "1..5000" {
                    description
                      "remote PSNP delay (milliseconds), default is 500";
                  }
                }
                description
                  "Set remote PSNP delay";
              }
              leaf priority {
                type uint32 {
                  range "0..127" {
                    description
                      "Priority value";
                  }
                }
                description
                  "Set priority for Designated Router election";
              }
              container priority-levels {
                description
                  "Set priority for one level only";
                list priority-level {
                  key "level-number";
                  description
                    "Set priority for one level only";
                  leaf level-number {
                    type uint32 {
                      range "1..2" {
                        description
                          "Set priority for this level only";
                      }
                    }
                    description
                      "Set priority for this level only";
                  }
                  leaf priority {
                    type uint32 {
                      range "0..127" {
                        description
                          "Priority value";
                      }
                    }
                    mandatory true;
                    description
                      "Set priority for Designated Router election";
                  }
                }
              }
              leaf csi {
                if-feature "isis_is_csi_config_supported";
                type empty;
                description
                  "Treat interface as a CSI link";
              }
              leaf point-to-point {
                type empty;
                description
                  "Treat active LAN interface as point-to-point";
              }
              leaf retransmit-interval {
                type uint32 {
                  range "0..65535" {
                    description
                      "(seconds)";
                  }
                }
                description
                  "Interval between retransmissions of the same LSP";
              }
              container retransmit-interval-levels {
                description
                  "Set retransmit-interval for one level only";
                list retransmit-interval-level {
                  key "level-number";
                  description
                    "Set retransmit-interval for one level only";
                  leaf level-number {
                    type uint32 {
                      range "1..2" {
                        description
                          "Set retransmit-interval for LSPs at this level only";
                      }
                    }
                    description
                      "Set retransmit-interval for LSPs at this level only";
                  }
                  leaf retransmit-interval {
                    type uint32 {
                      range "0..65535" {
                        description
                          "(seconds)";
                      }
                    }
                    mandatory true;
                    description
                      "Interval between retransmissions of the same LSP";
                  }
                }
              }
              leaf retransmit-throttle-interval {
                type uint32 {
                  range "0..65535" {
                    description
                      "(milliseconds)";
                  }
                }
                description
                  "Minimum interval betwen retransissions of different LSPs";
              }
              container retransmit-throttle-interval-levels {
                description
                  "Set retransmit-throttle-interval for one level only";
                list retransmit-throttle-interval-level {
                  key "level-number";
                  description
                    "Set retransmit-throttle-interval for one level only";
                  leaf level-number {
                    type uint32 {
                      range "1..2" {
                        description
                          "Set retransmit-throttle-interval at this level only";
                      }
                    }
                    description
                      "Set retransmit-throttle-interval at this level only";
                  }
                  leaf retransmit-throttle-interval {
                    type uint32 {
                      range "0..65535" {
                        description
                          "(milliseconds)";
                      }
                    }
                    mandatory true;
                    description
                      "Minimum interval betwen retransissions of different LSPs";
                  }
                }
              }
              container link-down {
                description
                  "Configure interface down event parameters";
                leaf fast-detect {
                  type empty;
                  description
                    "Enable high priority detection";
                }
              }
              container prefix-attributes {
                when "../interface-name !='Loopback.*'";
                description
                  "Set Prefix Attributes";
                leaf n-flag-clear {
                  type empty;
                  description
                    "Clear N-flag";
                }
                container n-flag-clear-levels {
                  description
                    "Clear N-flag";
                  list n-flag-clear-level {
                    key "level-number";
                    description
                      "Clear N-flag";
                    leaf level-number {
                      type uint32 {
                        range "1..2" {
                          description
                            "Clear N-flag at this level only";
                        }
                      }
                      description
                        "Clear N-flag for this level";
                    }
                  }
                }
                leaf anycast {
                  type empty;
                  description
                    "Prefix has anycast semantics";
                }
                container anycast-levels {
                  description
                    "Prefix has anycast semantics";
                  list anycast-level {
                    key "level-number";
                    description
                      "Prefix has anycast semantics";
                    leaf level-number {
                      type uint32 {
                        range "1..2" {
                          description
                            "Set anycast for this level";
                        }
                      }
                      description
                        "Set anycast at this level only";
                    }
                  }
                }
              }
              container affinity {
                description
                  "Application specific interface affinities";
                container flex-algo {
                  description
                    "Affinities for Flexible Algorithm application";
                  leaf-list flex-algo-argument {
                    type xr:Cisco-ios-xr-string {
                      length "1..32" {
                        description
                          "Affinity names";
                      }
                    }
                    max-elements "32";
                    description
                      "Affinity names";
                  }
                  leaf-list anomaly {
                    type xr:Cisco-ios-xr-string {
                      length "1..32" {
                        description
                          "Affinity names";
                      }
                    }
                    max-elements "32";
                    description
                      "Affinities to advertise when there is a link anomaly";
                  }
                }
              }
              container override {
                description
                  "Override a configuration setting";
                leaf metrics {
                  type enumeration {
                    enum "maximum" {
                      value 16777215;
                      description
                        "Set metric to unreachable value (wide metrics only)";
                    }
                    enum "high" {
                      value 16777214;
                      description
                        "Set metric to highest reachable value";
                    }
                    enum "disabled" {
                      value 0;
                      description
                        "Ignore reverse-metric requests from neighbors";
                    }
                  }
                  description
                    "Override the configured link metrics";
                }
              }
              container delay {
                description
                  "Delay configuration setting";
                container normalize {
                  description
                    "Delay normalization setting";
                  container interval {
                    description
                      "Normalization interval";
                    leaf interval-number {
                      type uint32 {
                        range "1..16777215" {
                          description
                            "Value in microseconds";
                        }
                      }
                      description
                        "Value in microseconds";
                    }
                    leaf offset {
                      type uint32 {
                        range "0..16777215" {
                          description
                            "Value in microseconds";
                        }
                      }
                      must "../interval-number";
                      description
                        "Normalization offset";
                    }
                  }
                }
              }
              leaf extended-sequence-numbers {
                type enumeration {
                  enum "disable" {
                    value 0;
                    description
                      "Do not send or verify extended sequence numbers";
                  }
                  enum "send" {
                    value 1;
                    description
                      "Send extended sequence numbers when cryptographic authentication is enabled";
                  }
                  enum "always-send" {
                    value 2;
                    description
                      "Send extended sequence numbers in all packets";
                  }
                  enum "verify" {
                    value 3;
                    description
                      "Send and verify extended sequence numbers when cryptographic authentication is enabled";
                  }
                }
                description
                  "RFC 7602 Extended Sequence Numbers";
              }
              container mpls {
                description
                  "Configure MPLS routing protocol parameters";
                container ldp {
                  description
                    "Configure LDP parameters";
                  container sync {
                    presence "Configure LDP ISIS synchronization";
                    description
                      "Configure LDP ISIS synchronization";
                    leaf level {
                      type uint32 {
                        range "1..2" {
                          description
                            "Set LDP synchronization at this level only";
                        }
                      }
                      description
                        "Set LDP synchronization for one level only";
                    }
                  }
                }
              }
              leaf disable {
                type empty;
                description
                  "do not form adjacency";
              }
              container disable-levels {
                description
                  "disable one level only";
                list disable-level {
                  key "level-number";
                  description
                    "disable one level only";
                  leaf level-number {
                    type uint32 {
                      range "1..2" {
                        description
                          "disable this level only";
                      }
                    }
                    description
                      "disable this level only";
                  }
                }
              }
              container bfd {
                when
                  "../interface-name !='Loopback.*' or
                   ../interface-name != 'Mgmt.*' or
                   ../interface-name != 'tunnel.*te' or
                   ../interface-name != 'Null.*' or
                   ../interface-name != 'ATM.*'";
                description
                  "Configure BFD parameters";
                container fast-detect {
                  description
                    "Enable Fast detection";
                  leaf ipv4 {
                    type empty;
                    description
                      "Address Family";
                  }
                  leaf ipv6 {
                    type empty;
                    description
                      "Address Family";
                  }
                }
                leaf minimum-interval {
                  type uint32 {
                    range "3..30000" {
                      description
                        "hello interval in milli-seconds";
                    }
                  }
                  description
                    "Hello interval";
                }
                leaf multiplier {
                  type uint32 {
                    range "2..50" {
                      description
                        "Detect multiplier";
                    }
                  }
                  description
                    "Detect multiplier";
                }
              }
              container address-families {
                description
                  "Enter the IS-IS interface address-family configuration submode";

                grouping ISIS-IF-AF {
                  description
                    "ISIS-IF-AF";
                  container metric {
                    description
                      "Configure the metric for interface";
                    choice METRIC {
                      description
                        "Configure the metric for interface";
                      case MAXIMUM {
                        leaf maximum {
                          type empty;
                          description
                            "Maximum wide metric. All routers will exclude this link from their SPF";
                        }
                      }
                      case DEFAULT-METRIC {
                        leaf default-metric {
                          type uint32 {
                            range "1..16777214" {
                              description
                                "Default metric: <1-63> for narrow, <1-16777214> for wide";
                            }
                          }
                          description
                            "Default metric: <1-63> for narrow, <1-16777214> for wide";
                        }
                      }
                    }
                    container fallback {
                      description
                        "Increase the link metric when an event occurs";
                      container bandwidth {
                        description
                          "Increase the link metric when the bandwidth falls below a threshold";
                        container multiplier {
                          description
                            "Multiply the link metric by the following amount";
                          leaf multiplier-number {
                            type uint32 {
                              range "2..100000" {
                                description
                                  "Metric multiplier";
                              }
                            }
                            must "../threshold";
                            description
                              "Metric multiplier";
                          }
                          leaf threshold {
                            type uint32 {
                              range "1..100" {
                                description
                                  "Set metric fallback at this threshold only";
                              }
                            }
                            must "../multiplier-number";
                            description
                              "Threshold interms of percentage of bandwidth";
                          }
                        }
                      }
                      container anomaly {
                        description
                          "Increase the link metric when a delay/loss anomaly occurs";

                        grouping ANOMALY-OCCURS {
                          description
                            "Only increase the link metric when a delay anomaly occurs";
                          container delay {
                            description
                              "Only increase the link metric when a delay anomaly occurs";
                            choice DELAY {
                              description
                                "Only increase the link metric when a delay anomaly occurs";
                              case INCREMENT {
                                leaf increment {
                                  type uint32 {
                                    range "1..16777213" {
                                      description
                                        "Metric increment";
                                    }
                                  }
                                  description
                                    "Increment the link metric by the following amount";
                                }
                              }
                              case MULTIPLIER {
                                leaf multiplier {
                                  type uint32 {
                                    range "2..100000" {
                                      description
                                        "Metric multiplier";
                                    }
                                  }
                                  description
                                    "Multiply the link metric by the following amount";
                                }
                              }
                              case MAXIMUM {
                                leaf maximum {
                                  type empty;
                                  description
                                    "Set the maximum wide metric. All routers will exclude this link from their SPF";
                                }
                              }
                            }
                          }
                          container loss {
                            description
                              "Only increase the link metric when a loss anomaly occurs";
                            choice LOSS {
                              description
                                "Only increase the link metric when a loss anomaly occurs";
                              case INCREMENT {
                                leaf increment {
                                  type uint32 {
                                    range "1..16777213" {
                                      description
                                        "Metric increment";
                                    }
                                  }
                                  description
                                    "Increment the link metric by the following amount";
                                }
                              }
                              case MULTIPLIER {
                                leaf multiplier {
                                  type uint32 {
                                    range "2..100000" {
                                      description
                                        "Metric multiplier";
                                    }
                                  }
                                  description
                                    "Multiply the link metric by the following amount";
                                }
                              }
                              case MAXIMUM {
                                leaf maximum {
                                  type empty;
                                  description
                                    "Set the maximum wide metric. All routers will exclude this link from their SPF";
                                }
                              }
                            }
                          }
                        }
                        container te-metric {
                          description
                            "Modify the TE metric";
                          choice TE-METRIC {
                            description
                              "Modify the TE metric";
                            case INCREMENT {
                              leaf increment {
                                type uint32 {
                                  range "1..16777213" {
                                    description
                                      "Metric increment";
                                  }
                                }
                                description
                                  "Increment the link metric by the following amount";
                              }
                            }
                            case MULTIPLIER {
                              leaf multiplier {
                                type uint32 {
                                  range "2..100000" {
                                    description
                                      "Metric multiplier";
                                  }
                                }
                                description
                                  "Multiply the link metric by the following amount";
                              }
                            }
                            case MAXIMUM {
                              leaf maximum {
                                type empty;
                                description
                                  "Set the maximum wide metric. All routers will exclude this link from their SPF";
                              }
                            }
                          }
                          uses ANOMALY-OCCURS;
                        }
                        container te-metric-level {
                          description
                            "Increase metric for one level only";
                          container levels {
                            description
                              "Increase metric for one level only";
                            list level {
                              key "level-number";
                              description
                                "Increase metric for one level only";
                              leaf level-number {
                                type uint32 {
                                  range "1..2" {
                                    description
                                      "Increase metric at this level only";
                                  }
                                }
                                description
                                  "Increase metric at this level only";
                              }
                              choice LEVEL {
                                mandatory true;
                                description
                                  "Increase metric for one level only";
                                case INCREMENT {
                                  leaf increment {
                                    type uint32 {
                                      range "1..16777213" {
                                        description
                                          "Metric increment";
                                      }
                                    }
                                    description
                                      "Increment the link metric by the following amount";
                                  }
                                }
                                case MULTIPLIER {
                                  leaf multiplier {
                                    type uint32 {
                                      range "2..100000" {
                                        description
                                          "Metric multiplier";
                                      }
                                    }
                                    description
                                      "Multiply the link metric by the following amount";
                                  }
                                }
                                case MAXIMUM {
                                  leaf maximum {
                                    type empty;
                                    description
                                      "Set the maximum wide metric. All routers will exclude this link from their SPF";
                                  }
                                }
                              }
                              uses ANOMALY-OCCURS;
                            }
                          }
                        }
                        container enable {
                          description
                            "enable";
                          choice ENABLE {
                            description
                              "enable";
                            case INCREMENT {
                              leaf increment {
                                type uint32 {
                                  range "1..16777213" {
                                    description
                                      "Metric increment";
                                  }
                                }
                                description
                                  "Increment the link metric by the following amount";
                              }
                            }
                            case MULTIPLIER {
                              leaf multiplier {
                                type uint32 {
                                  range "2..100000" {
                                    description
                                      "Metric multiplier";
                                  }
                                }
                                description
                                  "Multiply the link metric by the following amount";
                              }
                            }
                            case MAXIMUM {
                              leaf maximum {
                                type empty;
                                description
                                  "Set the maximum wide metric. All routers will exclude this link from their SPF";
                              }
                            }
                          }
                          uses ANOMALY-OCCURS;
                        }
                        container enable-level {
                          description
                            "Increase metric for one level only";
                          container levels {
                            description
                              "Increase metric for one level only";
                            list level {
                              key "level-number";
                              description
                                "Increase metric for one level only";
                              leaf level-number {
                                type uint32 {
                                  range "1..2" {
                                    description
                                      "Increase metric at this level only";
                                  }
                                }
                                description
                                  "Increase metric at this level only";
                              }
                              choice ENABLE-LEVEL {
                                mandatory true;
                                description
                                  "enable level";
                                case INCREMENT {
                                  leaf increment {
                                    type uint32 {
                                      range "1..16777213" {
                                        description
                                          "Metric increment";
                                      }
                                    }
                                    description
                                      "Increment the link metric by the following amount";
                                  }
                                }
                                case MULTIPLIER {
                                  leaf multiplier {
                                    type uint32 {
                                      range "2..100000" {
                                        description
                                          "Metric multiplier";
                                      }
                                    }
                                    description
                                      "Multiply the link metric by the following amount";
                                  }
                                }
                                case MAXIMUM {
                                  leaf maximum {
                                    type empty;
                                    description
                                      "Set the maximum wide metric. All routers will exclude this link from their SPF";
                                  }
                                }
                              }
                              uses ANOMALY-OCCURS;
                            }
                          }
                        }
                        container generic-metric {
                          description
                            "Configure an application specific Generic metric for the interface";
                          container flex-algo {
                            description
                              "Configure a Flex-algo Generic metric for the interface";
                            container types {
                              description
                                "Type of Generic metric";
                              list type {
                                key "type-number";
                                description
                                  "Type of Generic metric";
                                leaf type-number {
                                  type uint32 {
                                    range "128..255" {
                                      description
                                        "Generic metric type";
                                    }
                                  }
                                  description
                                    "Generic metric type";
                                }
                                choice TYPE {
                                  mandatory true;
                                  description
                                    "Type of Generic metric";
                                  case INCREMENT {
                                    leaf increment {
                                      type uint32 {
                                        range "1..16777213" {
                                          description
                                            "Metric increment";
                                        }
                                      }
                                      description
                                        "Increment the link metric by the following amount";
                                    }
                                  }
                                  case MULTIPLIER {
                                    leaf multiplier {
                                      type uint32 {
                                        range "2..100000" {
                                          description
                                            "Metric multiplier";
                                        }
                                      }
                                      description
                                        "Multiply the link metric by the following amount";
                                    }
                                  }
                                  case MAXIMUM {
                                    leaf maximum {
                                      type empty;
                                      description
                                        "Set the maximum wide metric. All routers will exclude this link from their SPF";
                                    }
                                  }
                                }
                                uses ANOMALY-OCCURS;
                              }
                            }
                            container type-levels {
                              description
                                "Type of Generic metric";
                              list type-level {
                                key "type-number level-number";
                                description
                                  "Type of Generic metric";
                                leaf type-number {
                                  type uint32 {
                                    range "128..255" {
                                      description
                                        "Generic metric type";
                                    }
                                  }
                                  description
                                    "Generic metric type";
                                }
                                leaf level-number {
                                  type uint32 {
                                    range "1..2" {
                                      description
                                        "Set metric at this level only";
                                    }
                                  }
                                  description
                                    "Set metric at this level only";
                                }
                                choice TYPE-LEVEL {
                                  mandatory true;
                                  description
                                    "Type of Generic metric";
                                  case INCREMENT {
                                    leaf increment {
                                      type uint32 {
                                        range "1..16777213" {
                                          description
                                            "Metric increment";
                                        }
                                      }
                                      description
                                        "Increment the link metric by the following amount";
                                    }
                                  }
                                  case MULTIPLIER {
                                    leaf multiplier {
                                      type uint32 {
                                        range "2..100000" {
                                          description
                                            "Metric multiplier";
                                        }
                                      }
                                      description
                                        "Multiply the link metric by the following amount";
                                    }
                                  }
                                  case MAXIMUM {
                                    leaf maximum {
                                      type empty;
                                      description
                                        "Set the maximum wide metric. All routers will exclude this link from their SPF";
                                    }
                                  }
                                }
                                uses ANOMALY-OCCURS;
                              }
                            }
                          }
                        }
                      }
                    }
                  }
                  container metric-levels {
                    description
                      "Set metric for one level only";
                    list metric-level {
                      must "maximum or default-metric";
                      key "level-number";
                      description
                        "Set metric for one level only";
                      leaf level-number {
                        type uint32 {
                          range "1..2" {
                            description
                              "Set metric at this level only";
                          }
                        }
                        description
                          "Set metric at this level only";
                      }
                      choice METRIC {
                        description
                          "METRIC";
                        case MAXIMUM {
                          leaf maximum {
                            type empty;
                            description
                              "Maximum wide metric. All routers will exclude this link from their SPF";
                          }
                        }
                        case DEFAULT-METRIC {
                          leaf default-metric {
                            type uint32 {
                              range "1..16777214" {
                                description
                                  "Default metric: <1-63> for narrow, <1-16777214> for wide";
                              }
                            }
                            description
                              "Default metric: <1-63> for narrow, <1-16777214> for wide";
                          }
                        }
                      }
                    }
                  }
                  container te-metric {
                    description
                      "Configure an application specific  TE metric for the interface";
                    leaf flex-algo {
                      type uint32 {
                        range "1..16777214" {
                          description
                            "Flex-algo traffic-engineering metric";
                        }
                      }
                      description
                        "Configure a Flex-algo TE metric for the interface";
                    }
                    container flex-algo-levels {
                      description
                        "Set metric for one level only";
                      list flex-algo-level {
                        key "level-number";
                        description
                          "Set metric for one level only";
                        leaf level-number {
                          type uint32 {
                            range "1..2" {
                              description
                                "Set metric at this level only";
                            }
                          }
                          description
                            "Set metric at this level only";
                        }
                        leaf flex-algo {
                          type uint32 {
                            range "1..16777214" {
                              description
                                "Flex-algo traffic-engineering metric";
                            }
                          }
                          mandatory true;
                          description
                            "Configure a Flex-algo TE metric for the interface";
                        }
                      }
                    }
                  }
                  container bandwidth-metric {
                    description
                      "Configure an application specific bandwidth metric for the interface";
                    leaf flex-algo {
                      type uint32 {
                        range "1..16777214" {
                          description
                            "Flex-algo bandwidth metric";
                        }
                      }
                      description
                        "Configure a Flex-algo bandwidth metric for the interface";
                    }
                    container flex-algo-levels {
                      description
                        "Set metric for one level only";
                      list flex-algo-level {
                        key "level-number";
                        description
                          "Set metric for one level only";
                        leaf level-number {
                          type uint32 {
                            range "1..2" {
                              description
                                "Set metric at this level only";
                            }
                          }
                          description
                            "Set metric at this level only";
                        }
                        leaf flex-algo {
                          type uint32 {
                            range "1..16777214" {
                              description
                                "Flex-algo bandwidth metric";
                            }
                          }
                          mandatory true;
                          description
                            "Configure a Flex-algo bandwidth metric for the interface";
                        }
                      }
                    }
                  }
                  container auto-cost {
                    presence "Auto-cost for bandwidth metric";
                    description
                      "Auto-cost for bandwidth metric";
                    leaf reference-bandwidth {
                      type uint64 {
                        range "1..18446744073709551615" {
                          description
                            "The reference bandwidth value (kbits/sec)";
                        }
                      }
                      mandatory true;
                      description
                        "Reference-bandwidth configuration for auto-cost";
                    }
                    leaf granularity {
                      type uint64 {
                        range "1..18446744073709551615" {
                          description
                            "Granularity value (kbits/sec)";
                        }
                      }
                      description
                        "Granularity";
                    }
                  }
                  container generic-metric {
                    description
                      "Configure an application specific Generic metric for the interface";
                    container flex-algo {
                      description
                        "Configure a Flex-algo Generic metric for the interface";
                      container types {
                        description
                          "Type of Generic metric";
                        list type {
                          key "type-number";
                          description
                            "Type of Generic metric";
                          leaf type-number {
                            type uint32 {
                              range "128..255" {
                                description
                                  "Generic metric type";
                              }
                            }
                            description
                              "Generic metric type";
                          }
                          leaf flex-algo-metric-value {
                            type uint32 {
                              range "1..16777214" {
                                description
                                  "Flex-algo generic metric value";
                              }
                            }
                            mandatory true;
                            description
                              "Flex-algo generic metric value";
                          }
                        }
                      }
                    }
                    container flex-algo-levels {
                      description
                        "Set metric for one level only";
                      list flex-algo-level {
                        key "level-number";
                        description
                          "Set metric for one level only";
                        leaf level-number {
                          type uint32 {
                            range "1..2" {
                              description
                                "Set metric at this level only";
                            }
                          }
                          description
                            "Set metric at this level only";
                        }
                        container types {
                          description
                            "Type of Generic metric";
                          list type {
                            key "type-number";
                            description
                              "Type of Generic metric";
                            leaf type-number {
                              type uint32 {
                                range "128..255" {
                                  description
                                    "Generic metric type";
                                }
                              }
                              description
                                "Generic metric type";
                            }
                            leaf flex-algo-metric-value {
                              type uint32 {
                                range "1..16777214" {
                                  description
                                    "Flex-algo generic metric value";
                                }
                              }
                              mandatory true;
                              description
                                "Flex-algo generic metric value";
                            }
                          }
                        }
                      }
                    }
                  }
                  container mpls {
                    description
                      "Configure MPLS routing protocol parameters";
                    container ldp {
                      description
                        "Configure LDP parameters";
                      container sync {
                        presence "Configure LDP ISIS synchronization";
                        description
                          "Configure LDP ISIS synchronization";
                        leaf level {
                          type uint32 {
                            range "1..2" {
                              description
                                "Set LDP synchronization at this level only";
                            }
                          }
                          description
                            "Set LDP synchronization for one level only";
                        }
                      }
                    }
                  }
                  leaf tag {
                    type uint32 {
                      range "1..4294967295" {
                        description
                          "Interface tag";
                      }
                    }
                    description
                      "Set interface tag";
                  }
                  container tag-levels {
                    description
                      "Set the tag only at supplied level";
                    list tag-level {
                      key "level-number";
                      description
                        "Set the tag only at supplied level";
                      leaf level-number {
                        type uint32 {
                          range "1..2" {
                            description
                              "Set the tag only at this level";
                          }
                        }
                        description
                          "Set the tag only at this level";
                      }
                      leaf tag {
                        type uint32 {
                          range "1..4294967295" {
                            description
                              "Interface tag";
                          }
                        }
                        mandatory true;
                        description
                          "Interface tag";
                      }
                    }
                  }
                  container prefix-sid {
                    when "../saf-name = 'unicast'";
                    description
                      "Specify the Prefix Segment ID";

                    grouping OPTIONS {
                      description
                        "OPTIONS";
                      leaf php-disable {
                        type empty;
                        description
                          "Disable Penultimate Hop Popping";
                      }
                      leaf explicit-null {
                        type empty;
                        description
                          "Upstream neighbor must replace prefix-sid with explicit null label";
                      }
                      leaf n-flag-clear {
                        type empty;
                        description
                          "Clear N-flag for the prefix-SID";
                      }
                    }
                    container strict-spf {
                      description
                        "Strict-SPF Prefix SID Configuration";
                      choice STRICT-SPF {
                        description
                          "STRICT-SPF";
                        case INDEX {
                          container index {
                            presence "Specify the index of Prefix Segement ID";
                            description
                              "Specify the index of Prefix Segement ID";
                            leaf index-id {
                              type uint32 {
                                range "0..1048575" {
                                  description
                                    "The Prefix Segment ID index";
                                }
                              }
                              mandatory true;
                              description
                                "The Prefix Segment ID index";
                            }
                            uses OPTIONS;
                          }
                        }
                        case ABSOLUTE {
                          container absolute {
                            presence "Specify the absolute value of Prefix Segement ID";
                            description
                              "Specify the absolute value of Prefix Segement ID";
                            leaf absolute-id {
                              type uint32 {
                                range "16000..1048575" {
                                  description
                                    "The Prefix Segment ID value";
                                }
                              }
                              mandatory true;
                              description
                                "The Prefix Segment ID value";
                            }
                            uses OPTIONS;
                          }
                        }
                      }
                    }
                    container algorithms {
                      description
                        "Algorithm Specific Prefix SID Configuration";
                      list algorithm {
                        must "index or absolute";
                        key "algorithm-number";
                        description
                          "Algorithm Specific Prefix SID Configuration";
                        leaf algorithm-number {
                          type uint32 {
                            range "128..255" {
                              description
                                "Algorithm number";
                            }
                          }
                          description
                            "Algorithm number";
                        }
                        choice ALGORITHM {
                          description
                            "ALGORITHM";
                          case INDEX {
                            container index {
                              presence "Specify the index of Prefix Segement ID";
                              description
                                "Specify the index of Prefix Segement ID";
                              leaf index-id {
                                type uint32 {
                                  range "0..1048575" {
                                    description
                                      "The Prefix Segment ID index";
                                  }
                                }
                                mandatory true;
                                description
                                  "The Prefix Segment ID index";
                              }
                              uses OPTIONS;
                            }
                          }
                          case ABSOLUTE {
                            container absolute {
                              presence "Specify the absolute value of Prefix Segement ID";
                              description
                                "Specify the absolute value of Prefix Segement ID";
                              leaf absolute-id {
                                type uint32 {
                                  range "16000..1048575" {
                                    description
                                      "The Prefix Segment ID value";
                                  }
                                }
                                mandatory true;
                                description
                                  "The Prefix Segment ID value";
                              }
                              uses OPTIONS;
                            }
                          }
                        }
                      }
                    }
                    choice PREFIX-SID {
                      description
                        "PREFIX-SID";
                      case INDEX {
                        container index {
                          presence "Specify the index of Prefix Segement ID";
                          description
                            "Specify the index of Prefix Segement ID";
                          leaf index-id {
                            type uint32 {
                              range "0..1048575" {
                                description
                                  "The Prefix Segment ID index";
                              }
                            }
                            mandatory true;
                            description
                              "The Prefix Segment ID index";
                          }
                          uses OPTIONS;
                        }
                      }
                      case ABSOLUTE {
                        container absolute {
                          presence "Specify the absolute value of Prefix Segement ID";
                          description
                            "Specify the absolute value of Prefix Segement ID";
                          leaf absolute-id {
                            type uint32 {
                              range "16000..1048575" {
                                description
                                  "The Prefix Segment ID value";
                              }
                            }
                            mandatory true;
                            description
                              "The Prefix Segment ID value";
                          }
                          uses OPTIONS;
                        }
                      }
                    }
                  }
                  container adjacency-sid {
                    when "../saf-name = 'unicast'";
                    description
                      "adjacency-sid";

                    grouping PROTECTED {
                      description
                        "Protect Adjacency SID";
                      leaf protected {
                        type empty;
                        description
                          "Protect Adjacency SID";
                      }
                    }
                    container indices {
                      description
                        "Specify the index of Adjacency Segement ID";
                      list index {
                        key "index-number";
                        description
                          "Specify the index of Adjacency Segement ID";
                        leaf index-number {
                          type uint32 {
                            range "0..1048575" {
                              description
                                "The Adjacency Segment ID index";
                            }
                          }
                          description
                            "The Adjacency Segment ID index";
                        }
                        uses PROTECTED;
                      }
                    }
                    container absolutes {
                      description
                        "Specify the absolute value of Adjacency Segement ID";
                      list absolute {
                        key "absolute-number";
                        description
                          "Specify the absolute value of Adjacency Segement ID";
                        leaf absolute-number {
                          type uint32 {
                            range "16000..1048575" {
                              description
                                "The Adjacency Segment ID value";
                            }
                          }
                          description
                            "The Adjacency Segment ID value";
                        }
                        uses PROTECTED;
                      }
                    }
                  }
                  container fast-reroute {
                    description
                      "Configure Fast ReRoute";
                    container enable {
                      description
                        "Enable Fast ReRoute for per-prefix or per-link";
                      leaf per-prefix {
                        type empty;
                        description
                          "per-prefix";
                      }
                      leaf per-link {
                        type empty;
                        description
                          "per-link";
                      }
                    }
                    container enable-levels {
                      description
                        "enable";
                      list enable-level {
                        must "per-link or per-prefix";
                        key "level-number";
                        description
                          "enable";
                        leaf level-number {
                          type uint32 {
                            range "1..2" {
                              description
                                "Configure FRR for one level only";
                            }
                          }
                          description
                            "Configure FRR for one level only";
                        }
                        leaf per-prefix {
                          type empty;
                          description
                            "per-prefix";
                        }
                        leaf per-link {
                          type empty;
                          description
                            "per-link";
                        }
                      }
                    }
                    container per-prefix {
                      description
                        "Prefix dependent computation";
                      container tiebreaker {
                        description
                          "Configure tiebreaker for multiple backups";
                        leaf default-backup-path {
                          type empty;
                          description
                            "Prefer default (link protecting) backup path";
                        }
                        container default-backup-path-levels {
                          description
                            "Configure tiebreaker for one level only";
                          list default-backup-path-level {
                            key "level-number";
                            description
                              "Configure tiebreaker for one level only";
                            leaf level-number {
                              type uint32 {
                                range "1..2" {
                                  description
                                    "Level";
                                }
                              }
                              description
                                "Level";
                            }
                          }
                        }
                        container node-protecting {
                          description
                            "Prefer node protecting backup path";
                          leaf index {
                            type uint32 {
                              range "1..255" {
                                description
                                  "Index";
                              }
                            }
                            description
                              "Set preference order among tiebreakers";
                          }
                        }
                        container node-protecting-levels {
                          description
                            "Configure tiebreaker for one level only";
                          list node-protecting-level {
                            key "level-number";
                            description
                              "Configure tiebreaker for one level only";
                            leaf level-number {
                              type uint32 {
                                range "1..2" {
                                  description
                                    "Level";
                                }
                              }
                              description
                                "Level";
                            }
                            leaf index {
                              type uint32 {
                                range "1..255" {
                                  description
                                    "Index";
                                }
                              }
                              mandatory true;
                              description
                                "Set preference order among tiebreakers";
                            }
                          }
                        }
                        container srlg-disjoint {
                          description
                            "Prefer SRLG disjoint backup path";
                          leaf index {
                            type uint32 {
                              range "1..255" {
                                description
                                  "Index";
                              }
                            }
                            description
                              "Set preference order among tiebreakers";
                          }
                        }
                        container srlg-disjoint-levels {
                          description
                            "Configure tiebreaker for one level only";
                          list srlg-disjoint-level {
                            key "level-number";
                            description
                              "Configure tiebreaker for one level only";
                            leaf level-number {
                              type uint32 {
                                range "1..2" {
                                  description
                                    "Level";
                                }
                              }
                              description
                                "Level";
                            }
                            leaf index {
                              type uint32 {
                                range "1..255" {
                                  description
                                    "Index";
                                }
                              }
                              mandatory true;
                              description
                                "Set preference order among tiebreakers";
                            }
                          }
                        }
                        container lc-disjoint {
                          description
                            "Prefer line card disjoint backup path";
                          leaf index {
                            type uint32 {
                              range "1..255" {
                                description
                                  "Index";
                              }
                            }
                            description
                              "Set preference order among tiebreakers";
                          }
                        }
                        container lc-disjoint-levels {
                          description
                            "Configure tiebreaker for one level only";
                          list lc-disjoint-level {
                            key "level-number";
                            description
                              "Configure tiebreaker for one level only";
                            leaf level-number {
                              type uint32 {
                                range "1..2" {
                                  description
                                    "Level";
                                }
                              }
                              description
                                "Level";
                            }
                            leaf index {
                              type uint32 {
                                range "1..255" {
                                  description
                                    "Index";
                                }
                              }
                              mandatory true;
                              description
                                "Set preference order among tiebreakers";
                            }
                          }
                        }
                      }
                      container remote-lfa {
                        description
                          "Enable remote LFA computation";
                        leaf maximum-metric {
                          type uint32 {
                            range "1..16777215" {
                              description
                                "Value of the metric";
                            }
                          }
                          description
                            "Limit remote LFA node selection within the metric";
                        }
                        container maximum-metric-levels {
                          description
                            "Enable remote LFA max metric for one level only";
                          list maximum-metric-level {
                            key "level-number";
                            description
                              "Enable remote LFA max metric for one level only";
                            leaf level-number {
                              type uint32 {
                                range "1..2" {
                                  description
                                    "Set remote LFA max metric value for this level";
                                }
                              }
                              description
                                "Set remote LFA max metric value for this level";
                            }
                            leaf maximum-metric {
                              type uint32 {
                                range "1..16777215" {
                                  description
                                    "Value of the metric";
                                }
                              }
                              mandatory true;
                              description
                                "Limit remote LFA node selection within the metric";
                            }
                          }
                        }
                        container tunnel {
                          description
                            "Enable remote LFA computation using tunnels";
                          leaf mpls-ldp {
                            type empty;
                            description
                              "Use MPLS LDP tunnel to reach the remote LFA node";
                          }
                          container mpls-ldp-levels {
                            description
                              "Enable remote LFA for one level only";
                            list mpls-ldp-level {
                              key "level-number";
                              description
                                "Enable remote LFA for one level only";
                              leaf level-number {
                                type uint32 {
                                  range "1..2" {
                                    description
                                      "Set remote LFA for this level";
                                  }
                                }
                                description
                                  "Set remote LFA for this level";
                              }
                            }
                          }
                        }
                      }
                      leaf ti-lfa {
                        if-feature "isis_srmpls_is_platform_supported";
                        type empty;
                        description
                          "Enable TI LFA computation";
                      }
                      container ti-lfa-levels {
                        description
                          "Enable EPCFRR LFA for one level only";
                        list ti-lfa-level {
                          if-feature "isis_srmpls_is_platform_supported";
                          key "level-number";
                          description
                            "Enable EPCFRR LFA for one level only";
                          leaf level-number {
                            type uint32 {
                              range "1..2" {
                                description
                                  "Set EPCFRR LFA for this level";
                              }
                            }
                            description
                              "Set EPCFRR LFA for this level";
                          }
                        }
                      }
                      container exclude {
                        description
                          "FRR exclusion information";
                        container interfaces {
                          description
                            "Exclude an interface from computation";
                          list interface {
                            key "exclude-interface-name";
                            description
                              "Exclude an interface from computation";
                            leaf exclude-interface-name {
                              type xr:Interface-name;
                              description
                                "exclude-interface-name";
                            }
                            leaf level {
                              type uint32 {
                                range "1..2" {
                                  description
                                    "Level";
                                }
                              }
                              description
                                "Exclude interface for one level only";
                            }
                          }
                        }
                      }
                      container lfa-candidate {
                        description
                          "FRR LFA candidate information";
                        container interfaces {
                          description
                            "Include an interface to LFA candidate in computation";
                          list interface {
                            key "lfa-interface-name";
                            description
                              "Include an interface to LFA candidate in computation";
                            leaf lfa-interface-name {
                              type xr:Interface-name;
                              description
                                "lfa-interface-name";
                            }
                            leaf level {
                              type uint32 {
                                range "1..2" {
                                  description
                                    "Level";
                                }
                              }
                              description
                                "Include interface for one level only";
                            }
                          }
                        }
                      }
                    }
                    container per-link {
                      description
                        "Prefix independent per-link computation";
                      container exclude {
                        description
                          "FRR exclusion information";
                        container interfaces {
                          description
                            "Exclude an interface from computation";
                          list interface {
                            key "exclude-interface-name";
                            description
                              "Exclude an interface from computation";
                            leaf exclude-interface-name {
                              type xr:Interface-name;
                              description
                                "exclude-interface-name";
                            }
                            leaf level {
                              type uint32 {
                                range "1..2" {
                                  description
                                    "Level";
                                }
                              }
                              description
                                "Exclude interface for one level only";
                            }
                          }
                        }
                      }
                      container lfa-candidate {
                        description
                          "FRR LFA candidate information";
                        container interfaces {
                          description
                            "Include an interface to LFA candidate in computation";
                          list interface {
                            key "lfa-interface-name";
                            description
                              "Include an interface to LFA candidate in computation";
                            leaf lfa-interface-name {
                              type xr:Interface-name;
                              description
                                "lfa-interface-name";
                            }
                            leaf level {
                              type uint32 {
                                range "1..2" {
                                  description
                                    "Level";
                                }
                              }
                              description
                                "Include interface for one level only";
                            }
                          }
                        }
                      }
                    }
                  }
                  container link-group {
                    description
                      "Set interface link group";
                    leaf link-group-string {
                      type string {
                        length "1..40" {
                          description
                            "Interface link group";
                        }
                      }
                      description
                        "Interface link group";
                    }
                    leaf level {
                      type uint32 {
                        range "1..2" {
                          description
                            "Set the tag only at this level";
                        }
                      }
                      must "../link-group-string";
                      description
                        "Set the tag only at supplied level";
                    }
                  }
                  leaf weight {
                    when "../saf-name = 'unicast'";
                    type uint32 {
                      range "1..16777214" {
                        description
                          "Configure weight for unequal load balancing";
                      }
                    }
                    description
                      "Configure weight for the interface";
                  }
                  container weight-levels {
                    description
                      "Set weight for one level only";
                    list weight-level {
                      key "level-number";
                      description
                        "Set weight for one level only";
                      leaf level-number {
                        type uint32 {
                          range "1..2" {
                            description
                              "Set weight at this level only";
                          }
                        }
                        description
                          "Set weight at this level only";
                      }
                      leaf weight {
                        type uint32 {
                          range "1..16777214" {
                            description
                              "Configure weight for unequal load balancing";
                          }
                        }
                        mandatory true;
                        description
                          "Configure weight for the interface";
                      }
                    }
                  }
                  container auto-metric {
                    description
                      "Configure the auto-metric for interface";
                    leaf proactive-protect {
                      type uint32 {
                        range "1..16777214" {
                          description
                            "Absolute metric: <1-63> for narrow, <1-16777214> for wide";
                        }
                      }
                      description
                        "set auto-metric proactive-protect mode";
                    }
                    container proactive-protect-levels {
                      description
                        "set auto-metric proactive-protect mode for one level only";
                      list proactive-protect-level {
                        key "level-number";
                        description
                          "set auto-metric proactive-protect mode for one level only";
                        leaf level-number {
                          type uint32 {
                            range "1..2" {
                              description
                                "set auto-metric proactive-protect mode for one level only";
                            }
                          }
                          description
                            "set auto-metric proactive-protect mode for one level only";
                        }
                        leaf proactive-protect {
                          type uint32 {
                            range "1..16777214" {
                              description
                                "Absolute metric: <1-63> for narrow, <1-16777214> for wide";
                            }
                          }
                          mandatory true;
                          description
                            "set auto-metric proactive-protect mode";
                        }
                      }
                    }
                  }
                  container advertise {
                    when "../saf-name = 'unicast'";
                    description
                      "Configure the AF specific advertisement";
                    container prefix-advertisement {
                      description
                        "Configure the prefix advertisement";
                      leaf route-policy {
                        type xr:Route-policy-name;
                        description
                          "Filter routes based on a route policy";
                      }
                      container route-policy-levels {
                        description
                          "Set advertisement for one level only";
                        list route-policy-level {
                          key "level-number";
                          description
                            "Set advertisement for one level only";
                          leaf level-number {
                            type uint32 {
                              range "1..2" {
                                description
                                  "Set advertisement at this level only";
                              }
                            }
                            description
                              "Set advertisement at this level only";
                          }
                          leaf route-policy {
                            type xr:Route-policy-name;
                            description
                              "Filter routes based on a route policy";
                          }
                        }
                      }
                    }
                  }
                  leaf disable {
                    type empty;
                    description
                      "Disable IS-IS for this topology on this interface";
                  }
                }
                list address-family {
                  key "af-name saf-name";
                  description
                    "Enter the IS-IS interface address-family configuration submode";
                  leaf af-name {
                    type enumeration {
                      enum "ipv4" {
                        value 0;
                        description
                          "IPv4 address family";
                      }
                      enum "ipv6" {
                        value 1;
                        description
                          "IPv6 address family";
                      }
                    }
                    description
                      "af-name";
                  }
                  leaf saf-name {
                    type enumeration {
                      enum "unicast" {
                        value 0;
                        description
                          "unicast topology";
                      }
                      enum "multicast" {
                        value 1;
                        description
                          "multicast topology";
                      }
                    }
                    description
                      "saf-name";
                  }
                  uses ISIS-IF-AF;
                }
                list address-family-topology {
                  key "af-name saf-name topology-name";
                  description
                    "Enter the IS-IS interface address-family configuration submode";
                  leaf af-name {
                    type enumeration {
                      enum "ipv4" {
                        value 0;
                        description
                          "IPv4 address family";
                      }
                      enum "ipv6" {
                        value 1;
                        description
                          "IPv6 address family";
                      }
                    }
                    description
                      "af-name";
                  }
                  leaf saf-name {
                    type enumeration {
                      enum "unicast" {
                        value 0;
                        description
                          "unicast topology";
                      }
                      enum "multicast" {
                        value 1;
                        description
                          "multicast topology";
                      }
                    }
                    description
                      "saf-name";
                  }
                  leaf topology-name {
                    type xr:Cisco-ios-xr-string {
                      length "1..32" {
                        description
                          "Topology name";
                      }
                    }
                    description
                      "Specify a non-default topology";
                  }
                  uses ISIS-IF-AF;
                }
              }
            }
          }
          container address-families {
            description
              "Enter the IS-IS address-family configuration submode";

            grouping ISIS-AF {
              description
                "ISIS-AF";
              container distance {
                description
                  "Configure IS-IS administrative distances";
                leaf global {
                  type uint32 {
                    range "1..255" {
                      description
                        "Administrative distance";
                    }
                  }
                  description
                    "Configure IS-IS administrative distances";
                }
                container ip-addresses {
                  description
                    "Route source for this distance";
                  list ip-address {
                    key "address address-prefix";
                    description
                      "Route source for this distance";
                    leaf address {
                      type inet:ip-address-no-zone;
                      description
                        "IP address";
                    }
                    leaf address-prefix {
                      type uint32 {
                        range "0..128" {
                          description
                            "IP address prefix";
                        }
                      }
                      description
                        "IP address prefix";
                    }
                    leaf distance-number {
                      type uint32 {
                        range "1..255" {
                          description
                            "Administrative distance";
                        }
                      }
                      mandatory true;
                      description
                        "Administrative distance";
                    }
                    leaf prefix-list-or-access-list-to {
                      type string {
                        length "1..800" {
                          description
                            "Prefix-list or access-list to filter routes for this distance";
                        }
                      }
                      must "../distance-number";
                      description
                        "Prefix-list or access-list to filter routes for this distance";
                    }
                  }
                }
              }
              container distribute-list {
                description
                  "Filter routes sent to the RIB";
                container prefix-list {
                  description
                    "Filter routes based on a prefix list";
                  leaf prefix-list-string {
                    type string {
                      length "1..1024" {
                        description
                          "Prefix-list name";
                      }
                    }
                    description
                      "Filter routes based on a prefix list";
                  }
                }
                leaf route-policy {
                  type xr:Route-policy-name;
                  description
                    "Filter routes based on a route policy";
                }
              }
              container redistribute {
                description
                  "Redistribute information from another routing protocol";

                grouping REDISTRIBUTE {
                  description
                    "REDISTRIBUTE";
                  leaf redistribute-route-level {
                    type enumeration {
                      enum "level-1-2" {
                        value 3;
                        description
                          "Redistribute routes into both levels";
                      }
                      enum "level-2" {
                        value 2;
                        description
                          "Redistribute routes into level 2 only (the default)";
                      }
                      enum "level-1" {
                        value 1;
                        description
                          "Redistribute routes into level 1 only";
                      }
                    }
                    description
                      "Redistribute routes into both levels";
                  }
                  leaf metric {
                    type uint32 {
                      range "0..16777215" {
                        description
                          "Default metric: <0-63> for narrow, <0-16777215> for wide";
                      }
                    }
                    description
                      "Metric for redistributed routes";
                  }
                  leaf route-policy {
                    type xr:Route-policy-name;
                    description
                      "Route policy reference";
                  }
                  leaf metric-type {
                    type enumeration {
                      enum "internal" {
                        value 0;
                        description
                          "Set IS-IS Internal metric type";
                      }
                      enum "external" {
                        value 1;
                        description
                          "Set IS-IS External metric type";
                      }
                      enum "rib-metric-as-internal" {
                        value 2;
                        description
                          "Set IS-IS Internal metric type and use RIB metric";
                      }
                      enum "rib-metric-as-external" {
                        value 3;
                        description
                          "Set IS-IS External metric type and use RIB metric";
                      }
                    }
                    description
                      "IS-IS metric type for redistributed routes";
                  }
                  leaf down-flag-clear {
                    type empty;
                    description
                      "Set the up/down bit to 0 in prefix advertisements";
                  }
                }
                container connected {
                  presence "Connected routes";
                  description
                    "Connected routes";
                  uses REDISTRIBUTE;
                }
                container static {
                  presence "Static routes";
                  description
                    "Static routes";
                  uses REDISTRIBUTE;
                }
                container subscriber {
                  presence "Subscriber routes";
                  description
                    "Subscriber routes";
                  uses REDISTRIBUTE;
                }
                container rip {
                  presence "RIP routes";
                  description
                    "RIP routes";
                  uses REDISTRIBUTE;
                }
                container mobile {
                  presence "Mobile routes";
                  description
                    "Mobile routes";
                  uses REDISTRIBUTE;
                }
                container applications {
                  description
                    "Application routes";
                  list application {
                    key "application-string";
                    description
                      "Application routes";
                    leaf application-string {
                      type string {
                        length "1..1024" {
                          description
                            "OnePK application name";
                        }
                      }
                      description
                        "OnePK application name";
                    }
                    uses REDISTRIBUTE;
                  }
                }
                container isis-processes {
                  description
                    "IS-IS";
                  list isis-process {
                    key "isis-string";
                    description
                      "IS-IS";
                    leaf isis-string {
                      type xr:Cisco-ios-xr-string {
                        length "1..1024" {
                          description
                            "IS-IS instance identifier";
                        }
                      }
                      description
                        "IS-IS instance identifier";
                    }
                    uses REDISTRIBUTE;
                  }
                }
                container bgps {
                  description
                    "Border Gateway Protocol (BGP)";
                  list bgp {
                    key "as-number";
                    description
                      "Border Gateway Protocol (BGP)";
                    leaf as-number {
                      type xr:Bgp-as-number;
                      description
                        "as-number";
                    }
                    uses REDISTRIBUTE;
                  }
                }
                container eigrp {
                  description
                    "EIGRP Protocol";
                  container autonomous-system-numbers {
                    description
                      "EIGRP Protocol";
                    list autonomous-system-number {
                      key "system-number";
                      description
                        "EIGRP Protocol";
                      leaf system-number {
                        type uint32 {
                          range "1..65535" {
                            description
                              "Autonomous system number";
                          }
                        }
                        description
                          "Autonomous system number";
                      }
                      container match {
                        description
                          "Redistribution of EIGRP routes";
                        choice MATCH {
                          description
                            "Redistribution of EIGRP routes";
                          case INTERNAL {
                            leaf internal {
                              type empty;
                              description
                                "Redistribute EIGRP internal routes";
                            }
                          }
                          case EXTERNAL {
                            leaf external {
                              type empty;
                              description
                                "Redistribute EIGRP external routes";
                            }
                          }
                        }
                      }
                      uses REDISTRIBUTE;
                    }
                  }
                }
                container ospfs {
                  description
                    "Open Shortest Path First (OSPF)";
                  list ospf {
                    key "ospf-process-id";
                    description
                      "Open Shortest Path First (OSPF)";
                    leaf ospf-process-id {
                      type xr:Cisco-ios-xr-string {
                        length "1..1024" {
                          description
                            "OSPF process ID";
                        }
                      }
                      description
                        "OSPF process ID";
                    }
                    container match {
                      description
                        "Redistribution of OSPF routes";
                      choice MATCH {
                        description
                          "Redistribution of OSPF routes";
                        case INTERNAL {
                          leaf internal {
                            type empty;
                            description
                              "Redistribute OSPF internal routes";
                          }
                        }
                        case EXTERNAL {
                          container external {
                            presence "Redistribute OSPF external routes";
                            description
                              "Redistribute OSPF external routes";
                            leaf external-type-routes {
                              type enumeration {
                                enum "1" {
                                  value 8;
                                  description
                                    "Redistribute external type 1 routes";
                                }
                                enum "2" {
                                  value 16;
                                  description
                                    "Redistribute external type 2 routes";
                                }
                              }
                              description
                                "Redistribute OSPF external routes";
                            }
                          }
                        }
                        case NSSA-EXTERNAL {
                          container nssa-external {
                            presence "Redistribute OSPF NSSA external routes";
                            description
                              "Redistribute OSPF NSSA external routes";
                            leaf nssa-external-type-routes {
                              type enumeration {
                                enum "1" {
                                  value 4096;
                                  description
                                    "Redistribute external type 1 routes";
                                }
                                enum "2" {
                                  value 8192;
                                  description
                                    "Redistribute external type 2 routes";
                                }
                              }
                              description
                                "Redistribute OSPF NSSA external routes";
                            }
                          }
                        }
                      }
                    }
                    uses REDISTRIBUTE;
                  }
                }
                container ospfv3s {
                  description
                    "Open Shortest Path First (OSPFv3)";
                  list ospfv3 {
                    key "ospfv3-process-id";
                    description
                      "Open Shortest Path First (OSPFv3)";
                    leaf ospfv3-process-id {
                      type xr:Cisco-ios-xr-string {
                        length "1..1024" {
                          description
                            "OSPFv3 process ID";
                        }
                      }
                      description
                        "OSPFv3 process ID";
                    }
                    container match {
                      description
                        "Redistribution of OSPF routes";
                      choice MATCH {
                        description
                          "Redistribution of OSPF routes";
                        case INTERNAL {
                          leaf internal {
                            type empty;
                            description
                              "Redistribute OSPF internal routes";
                          }
                        }
                        case EXTERNAL {
                          container external {
                            presence "Redistribute OSPF external routes";
                            description
                              "Redistribute OSPF external routes";
                            leaf external-type-routes {
                              type enumeration {
                                enum "1" {
                                  value 8;
                                  description
                                    "Redistribute external type 1 routes";
                                }
                                enum "2" {
                                  value 16;
                                  description
                                    "Redistribute external type 2 routes";
                                }
                              }
                              description
                                "Redistribute OSPF external routes";
                            }
                          }
                        }
                        case NSSA-EXTERNAL {
                          container nssa-external {
                            presence "Redistribute OSPF NSSA external routes";
                            description
                              "Redistribute OSPF NSSA external routes";
                            leaf nssa-external-type-routes {
                              type enumeration {
                                enum "1" {
                                  value 4096;
                                  description
                                    "Redistribute external type 1 routes";
                                }
                                enum "2" {
                                  value 8192;
                                  description
                                    "Redistribute external type 2 routes";
                                }
                              }
                              description
                                "Redistribute OSPF NSSA external routes";
                            }
                          }
                        }
                      }
                    }
                    uses REDISTRIBUTE;
                  }
                }
              }
              leaf maximum-paths {
                type uint32 {
                  range "1..64" {
                    description
                      "Number of paths";
                  }
                }
                description
                  "Maximum number of active parallel paths per route";
              }
              container router-id {
                description
                  "Stable IP address for system";
                choice ROUTER-ID {
                  description
                    "Stable IP address for system";
                  case INTERFACE-NAME {
                    leaf interface-name {
                      type xr:Interface-name;
                      description
                        "Router ID Interface";
                    }
                  }
                  case IP-ADDRESS {
                    leaf ip-address {
                      type inet:ip-address-no-zone;
                      description
                        "Router ID address";
                    }
                  }
                }
              }
              container advertise {
                description
                  "Control what we advertise in our LSP";
                container application {
                  description
                    "Application Specific Data";
                  container lfa {
                    description
                      "LFA Application";
                    container link-attributes {
                      description
                        "Application Specific Link Attributes";
                      leaf srlg {
                        type empty;
                        description
                          "Shared Risk Ling Group";
                      }
                    }
                  }
                  container flex-algo {
                    description
                      "Flex-Algo Application";
                    container link-attributes {
                      description
                        "Application Specific Link Attributes";
                      leaf srlg {
                        type empty;
                        description
                          "Shared Risk Ling Group";
                      }
                    }
                  }
                }
                container link {
                  description
                    "IS Neighbor attributes";
                  leaf attributes {
                    type empty;
                    description
                      "Advertise additional link attributes";
                  }
                }
                leaf passive-only {
                  type empty;
                  description
                    "Advertise prefixes of passive interfaces only";
                }
              }
              container ucmp {
                if-feature "isis_ucmp_is_platform_supported";
                description
                  "UnEqual Cost Multipath feature";
                container enable {
                  presence "UnEqual Cost Multipath feature";
                  description
                    "UnEqual Cost Multipath feature";
                  leaf variance {
                    type uint32 {
                      range "101..10000" {
                        description
                          "Variance value";
                      }
                    }
                    description
                      "Specify Variance parameter to filter UCMP paths based on cost";
                  }
                  leaf prefix-list {
                    type string {
                      length "1..1024" {
                        description
                          "Name of the prefix-list";
                      }
                    }
                    description
                      "Specify prefix-list name to filter UCMP paths based on prefixes";
                  }
                }
                container exclude {
                  description
                    "UCMP interface exclusion information";
                  container interfaces {
                    description
                      "Exclude an interface from UCMP computation";
                    list interface {
                      key "interface-name";
                      description
                        "Exclude an interface from UCMP computation";
                      leaf interface-name {
                        type xr:Interface-name;
                        description
                          "Interface to be excluded";
                      }
                    }
                  }
                }
                leaf delay-interval {
                  type uint32 {
                    range "100..65535" {
                      description
                        "Delay interval value in milliseconds";
                    }
                  }
                  description
                    "UCMP delay interval";
                }
              }
              container microloop {
                description
                  "Enable microloop protection feature";
                container avoidance {
                  description
                    "Enable local microloop avoidance";
                  container enable {
                    presence "Enable local microloop avoidance";
                    description
                      "Enable local microloop avoidance";
                    leaf protected {
                      type empty;
                      description
                        "Enable microloop avoidance for only protected prefixes";
                    }
                    container segment-routing {
                      presence "Enable segment routing microloop avoidance";
                      description
                        "Enable segment routing microloop avoidance";
                      leaf route-policy {
                        type xr:Route-policy-name;
                        description
                          "Provide Uloop protection based on a route policy";
                      }
                    }
                  }
                  leaf rib-update-delay {
                    type uint32 {
                      range "1000..65535" {
                        description
                          "Set value of delay";
                      }
                    }
                    description
                      "Delay in milliseconds";
                  }
                }
              }
              container apply-weight {
                description
                  "Apply weight";
                choice APPLY-WEIGHT {
                  description
                    "Apply weight";
                  case ECMP-ONLY {
                    container ecmp-only {
                      presence "Apply weights to ecmp paths only";
                      description
                        "Apply weights to ecmp paths only";
                      leaf bandwidth {
                        type empty;
                        description
                          "Apply weight calculated based on interface bandwidth";
                      }
                    }
                  }
                  case UCMP-ONLY {
                    leaf ucmp-only {
                      type empty;
                      description
                        "Apply weights to ucmp paths only";
                    }
                  }
                }
              }
              container summary-prefix {
                description
                  "Configure IP prefix summaries";
                container ip-addresses {
                  description
                    "Summary prefix";
                  list ip-address {
                    key "address address-prefix";
                    description
                      "Summary prefix";
                    leaf address {
                      type inet:ip-address-no-zone;
                      description
                        "IP address";
                    }
                    leaf address-prefix {
                      type uint32 {
                        range "0..128" {
                          description
                            "IP address prefix";
                        }
                      }
                      description
                        "IP address prefix";
                    }
                    leaf tag {
                      type uint32 {
                        range "1..4294967295" {
                          description
                            "The tag value used for summary prefix advertisement";
                        }
                      }
                      description
                        "Set a tag";
                    }
                    leaf level {
                      type uint32 {
                        range "1..2" {
                          description
                            "Level";
                        }
                      }
                      description
                        "Summarize routes in one level only";
                    }
                    leaf algorithm {
                      when "../../../../saf-name = 'unicast'";
                      type uint32 {
                        range "128..255" {
                          description
                            "Algorithm number";
                        }
                      }
                      description
                        "Flex Algorithm number";
                    }
                    leaf explicit {
                      when "../../../../saf-name = 'unicast'";
                      type empty;
                      description
                        "Strict flex-algo locator summarization mode";
                    }
                    container adv-unreachable {
                      presence "Advertise unreachable summary components";
                      description
                        "Advertise unreachable summary components";
                      container unreachable-component-tag {
                        description
                          "Advertise unreachability only for summary components with a tag";
                        leaf unreachable-component-tag-number {
                          type uint32 {
                            range "1..4294967295" {
                              description
                                "The tag value of the summary component";
                            }
                          }
                          description
                            "The tag value of the summary component";
                        }
                        leaf exclude {
                          type empty;
                          must "../unreachable-component-tag-number";
                          description
                            "Exclude unreachability advertisement for prefixes with a tag";
                        }
                      }
                    }
                    leaf partition-repair {
                      type empty;
                      description
                        "React to area or domain partition - deaggregate by default";
                    }
                  }
                }
              }
              leaf metric {
                type uint32 {
                  range "1..16777214" {
                    description
                      "Default metric: <1-63> for narrow, <1-16777214> for wide";
                  }
                }
                description
                  "Configure default metric";
              }
              container metric-levels {
                description
                  "Set metric for one level only";
                list metric-level {
                  key "level-number";
                  description
                    "Set metric for one level only";
                  leaf level-number {
                    type uint32 {
                      range "1..2" {
                        description
                          "Set metric at this level only";
                      }
                    }
                    description
                      "Set metric for one level only";
                  }
                  leaf metric {
                    type uint32 {
                      range "1..16777214" {
                        description
                          "Default metric: <1-63> for narrow, <1-16777214> for wide";
                      }
                    }
                    mandatory true;
                    description
                      "Configure default metric";
                  }
                }
              }
              container auto-cost {
                presence "Auto-cost for bandwidth metric";
                description
                  "Auto-cost for bandwidth metric";
                leaf reference-bandwidth {
                  type uint64 {
                    range "1..18446744073709551615" {
                      description
                        "The reference bandwidth value (kbits/sec)";
                    }
                  }
                  mandatory true;
                  description
                    "Reference-bandwidth configuration for auto-cost";
                }
                leaf granularity {
                  type uint64 {
                    range "1..18446744073709551615" {
                      description
                        "Granularity value (kbits/sec)";
                    }
                  }
                  description
                    "Granularity";
                }
              }
              container metric-style {
                description
                  "Use old-style (ISO 10589) or new-style packet formats";
                choice METRIC-STYLE {
                  description
                    "Use old-style (ISO 10589) or new-style packet formats";
                  case NARROW {
                    container narrow {
                      presence "Use old style of TLVs with narrow metric";
                      description
                        "Use old style of TLVs with narrow metric";
                      leaf transition {
                        type empty;
                        description
                          "Accept both styles of TLVs during transition";
                      }
                    }
                  }
                  case WIDE {
                    container wide {
                      presence "Use new style of TLVs to carry wider metric";
                      description
                        "Use new style of TLVs to carry wider metric";
                      leaf transition {
                        type empty;
                        description
                          "Accept both styles of TLVs during transition";
                      }
                    }
                  }
                  case TRANSITION {
                    leaf transition {
                      type empty;
                      description
                        "Send and accept both styles of TLVs during transition";
                    }
                  }
                }
              }
              container metric-style-levels {
                description
                  "Set metric-style for one level only";
                list metric-style-level {
                  key "level-number";
                  description
                    "Set metric-style for one level only";
                  leaf level-number {
                    type uint32 {
                      range "1..2" {
                        description
                          "Level";
                      }
                    }
                    description
                      "Level";
                  }
                  choice METRIC-STYLE {
                    mandatory true;
                    description
                      "metric-sytle";
                    case NARROW {
                      container narrow {
                        presence "Use old style of TLVs with narrow metric";
                        description
                          "Use old style of TLVs with narrow metric";
                        leaf transition {
                          type empty;
                          description
                            "Accept both styles of TLVs during transition";
                        }
                      }
                    }
                    case WIDE {
                      container wide {
                        presence "Use new style of TLVs to carry wider metric";
                        description
                          "Use new style of TLVs to carry wider metric";
                        leaf transition {
                          type empty;
                          description
                            "Accept both styles of TLVs during transition";
                        }
                      }
                    }
                    case TRANSITION {
                      leaf transition {
                        type empty;
                        description
                          "Send and accept both styles of TLVs during transition";
                      }
                    }
                  }
                }
              }
              container spf-interval {
                description
                  "Route calculation scheduling parameters (FSPF, PRC)";
                container ietf {
                  presence "Use RFC 8405 backoff algorithm";
                  description
                    "Use RFC 8405 backoff algorithm";
                  leaf initial-wait {
                    type uint32 {
                      range "0..120000" {
                        description
                          "Delay in milliseconds";
                      }
                    }
                    description
                      "Initial delay before running a route calculation [50]";
                  }
                  leaf short-wait {
                    type uint32 {
                      range "0..120000" {
                        description
                          "Delay in milliseconds";
                      }
                    }
                    description
                      "Short delay before running a route calculation [200]";
                  }
                  leaf long-wait {
                    type uint32 {
                      range "0..120000" {
                        description
                          "Delay in milliseconds";
                      }
                    }
                    description
                      "Long delay before running a route calculation [5000]";
                  }
                  leaf learn-interval {
                    type uint32 {
                      range "0..120000" {
                        description
                          "Delay in milliseconds";
                      }
                    }
                    description
                      "Time To Learn interval for running a route calculation [500]";
                  }
                  leaf holddown-interval {
                    type uint32 {
                      range "0..120000" {
                        description
                          "Delay in milliseconds";
                      }
                    }
                    description
                      "Holddown interval for running a route calculation [10000]";
                  }
                }
                leaf initial-wait {
                  type uint32 {
                    range "0..120000" {
                      description
                        "Delay in milliseconds";
                    }
                  }
                  description
                    "Initial delay before running a route calculation [50]";
                }
                leaf secondary-wait {
                  type uint32 {
                    range "0..120000" {
                      description
                        "Delay in milliseconds";
                    }
                  }
                  description
                    "Secondary delay before running a route calculation [200]";
                }
                leaf maximum-wait {
                  type uint32 {
                    range "0..120000" {
                      description
                        "Delay in milliseconds";
                    }
                  }
                  description
                    "Maximum delay before running a route calculation [5000]";
                }
              }
              container spf-interval-levels {
                description
                  "Set SPF interval for one level only";
                list level {
                  must "ietf or initial-wait or secondary-wait or maximum-wait";
                  key "level-number";
                  description
                    "Set SPF interval for one level only";
                  leaf level-number {
                    type uint32 {
                      range "1..2" {
                        description
                          "Level";
                      }
                    }
                    description
                      "Level";
                  }
                  container ietf {
                    presence "Use RFC 8405 backoff algorithm";
                    description
                      "Use RFC 8405 backoff algorithm";
                    leaf initial-wait {
                      type uint32 {
                        range "0..120000" {
                          description
                            "Delay in milliseconds";
                        }
                      }
                      description
                        "Initial delay before running a route calculation [50]";
                    }
                    leaf short-wait {
                      type uint32 {
                        range "0..120000" {
                          description
                            "Delay in milliseconds";
                        }
                      }
                      description
                        "Short delay before running a route calculation [200]";
                    }
                    leaf long-wait {
                      type uint32 {
                        range "0..120000" {
                          description
                            "Delay in milliseconds";
                        }
                      }
                      description
                        "Long delay before running a route calculation [5000]";
                    }
                    leaf learn-interval {
                      type uint32 {
                        range "0..120000" {
                          description
                            "Delay in milliseconds";
                        }
                      }
                      description
                        "Time To Learn interval for running a route calculation [500]";
                    }
                    leaf holddown-interval {
                      type uint32 {
                        range "0..120000" {
                          description
                            "Delay in milliseconds";
                        }
                      }
                      description
                        "Holddown interval for running a route calculation [10000]";
                    }
                  }
                  leaf initial-wait {
                    type uint32 {
                      range "0..120000" {
                        description
                          "Delay in milliseconds";
                      }
                    }
                    description
                      "Initial delay before running a route calculation [50]";
                  }
                  leaf secondary-wait {
                    type uint32 {
                      range "0..120000" {
                        description
                          "Delay in milliseconds";
                      }
                    }
                    description
                      "Secondary delay before running a route calculation [200]";
                  }
                  leaf maximum-wait {
                    type uint32 {
                      range "0..120000" {
                        description
                          "Delay in milliseconds";
                      }
                    }
                    description
                      "Maximum delay before running a route calculation [5000]";
                  }
                }
              }
              container spf {
                description
                  "SPF configuration";
                container prefix-priority {
                  description
                    "Configure a prefix priority list";
                  container critical {
                    description
                      "Specify critical priority prefixes";
                    choice CRITICAL {
                      description
                        "Specify critical priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                  container high {
                    description
                      "Specify critical priority prefixes";
                    choice HIGH {
                      description
                        "Specify critical priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                  container medium {
                    description
                      "Specify critical priority prefixes";
                    choice MEDIUM {
                      description
                        "Specify critical priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                }
                container prefix-priority-critical-levels {
                  description
                    "Configure SPF prefix priority list for one level only";
                  list prefix-priority-critical-level {
                    key "level-number";
                    description
                      "Specify critical priority prefixes";
                    leaf level-number {
                      type uint32 {
                        range "1..2" {
                          description
                            "Level";
                        }
                      }
                      description
                        "Level";
                    }
                    choice PREFIX-PRIORITY-CRITICAL-LEVEL {
                      mandatory true;
                      description
                        "Specify critical priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                }
                container prefix-priority-high-levels {
                  description
                    "Configure SPF prefix priority list for one level only";
                  list prefix-priority-high-level {
                    key "level-number";
                    description
                      "Specify high priority prefixes";
                    leaf level-number {
                      type uint32 {
                        range "1..2" {
                          description
                            "Level";
                        }
                      }
                      description
                        "Level";
                    }
                    choice PREFIX-PRIORITY-HIGH-LEVEL {
                      mandatory true;
                      description
                        "Specify high priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                }
                container prefix-priority-medium-levels {
                  description
                    "Configure SPF prefix priority list for one level only";
                  list prefix-priority-medium-level {
                    key "level-number";
                    description
                      "Specify medium priority prefixes";
                    leaf level-number {
                      type uint32 {
                        range "1..2" {
                          description
                            "Level";
                        }
                      }
                      description
                        "Level";
                    }
                    choice PREFIX-PRIORITY-MEDIUM-LEVEL {
                      mandatory true;
                      description
                        "Specify medium priority prefixes";
                      case TAG {
                        leaf tag {
                          type uint32 {
                            range "1..4294967295" {
                              description
                                "The tag to indicate priority";
                            }
                          }
                          description
                            "Specify a tag to indicate priority";
                        }
                      }
                      case PREFIXLIST-NAME {
                        leaf prefixlist-name {
                          type string {
                            length "1..1024" {
                              description
                                "Prefix-list name";
                            }
                          }
                          description
                            "Prefix-list name";
                        }
                      }
                    }
                  }
                }
                container periodic {
                  description
                    "Configure the periodic SPF";
                  choice PERIODIC {
                    description
                      "Configure the periodic SPF";
                    case INTERVAL {
                      leaf interval {
                        type uint32 {
                          range "1..3600" {
                            description
                              "Maximum interval in between SPF runs in seconds";
                          }
                        }
                        description
                          "Set the maximum interval in between SPF runs";
                      }
                    }
                    case DISABLE {
                      leaf disable {
                        type empty;
                        description
                          "Disable the periodic SPF";
                      }
                    }
                  }
                }
                container periodic-levels {
                  description
                    "Configure periodic SPF interval for for one level only";
                  list periodic-level {
                    must "interval or disable";
                    key "level-number";
                    description
                      "Configure periodic SPF interval for for one level only";
                    leaf level-number {
                      type uint32 {
                        range "1..2" {
                          description
                            "Level";
                        }
                      }
                      description
                        "Level";
                    }
                    choice PERIODIC {
                      description
                        "periodic";
                      case INTERVAL {
                        leaf interval {
                          type uint32 {
                            range "1..3600" {
                              description
                                "Maximum interval in between SPF runs in seconds";
                            }
                          }
                          description
                            "Set the maximum interval in between SPF runs";
                        }
                      }
                      case DISABLE {
                        leaf disable {
                          type empty;
                          description
                            "Disable the periodic SPF";
                        }
                      }
                    }
                  }
                }
              }
              leaf maximum-redistributed-prefixes {
                type uint32 {
                  range "1..28000" {
                    description
                      "maximum limit on number of redistributed prefixes";
                  }
                }
                description
                  "Maximum number of redistributed prefixes";
              }
              container maximum-redistributed-prefixes-levels {
                description
                  "Set maximum redistributed prefixes for one level only";
                list maximum-redistributed-prefixes-level {
                  key "level-number";
                  description
                    "Set maximum redistributed prefixes for one level only";
                  leaf level-number {
                    type uint32 {
                      range "1..2" {
                        description
                          "Level";
                      }
                    }
                    description
                      "Set maximum redistributed prefixes for one level only";
                  }
                  leaf maximum-redistributed-prefixes {
                    type uint32 {
                      range "1..28000" {
                        description
                          "maximum limit on number of redistributed prefixes";
                      }
                    }
                    mandatory true;
                    description
                      "Maximum number of redistributed prefixes";
                  }
                }
              }
              container propagate {
                description
                  "Propagate routes between IS-IS levels";
                container levels {
                  description
                    "Propagate routes between IS-IS levels";
                  list level {
                    must "route-policy";
                    key "source-level destination-level";
                    description
                      "Propagate routes between IS-IS levels";
                    leaf source-level {
                      type uint32 {
                        range "1..2" {
                          description
                            "Level";
                        }
                      }
                      description
                        "Source level";
                    }
                    leaf destination-level {
                      type uint32 {
                        range "1..2" {
                          description
                            "Level";
                        }
                      }
                      description
                        "Destination level";
                    }
                    leaf route-policy {
                      type xr:Route-policy-name;
                      description
                        "Propagate only specified routes";
                    }
                  }
                }
              }
              container adjacency-check {
                description
                  "Suppress checking of consistent AF support on received IIHs";
                leaf disable {
                  type empty;
                  description
                    "Disable adjacency-checking";
                }
              }
              container route {
                description
                  "Control the advertisement of routes in the RIB";
                container source {
                  description
                    "Control the path source value";
                  leaf first-hop {
                    type empty;
                    description
                      "Use the IP address of the first-hop";
                  }
                }
              }
              container attached-bit {
                description
                  "Modify behavior of the attached-bit";
                container receive {
                  description
                    "Modify how we treat received attached bits";
                  leaf ignore {
                    type empty;
                    description
                      "Ignore the attached bit in received LSPs";
                  }
                }
                leaf send {
                  type enumeration {
                    enum "always-set" {
                      value 1;
                      description
                        "Always set the attached bit in our LSP";
                    }
                    enum "never-set" {
                      value 2;
                      description
                        "Never set the attached bit our LSP";
                    }
                  }
                  description
                    "Modify how we set the attached bit";
                }
              }
              leaf topology-id {
                type uint32 {
                  range "6..4095" {
                    description
                      "The IS-IS MT ID to identify the topology";
                  }
                }
                description
                  "Specify the IS-IS MT ID for this topology";
              }
              container fast-reroute {
                description
                  "Configure Fast ReRoute";
                container per-prefix {
                  description
                    "Prefix dependent computation";
                  container srlg-protection {
                    description
                      "Type of SRLG protection";
                    leaf weighted-global {
                      type empty;
                      description
                        "Weighted global SRLG protection";
                    }
                    container weighted-global-levels {
                      description
                        "Set SRLG protection type for one level only";
                      list weighted-global-level {
                        key "level-number";
                        description
                          "Set SRLG protection type for one level only";
                        leaf level-number {
                          type uint32 {
                            range "1..2" {
                              description
                                "Level";
                            }
                          }
                          description
                            "Set SRLG protection type for one level only";
                        }
                      }
                    }
                  }
                  container remote-lfa {
                    description
                      "Enable remote LFA related configuration";
                    leaf prefix-list {
                      type string {
                        length "1..1024" {
                          description
                            "Prefix-list name";
                        }
                      }
                      description
                        "Filter PQ node router ID based on prefix list";
                    }
                    container prefix-list-levels {
                      description
                        "Enable router ID filtering for one level only";
                      list prefix-list-level {
                        key "level-number";
                        description
                          "Enable router ID filtering for one level only";
                        leaf level-number {
                          type uint32 {
                            range "1..2" {
                              description
                                "Level";
                            }
                          }
                          description
                            "Enable router ID filtering for one level only";
                        }
                        leaf prefix-list {
                          type string {
                            length "1..1024" {
                              description
                                "Prefix-list name";
                            }
                          }
                          mandatory true;
                          description
                            "Filter PQ node router ID based on prefix list";
                        }
                      }
                    }
                  }
                  container load-sharing {
                    description
                      "Load share prefixes across multiple backups";
                    leaf disable {
                      type empty;
                      description
                        "Disable load sharing";
                    }
                    container disable-levels {
                      description
                        "Disable load sharing for one level only";
                      list disable-level {
                        key "level-number";
                        description
                          "Disable load sharing for one level only";
                        leaf level-number {
                          type uint32 {
                            range "1..2" {
                              description
                                "Level";
                            }
                          }
                          description
                            "Disable load sharing for one level only";
                        }
                      }
                    }
                  }
                  container tiebreaker {
                    description
                      "Configure tiebreaker for multiple backups";
                    container downstream {
                      description
                        "Prefer backup path via downstream node";
                      leaf index {
                        type uint32 {
                          range "1..255" {
                            description
                              "Index";
                          }
                        }
                        description
                          "Set preference order among tiebreakers";
                      }
                    }
                    container lc-disjoint {
                      description
                        "Prefer line card disjoint backup path";
                      leaf index {
                        type uint32 {
                          range "1..255" {
                            description
                              "Index";
                          }
                        }
                        description
                          "Set preference order among tiebreakers";
                      }
                    }
                    container lowest-backup-metric {
                      description
                        "Prefer backup path with lowest total metric";
                      leaf index {
                        type uint32 {
                          range "1..255" {
                            description
                              "Index";
                          }
                        }
                        description
                          "Set preference order among tiebreakers";
                      }
                    }
                    container node-protecting {
                      description
                        "Prefer node protecting backup path";
                      leaf index {
                        type uint32 {
                          range "1..255" {
                            description
                              "Index";
                          }
                        }
                        description
                          "Set preference order among tiebreakers";
                      }
                    }
                    container primary-path {
                      description
                        "Prefer backup path from ECMP set";
                      leaf index {
                        type uint32 {
                          range "1..255" {
                            description
                              "Index";
                          }
                        }
                        description
                          "Set preference order among tiebreakers";
                      }
                    }
                    container secondary-path {
                      description
                        "Prefer non-ECMP backup path";
                      leaf index {
                        type uint32 {
                          range "1..255" {
                            description
                              "Index";
                          }
                        }
                        description
                          "Set preference order among tiebreakers";
                      }
                    }
                    container srlg-disjoint {
                      description
                        "Prefer SRLG disjoint backup path";
                      leaf index {
                        type uint32 {
                          range "1..255" {
                            description
                              "Index";
                          }
                        }
                        description
                          "Set preference order among tiebreakers";
                      }
                    }
                  }
                  container tiebreaker-downstream-levels {
                    description
                      "Configure tiebreaker for one level only";
                    list tiebreaker-downstream-level {
                      key "level-number";
                      description
                        "Prefer backup path via downstream node";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-lc-disjoint-levels {
                    description
                      "Configure tiebreaker for one level only";
                    list tiebreaker-lc-disjoint-level {
                      key "level-number";
                      description
                        "Configure tiebreaker for one level only";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-lowest-backup-metric-levels {
                    description
                      "Configure tiebreaker for one level only";
                    list tiebreaker-lowest-backup-metric-level {
                      key "level-number";
                      description
                        "Prefer backup path with lowest total metric";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-node-protecting-levels {
                    description
                      "Configure tiebreaker for one level only";
                    list tiebreaker-node-protecting-level {
                      key "level-number";
                      description
                        "Prefer node protecting backup path";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-primary-path-levels {
                    description
                      "Configure tiebreaker for one level only";
                    list tiebreaker-primary-path-level {
                      key "level-number";
                      description
                        "Prefer backup path from ECMP set";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-secondary-path-levels {
                    description
                      "Configure tiebreaker for one level only";
                    list tiebreaker-secondary-path-level {
                      key "level-number";
                      description
                        "Prefer non-ECMP backup path";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  container tiebreaker-srlg-disjoint-levels {
                    description
                      "Configure tiebreaker for one level only";
                    list tiebreaker-srlg-disjoint-level {
                      key "level-number";
                      description
                        "Prefer SRLG disjoint backup path";
                      leaf level-number {
                        type uint32 {
                          range "1..2" {
                            description
                              "Level";
                          }
                        }
                        description
                          "Level";
                      }
                      leaf index {
                        type uint32 {
                          range "1..255" {
                            description
                              "Index";
                          }
                        }
                        mandatory true;
                        description
                          "Set preference order among tiebreakers";
                      }
                    }
                  }
                  leaf use-candidate-only {
                    type empty;
                    description
                      "Exclude all interfaces from computation";
                  }
                  container use-candidate-only-levels {
                    description
                      "Exclude all interfaces for one level only";
                    list use-candidate-only-level {
                      key "level-number";
                      description
                        "Exclude all interfaces for one level only";
                      leaf level-number {
                        type uint32 {
                          range "1..2" {
                            description
                              "Level";
                          }
                        }
                        description
                          "Level";
                      }
                    }
                  }
                  leaf priority-limit {
                    type enumeration {
                      enum "critical" {
                        value 0;
                        description
                          "Compute for critical priority prefixes only";
                      }
                      enum "high" {
                        value 1;
                        description
                          "Compute for critical & high priority prefixes";
                      }
                      enum "medium" {
                        value 2;
                        description
                          "Compute for critical, high & medium priority prefixes";
                      }
                    }
                    description
                      "Limit backup computation upto the prefix priority";
                  }
                  container priority-limit-levels {
                    description
                      "Set priority-limit for one level only";
                    list priority-limit-level {
                      key "level-number";
                      description
                        "Set priority-limit for one level only";
                      leaf level-number {
                        type uint32 {
                          range "1..2" {
                            description
                              "Level";
                          }
                        }
                        description
                          "Level";
                      }
                      leaf priority-limit {
                        type enumeration {
                          enum "critical" {
                            value 0;
                            description
                              "Compute for critical priority prefixes only";
                          }
                          enum "high" {
                            value 1;
                            description
                              "Compute for critical & high priority prefixes";
                          }
                          enum "medium" {
                            value 2;
                            description
                              "Compute for critical, high & medium priority prefixes";
                          }
                        }
                        mandatory true;
                        description
                          "Limit backup computation upto the prefix priority";
                      }
                    }
                  }
                }
                container per-link {
                  description
                    "Prefix independent per-link computation";
                  leaf use-candidate-only {
                    type empty;
                    description
                      "Exclude all interfaces from computation";
                  }
                  container use-candidate-only-levels {
                    description
                      "Exclude all interfaces for one level only";
                    list use-candidate-only-level {
                      key "level-number";
                      description
                        "Exclude all interfaces for one level only";
                      leaf level-number {
                        type uint32 {
                          range "1..2" {
                            description
                              "Level";
                          }
                        }
                        description
                          "Level";
                      }
                    }
                  }
                  leaf priority-limit {
                    type enumeration {
                      enum "critical" {
                        value 0;
                        description
                          "Compute for critical priority prefixes only";
                      }
                      enum "high" {
                        value 1;
                        description
                          "Compute for critical & high priority prefixes";
                      }
                      enum "medium" {
                        value 2;
                        description
                          "Compute for critical, high & medium priority prefixes";
                      }
                    }
                    description
                      "Limit backup computation upto the prefix priority";
                  }
                  container priority-limit-levels {
                    description
                      "Set priority-limit for one level only";
                    list priority-limit-level {
                      key "level-number";
                      description
                        "Set priority-limit for one level only";
                      leaf level-number {
                        type uint32 {
                          range "1..2" {
                            description
                              "Level";
                          }
                        }
                        description
                          "Level";
                      }
                      leaf priority-limit {
                        type enumeration {
                          enum "critical" {
                            value 0;
                            description
                              "Compute for critical priority prefixes only";
                          }
                          enum "high" {
                            value 1;
                            description
                              "Compute for critical & high priority prefixes";
                          }
                          enum "medium" {
                            value 2;
                            description
                              "Compute for critical, high & medium priority prefixes";
                          }
                        }
                        mandatory true;
                        description
                          "Limit backup computation upto the prefix priority";
                      }
                    }
                  }
                }
                leaf delay-interval {
                  type uint32 {
                    range "100..60000" {
                      description
                        "Delay before running FRR (milliseconds)";
                    }
                  }
                  description
                    "Delay before running FRR computation";
                }
              }
              leaf single-topology {
                when "../af-name = 'ipv6' and ../saf-name = 'unicast'";
                type empty;
                description
                  "Run IPv6 Unicast using the standard (IPv4 Unicast) topology";
              }
              container default-information {
                description
                  "Control distribution of default information";
                container originate {
                  presence "Distribute a default route";
                  description
                    "Distribute a default route";
                  leaf external {
                    type empty;
                    description
                      "Originate default prefix as an external route";
                  }
                  container route-policy {
                    presence "Route policy reference";
                    description
                      "Route policy reference";
                    leaf text {
                      type xr:Route-policy-name;
                      mandatory true;
                      description
                        "text";
                    }
                  }
                }
              }
              container segment-routing {
                description
                  "Enable Segment Routing";
                container srv6 {
                  presence "Enable SRv6";
                  description
                    "Enable SRv6";
                  container capability-subsubtlv {
                    when "../../../af-name = 'ipv6' and ../../../saf-name = 'unicast'";
                    if-feature "isis_srv6_is_srv6_cap_config_supported";
                    description
                      "Specify SRv6 Capability subsub TLV";
                    leaf max-sl {
                      type uint32 {
                        range "0..255" {
                          description
                            "Max SL Value";
                        }
                      }
                      description
                        "Specify the value of Max SL subsub TLV";
                    }
                    leaf max-end-pop-srh {
                      type uint32 {
                        range "0..255" {
                          description
                            "Max End Pop SRH Value";
                        }
                      }
                      description
                        "Specify the value of Max-End-Pop-SRH subsub TLV";
                    }
                    leaf max-t-insert {
                      type uint32 {
                        range "0..255" {
                          description
                            "Max End T Insert Value";
                        }
                      }
                      description
                        "Specify the value of Max-T.Insert subsub TLV";
                    }
                    leaf max-t-encap {
                      type uint32 {
                        range "0..255" {
                          description
                            "Max End T Encap Value";
                        }
                      }
                      description
                        "Specify the value of Max-T.Encap subsub TLV";
                    }
                    leaf max-end-d {
                      type uint32 {
                        range "0..255" {
                          description
                            "Max End End DValue";
                        }
                      }
                      description
                        "Specify the value of Max-End-D subsub TLV";
                    }
                  }
                  container encapsulate {
                    when "../../../af-name = 'ipv6' and ../../../saf-name = 'unicast'";
                    description
                      "Encapsulate traffic for specified prefixes";
                    choice ENCAPSULATE {
                      description
                        "Encapsulate traffic for specified prefixes";
                      case PREFIX-LIST {
                        leaf prefix-list {
                          type xr:Cisco-ios-xr-string {
                            length "1..1024";
                          }
                          description
                            "Encapsulate destinations based on a prefix list";
                        }
                      }
                      case ROUTE-POLICY {
                        leaf route-policy {
                          type xr:Route-policy-name;
                          description
                            "Encapsulate destinations based on a route policy";
                        }
                      }
                    }
                  }
                  container locators {
                    description
                      "Enter SRv6 Locator submode";
                    list locator {
                      key "locator-string";
                      description
                        "Enter SRv6 Locator submode";
                      leaf locator-string {
                        type xr:Cisco-ios-xr-string {
                          length "1..59" {
                            description
                              "Locator name";
                          }
                        }
                        description
                          "Locator name";
                      }
                      leaf level {
                        when "../../../../../af-name = 'ipv6' and ../../../../../saf-name = 'unicast'";
                        type uint32 {
                          range "1..2" {
                            description
                              "Level";
                          }
                        }
                        description
                          "Advertise the locator only in the specified level";
                      }
                      leaf metric {
                        when "../../../../../af-name = 'ipv6' and ../../../../../saf-name = 'unicast'";
                        type uint32 {
                          range "1..16777214" {
                            description
                              "Srv6 locator metric";
                          }
                        }
                        description
                          "Advertise the locator metric for a given level";
                      }
                      container metric-levels {
                        description
                          "Set Metric for one level only";
                        list metric-level {
                          key "level-number";
                          description
                            "Set Metric for one level only";
                          leaf level-number {
                            type uint32 {
                              range "1..2" {
                                description
                                  "Set Metric at this level only";
                              }
                            }
                            description
                              "Set Metric for one level only";
                          }
                          leaf metric {
                            type uint32 {
                              range "1..16777214" {
                                description
                                  "Srv6 locator metric";
                              }
                            }
                            mandatory true;
                            description
                              "Srv6 locator metric";
                          }
                        }
                      }
                      leaf tag {
                        when "../../../../../af-name = 'ipv6' and ../../../../../saf-name = 'unicast'";
                        type uint32 {
                          range "1..4294967295" {
                            description
                              "Srv6 locator tag";
                          }
                        }
                        description
                          "Advertise the locator tag for a given level";
                      }
                      container tag-levels {
                        description
                          "Set Tag for one level only";
                        list tag-level {
                          key "level-number";
                          description
                            "Set Tag for one level only";
                          leaf level-number {
                            type uint32 {
                              range "1..2" {
                                description
                                  "Set Tag at this level only";
                              }
                            }
                            description
                              "Set Tag for one level only";
                          }
                          leaf tag {
                            type uint32 {
                              range "1..4294967295" {
                                description
                                  "Srv6 locator tag";
                              }
                            }
                            mandatory true;
                            description
                              "Srv6 locator tag";
                          }
                        }
                      }
                    }
                  }
                }
                container mpls {
                  description
                    "Enable Segment Routing using MPLS encapsulation";
                  leaf enable {
                    type empty;
                    description
                      "Enable Segment Routing using MPLS encapsulation";
                  }
                  leaf sr-prefer {
                    type empty;
                    description
                      "Prefer segment routing labels over LDP labels";
                  }
                  container unlabeled {
                    description
                      "Options for prefixes without a segment-routing label";
                    container protection {
                      description
                        "TI-LFA and microloop protection";
                      choice PROTECTION {
                        description
                          "TI-LFA and microloop protection";
                        case PREFIX-LIST {
                          leaf prefix-list {
                            type string {
                              length "1..1024" {
                                description
                                  "Prefix-list name";
                              }
                            }
                            description
                              "Enable TI-LFA and microloop protection based on a prefix list";
                          }
                        }
                        case ROUTE-POLICY {
                          leaf route-policy {
                            type xr:Route-policy-name;
                            description
                              "Enable TI-LFA and microloop protection based on a route policy";
                          }
                        }
                        case DISABLE {
                          leaf disable {
                            type empty;
                            description
                              "Disable TI-LFA and microloop protection";
                          }
                        }
                      }
                    }
                  }
                  container prefix-sid-map {
                    description
                      "Enable prefix-sid-map";
                    container receive {
                      presence "Use remote mapping server advertisements";
                      description
                        "Use remote mapping server advertisements";
                      leaf disable {
                        type empty;
                        description
                          "disable";
                      }
                    }
                    container advertise-local {
                      presence "Advertise active local prefix-SID mappings";
                      description
                        "Advertise active local prefix-SID mappings";
                      leaf domain-wide {
                        type empty;
                        description
                          "Domain wide prefix-SID mappings";
                      }
                    }
                  }
                  container connected-prefix-sid-map {
                    presence "Enter connected prefix sid map submode";
                    description
                      "Enter connected prefix sid map submode";
                    container addresses {
                      description
                        "Specify prefix associated with this Prefix Segement ID";

                      grouping OPTIONS {
                        description
                          "OPTIONS";
                        leaf interface {
                          type xr:Interface-name;
                          description
                            "Specify the interface associated with the prefix sid";
                        }
                        leaf php-disable {
                          type empty;
                          description
                            "Disable Penultimate Hop Popping";
                        }
                        leaf explicit-null {
                          type empty;
                          description
                            "Upstream neighbor must replace prefix-sid with explicit null label";
                        }
                      }
                      list address {
                        must "index or absolute";
                        key "ip-address address-prefix";
                        description
                          "Specify prefix associated with this Prefix Segement ID";
                        leaf ip-address {
                          type inet:ip-address-no-zone;
                          description
                            "IP address";
                        }
                        leaf address-prefix {
                          type uint32 {
                            range "0..128" {
                              description
                                "IP address prefix";
                            }
                          }
                          description
                            "IP address prefix";
                        }
                        choice ADDRESS {
                          description
                            "ADDRESS";
                          case INDEX {
                            container index {
                              presence "Specify the index of Prefix Segement ID";
                              description
                                "Specify the index of Prefix Segement ID";
                              leaf index-id {
                                type uint32 {
                                  range "0..1048575" {
                                    description
                                      "The Prefix Segment ID index";
                                  }
                                }
                                mandatory true;
                                description
                                  "The Prefix Segment ID index";
                              }
                              uses OPTIONS;
                            }
                          }
                          case ABSOLUTE {
                            container absolute {
                              presence "Specify the absolute value of Prefix Segement ID";
                              description
                                "Specify the absolute value of Prefix Segement ID";
                              leaf absolute-id {
                                type uint32 {
                                  range "16000..1048575" {
                                    description
                                      "The Prefix Segment ID value";
                                  }
                                }
                                mandatory true;
                                description
                                  "The Prefix Segment ID value";
                              }
                              uses OPTIONS;
                            }
                          }
                        }
                      }
                      list flex-algo-address {
                        must "index or absolute";
                        key "ip-address address-prefix flex-algo";
                        description
                          "Specify prefix associated with this Prefix Segement ID";
                        leaf ip-address {
                          type inet:ip-address-no-zone;
                          description
                            "IP address";
                        }
                        leaf address-prefix {
                          type uint32 {
                            range "0..128" {
                              description
                                "IP address prefix";
                            }
                          }
                          description
                            "IP address prefix";
                        }
                        leaf flex-algo {
                          type uint32 {
                            range "128..255" {
                              description
                                "Algo number";
                            }
                          }
                          description
                            "Specify the custom flex-algo algorithm to use";
                        }
                        choice FLEX-ALGO-ADDRESS {
                          description
                            "FLEX-ALGO-ADDRESS";
                          case INDEX {
                            container index {
                              presence "Specify the index of Prefix Segement ID";
                              description
                                "Specify the index of Prefix Segement ID";
                              leaf index-id {
                                type uint32 {
                                  range "0..1048575" {
                                    description
                                      "The Prefix Segment ID index";
                                  }
                                }
                                mandatory true;
                                description
                                  "The Prefix Segment ID index";
                              }
                              uses OPTIONS;
                            }
                          }
                          case ABSOLUTE {
                            container absolute {
                              presence "Specify the absolute value of Prefix Segement ID";
                              description
                                "Specify the absolute value of Prefix Segement ID";
                              leaf absolute-id {
                                type uint32 {
                                  range "16000..1048575" {
                                    description
                                      "The Prefix Segment ID value";
                                  }
                                }
                                mandatory true;
                                description
                                  "The Prefix Segment ID value";
                              }
                              uses OPTIONS;
                            }
                          }
                        }
                      }
                      list strict-spf-address {
                        must "index or absolute";
                        key "ip-address address-prefix";
                        description
                          "Specify prefix associated with this Prefix Segement ID";
                        leaf ip-address {
                          type inet:ip-address-no-zone;
                          description
                            "IP address";
                        }
                        leaf address-prefix {
                          type uint32 {
                            range "0..128" {
                              description
                                "IP address prefix";
                            }
                          }
                          description
                            "IP address prefix";
                        }
                        choice STRICT-SPF-ADDRESS {
                          description
                            "STRICT-SPF-ADDRESS";
                          case INDEX {
                            container index {
                              presence "Specify the index of Prefix Segement ID";
                              description
                                "Specify the index of Prefix Segement ID";
                              leaf index-id {
                                type uint32 {
                                  range "0..1048575" {
                                    description
                                      "The Prefix Segment ID index";
                                  }
                                }
                                mandatory true;
                                description
                                  "The Prefix Segment ID index";
                              }
                              uses OPTIONS;
                            }
                          }
                          case ABSOLUTE {
                            container absolute {
                              presence "Specify the absolute value of Prefix Segement ID";
                              description
                                "Specify the absolute value of Prefix Segement ID";
                              leaf absolute-id {
                                type uint32 {
                                  range "16000..1048575" {
                                    description
                                      "The Prefix Segment ID value";
                                  }
                                }
                                mandatory true;
                                description
                                  "The Prefix Segment ID value";
                              }
                              uses OPTIONS;
                            }
                          }
                        }
                      }
                    }
                  }
                }
                leaf bundle-member-adj-sid {
                  type empty;
                  description
                    "Enable per bundle member adjacency SID";
                }
                leaf labeled-only {
                  type empty;
                  description
                    "Only install SR labeled paths";
                }
                leaf protected-adjacency-sid-delay {
                  type uint32 {
                    range "30..3600" {
                      description
                        "seconds";
                    }
                  }
                  description
                    "Protected Adjacency SID deletion delay (seconds)";
                }
              }
              container partition-detect {
                presence "Detect area or domain partition";
                description
                  "Detect area or domain partition";
                container tracks {
                  description
                    "Track ABR or ASBR reachability";
                  list track {
                    must "ipv4 or ipv6";
                    key "address";
                    description
                      "Track ABR or ASBR reachability";
                    leaf address {
                      type inet:ip-address-no-zone;
                      description
                        "IPaddress";
                    }
                    leaf ipv4 {
                      type empty;
                      description
                        "Ipv4 Track";
                    }
                    leaf ipv6 {
                      type empty;
                      description
                        "Ipv6 Track";
                    }
                  }
                }
                container external-address-tracks {
                  description
                    "Track ABR or ASBR reachability";
                  list external-address-track {
                    key "address";
                    description
                      "Track ABR or ASBR reachability";
                    leaf address {
                      type inet:ip-address-no-zone;
                      description
                        "IPaddress";
                    }
                    leaf external-address {
                      type inet:ip-address-no-zone;
                      mandatory true;
                      description
                        "External ASBR address to track";
                    }
                  }
                }
              }
              container mpls {
                when "../af-name = 'ipv4' and ../saf-name = 'unicast'";
                description
                  "Configure MPLS routing protocol parameters";
                container traffic-eng {
                  description
                    "Routing protocol commands for MPLS Traffic Engineering";
                  container router-id {
                    description
                      "Traffic Engineering stable IP address for system";
                    choice ROUTER-ID {
                      description
                        "ROUTER-ID";
                      case IPV4-ADDRESS {
                        leaf ipv4-address {
                          type inet:ipv4-address-no-zone;
                          description
                            "ipv4-address";
                        }
                      }
                      case INTERFACE-NAME {
                        leaf interface-name {
                          type xr:Interface-name;
                          description
                            "interface-name";
                        }
                      }
                    }
                  }
                  leaf igp-intact {
                    type empty;
                    description
                      "Install both TE and non-TE nexthops in the RIB.";
                  }
                  leaf multicast-intact {
                    type empty;
                    description
                      "Install non-TE nexthops in the RIB for use by multicast";
                  }
                  container tunnel {
                    description
                      "Tunnel selection";
                    leaf restricted {
                      type empty;
                      description
                        "Use only primary tunnel for destination IP address";
                    }
                    leaf preferred {
                      type empty;
                      description
                        "Prefer TE tunnels over equal-cost physical paths";
                    }
                    leaf metric {
                      type uint32 {
                        range "1..16777214" {
                          description
                            "Default metric for forwarding-adjacency tunnels";
                        }
                      }
                      description
                        "Default metric for forwarding-adjacency tunnels";
                    }
                    container metric-levels {
                      description
                        "Set metric for one level only";
                      list metric-level {
                        key "level-number";
                        description
                          "Set metric for one level only";
                        leaf level-number {
                          type uint32 {
                            range "1..2" {
                              description
                                "Set metric at this level only";
                            }
                          }
                          description
                            "Set metric at this level only";
                        }
                        leaf metric {
                          type uint32 {
                            range "1..16777214" {
                              description
                                "Default metric for forwarding-adjacency tunnels";
                            }
                          }
                          mandatory true;
                          description
                            "Default metric for forwarding-adjacency tunnels";
                        }
                      }
                    }
                    leaf anycast-prefer-igp-cost {
                      type empty;
                      description
                        "Prefer anycast prefix with lowest IGP cost";
                    }
                  }
                  container traffic-eng-level {
                    description
                      "traffic-eng-level";
                    choice TRAFFIC-ENG-LEVEL {
                      description
                        "TRAFFIC-ENG-LEVEL";
                      case LEVEL-ONE-TWO {
                        leaf level-one-two {
                          type empty;
                          description
                            "Enable mpls traffic-eng at both level 1 and 2";
                        }
                      }
                      case LEVEL-ONE {
                        leaf level-one {
                          type empty;
                          description
                            "Enable mpls traffic-eng at level 1";
                        }
                      }
                      case LEVEL-TWO-ONLY {
                        leaf level-two-only {
                          type empty;
                          description
                            "Enable mpls traffic-eng at level 2";
                        }
                      }
                    }
                  }
                }
                container ldp {
                  description
                    "Configure LDP parameters";
                  leaf auto-config {
                    type empty;
                    description
                      "Enable LDP IGP interface auto-configuration";
                  }
                }
              }
              container prefix-unreachable {
                presence "Prefix Unreachablity";
                description
                  "Prefix Unreachablity";
                leaf adv-maximum {
                  type uint32 {
                    range "1..65535" {
                      description
                        "Number of prefix-unreachable advertisements";
                    }
                  }
                  description
                    "Maximum number of prefix-unreachable advertisements";
                }
                leaf adv-lifetime {
                  type uint32 {
                    range "30..65535" {
                      description
                        "Lifetime value";
                    }
                  }
                  description
                    "Lifetime of the prefix-unreachable advertisements";
                }
                leaf adv-metric {
                  type uint32 {
                    range "4261412865..4294967294" {
                      description
                        "Metric value";
                    }
                  }
                  description
                    "Metric of the prefix-unreachable advertisements";
                }
                leaf rx-process-enable {
                  type empty;
                  description
                    "Enable processing of received prefix-unreachable advertisements";
                }
              }
              container monitor-convergence {
                presence "Enables convergence monitoring";
                description
                  "Enables convergence monitoring";
                leaf prefix-list {
                  type string {
                    length "1..1024" {
                      description
                        "Prefix List Name";
                    }
                  }
                  description
                    "Enables Individual Prefix Monitoring";
                }
                leaf track-ip-frr {
                  type empty;
                  description
                    "Enables Tracking IP-Frr Convergence";
                }
              }
            }
            list address-family {
              key "af-name saf-name";
              description
                "Enter the IS-IS address-family configuration submode";
              leaf af-name {
                type enumeration {
                  enum "ipv4" {
                    value 0;
                    description
                      "IPv4 address family";
                  }
                  enum "ipv6" {
                    value 1;
                    description
                      "IPv6 address family";
                  }
                }
                description
                  "af-name";
              }
              leaf saf-name {
                type enumeration {
                  enum "unicast" {
                    value 0;
                    description
                      "unicast topology";
                  }
                  enum "multicast" {
                    value 1;
                    description
                      "multicast topology";
                  }
                }
                description
                  "saf-name";
              }
              uses ISIS-AF;
            }
            list address-family-topology {
              key "af-name saf-name topology-name";
              description
                "Enter the IS-IS address-family configuration submode";
              leaf af-name {
                type enumeration {
                  enum "ipv4" {
                    value 0;
                    description
                      "IPv4 address family";
                  }
                  enum "ipv6" {
                    value 1;
                    description
                      "IPv6 address family";
                  }
                }
                description
                  "af-name";
              }
              leaf saf-name {
                type enumeration {
                  enum "unicast" {
                    value 0;
                    description
                      "unicast topology";
                  }
                  enum "multicast" {
                    value 1;
                    description
                      "multicast topology";
                  }
                }
                description
                  "saf-name";
              }
              leaf topology-name {
                type xr:Cisco-ios-xr-string {
                  length "1..32" {
                    description
                      "Topology name";
                  }
                }
                description
                  "Specify a non-default topology";
              }
              uses ISIS-AF;
            }
          }
          container link-groups {
            description
              "Link Group";
            list link-group {
              key "link-group-name";
              description
                "Link Group";
              leaf link-group-name {
                type xr:Cisco-ios-xr-string {
                  length "1..1024" {
                    description
                      "link group name";
                  }
                }
                description
                  "link group name";
              }
              leaf minimum-members {
                type uint32 {
                  range "2..64" {
                    description
                      "count";
                  }
                }
                description
                  "Minimum number of members in the link group";
              }
              leaf revert-members {
                type uint32 {
                  range "2..64" {
                    description
                      "count";
                  }
                }
                description
                  "Number of members after which to revert in the link group";
              }
              container metric-offset {
                description
                  "Configure the metric offset for link group";
                choice METRIC-OFFSET {
                  description
                    "METRIC-OFFSET";
                  case MAXIMUM {
                    leaf maximum {
                      type empty;
                      description
                        "Maximum wide metric offset. All routers will exclude this link from their SPF";
                    }
                  }
                  case DEFAULT-METRIC-OFFSET {
                    leaf default-metric-offset {
                      type uint32 {
                        range "1..16777214" {
                          description
                            "Default metric offset: <1-63> for narrow, <1-16777214> for wide";
                        }
                      }
                      description
                        "Default metric offset: <1-63> for narrow, <1-16777214> for wide";
                    }
                  }
                }
              }
            }
          }
          container flex-algoes {
            description
              "Flex Algorithm definition";
            list flex-algo {
              key "flex-algo-number";
              description
                "Flex Algorithm definition";

              grouping MAXIMUM-PATHS {
                description
                  "MAXIMUM-PATHS";
                container maximum-paths {
                  description
                    "Maximum number of active parallel paths per route";
                  choice MAXIMUM-PATHS {
                    description
                      "MAXIMUM-PATHS";
                    case NUMBER-OF-PATHS {
                      leaf number-of-paths {
                        type uint32 {
                          range "1..64" {
                            description
                              "Number of paths";
                          }
                        }
                        description
                          "Number of paths";
                      }
                    }
                    case ROUTE-POLICY {
                      leaf route-policy {
                        type xr:Route-policy-name;
                        description
                          "Filter routes based on a route policy";
                      }
                    }
                  }
                }
              }
              leaf flex-algo-number {
                type uint32 {
                  range "128..255" {
                    description
                      "Algorithm number";
                  }
                }
                description
                  "Algorithm number";
              }
              container auto-cost {
                description
                  "Auto-cost for bandwidth metric";
                container reference {
                  presence "Reference-bandwidth method for auto-cost";
                  description
                    "Reference-bandwidth method for auto-cost";
                  container reference-bandwidth {
                    presence "Reference-bandwidth configuration for auto-cost";
                    description
                      "Reference-bandwidth configuration for auto-cost";
                    leaf reference-bandwidth-number {
                      type uint64 {
                        range "1..18446744073709551615" {
                          description
                            "The reference bandwidth value (kbits/sec)";
                        }
                      }
                      mandatory true;
                      description
                        "The reference bandwidth value (kbits/sec)";
                    }
                    leaf granularity {
                      type uint64 {
                        range "1..18446744073709551615" {
                          description
                            "Granularity value (kbits/sec)";
                        }
                      }
                      description
                        "Granularity";
                    }
                  }
                  leaf group-mode {
                    type empty;
                    description
                      "Enable Group mode for bandwidth metric computation";
                  }
                }
              }
              container affinity {
                description
                  "Specify affinity names";
                container exclude-any {
                  description
                    "Exclude objects in flex-algo calculation";
                  leaf-list exclude-any-argument {
                    type xr:Cisco-ios-xr-string {
                      length "1..32" {
                        description
                          "Affinity to exclude";
                      }
                    }
                    max-elements "32";
                    description
                      "Affinity to exclude";
                  }
                }
                container include-any {
                  description
                    "Include objects in flex-algo calculation";
                  leaf-list include-any-argument {
                    type xr:Cisco-ios-xr-string {
                      length "1..32" {
                        description
                          "Affinity to include";
                      }
                    }
                    max-elements "32";
                    description
                      "Affinity to include";
                  }
                }
                container include-all {
                  description
                    "Include objects in flex-algo calculation";
                  leaf-list include-all-argument {
                    type xr:Cisco-ios-xr-string {
                      length "1..32" {
                        description
                          "Affinity to include";
                      }
                    }
                    max-elements "32";
                    description
                      "Affinity to include";
                  }
                }
                container reverse {
                  description
                    "Apply to links in the reverse direction";
                  container exclude-any {
                    description
                      "Exclude objects in flex-algo calculation";
                    leaf-list exclude-any-argument {
                      type xr:Cisco-ios-xr-string {
                        length "1..32" {
                          description
                            "Reverse affinity to exclude";
                        }
                      }
                      max-elements "32";
                      description
                        "Reverse affinity to exclude";
                    }
                  }
                  container include-any {
                    description
                      "Include objects in flex-algo calculation";
                    leaf-list include-any-argument {
                      type xr:Cisco-ios-xr-string {
                        length "1..32" {
                          description
                            "Reverse affinity to include";
                        }
                      }
                      max-elements "32";
                      description
                        "Reverse affinity to include";
                    }
                  }
                  container include-all {
                    description
                      "Include objects in flex-algo calculation";
                    leaf-list include-all-argument {
                      type xr:Cisco-ios-xr-string {
                        length "1..32" {
                          description
                            "Reverse affinity to include";
                        }
                      }
                      max-elements "32";
                      description
                        "Reverse affinity to include";
                    }
                  }
                }
              }
              leaf minimum-bandwidth {
                type uint32 {
                  range "1..4294967295" {
                    description
                      "Minimum link bandwidth (kbits/sec)";
                  }
                }
                description
                  "Specify minimum link bandwidth";
              }
              leaf maximum-delay {
                type uint32 {
                  range "1..10000000" {
                    description
                      "Maximum link delay (microseconds)";
                  }
                }
                description
                  "Specify maximum link delay";
              }
              container srlg {
                description
                  "Specify SRLG names";
                container exclude-any {
                  description
                    "Exclude objects in flex-algo calculation";
                  leaf-list exclude-any-argument {
                    type xr:Cisco-ios-xr-string {
                      length "1..64" {
                        description
                          "SRLG to exclude";
                      }
                    }
                    max-elements "32";
                    description
                      "SRLG to exclude";
                  }
                }
              }
              leaf priority {
                type uint32 {
                  range "0..255" {
                    description
                      "Priority value";
                  }
                }
                description
                  "Flex-Algo definition priority";
              }
              leaf metric-type {
                type union {
                  type uint32 {
                    range "128..255" {
                      description
                        "Generic metric type";
                    }
                  }
                  type enumeration {
                    enum "delay" {
                      value 1;
                      description
                        "Use delay as metric";
                    }
                    enum "te" {
                      value 2;
                      description
                        "Use Traffic Engineering metric";
                    }
                    enum "bandwidth" {
                      value 3;
                      description
                        "Use bandwidth metric";
                    }
                    enum "generic" {
                      value 4;
                      description
                        "Generic metric";
                    }
                  }
                }
                description
                  "Metric-type used by flex-algo calculation";
              }
              container fast-reroute {
                description
                  "Configure Fast ReRoute";
                leaf disable {
                  type empty;
                  description
                    "Disable Fast ReRoute for Flex-Algo";
                }
              }
              container microloop {
                description
                  "Configure Microloop";
                container avoidance {
                  description
                    "Configure Microloop Avoidance";
                  leaf disable {
                    type empty;
                    description
                      "Disable Microloop Avoidance for Flex-Algo";
                  }
                }
              }
              leaf advertise-definition {
                type empty;
                description
                  "Advertise the Flex-Algo Definition";
              }
              leaf prefix-metric {
                type empty;
                description
                  "Use Flex-Algo Prefix Metric";
              }
              container data-plane {
                description
                  "Flex-Algo Data Plane";
                leaf segment-routing {
                  type empty;
                  description
                    "Segment Routing";
                }
                leaf ip {
                  type empty;
                  description
                    "IP";
                }
              }
              container ucmp {
                description
                  "Configure UCMP";
                leaf disable {
                  type empty;
                  description
                    "Disable Unequal Cost Load Balancing (UCMP) for Flex-Algo";
                }
              }
              container address-families {
                description
                  "Enter the IS-IS Flex-Algo address-family configuration submode";
                list address-family {
                  key "af-name saf-name";
                  description
                    "Enter the IS-IS Flex-Algo address-family configuration submode";
                  leaf af-name {
                    type enumeration {
                      enum "ipv4" {
                        value 0;
                        description
                          "IPv4 address family";
                      }
                      enum "ipv6" {
                        value 1;
                        description
                          "IPv6 address family";
                      }
                    }
                    description
                      "af-name";
                  }
                  leaf saf-name {
                    type enumeration {
                      enum "unicast" {
                        value 0;
                        description
                          "unicast topology";
                      }
                      enum "multicast" {
                        value 1;
                        description
                          "multicast topology";
                      }
                    }
                    description
                      "saf-name";
                  }
                  uses MAXIMUM-PATHS;
                }
              }
            }
          }
        }
      }
    }
  }
}
