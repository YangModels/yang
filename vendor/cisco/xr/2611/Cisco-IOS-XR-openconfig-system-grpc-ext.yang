module Cisco-IOS-XR-openconfig-system-grpc-ext {
  yang-version 1;
  namespace "http://cisco.com/ns/yang/Cisco-IOS-XR-openconfig-system-grpc-ext";
  prefix oc-sys-grpc-ext;

  import openconfig-extensions {
    prefix oc-ext;
  }
  import openconfig-system-grpc {
    prefix oc-grpc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco grpc package configuration.
     
     Copyright (c) 2025 by Cisco Systems, Inc.
     All rights reserved.
     This module contains a collection of YANG definitions
     for Cisco IOS-XR openconfig-system-grpc-ext package
     configuration.
     This module is a YANG extension to the OpenConfig
     openconfig-system-grpc module.";

  revision 2021-04-06 {
    description
      "Initial revision.";
    reference "0.1.0";
  }

  identity CNMI {
    base oc-grpc:GRPC_SERVICE;
    description
      "CNMI: Cisco gnmi";
  }

  identity SLAPI {
    base oc-grpc:GRPC_SERVICE;
    description
      "SLAPI";
  }

  identity SRTE {
    base oc-grpc:GRPC_SERVICE;
    description
      "SRTE";
  }

  identity GNOI {
    base oc-grpc:GRPC_SERVICE;
    description
      "GNOI";
  }

  identity ATTESTZ {
    base oc-grpc:GRPC_SERVICE;
    description
      "ATTESTZ";
  }

  identity ENROLLZ {
    base oc-grpc:GRPC_SERVICE;
    description
      "ENROLLZ";
  }
  oc-ext:openconfig-version "0.1.0";
}
