module Cisco-IOS-XR-um-if-nv-sat-ethernet-cfm-cfg {
  namespace "http://cisco.com/ns/yang/Cisco-IOS-XR-um-if-nv-sat-ethernet-cfm-cfg";
  prefix um-if-nv-sat-ethernet-cfm-cfg;

  import Cisco-IOS-XR-um-interface-cfg {
    prefix a1;
  }
  import Cisco-IOS-XR-um-nv-satellite-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-nv-sat-ethernet-cfm package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-04-23 {
    description
      "Initial release";
    semver:module-version "1.0.0";
  }

  grouping IF-NV-BODY {
    description
      "Grouping for interface-nv";
    container ethernet {
      description
        "Ethernet configuration commands";
      container cfm {
        presence "Indicates a cfm node is configured.";
        description
          "Configuration for 802.1ag CFM on Satellite Fabric Links";
        leaf level {
          type uint32 {
            range "0..7" {
              description
                "Level";
            }
          }
          description
            "Maintenance Domain level to run at";
        }
        container continuity-check {
          description
            "Continuity-check configuration";
          leaf interval {
            type enumeration {
              enum "3.3ms" {
                value 1;
                description
                  "Interval of 3.3 milliseconds";
              }
              enum "10ms" {
                value 2;
                description
                  "Interval of 10 milliseconds";
              }
              enum "100ms" {
                value 3;
                description
                  "Interval of 100 milliseconds";
              }
              enum "1s" {
                value 4;
                description
                  "Interval of 1 second";
              }
              enum "10s" {
                value 5;
                description
                  "Interval of 10 seconds";
              }
              enum "1m" {
                value 6;
                description
                  "Interval of 1 minute";
              }
              enum "10m" {
                value 7;
                description
                  "Interval of 10 minutes";
              }
            }
            description
              "Set the continuity-check interval";
          }
        }
      }
    }
  }

  augment "/a1:interfaces/a1:interface/a2:nv/a2:satellite-fabric-link/a2:satellite" {
    description
      "This augment extends active nodes configuration";
    uses IF-NV-BODY;
  }
  augment "/a1:interfaces/a1:interface-preconfigure/a2:nv/a2:satellite-fabric-link/a2:satellite" {
    description
      "This augment extends preconfigured nodes
       configuration";
    uses IF-NV-BODY;
  }
}
