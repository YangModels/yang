module Cisco-IOS-XR-um-hw-module-subslot-cfg {
  namespace "http://cisco.com/ns/yang/Cisco-IOS-XR-um-hw-module-subslot-cfg";
  prefix um-hw-module-subslot-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-subslot package configuration.
     
     This YANG module augments the
     modules with configuration data.
     
     Copyright (c) 2020-2025 by Cisco Systems, Inc., and/or its affiliates.
     All rights reserved.";

  revision 2020-09-22 {
    description
      "Initial release";
    semver:module-version "1.0.0";
  }

  container hw-module {
    description
      "Configure h/w module";
    container subslots {
      description
        "Configure subslot h/w module";
      list subslot {
        must "shutdown";
        key "subslot-name";
        description
          "Configure subslot h/w module";
        leaf subslot-name {
          type xr:Node-id;
          description
            "Configure subslot h/w module";
        }
        container shutdown {
          presence "Indicates a shutdown node is configured.";
          description
            "Shutdown a subslot h/w module";
        }
      }
    }
  }
}
