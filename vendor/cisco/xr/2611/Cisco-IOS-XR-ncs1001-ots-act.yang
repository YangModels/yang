module Cisco-IOS-XR-ncs1001-ots-act {
  namespace "http://cisco.com/ns/yang/Cisco-IOS-XR-ncs1001-ots-act";
  prefix ncs1001-ots-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots-act package configuration.
     
     This module contains definitions
     for the following management objects:
       hardware-module-action: NCS1k1 HW module config
     
     Copyright (c) 2013-2020 by Cisco Systems, Inc.
     All rights reserved.";

  revision 2019-05-28 {
    description
      "added OTDR periodic scan and event triggered auto scan";
  }
  revision 2019-05-22 {
    description
      "added OTDR alarm support";
  }
  revision 2019-04-05 {
    description
      "Establish semantic version baseline.";
    semver:module-version "1.0.0";
  }
  revision 2018-03-12 {
    description
      "Added Otdr commands";
  }
  revision 2017-08-04 {
    description
      "IOS XR 6.3.1 revision.";
  }

  typedef Ots-psm-manual-switch {
    type enumeration {
      enum "working" {
        value 1;
        description
          "Working port";
      }
      enum "protected" {
        value 2;
        description
          "Protected port";
      }
    }
    description
      "Ots psm manual switch";
  }

  typedef Otdr-direction {
    type enumeration {
      enum "tx" {
        value 0;
        description
          "Tx Direction";
      }
      enum "rx" {
        value 1;
        description
          "Rx Direction";
      }
    }
    description
      "Otdr direction type";
  }

  typedef Otdr-scan-mode {
    type enumeration {
      enum "auto" {
        value 0;
        description
          "Automatic scan mode";
      }
      enum "expert" {
        value 1;
        description
          "Expert scan mode";
      }
    }
    description
      "Otdr scan mode type";
  }

  rpc psm-manual-switch-to {
    description
      "Psm manual switch to port";
    input {
      leaf slot-id {
        type uint32 {
          range "1..3";
        }
        mandatory true;
        description
          "Set Slot";
      }
      leaf manual-switch-to {
        type Ots-psm-manual-switch;
        mandatory true;
        description
          "Switch active path to selected port";
      }
    }
  }
  rpc otdr-scan {
    description
      "Otdr scan commands";
    input {
      leaf slot-id {
        type uint32 {
          range "1..3";
        }
        mandatory true;
        description
          "Set Slot";
      }
      leaf port-id {
        type uint32 {
          range "1..2";
        }
        mandatory true;
        description
          "Set Port";
      }
      leaf direction {
        type Otdr-direction;
        mandatory true;
        description
          "Set Direction";
      }
      leaf scan-mode {
        type Otdr-scan-mode;
        mandatory true;
        description
          "Otdr scan mode";
      }
    }
  }
  rpc otdr-scan-abort {
    description
      "Otdr scan abort command";
    input {
      leaf slot-id {
        type uint32 {
          range "1..3";
        }
        mandatory true;
        description
          "Set Slot";
      }
      leaf port-id {
        type uint32 {
          range "1..2";
        }
        mandatory true;
        description
          "Set Port";
      }
    }
  }
  rpc otdr-save-baseline {
    description
      "Otdr save baseline command";
    input {
      leaf slot-id {
        type uint32 {
          range "1..3";
        }
        mandatory true;
        description
          "Set Slot";
      }
      leaf baseline-id {
        type uint32;
        mandatory true;
        description
          "Set Baseline";
      }
    }
  }
}
