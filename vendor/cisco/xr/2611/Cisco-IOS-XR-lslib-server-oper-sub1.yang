submodule Cisco-IOS-XR-lslib-server-oper-sub1 {
  belongs-to Cisco-IOS-XR-lslib-server-oper {
    prefix Cisco-IOS-XR-lslib-server-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR lslib-server package operational data.
     
     Copyright (c) 2013-2025 by Cisco Systems, Inc.
     All rights reserved.";

  revision 2025-02-24 {
    description
      "Added producer name and total count in producer stats. Modified unknown_error as unknown_nlri_error_count";
    semver:module-version "1.0.0";
  }
  revision 2025-02-14 {
    description
      "Made uptime as string and added producer name leaf";
  }
  revision 2025-02-12 {
    description
      "Added total count of NLRI in producer details oper.";
  }
  revision 2024-10-28 {
    description
      "Initial Oper yang";
  }
  revision 2019-04-05 {
    description
      "Establish semantic version baseline.";
  }
  revision 2015-11-09 {
    description
      "IOS XR 6.0 revision.";
  }

  grouping LSLIB-SERVER-MEM-HEAP {
    description
      "LSLIB Server Memory Heap Info";
    leaf mem-name {
      type string;
      description
        "Memory Name";
    }
    leaf allocations {
      type uint64;
      description
        "Number of memory allocations done";
    }
    leaf frees {
      type uint64;
      description
        "Number of frees done";
    }
    leaf count {
      type uint32;
      description
        "Current count of allocation";
    }
    leaf fails {
      type uint32;
      description
        "Number of allocation failures";
    }
    leaf total-size {
      type uint64;
      units "kilobyte";
      description
        "Size of all chunks in kilobytes";
    }
  }

  grouping LSLIB-SERVER-SHOW-MATCH-FILTER {
    description
      "LSLIB Server Show Match Filter";
    leaf identifier {
      type uint64;
      description
        "Identifier";
    }
    leaf protocol {
      type uint8;
      description
        "Protocol";
    }
    leaf nlri-type {
      type uint8;
      description
        "NLRI Type";
    }
    leaf identifier-present {
      type uint8;
      description
        "Identifier present";
    }
    leaf protocol-present {
      type uint8;
      description
        "Protocol present";
    }
    leaf nlri-type-present {
      type uint8;
      description
        "NLRI Type present";
    }
  }

  grouping LSLIB-SERVER-SHOW-CLIENT {
    description
      "LSLIB Server Show Client";
    container initial-filter-match-stats {
      description
        "Initial Statistics of entries which matched the
         filters before EOD";
      uses LSLIB-SERVER-SHOW-STATS;
    }
    container initial-filter-un-match-stats {
      description
        "Initial Statistics of entries which did not
         match the filters before EOD";
      uses LSLIB-SERVER-SHOW-STATS;
    }
    container filter-match-stats {
      description
        "Statistics of entries which matched the filters";
      uses LSLIB-SERVER-SHOW-STATS;
    }
    container filter-un-match-stats {
      description
        "Statistics of entries which did not match the
         filters";
      uses LSLIB-SERVER-SHOW-STATS;
    }
    leaf client-id-xr {
      type uint32;
      description
        "Client ID";
    }
    leaf vrf-name {
      type string;
      description
        "VRF name";
    }
    leaf subscribed-time {
      type string;
      description
        "Time at which client subscribed";
    }
    leaf unsubscribed-time {
      type string;
      description
        "Time at which client unsubscribed";
    }
    leaf sod-sent-time {
      type string;
      description
        "Time at which Start Of Download sent";
    }
    leaf eod-sent-time {
      type string;
      description
        "Time at which End Of Download sent";
    }
    leaf up-time {
      type string;
      description
        "Time in hh:mm:ss format since the connection
         came up";
    }
    leaf connected {
      type boolean;
      description
        "Client connected";
    }
    leaf eod-added {
      type boolean;
      description
        "To indicate whether End of Download is added";
    }
    list match-filter {
      description
        "List of Match Filters";
      uses LSLIB-SERVER-SHOW-MATCH-FILTER;
    }
  }

  grouping LSLIB-SERVER-MEM-CHUNK {
    description
      "LSLIB Server Memory Chunk Info";
    leaf chunk-name-xr {
      type string;
      description
        "Chunk Name";
    }
    leaf elements-per-chunk {
      type uint16;
      description
        "Number of elements in a Chunk";
    }
    leaf num-chunks {
      type uint16;
      description
        "Number of Chunks allocated";
    }
    leaf elements-inuse {
      type uint32;
      description
        "Number of elements in use";
    }
    leaf element-size {
      type uint32;
      units "byte";
      description
        "Size of single element in bytes";
    }
    leaf chunk-size {
      type uint64;
      units "kilobyte";
      description
        "Size of Chunk in kilobytes";
    }
    leaf total-size {
      type uint64;
      units "kilobyte";
      description
        "Size of all chunks in kilobytes";
    }
    leaf allocations {
      type uint64;
      description
        "Number of memory allocations done";
    }
    leaf frees {
      type uint64;
      description
        "Number of frees done";
    }
    leaf count {
      type uint32;
      description
        "Current count of allocation";
    }
    leaf fails {
      type uint32;
      description
        "Number of allocation failures";
    }
  }

  grouping LSLIB-SERVER-SHOW-STATS {
    description
      "LSLIB Server Show Statistics";
    leaf sod-count {
      type uint32;
      description
        "Number of Start Of Downloads";
    }
    leaf eod-count {
      type uint32;
      description
        "Number of End of Downloads";
    }
    leaf node-add-count {
      type uint32;
      description
        "Number of Add or Update Node NLRIs";
    }
    leaf node-del-count {
      type uint32;
      description
        "Number of Delete Node NLRIs";
    }
    leaf node-error-count {
      type uint32;
      description
        "Number of errors occured with Node NLRI";
    }
    leaf link-add-count {
      type uint32;
      description
        "Number of Add or Update Link NLRIs";
    }
    leaf link-del-count {
      type uint32;
      description
        "Number of Delete Link NLRIs";
    }
    leaf link-error-count {
      type uint32;
      description
        "Number of errors occured with Link NLRIs";
    }
    leaf prefix-add-count {
      type uint32;
      description
        "Nuber of Add or Update IPv4 and IPv6 Prefix
         NLRIs";
    }
    leaf prefix-del-count {
      type uint32;
      description
        "Nuber of Delete IPv4 and IPv6 Prefix NLRIs";
    }
    leaf prefix-error-count {
      type uint32;
      description
        "Number of errors occured with Prefix NLRIs";
    }
    leaf sid-add-count {
      type uint32;
      description
        "Number of Add or Update SRv6 Segment Identifier
         NLRIs";
    }
    leaf sid-del-count {
      type uint32;
      description
        "Number of Delete SRv6 Segment Identifier NLRIs";
    }
    leaf sid-error-count {
      type uint32;
      description
        "Number of errors occured with SRv6 Segment
         Identifier NLRIs";
    }
    leaf srte-cp-add-count {
      type uint32;
      description
        "Number of Add or Update SRTE Candidate Path
         NLRIs";
    }
    leaf srte-cp-del-count {
      type uint32;
      description
        "Number of Delete SRTE Candidate Path NLRIs";
    }
    leaf srte-cp-error-count {
      type uint32;
      description
        "Number of errors occured with SRTE Candidate
         Path NLRIs";
    }
    leaf unknown-nlri-error-count {
      type uint32;
      description
        "Number of errors occured with Unknown NLRI types";
    }
    leaf total-add-count {
      type uint64;
      description
        "Total number of Add or Update NLRIs";
    }
    leaf total-del-count {
      type uint64;
      description
        "Total number of Delete NLRIs";
    }
    leaf total-error-count {
      type uint64;
      description
        "Total number of errors occured with all NLRIs";
    }
  }

  grouping LSLIB-SERVER-SHOW-PRODUCER {
    description
      "LSLIB Server Show Producer";
    container initial-data-stats {
      description
        "Initial Data Statictics of NLRIs, Markers and
         errors from producer before EOD";
      uses LSLIB-SERVER-SHOW-STATS;
    }
    container cumulative-stats {
      description
        "Cumulative Statictics of NLRIs, Markers and
         errors from producer";
      uses LSLIB-SERVER-SHOW-STATS;
    }
    leaf instance-id {
      type uint64;
      description
        "Instance Identifier of the given producer
         process";
    }
    leaf producer-proc {
      type uint8;
      description
        "Producer Process Information";
    }
    leaf producer-id {
      type uint8;
      description
        "LSLIB Server's local Producer Identifier";
    }
    leaf producer-name {
      type string;
      description
        "Producer Process name in string";
    }
    leaf is-checkpointed {
      type boolean;
      description
        "Flag to know whether Producer Information is
         checkpointed";
    }
    leaf is-eod-timer-running {
      type boolean;
      description
        "Flag to indicate if EOD Timer running";
    }
    leaf eod-pending {
      type boolean;
      description
        "Flag to indicate EOD is pending from Producer";
    }
    leaf connected-time {
      type string;
      description
        "Time at which Producer connected";
    }
    leaf disconnected-time {
      type string;
      description
        "Time at which Producer disconnected";
    }
    leaf sod-recv-time {
      type string;
      description
        "Time at which Start Of Download received";
    }
    leaf eod-recv-time {
      type string;
      description
        "Time at which End Of Download received";
    }
    leaf up-time {
      type string;
      description
        "Time in hh:mm:ss format since the producer came
         up";
    }
  }

  grouping LSLIB-SERVER-SHOW-LSDB-STATS {
    description
      "LSLIB Server LSDB statistics";
    leaf node-count {
      type uint32;
      description
        "Number of Node NLRIs in LSDB";
    }
    leaf link-count {
      type uint32;
      description
        "Number of Link NLRIs in LSDB";
    }
    leaf ipv4-prefix-count {
      type uint32;
      description
        "Number of IPv4 Prefix NLRIs in LSDB";
    }
    leaf ipv6-prefix-count {
      type uint32;
      description
        "Number of IPv6 Prefix NLRIs in LSDB";
    }
    leaf sr-policy-count {
      type uint32;
      description
        "Number of SR Policy NLRIs in LSDB";
    }
    leaf srv6sid-count {
      type uint32;
      description
        "Number of SRv6 SID NLRIs in LSDB";
    }
    leaf total-count {
      type uint64;
      description
        "Total count of all types of NLRIs in LSDB";
    }
  }

  grouping LSLIB-SERVER-SHOW-PROD-STATS {
    description
      "LSLIB Server Producer statistics";
    container producer-stats {
      description
        "Statistics of NLRIs from this producer";
      uses LSLIB-SERVER-SHOW-LSDB-STATS;
    }
    leaf producer-name {
      type string;
      description
        "Producer Process name in string";
    }
  }
}
