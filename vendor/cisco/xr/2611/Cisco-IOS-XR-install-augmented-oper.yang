module Cisco-IOS-XR-install-augmented-oper {
  namespace "http://cisco.com/ns/yang/Cisco-IOS-XR-install-augmented-oper";
  prefix install-augmented-oper;

  import Cisco-IOS-XR-types {
    prefix xr;
  }
  import cisco-semver {
    prefix semver;
  }
  include Cisco-IOS-XR-install-augmented-oper-sub2 {
    revision-date 2025-09-24;
  }
  include Cisco-IOS-XR-install-augmented-oper-sub1 {
    revision-date 2025-09-24;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install-augmented package operational data.
     
     This module contains definitions
     for the following management objects:
       install: Install operational data
       install-local: Install operational per-node data
     
     Copyright (c) 2013-2025 by Cisco Systems, Inc.
     All rights reserved.";

  revision 2025-09-24 {
    description
      "Move schema items from InstallAgent to InstallLocal
       2025-09-03
         Add new RPM rejection reason for owner packages with files with setuid or setgid bit set.
       2025-08-15
         Add new RPM rejection reason for owner packages with special files.
       2025-07-29
         Add new activity enum values to report post reimage flows.
       2025-05-06
         Add enum values for several previously unreported node activities and message types.
       2025-05-01
         Add new activity enum values to report early FPD upgrade flows.
       2025-04-25
         Add new fields in not installed package reason bag for owner packages with invalid signatures.
       2025-04-16
         Add new enum value to activation type for apply by reimage reporting.
       2024-09-19
         Add new fields in package op bag for added and removed supported PIDs.
       2024-05-23
         Add new bagtypes for list of PIDs and node inventory.
       2024-05-03
         Add new constraint for owner packages with cisco key id.
       2024-02-22
         Add origin filtering to available package queries.
       2023-12-12
         Add summary to available package queries.
       2023-11-16
         Add origin information for owner RPMs.
       2023-07-11
         Add packages which were not installed at boot time.
       2023-02-10
         Add awaited unsolicited messages to internal data.
       2022-12-20
         Add username information.
       2022-11-17
         Add latest reimage bags.
       2022-05-05
         Add warning to inst_request_verbose_bag.
       2022-02-18
         Add detailed intervention event information.
       2021-10-27
         Add new bag for platform-specific disabled packages.
       2021-10-25
         Add source to package operation reporting.
       2021-10-01
         Add details in history for package verification failure reporting.";
    semver:module-version "2.3.0";
  }
  revision 2021-08-25 {
    description
      "7.5.1 release features.";
    semver:module-version "2.2.0";
  }
  revision 2021-03-22 {
    description
      "7.4.1 release features.
       2020-09-30
           7.3.1 release features.";
    semver:module-version "2.1.0";
  }
  revision 2020-05-12 {
    description
      "Removal of compound from enum naming conventions to avoid confusion.
       2019-12-11
         Obsoleted the nodes list for history items.
       2019-10-14
         Combined platform updates including updates to show install rollback list-ids";
    semver:module-version "2.0.0";
  }
  revision 2019-10-13 {
    description
      "NCS540L 7.1.1 release
       2019-10-12
       8000 series 7.0.11 release";
    semver:module-version "1.1.0";
  }
  revision 2019-04-05 {
    description
      "Establish semantic version baseline.";
    semver:module-version "1.0.0";
  }
  revision 2015-11-09 {
    description
      "IOS XR 6.0 revision.";
  }

  grouping PACKAGING-OPERATION-FULL-ERRORS {
    description
      "Common node of packaging-operation,
       latest-packaging-operation";
    container packaging-operation-full-errors {
      description
        "Information about per-node and global
         intervention events during a packaging operation";
      container packaging-operation-full-errors-global {
        description
          "System-wide intervention event information
           during a packaging operation";
        uses INST-OP-INTERVENTION-EVENTS-BAG;
      }
      container packaging-operation-full-errors-nodes {
        description
          "Table for per-node intervention event
           information when carrying out a packaging
           operation";
        list packaging-operation-full-errors-node {
          key "node";
          description
            "Node specific intervention event information
             during a packaging operation";
          leaf node {
            type xr:Node-id;
            description
              "Node name";
          }
          uses INST-OP-INTERVENTION-EVENTS-BAG;
        }
      }
    }
  }

  grouping ATOMIC-CHANGE-TABLE {
    description
      "Common node of transaction, latest-transaction";
    container atomic-changes {
      description
        "Table for atomic software change specific
         operational data";
      list atomic-change {
        key "index";
        description
          "Information about a particular atomic change";
        leaf index {
          type uint32;
          description
            "Index";
        }
        uses ATOMIC-CHANGE-FULL-ERRORS;
        uses PACKAGING-OPERATION-TABLE;
        uses ATOMIC-CHANGE-INFO;
        uses ATOMIC-CHANGE-INFO-NODE-TABLE;
      }
    }
  }

  grouping TRANSACTION-INFO-NODE-TABLE {
    description
      "Common node of transaction, latest-transaction";
    container transaction-info-nodes {
      description
        "Table for per-node information during a
         transaction";
      list transaction-info-node {
        key "node";
        description
          "Node specific information during a transaction";
        leaf node {
          type xr:Node-id;
          description
            "Node name";
        }
        uses INST-TRANS-NODE-BAG;
      }
    }
  }

  grouping TRANSACTION-FULL-ERRORS {
    description
      "Common node of transaction, latest-transaction";
    container transaction-full-errors {
      description
        "Information about per-node and global install
         intervention events during a transaction";
      container transaction-full-errors-nodes {
        description
          "Table for per-node intervention event
           information when carrying out a transaction";
        list transaction-full-errors-node {
          key "node";
          description
            "Node specific intervention event information
             during a transaction";
          leaf node {
            type xr:Node-id;
            description
              "Node name";
          }
          uses INST-OP-INTERVENTION-EVENTS-BAG;
        }
      }
      container transaction-full-errors-global {
        description
          "System-wide intervention event information
           during a transaction";
        uses INST-OP-INTERVENTION-EVENTS-BAG;
      }
    }
  }

  grouping TRANSACTION-INFO {
    description
      "Common node of transaction, latest-transaction";
    container transaction-info {
      description
        "Summary information about the transaction";
      uses INST-TRANS-BAG;
    }
  }

  grouping ATOMIC-CHANGE-INFO {
    description
      "Common node of atomic-change,
       latest-atomic-change";
    container atomic-change-info {
      description
        "Summary information about the atomic change";
      uses INST-ATOMIC-CHANGE-BAG;
    }
  }

  grouping PACKAGING-OPERATION-INFO-NODE-TABLE {
    description
      "Common node of latest-packaging-operation,
       packaging-operation";
    container packaging-operation-info-nodes {
      description
        "Table for per-node information during a
         packaging operation";
      list packaging-operation-info-node {
        key "node";
        description
          "Node specific information during a packaging
           operation";
        leaf node {
          type xr:Node-id;
          description
            "Node name";
        }
        uses INST-PKG-OP-NODE-BAG;
      }
    }
  }

  grouping ATOMIC-CHANGE-FULL-ERRORS {
    description
      "Common node of atomic-change,
       latest-atomic-change";
    container atomic-change-full-errors {
      description
        "Information about per-node and global
         intervention event during an atomic change";
      container atomic-change-full-errors-nodes {
        description
          "Table for per-node intervention event
           information when carrying out an atomic change";
        list atomic-change-full-errors-node {
          key "node";
          description
            "Node specific intervention event information
             during an atomic change";
          leaf node {
            type xr:Node-id;
            description
              "Node name";
          }
          uses INST-OP-INTERVENTION-EVENTS-BAG;
        }
      }
      container atomic-change-full-errors-global {
        description
          "System-wide intervention event information
           during an atomic change";
        uses INST-OP-INTERVENTION-EVENTS-BAG;
      }
    }
  }

  grouping PACKAGING-OPERATION-TABLE {
    description
      "Common node of atomic-change,
       latest-atomic-change";
    container packaging-operations {
      description
        "Table for packaging operation specific
         operational data";
      list packaging-operation {
        key "index";
        description
          "Data about a particular packaging operation";
        leaf index {
          type uint32;
          description
            "Index";
        }
        uses PACKAGING-OPERATION-ERRORS-NODE-TABLE;
        uses PACKAGING-OPERATION-INFO-NODE-TABLE;
        uses PACKAGING-OPERATION-FULL-ERRORS;
        uses PACKAGING-OPERATION-INFO;
      }
    }
  }

  grouping PACKAGING-OPERATION-ERRORS-NODE-TABLE {
    description
      "Common node of latest-packaging-operation,
       packaging-operation";
    container packaging-operation-errors-nodes {
      description
        "Table for per-node DNF errors during a packaging
         operation";
      list packaging-operation-errors-node {
        key "node";
        description
          "Node specific DNF error logs during a packaging
           operation";
        leaf node {
          type xr:Node-id;
          description
            "Node name";
        }
        uses INST-PKG-OP-ERRORS-BAG;
      }
    }
  }

  grouping PACKAGING-OPERATION-INFO {
    description
      "Common node of latest-packaging-operation,
       packaging-operation";
    container packaging-operation-info {
      description
        "Information about a packaging operation";
      uses INST-PKG-OP-BAG;
    }
  }

  grouping NODE-INCONSISTENCIES {
    description
      "Common node of committed, active";
    container node-inconsistencies {
      description
        "All packages with node inconsistencies";
      uses INST-NODE-INCONSISTENCIES-BAG;
    }
  }

  grouping ATOMIC-CHANGE-INFO-NODE-TABLE {
    description
      "Common node of atomic-change,
       latest-atomic-change";
    container atomic-change-info-nodes {
      description
        "Table for per-node information during an atomic
         change";
      list atomic-change-info-node {
        key "node";
        description
          "Node specific information during an atomic
           change";
        leaf node {
          type xr:Node-id;
          description
            "Node name";
        }
        uses INST-ATOMIC-CHANGE-NODE-BAG;
      }
    }
  }

  container install {
    config false;
    description
      "Install operational data";
    container platform-support {
      description
        "Information about what features are supported on
         this platform";
      container platform-support-info {
        description
          "Information about what features are supported
           on this platform";
        uses INST-PLATFORM-SUPPORT-BAG;
      }
    }
    container history {
      description
        "Operation history";
      container reimages {
        description
          "Table for reimage history data";
        list reimage {
          key "reimage-id";
          description
            "Information about a particular reimage";
          container reimage-info {
            description
              "Information about a particular reimage";
            uses INST-REIMAGE-HISTORY-BAG;
          }
          container reimage-errors {
            description
              "Error information during a reimage";
            uses INST-OP-INTERVENTION-EVENTS-BAG;
          }
          leaf reimage-id {
            type uint32;
            description
              "Install Reimage ID";
          }
        }
      }
      container latest-transaction {
        description
          "Latest transaction data";
        uses TRANSACTION-INFO-NODE-TABLE;
        uses TRANSACTION-FULL-ERRORS;
        uses TRANSACTION-INFO;
        uses ATOMIC-CHANGE-TABLE;
      }
      container latest-packaging-operation {
        description
          "Information about the latest packaging
           operation";
        uses PACKAGING-OPERATION-ERRORS-NODE-TABLE;
        uses PACKAGING-OPERATION-INFO-NODE-TABLE;
        uses PACKAGING-OPERATION-FULL-ERRORS;
        uses PACKAGING-OPERATION-INFO;
      }
      container latest-atomic-change {
        description
          "Latest atomic software change";
        uses ATOMIC-CHANGE-FULL-ERRORS;
        uses PACKAGING-OPERATION-TABLE;
        uses ATOMIC-CHANGE-INFO;
        uses ATOMIC-CHANGE-INFO-NODE-TABLE;
      }
      container transactions {
        description
          "Table for transaction-specific operational data";
        list transaction {
          key "transaction-id";
          description
            "Information about a particular transaction";
          leaf transaction-id {
            type uint32;
            description
              "Install Transaction ID";
          }
          uses TRANSACTION-INFO-NODE-TABLE;
          uses TRANSACTION-FULL-ERRORS;
          uses TRANSACTION-INFO;
          uses ATOMIC-CHANGE-TABLE;
        }
      }
      container latest-reimage {
        description
          "Container for latest reimage information";
        container reimage-info {
          description
            "Information about the latest reimage";
          uses INST-REIMAGE-HISTORY-BAG;
        }
        container reimage-errors {
          description
            "Errors information about the latest reimage";
          uses INST-OP-INTERVENTION-EVENTS-BAG;
        }
      }
    }
    container packages {
      description
        "Package information";
      container active {
        description
          "Information about active packages";
        uses NODE-INCONSISTENCIES;
      }
      container cached {
        description
          "Information about cached packages";
        container summary {
          description
            "Summary packages";
          uses INST-PACKAGES-BAG;
        }
        container all {
          description
            "All packages including card-specific
             dependencies";
          uses INST-PACKAGES-BAG;
        }
      }
      container committed {
        description
          "Information about committed packages";
        uses NODE-INCONSISTENCIES;
      }
      container available {
        description
          "Information about available packages";
        container summary {
          description
            "All user-installable packages compatible with
             the current XR version";
          uses INST-AVAILABLE-PACKAGES-BAG;
        }
        container internal {
          description
            "All packages including card-specific
             dependencies";
          uses INST-AVAILABLE-PACKAGES-BAG;
        }
        container all {
          description
            "All user-installable packages";
          uses INST-AVAILABLE-PACKAGES-BAG;
        }
      }
    }
    container upgrade-matrix {
      description
        "Upgrade compatibility matrix information";
      container rollbacks {
        description
          "Table containing upgrade matrix data from the
           current active version to the rollback point";
        list rollback {
          key "id";
          description
            "Rollback point information";
          container all {
            description
              "Bag containing upgrade matrix data for all
               supported known paths for the rollback point";
            uses INSTALL-UPGRADE-MATRIX-ISO;
          }
          container from-running {
            description
              "Bag containing upgrade matrix data from the
               current active version to the rollback point";
            uses INSTALL-UPGRADE-MATRIX-ISO;
          }
          leaf id {
            type uint32;
            description
              "Rollback point ID";
          }
        }
      }
    }
    container supported-pids {
      description
        "Supported PIDs";
      container rollback-point-pids {
        description
          "Table for supported PIDs of rollback points";
        list rollback-point-pid {
          key "id";
          description
            "PIDs supported by a rollback point";
          leaf id {
            type uint32;
            description
              "Transaction ID";
          }
          uses INST-SUPPORTED-PIDS-BAG;
        }
      }
      container active-supported-pids {
        description
          "PIDs supported by the active software";
        uses INST-SUPPORTED-PIDS-BAG;
      }
      container committed-supported-pids {
        description
          "PIDs supported by the committed software";
        uses INST-SUPPORTED-PIDS-BAG;
      }
      container iso-pids {
        description
          "Table for PIDs supported by an iso";
        list iso-pid {
          key "iso";
          description
            "PIDs supported by an iso";
          leaf iso {
            type xr:Cisco-ios-xr-string;
            description
              "Iso";
          }
          uses INST-SUPPORTED-PIDS-BAG;
        }
      }
    }
    container inventory {
      description
        "Inventory information";
      container inventory-nodes {
        description
          "Table for inventory nodes";
        list inventory-node {
          key "node";
          description
            "Information for a Node in the inventory";
          leaf node {
            type xr:Node-id;
            description
              "Node name";
          }
          uses INST-INV-NODE-BAG;
        }
      }
    }
    container internal {
      description
        "Internal debug information";
      container fixes {
        description
          "Information about fixes that are available";
        container available-group-fixes {
          description
            "Groups of fixes";
          list available-group-fixe {
            key "ddts";
            description
              "Information about groups of fixes that are
               available";
            leaf ddts {
              type xr:Cisco-ios-xr-string;
              description
                "First DDTS Id in list";
            }
            uses INST-AVAILABLE-GROUP-FIXES-BAG;
          }
        }
      }
      container packages {
        description
          "Package information";
        container pkgmgr {
          description
            "Information about package-manager installed
             packages. During an atomic change, this is the
             full set of packages that will be active after
             the atomic change is applied";
          container nodes {
            description
              "Table for node level data";
            list node {
              key "node";
              description
                "Per-node packages";
              leaf node {
                type xr:Node-id;
                description
                  "Node name";
              }
              uses INST-PACKAGES-BAG;
            }
          }
          container summary {
            description
              "Summary packages";
            uses INST-PACKAGES-BAG;
          }
        }
        container disabled {
          description
            "Packages that are disabled on this platform";
          uses INST-DISABLED-PKGS-BAG;
        }
      }
    }
    container request {
      description
        "Information about the latest user request";
      container verbose {
        description
          "Verbose information about the status of current
           install operation";
        uses INST-REQUEST-VERBOSE-BAG;
      }
    }
    container version {
      description
        "Install version information";
      container detail {
        description
          "Install version detailed information";
        uses INST-VERSION-BAG;
      }
      container brief {
        description
          "Install version brief information";
        uses INST-VERSION-BAG;
      }
    }
    container rollback {
      description
        "Information about software rollback options";
      container rollback-points {
        description
          "Table for rollback points";
        list rollback-point {
          key "id";
          description
            "Rollback point information";
          container summary {
            description
              "Summary of changes when rolling back to a a
               rollback point";
            uses INST-ROLLBACK-SUMMARY-BAG;
          }
          container installed-packages {
            description
              "Installed packages";
            container user-installable {
              description
                "User-installable packages associated with
                 rollback point";
              uses INST-PACKAGES-BAG;
            }
            container changes {
              description
                "Changes in packages if rolling back";
              uses INST-CHANGES-BAG;
            }
            container pkgs-and-fixes {
              description
                "User-installable packages (and their fixes)
                 associated with rollback point";
              uses INST-ROLLBACK-POINT-BAG;
            }
          }
          leaf id {
            type uint32;
            description
              "Rollback point ID";
          }
        }
      }
    }
    container fixes {
      description
        "Information about DDTS fixes";
      container deactivate-fixes {
        description
          "This command is deprecated as of IOS XR 25.4.1.
           To remove bugfixes, it is recommended to build
           and replace to a GISO with the desired software
           .";
        list deactivate-fixe {
          key "ddt-ss";
          description
            "Information about groups of fixes that are
             available";
          leaf ddt-ss {
            type xr:Cisco-ios-xr-string;
            description
              "Comma separated DDTS list of DDTSs to
               deactivate";
          }
          uses INST-DEACTIVATE-DDTS-IDS-BAG;
        }
      }
      container available {
        description
          "Information about fixes that are available";
        uses INST-AVAILABLE-FIXES-BAG;
      }
    }
  }
  container install-local {
    config false;
    description
      "Install operational per-node data";
    container nodes {
      description
        "Node table for node-specific operational data";
      list node {
        key "node";
        description
          "Node-specific data for a particular node";
        container boot {
          description
            "Boot related information";
          container not-installed {
            description
              "Packages which were not installed at boot
               time";
            container packages {
              description
                "Table for package names";
              list package {
                key "name";
                description
                  "Package";
                leaf name {
                  type xr:Cisco-ios-xr-string;
                  description
                    "Package Name";
                }
                uses INST-NOT-INSTALLED-PKG-BAG;
              }
            }
          }
        }
        container rpmdb {
          description
            "Information about contents of the rpmdb";
          container keys {
            description
              "Details of all keys in the rpmdb";
            list key {
              key "name";
              description
                "Key";
              leaf name {
                type xr:Cisco-ios-xr-string;
                description
                  "Key Name";
              }
              uses INST-RPMDB-KEY-BAG;
            }
          }
          container unverified-packages {
            description
              "Unverified Packages";
            uses INST-RPMDB-UNVERIFIED-PKGS-BAG;
          }
        }
        leaf node {
          type xr:Node-id;
          description
            "Node";
        }
      }
    }
  }
}
