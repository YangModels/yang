//*************  DO-NOT EDIT  **************
//*********** Auto-generated file ********** 

 module cisco-xr-openconfig-system-grpc-deviations {

  namespace "http://cisco.com/ns/yang/cisco-xr-openconfig-system-grpc-deviations";
  prefix  "oc-sys-grpcdevs";

  import openconfig-system-grpc { prefix oc-sys-grpc; }
  import openconfig-system { prefix oc-sys; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-system-grpc.yang@2022-04-19 

     on Cisco IOS-XR devices.

     Copyright (c) 2017, 2022, 2024 by Cisco Systems, Inc.
     All rights reserved.";

  revision "2025-05-31" {
    description
      "Keep only deviation for oc-sys-grpc:connections";
  }
  revision "2022-12-18" {
    description
      "Add deviation for oc-sys-grpc:listen-addresses";
  }
  revision "2022-07-05" {
    description
      "Initial revision applicable to IOS-XR 6.4.1";
  }

  deviation /oc-sys:system/oc-sys-grpc:grpc-servers/oc-sys-grpc:grpc-server/oc-sys-grpc:connections {
    deviate not-supported;
  }


}
//total deviations:1
