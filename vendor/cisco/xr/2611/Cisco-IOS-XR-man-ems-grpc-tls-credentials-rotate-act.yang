module Cisco-IOS-XR-man-ems-grpc-tls-credentials-rotate-act {
  namespace "http://cisco.com/ns/yang/Cisco-IOS-XR-man-ems-tls-credentials-rotate-act";
  prefix grpc-tls-credentials-rotate-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2021 by Cisco Systems, Inc.
     All rights reserved.";

  revision 2024-04-04 {
    description
      "IOS XR 24.3.1 revision.";
    semver:module-version "1.0.0";
  }

  rpc tls-credentials-file-path {
    description
      "Action to load the gRPC location of the PEM file containing the Certificate, Private Key associated with the certificate, and the CA trust bundle.";
    input {
      leaf path {
        type string {
          length "1..1024";
        }
        mandatory true;
        description
          "Path string to indicate the location of PEM file which contains the TLS credentials.";
      }
    }
    xr:xr-task "root-lr";
    xr:cli-command "ems grpc tls-credentials rotate filepath <path>";
  }
}
