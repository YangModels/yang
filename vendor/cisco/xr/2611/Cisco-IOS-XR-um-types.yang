module Cisco-IOS-XR-um-types {
  yang-version 1.1;
  namespace "http://cisco.com/ns/yang/Cisco-IOS-XR-um-types";
  prefix um-types;

  import ietf-inet-types {
    prefix inet;
  }
  import ietf-yang-types {
    prefix yang;
  }
  import cisco-semver {
    prefix semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of IOS-XR YANG data types for the
     unified configuration models.
     
     Copyright (c) 2025 by Cisco Systems, Inc., and/or its affiliates.
     All rights reserved.";

  revision 2025-08-26 {
    description
      "Initial version.";
    semver:module-version "1.0.0";
  }

  typedef bounded-string {
    type string {
      length "1..800";
    }
    description
      "A non-empty string with a maximum length of 800 characters.";
  }

  typedef restricted-string {
    type bounded-string {
      pattern "[\\w\\-\\.,:;@#~%$&!\\*\\^\\+=<>{}\\[\\]\\|]+";
    }
    description
      "A non-empty string with a maximum length of 800 characters, only
       containing word characters as well as a restricted set of special
       characters.
       
       Note that whitespace is not allowed in this string.
       
       This type ensures that the string is compatible with IOS-XR internal
       database representations.";
  }

  typedef whitespace-string {
    type bounded-string {
      pattern "[\\w\\-\\.,:;@#~%$&!\\*\\^\\+=<>{}\\[\\]\\| ]+";
    }
    description
      "A non-empty string with a maximum length of 800 characters, only
       containing word characters as well as a restricted set of special
       characters, including whitespace.
       
       This type is identical to the 'restricted-string' type, but allows
       whitespace characters.";
  }

  typedef extended-bounded-string {
    type string {
      length "1..1024";
    }
    description
      "A non-empty string with a maximum length of 1024 characters.
       
       This type is identical to the 'bounded-string' type, but allows a
       longer string length of up to 1024 characters.";
  }

  typedef extended-restricted-string {
    type extended-bounded-string {
      pattern "[\\w\\-\\.,:;@#~%$&!\\*\\^\\+=<>{}\\[\\]\\|]+";
    }
    description
      "A non-empty string with a maximum length of 1024 characters, only
       containing word characters as well as a restricted set of special
       characters.
       
       This type is identical to the 'restricted-string' type, but allows
       a longer string length of up to 1024 characters.";
  }

  typedef extended-whitespace-string {
    type extended-bounded-string {
      pattern "[\\w\\-\\.,:;@#~%$&!\\*\\^\\+=<>{}\\[\\]\\| ]+";
    }
    description
      "A non-empty string with a maximum length of 1024 characters, only
       containing word characters as well as a restricted set of special
       characters, including whitespace.
       
       This type is identical to the 'extended-restricted-string' type,
       but allows whitespace characters.";
  }

  typedef lowercase-string {
    type restricted-string;
    description
      "A string whose canonical representation is in lowercase.
       
       The string may be input in either lowercase or uppercase.
       
       The restrictions on the string are the same as for the
       'restricted-string' type";
  }

  typedef uppercase-string {
    type restricted-string;
    description
      "A string whose canonical representation is in uppercase.
       
       The string may be input in either lowercase or uppercase.
       
       The restrictions on the string are the same as for the
       'restricted-string' type";
  }

  typedef char-num {
    type union {
      type string {
        pattern "0x[0-9A-Fa-f]{1,2}|\\p{IsBasicLatin}|\\p{IsLatin-1Supplement}";
      }
      type uint8;
    }
    description
      "Takes a character or its ASCII decimal equivalent in hexadecimal
       format (0x0-0xff).";
  }

  typedef identifier {
    type bounded-string {
      pattern "[a-zA-Z0-9_\\-]+";
    }
    description
      "An identifier, containing only alphanumeric characters, underscores or
       hyphens.";
  }

  typedef username {
    type restricted-string;
    description
      "A username for user authentication and/or identification.";
  }

  typedef percentage {
    type uint8 {
      range "0..100";
    }
    description
      "A percentage value, ranging from 0 to 100 inclusive.";
  }

  typedef hex-uint64 {
    type string {
      pattern "[0-9a-fA-F]{1,16}";
    }
    description
      "An unsigned 64-bit integer represented in hexadecimal format, with no
       leading '0x'.
       
       The canonical representation uses lowercase characters.";
  }

  typedef hex-uint32 {
    type string {
      pattern "[0-9a-fA-F]{1,8}";
    }
    description
      "An unsigned 32-bit integer represented in hexadecimal format, with no
       leading '0x'.
       
       The canonical representation uses lowercase characters.";
  }

  typedef hex-uint16 {
    type string {
      pattern "[0-9a-fA-F]{1,4}";
    }
    description
      "An unsigned 16-bit integer represented in hexadecimal format, with no
       leading '0x'.
       
       The canonical representation uses lowercase characters.";
  }

  typedef hex-uint8 {
    type string {
      pattern "[0-9a-fA-F]{1,2}";
    }
    description
      "An unsigned 8-bit integer represented in hexadecimal format, with no
       leading '0x'.
       
       The canonical representation uses lowercase characters.";
  }

  typedef hex-zerox-uint64 {
    type string {
      pattern "0x[0-9a-fA-F]{1,16}";
    }
    description
      "An unsigned 64-bit integer represented in hexadecimal format, with
       leading '0x'.
       
       The canonical representation uses lowercase characters.";
  }

  typedef hex-zerox-uint32 {
    type string {
      pattern "0x[0-9a-fA-F]{1,8}";
    }
    description
      "An unsigned 32-bit integer represented in hexadecimal format, with
       leading '0x'.
       
       The canonical representation uses lowercase characters.";
  }

  typedef hex-zerox-uint16 {
    type string {
      pattern "0x[0-9a-fA-F]{1,4}";
    }
    description
      "An unsigned 16-bit integer represented in hexadecimal format, with
       leading '0x'.
       
       The canonical representation uses lowercase characters.";
  }

  typedef hex-zerox-uint8 {
    type string {
      pattern "0x[0-9a-fA-F]{1,2}";
    }
    description
      "An unsigned 8-bit integer represented in hexadecimal format, with
       leading '0x'.
       
       The canonical representation uses lowercase characters.";
  }

  typedef date {
    type string {
      pattern "\\d{4}-(0[1-9]|1[0-2])-(0[1-9]|[1-2][0-9]|3[0-1])";
    }
    description
      "A date in the ISO 8601 compatible format 'YYYY-MM-DD', where:
       
       - YYYY is the year (4 digits).
       - MM is the month (2 digits, 01-12).
       - DD is the day of the month (2 digits, 01-31).
       
       This follows the 'full-date' format as defined in RFC 3339.";
    reference "RFC 3339 - Date and Time on the Internet: Timestamps";
  }

  typedef date-and-time {
    type string {
      pattern "\\d{4}-(0[1-9]|1[0-2])-(0[1-9]|[1-2][0-9]|3[0-1])T([0-1][0-9]|2[0-3]):[0-5][0-9]:([0-5][0-9]|60)(\\.\\d+)?(Z|[\\+\\-]\\d{2}:\\d{2})";
    }
    description
      "A date in the ISO 8601 compatible format
       '<date>T<partial-time><time-offset>', where:
       
       - <date> is in the format 'YYYY-MM-DD', as per the 'date' type.
       - <partial-time> is in the format 'HH:MM:SS[.<fractional-seconds>]',
         where:
         - HH is the hour (2 digits, 00-23).
         - MM is the minute (2 digits, 00-59).
         - SS is the second (2 digits, 00-60).
           - Note that the seconds value of '60' is only allowed to
             account for leap seconds.
         - <fractional-seconds> is an optional decimal fraction of a second,
            with an arbitrary number of digits.
       - <time-offset> is either 'Z' to indicate UTC time, or a time offset
         from UTC in the format '[+-]HH:MM', where:
         - HH is the hour offset (2 digits, 00-23).
         - MM is the minute offset (2 digits, 00-59).
       
       This follows the 'date-time' format as defined in RFC 3339.";
    reference "RFC 3339 - Date and Time on the Internet: Timestamps";
  }

  typedef encrypted {
    type restricted-string {
      pattern "(!.+)|([^!].+)";
    }
    description
      "General type for storing encrypted data.
       
       Note that this type is never used directly in a model. Instead, types
       are derived from it for each supported encryption algorithm.
       
       When a clear text value is supplied for a leaf of this type, the value
       is encrypted and the server stores the encrypted value in the datastore.
       The data is never stored in clear text.
       
       When a leaf of this type is read, the encrypted data is returned.
       
       A value of this type matches one of the forms:
       
         !<clear text value>
         <encrypted value>
       
       The '!' prefix signals that the value is clear text.
       When such a value is received by the server, the value is encrypted
       before being stored in the configuration data store.
       If a value starting without '!' is received, the server knows that the
       value already represents an encrypted value, and stores it as is in
       the data store.";
  }

  typedef md5-encrypted {
    type um-types:encrypted;
    description
      "A value encrypted using the MD5 hash function.";
    reference "RFC 1321 - The MD5 Message-Digest Algorithm";
  }

  typedef type6-encrypted {
    type um-types:encrypted;
    description
      "A value encrypted using the AES-128 algorithmic encryption.";
    reference "FIPS 197 - Advanced Encryption Standard (AES)";
  }

  typedef type7-encrypted {
    type um-types:encrypted;
    description
      "A value encrypted using Vigenere obfuscation.
       
       Note that such values are simply obfuscated and should not be
       considered as truly encrypted.";
  }

  typedef type8-encrypted {
    type um-types:encrypted;
    description
      "A value encrypted using the SHA-256 algorithmic encryption.";
    reference
      "RFC 6234 - US Secure Hash Algorithms
                  (SHA and SHA-based HMAC and HKDF)";
  }

  typedef type9-encrypted {
    type um-types:encrypted;
    description
      "A value encrypted using the scrypt algorithmic encryption.";
    reference "RFC 7914 - The scrypt Password-Based Key Derivation Function";
  }

  typedef type10-encrypted {
    type um-types:encrypted;
    description
      "A value encrypted using the SHA-512 algorithmic encryption.";
    reference
      "RFC 6234 - US Secure Hash Algorithms
                  (SHA and SHA-based HMAC and HKDF)";
  }

  typedef interface-name {
    type string {
      pattern "[a-zA-Z0-9.:_/-]+" {
        description
          "Interface name in the format '<type><instance>[.<sub-interface>]'";
      }
    }
    description
      "An interface name consisting of:
       
       - An interface type, e.g. 'MgmtEth', 'TenGigE', 'Bundle-Ether'
       - An interface instance identifier
       - An optional sub-interface identifier
         - The sub-interface identifier is separated from the
           interface instance identifier by a single dot ('.') character.";
  }

  typedef controller-name {
    type string {
      pattern "[a-zA-Z0-9.:_/-]+" {
        description
          "Controller name in the format '<type><instance>[.<sub-controller>]'";
      }
    }
    description
      "A controller name consisting of:
       
       - A controller type, e.g. 'dwdm', 'GigabitEthCtrlr', 'Optics'
       - A controller instance identifier
       - An optional sub-controller identifier
         - The sub-controller identifier is separated from the
           controller instance identifier by a single dot ('.') character.";
  }

  typedef node-id {
    type string {
      pattern "([a-zA-Z0-9_]*\\d+/){1,2}([a-zA-Z0-9_]*\\d*)" {
        description
          "Specified in 'rack/slot/module' format.";
      }
    }
    description
      "A fully qualified hardware location.
       
       This consists of the following:
       
        - The rack number where the hardware is located.
        - The physical slot within the rack where the hardware is installed.
        - The module or card within the slot.
       
        Note that slots and modules may include text as well as numbers,
        such as 'RP0', 'CPU0', etc.";
  }

  typedef partially-qualified-node-id {
    type string {
      pattern "((([a-zA-Z0-9_]*\\d+)|(\\*))/){2}(([a-zA-Z0-9_]*\\d+)|(\\*))" {
        description
          "Specified in 'rack/slot/module' format.";
      }
    }
    description
      "A partially qualified hardware location.
       
       This is the same as the 'node-id' type, but additionally supports
       wildcarding location specifications, e.g. '1/*/*'.";
  }

  typedef vrf-name {
    type restricted-string {
      length "1..32";
      pattern "default|global|all" {
        modifier "invert-match";
      }
    }
    description
      "A Virtual Routing and Forwarding (VRF) name.
       
       The following names are reserved and may not be used:
       - 'all'
       - 'default'
       - 'global'";
  }

  typedef vrf-name-or-default {
    type union {
      type um-types:vrf-name;
      type enumeration {
        enum "default" {
          description
            "Default VRF";
        }
      }
    }
    description
      "A VRF name, or the 'default' VRF.";
  }

  typedef acl-name {
    type restricted-string {
      length "1..128";
      pattern "[a-z0-9A-Z][-_.:a-z0-9A-Z]*";
    }
    description
      "An Access List (ACL) name.
       
       The name must start with an alphanumeric character, and may contain
       alphanumeric characters, hyphens, underscores, colons or periods.";
  }

  typedef ipv4-address {
    type inet:ipv4-address-no-zone;
    description
      "An IPv4 address in dotted quad notation, without a zone index.";
    reference
      "RFC 791 - Internet Protocol
       RFC 4001 - Textual Conventions for Internet Network Addresses";
  }

  typedef ipv4-address-zoned {
    type inet:ipv4-address;
    description
      "An IPv4 address in dotted quad notation, with an optional zone index.";
    reference
      "RFC 791 - Internet Protocol
       RFC 4001 - Textual Conventions for Internet Network Addresses";
  }

  typedef ipv4-prefix {
    type inet:ipv4-prefix;
    description
      "An IPv4 address prefix.";
    reference
      "RFC 791 - Internet Protocol
       RFC 4001 - Textual Conventions for Internet Network Addresses";
  }

  typedef ipv4-prefix-length {
    type uint8 {
      range "0..32";
    }
    description
      "An IPv4 address prefix length.";
    reference "RFC 791 - Internet Protocol";
  }

  typedef ipv6-address {
    type inet:ipv6-address-no-zone;
    description
      "An IPv6 address without a zone index.
       
       This may be represented in either full, mixed, shortened or
       shortened-mixed notation.";
    reference
      "RFC 2460 - Internet Protocol, Version 6 (IPv6) Specification
       RFC 4001 - Textual Conventions for Internet Network Addresses";
  }

  typedef ipv6-address-zoned {
    type inet:ipv6-address;
    description
      "An IPv6 address with an optional zone index.
       
       This may be represented in either full, mixed, shortened or
       shortened-mixed notation.";
    reference
      "RFC 2460 - Internet Protocol, Version 6 (IPv6) Specification
       RFC 4001 - Textual Conventions for Internet Network Addresses";
  }

  typedef ipv6-prefix {
    type inet:ipv6-prefix;
    description
      "An IPv6 address prefix.";
    reference
      "RFC 2460 - Internet Protocol, Version 6 (IPv6) Specification
       RFC 4001 - Textual Conventions for Internet Network Addresses";
  }

  typedef ipv6-prefix-length {
    type uint8 {
      range "0..128";
    }
    description
      "An IPv6 address prefix length.";
    reference "RFC 2460 - Internet Protocol, Version 6 (IPv6) Specification";
  }

  typedef ip-address {
    type union {
      type ipv4-address;
      type ipv6-address;
    }
    description
      "An IP address, which can be either an IPv4 or IPv6 address, without a
       zone index.";
    reference
      "RFC 791 - Internet Protocol
       RFC 2460 - Internet Protocol, Version 6 (IPv6) Specification
       RFC 4001 - Textual Conventions for Internet Network Addresses";
  }

  typedef ip-address-zoned {
    type union {
      type ipv4-address-zoned;
      type ipv6-address-zoned;
    }
    description
      "An IP address, which can be either an IPv4 or IPv6 address, with an
       optional zone index.";
    reference
      "RFC 791 - Internet Protocol
       RFC 2460 - Internet Protocol, Version 6 (IPv6) Specification
       RFC 4001 - Textual Conventions for Internet Network Addresses";
  }

  typedef ip-prefix {
    type union {
      type ipv4-prefix;
      type ipv6-prefix;
    }
    description
      "An IP address prefix, which can be either an IPv4 or IPv6 address
       prefix.";
    reference
      "RFC 791 - Internet Protocol
       RFC 2460 - Internet Protocol, Version 6 (IPv6) Specification
       RFC 4001 - Textual Conventions for Internet Network Addresses";
  }

  typedef mac-address {
    type yang:mac-address;
    description
      "An IEEE 802 MAC address.
       
       The address is represented as a string in the format
       'xx:xx:xx:xx:xx:xx', where each 'x' is a hexadecimal digit.
       The canonical representation uses lowercase characters.";
    reference
      "IEEE 802.3 - IEEE Standard for Local and Metropolitan Area
                    Networks: Overview and Architecture";
  }

  typedef ip-address-family {
    type enumeration {
      enum "ipv4" {
        value 1;
        description
          "IPv4 address family";
      }
      enum "ipv6" {
        value 2;
        description
          "IPv6 address family";
      }
    }
    description
      "An address family, limited to only IPv4 or IPv6.
       
       The value associated with each address family corresponds to the
       IANA assigned address family number.";
    reference
      "RFC 4760 - Multiprotocol Extensions for BGP-4
       IANA - Address Family Numbers Registry";
  }

  typedef port-number {
    type uint16 {
      range "1..max";
    }
    description
      "A port number of an internet transport layer protocol, such as TCP or
       UDP.
       
       The port number of zero is reserved by IANA and is excluded from
       this type.";
    reference "IANA - Service Name and Transport Protocol Port Number Registry";
  }

  typedef dscp {
    type union {
      type enumeration {
        enum "default" {
          value 0;
          description
            "Default forwarding DSCP (000000)";
        }
        enum "af11" {
          value 10;
          description
            "AF11 DSCP (001010)";
        }
        enum "af12" {
          value 12;
          description
            "AF12 DSCP (001100)";
        }
        enum "af13" {
          value 14;
          description
            "AF13 DSCP (001110)";
        }
        enum "af21" {
          value 18;
          description
            "AF21 DSCP (010010)";
        }
        enum "af22" {
          value 20;
          description
            "AF22 DSCP (010100)";
        }
        enum "af23" {
          value 22;
          description
            "AF23 DSCP (010110)";
        }
        enum "af31" {
          value 26;
          description
            "AF31 DSCP (011010)";
        }
        enum "af32" {
          value 28;
          description
            "AF32 DSCP (011100)";
        }
        enum "af33" {
          value 30;
          description
            "AF33 DSCP (011110)";
        }
        enum "af41" {
          value 34;
          description
            "AF41 DSCP (100010)";
        }
        enum "af42" {
          value 36;
          description
            "AF42 DSCP (100100)";
        }
        enum "af43" {
          value 38;
          description
            "AF43 DSCP (100110)";
        }
        enum "cs1" {
          value 8;
          description
            "CS1 (IP precedence 1) DSCP (001000)";
        }
        enum "cs2" {
          value 16;
          description
            "CS2 (IP precedence 2) DSCP (010000)";
        }
        enum "cs3" {
          value 24;
          description
            "CS3 (IP precedence 3) DSCP (011000)";
        }
        enum "cs4" {
          value 32;
          description
            "CS4 (IP precedence 4) DSCP (100000)";
        }
        enum "cs5" {
          value 40;
          description
            "CS5 (IP precedence 5) DSCP (101000)";
        }
        enum "cs6" {
          value 48;
          description
            "CS6 (IP precedence 6) DSCP (110000)";
        }
        enum "cs7" {
          value 56;
          description
            "CS7 (IP precedence 7) DSCP (111000)";
        }
        enum "ef" {
          value 46;
          description
            "Expedited forwarding (EF) DSCP (101110)";
        }
      }
      type uint8 {
        range "0..63";
      }
    }
    description
      "A differentiated services code point (DSCP) used for packet
       classification purposes.
       
       This may be input as a 6-bit unsigned integer DSCP value, or as a DSCP
       name.
       
       The canonical representation uses the enumeration format.";
    reference
      "RFC 2474 - Definition of the Differentiated Services Field (DS Field)
                  in the IPv4 and IPv6 Headers
       RFC 2597 - Assured Forwarding PHB Group
       RFC 3246 - An Expedited Forwarding PHB (Per-Hop Behavior)
       IANA - Differentiated Services Code Point (DSCP) Registry";
  }

  typedef as-number {
    type union {
      type uint16 {
        range "1..max" {
          description
            "2-byte AS number";
        }
      }
      type string {
        pattern "[1-9][0-9]{0,4}\\.[0-9]{1,5}" {
          description
            "4-byte AS number in asdot (X.Y) format";
        }
      }
      type uint32 {
        range "65536..max" {
          description
            "4-byte AS number in asplain format";
        }
      }
    }
    description
      "An Autonomous System (AS) number used to identify an Autonomous System.
       
       The AS number can be specified as a 2-byte or 4-byte value. In the
       4-byte case, the value can be specified in asplain or asdot format.";
    reference
      "RFC 1930 - Guidelines for creation, selection, and registration
                  of an Autonomous System (AS)
       RFC 4271 - A Border Gateway Protocol 4 (BGP-4)
       RFC 5396 - Textual Representation of Autonomous System (AS) Numbers
       RFC 6793 - BGP Support for Four-Octet Autonomous System (AS) Number";
  }

  typedef parameterized-route-policy {
    type string {
      pattern "[a-zA-Z0-9][a-zA-Z0-9:\\._\\-]{0,254}(\\(\\s*[a-zA-Z0-9][a-zA-Z0-9:\\._\\-]{0,254}(,\\s*[a-zA-Z0-9][a-zA-Z0-9:\\._\\-]{0,254}){0,15}\\s*\\))?";
    }
    description
      "The name of a route policy, possibly with parameters.
       
       If the route policy has parameters, they are specified as a
       comma-separated list of values, enclosed in parentheses, following
       the route policy name.";
  }

  typedef vpn-id {
    type string {
      pattern "[0-9a-f]{1,8}:[0-9a-f]{1,8}" {
        description
          "VPN ID format (OUI:VPN-Index in hex integer format)";
      }
    }
    description
      "A VPN Identifier consisting of:
        -  an Organizationally Unique Identifier (OUI) (4 octets)
        -  a VPN Index (4 octets)";
    reference "RFC 2685 - Virtual Private Networks Identifier";
  }

  typedef ospf-area-id {
    type union {
      type uint32;
      type yang:dotted-quad;
    }
    description
      "An OSPF area identifier.
       
       This can be specified either as a decimal value or in dotted
       decimal format.";
    reference "RFC 2328 - OSPF Version 2";
  }
}
