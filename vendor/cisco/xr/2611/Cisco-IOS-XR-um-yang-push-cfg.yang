module Cisco-IOS-XR-um-yang-push-cfg {
  namespace "http://cisco.com/ns/yang/Cisco-IOS-XR-um-yang-push-cfg";
  prefix um-yang-push-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco yang-push package configuration.
     Copyright (c) 2024-2025 by Cisco Systems, Inc., and/or its affiliates.
     All rights reserved.";

  revision 2025-04-14 {
    description
      "Relax unnecessary string length constraints";
    semver:module-version "1.0.0";
  }
  revision 2025-03-07 {
    description
      "Add sync-on-start support";
  }
  revision 2025-02-18 {
    description
      "Removed tcp transport";
  }
  revision 2024-12-20 {
    description
      "Initial UM2 release";
  }

  container yang-push {
    presence "YANG push configuration";
    description
      "YANG push configuration";
    container subscriptions {
      description
        "YANG push subscription configuration";
      list subscription {
        key "subscription-id";
        description
          "YANG push subscription configuration";
        leaf subscription-id {
          type uint32 {
            range "0..65535" {
              description
                "Subscription ID";
            }
          }
          description
            "Subscription ID";
        }
        leaf dscp {
          type union {
            type uint32 {
              range "0..63" {
                description
                  "Differentiated services code point";
              }
            }
            type enumeration {
              enum "af11" {
                value 10;
                description
                  "AF11 (DSCP 001010)";
              }
              enum "af12" {
                value 12;
                description
                  "AF12 (DSCP 001100)";
              }
              enum "af13" {
                value 14;
                description
                  "AF13 (DSCP 001110)";
              }
              enum "af21" {
                value 18;
                description
                  "AF21 (DSCP 010010)";
              }
              enum "af22" {
                value 20;
                description
                  "AF22 (DSCP 010100)";
              }
              enum "af23" {
                value 22;
                description
                  "AF23 (DSCP 010110)";
              }
              enum "af31" {
                value 26;
                description
                  "AF31 (DSCP 011010)";
              }
              enum "af32" {
                value 28;
                description
                  "AF32 (DSCP 011100)";
              }
              enum "af33" {
                value 30;
                description
                  "AF33 (DSCP 011110)";
              }
              enum "af41" {
                value 34;
                description
                  "AF41 (DSCP 100010)";
              }
              enum "af42" {
                value 36;
                description
                  "AF42 (DSCP 100100)";
              }
              enum "af43" {
                value 38;
                description
                  "AF43 (DSCP 100110)";
              }
              enum "cs1" {
                value 8;
                description
                  "CS1 (Precedence 1) (DSCP 001000)";
              }
              enum "cs2" {
                value 16;
                description
                  "CS2 (Precedence 2) (DSCP 010000)";
              }
              enum "cs3" {
                value 24;
                description
                  "CS3 (Precedence 3) (DSCP 011000)";
              }
              enum "cs4" {
                value 32;
                description
                  "CS4 (Precedence 4) (DSCP 100000)";
              }
              enum "cs5" {
                value 40;
                description
                  "CS5 (Precedence 5) (DSCP 101000)";
              }
              enum "cs6" {
                value 48;
                description
                  "CS6 (Precedence 6) (DSCP 110000)";
              }
              enum "cs7" {
                value 56;
                description
                  "CS7 (Precedence 7) (DSCP 111000)";
              }
              enum "default" {
                value 0;
                description
                  "Default (DSCP 000000)";
              }
              enum "ef" {
                value 46;
                description
                  "EF (DSCP 101110)";
              }
            }
          }
          description
            "DSCP setting for packet classification for this subscription";
        }
        container encoding {
          description
            "YANG push subscription encoding";
          choice ENCODING {
            description
              "YANG push subscription encoding";
            case JSON {
              leaf json {
                type empty;
                description
                  "IETF JSON YANG";
              }
            }
          }
        }
        container filter {
          description
            "YANG push subscription filter";
          container xpaths {
            description
              "YANG push subscription filter xpath";
            list xpath {
              key "xpath-string";
              description
                "YANG push subscription filter xpath";
              leaf xpath-string {
                type string {
                  length "1..512" {
                    description
                      "Filter xpath";
                  }
                }
                description
                  "YANG push subscription filter xpath";
              }
            }
          }
        }
        leaf purpose {
          type string {
            length "1..512" {
              description
                "Purpose";
            }
          }
          description
            "YANG push subscription purpose";
        }
        leaf source-interface {
          type xr:Interface-name;
          description
            "YANG push subscription source-interface";
        }
        container update-policy {
          description
            "YANG push subscription update policy";
          choice UPDATE-POLICY {
            description
              "YANG push subscription update policy";
            case ON-CHANGE {
              container on-change {
                presence "On-change";
                description
                  "On-change";
                leaf sync-on-start {
                  type empty;
                  description
                    "Send a complete update of all subscribed data on starting the subscription.";
                }
              }
            }
            case PERIODIC {
              container periodic {
                presence "Periodic";
                description
                  "Periodic";
                leaf period {
                  type uint32 {
                    range "3000..4294967295" {
                      description
                        "Period (in centiseconds)";
                    }
                  }
                  mandatory true;
                  description
                    "Period interval";
                }
                leaf anchor-time-value {
                  type string {
                    length "1..1024" {
                      description
                        "Anchor time (as an ISO 8601 compatible date-time string)";
                    }
                  }
                  description
                    "Anchor time";
                }
              }
            }
          }
        }
        container receivers {
          description
            "YANG push subscription receiver";
          list receiver {
            key "receiver-name";
            description
              "YANG push subscription receiver";
            leaf receiver-name {
              type string {
                length "1..1024" {
                  description
                    "Receiver name";
                }
              }
              description
                "YANG push subscription receiver";
            }
          }
        }
        container modules {
          description
            "YANG push module configuration";
          list module {
            key "module-name";
            description
              "YANG push module configuration";
            leaf module-name {
              type string {
                length "1..1024" {
                  description
                    "Module name";
                }
              }
              description
                "Module name";
            }
            leaf revision {
              type string {
                length "1..512" {
                  description
                    "Module revision date";
                }
              }
              description
                "Required module revision date";
            }
          }
        }
      }
    }
    container receivers {
      description
        "YANG push receiver configuration";
      list receiver {
        key "receiver-name";
        description
          "YANG push receiver configuration";
        leaf receiver-name {
          type string {
            length "1..1024" {
              description
                "Receiver name";
            }
          }
          description
            "Receiver name";
        }
        container transport {
          description
            "YANG push receiver transport";
          choice TRANSPORT {
            description
              "YANG push receiver transport";
            case UDP-NOTIF {
              container udp-notif {
                presence "UDP-Notif";
                description
                  "UDP-Notif";
                leaf max-segment-size {
                  type uint32 {
                    range "1232..65527" {
                      description
                        "Maximum segment size (bytes)";
                    }
                  }
                  description
                    "Maximum segment size (default 1232)";
                }
              }
            }
          }
        }
        leaf address {
          type inet:ip-address-no-zone;
          description
            "YANG push receiver address";
        }
        leaf port {
          type uint32 {
            range "1..65535" {
              description
                "YANG push receiver port";
            }
          }
          description
            "YANG push receiver port";
        }
      }
    }
  }
}
