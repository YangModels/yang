module Cisco-IOS-XR-um-logging-events-cfg {
  namespace "http://cisco.com/ns/yang/Cisco-IOS-XR-um-logging-events-cfg";
  prefix um-logging-events-cfg;

  import Cisco-IOS-XR-um-logging-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR logging-events package configuration.
     
     This YANG module augments the
     modules with configuration data.
     
     Copyright (c) 2020-2025 by Cisco Systems, Inc., and/or its affiliates.
     All rights reserved.";

  revision 2022-07-11 {
    description
      "Added missing description statement to nodes";
    semver:module-version "1.0.0";
  }
  revision 2020-10-06 {
    description
      "Initial release";
    semver:module-version "1.0.0";
  }

  augment "/a1:logging" {
    description
      "This augment extends logging nodes configuration";
    container events {
      description
        "Configure event monitoring parameters";
      leaf buffer-size {
        type uint32 {
          range "1024..1024000" {
            description
              "Size of the local event buffer";
          }
        }
        description
          "Set size of the local event buffer";
      }
      container filter {
        description
          "Configure filter";
        list match {
          key "match-string";
          description
            " Configure match string to filter";
          leaf match-string {
            type string {
              length "1..32" {
                description
                  "String to match with alarms";
              }
            }
            description
              " Configure match string to filter";
          }
        }
      }
      container display-location {
        presence "Indicates a display-location node is configured.";
        description
          "Include alarm source location in message text";
      }
      leaf level {
        type enumeration {
          enum "emergencies" {
            value 0;
            description
              "(level=0) System is unusable";
          }
          enum "alerts" {
            value 1;
            description
              "(level=1) Immediate action needed";
          }
          enum "critical" {
            value 2;
            description
              "(level=2) Critical conditions";
          }
          enum "errors" {
            value 3;
            description
              "(level=3) Error conditions";
          }
          enum "warnings" {
            value 4;
            description
              "(level=4) Warning conditions";
          }
          enum "notifications" {
            value 5;
            description
              "(level=5) Normal but significant conditions";
          }
          enum "informational" {
            value 6;
            description
              "(level=6) Informational messages";
          }
        }
        description
          "Log all events with equal or higher (lower level) severity";
      }
      leaf threshold {
        type uint32 {
          range "10..100" {
            description
              "Capacity alarm threshold";
          }
        }
        description
          "Configure threshold (%) for capacity alarm";
      }
      leaf precfg-suppression {
        type enumeration {
          enum "enable" {
            value 1;
            description
              "Suppress events from a card/VM till its configuration is complete";
          }
        }
        description
          "Suppress events from a card/VM till its configuration is complete";
      }
      leaf precfg-suppression-timeout {
        type uint32 {
          range "1..60" {
            description
              "Timeout (in minutes) for pre-config events suppression (default 15)";
          }
        }
        description
          "Timeout (in minutes) for pre-config events suppression (default 15)";
      }
    }
  }
}
