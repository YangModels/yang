module Cisco-IOS-XR-um-hw-module-shut-cfg {
  namespace "http://cisco.com/ns/yang/Cisco-IOS-XR-um-hw-module-shut-cfg";
  prefix um-hw-module-shut-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-shut package configuration.
     
     This YANG module augments the
     modules with configuration data.
     
     Copyright (c) 2020-2025 by Cisco Systems, Inc., and/or its affiliates.
     All rights reserved.";

  revision 2022-03-08 {
    description
      "Removed Cisco-IOS-XR-types import";
    semver:module-version "1.1.0";
  }
  revision 2020-09-22 {
    description
      "Initial release";
    semver:module-version "1.0.0";
  }

  container hw-module {
    description
      "Configure h/w module";
    container locations {
      description
        "Specify the location";
      list location {
        must "shut or unshut";
        key "location-name";
        description
          "Specify the location";
        leaf location-name {
          type string {
            length "1..1024" {
              description
                "hardware location in format <Rack>/<Slot>";
            }
          }
          description
            "Specify the location";
        }
        container shut {
          must "not(../unshut)";
          presence "Indicates a shut node is configured.";
          description
            "shutdown the hw-module";
        }
        container unshut {
          must "not(../shut)";
          presence "Indicates an unshut node is configured.";
          description
            "Unshut the hw-module";
        }
      }
    }
  }
}
