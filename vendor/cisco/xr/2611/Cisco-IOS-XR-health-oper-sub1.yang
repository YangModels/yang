submodule Cisco-IOS-XR-health-oper-sub1 {
  belongs-to Cisco-IOS-XR-health-oper {
    prefix Cisco-IOS-XR-health-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR health package operational data.
     
     Copyright (c) 2013-2025 by Cisco Systems, Inc.
     All rights reserved.";

  revision 2025-09-22 {
    description
      "Added more fields to the Health component information";
    semver:module-version "1.0.0";
  }
  revision 2025-03-12 {
    description
      "Updated data type to enum for health status to make it descriptive";
  }
  revision 2024-05-29 {
    description
      "Initial native yang support for operational data related to Health functionality";
  }
  revision 2019-04-05 {
    description
      "Establish semantic version baseline.";
  }
  revision 2015-11-09 {
    description
      "IOS XR 6.0 revision.";
  }

  typedef Health-status {
    type enumeration {
      enum "healthy" {
        value 0;
        description
          "HEALTHY";
      }
      enum "unhealthy" {
        value 1;
        description
          "UNHEALTHY";
      }
      enum "error" {
        value 2;
        description
          "ERROR";
      }
    }
    description
      "Health status";
  }

  grouping XRHEALTH-STATE {
    description
      "XRHealth component state information";
    leaf component {
      type string;
      description
        "Component";
    }
    leaf event-id {
      type string;
      description
        "Event ID";
    }
    leaf event-type {
      type string;
      description
        "Event type description";
    }
    leaf last-unhealthy {
      type uint64;
      units "nanosecond";
      description
        "Time since Unix epoch when the last unhealthy
         event occured (in nanoseconds)";
    }
    leaf parent {
      type string;
      description
        "Parent component";
    }
    leaf producer {
      type string;
      description
        "Producer that generated the event";
    }
    leaf status {
      type Health-status;
      description
        "Health status code";
    }
    leaf unhealthy-count {
      type uint32;
      description
        "Count of unhealthy events";
    }
  }
}
