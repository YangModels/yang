module Cisco-IOS-XR-sysadmin-ethsw-esdma-bcmshell {
  namespace "http://www.cisco.com/ns/yang/Cisco-IOS-XR-sysadmin-ethsw-esdma-bcmshell";
  prefix esdma_bcmshell;

  import Cisco-IOS-XR-sysadmin-ethsw-esdma-types {
    prefix esdma_types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR Sysadmin
     'show controller switch bcmshell location <> <cmd>' commands.
     
     Copyright(c) 2020 by Cisco Systems, Inc.
     All rights reserved.
     
     Copyright (c) 2012-2020 by Cisco Systems, Inc.
     All rights reserved.";

  revision 2020-12-22 {
    description
      "Initial revision";
    semver:module-version "1.0.0";
  }

  grouping switch-bcmshell-group {
    container bcmshell {
      list location {
        key "rack card switch-id";
        leaf rack {
          type esdma_types:esdma-rack-num-enum;
        }
        leaf card {
          type esdma_types:esdma-cpu;
          description
            "Card that owns a switch of interest";
        }
        leaf switch-id {
          type esdma_types:esdma-switch-type-enum;
          description
            "Switch type";
        }
        list bcm_cmd {
          key "bcm_cmd_str";
          leaf bcm_cmd_str {
            type esdma_types:esdma_diag_shell_cmd_type;
          }
          leaf bcm_output {
            type esdma_types:esdma_diag_shell_cmd_type;
            description
              "Output";
          }
        }
      }
    }
  }
}
